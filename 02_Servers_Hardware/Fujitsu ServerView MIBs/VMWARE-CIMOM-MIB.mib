-- **********************************************************
-- Copyright 2010 VMware, Inc.  All rights reserved. 
-- **********************************************************

VMWARE-CIMOM-MIB DEFINITIONS ::= BEGIN

    IMPORTS
        MODULE-IDENTITY, NOTIFICATION-TYPE
    FROM SNMPv2-SMI
        MODULE-COMPLIANCE, NOTIFICATION-GROUP
    FROM SNMPv2-CONF
        vmwEnvIndicationTime
    FROM VMWARE-ENV-MIB;

--     vmwCIMOMMIB MODULE-IDENTITY
--     LAST-UPDATED "201008200000Z"
--     ORGANIZATION "VMware, Inc"
--     CONTACT-INFO
--     "VMware, Inc
--     3401 Hillview Ave
--     Palo Alto, CA 94304
--     Tel: 1-877-486-9273 or 650-427-5000
--     Fax: 650-427-5001
--     Web: http://communities.vmware.com/community/developer/forums/managementapi
--     "
-- DESCRIPTION
--      "This MIB module provides instrumentation of a CIM Object Manager." 
-- REVISION      "201008200000Z"
-- DESCRIPTION
--      "Information on a CIM object manager subsystem."
-- ::= { vmwCimOm 10 }

vmware MODULE-IDENTITY
       LAST-UPDATED "201004020000Z"
       ORGANIZATION "VMware, Inc"
       CONTACT-INFO
               "VMware, Inc
                3401 Hillview Ave
                Palo Alto, CA 94304
                Tel: 1-877-486-9273 or 650-427-5000
                Fax: 650-427-5001
                Web: http://communities.vmware.com/community/developer/forums/managementapi
                "
       DESCRIPTION
               "VMware managed object root assignements
                This module defines the VMware SNMP MIB root
                and its primary subtrees.
               "

       REVISION      "201004020000Z"
       DESCRIPTION
               "Arc vmwDocumentation defined."

       REVISION      "200707300000Z"
       DESCRIPTION
               "The initial revision. Prior version was released in 
                SMIv1 format as VMWARE-ROOT-MIB."
       ::= { enterprises 6876 }
vmwProductSpecific OBJECT-IDENTITY
STATUS  current
DESCRIPTION
    "parent of objects specific to a given hardware/software product."
::= { vmware 4 }

vmwCimOm OBJECT IDENTIFIER
    ::= { vmwProductSpecific 90 }

vmwCimOmNotifications OBJECT IDENTIFIER 
    ::= {vmwCimOm 0 }

vmwEnvCIM OBJECT IDENTIFIER
    ::= { vmwProductSpecific 30 }

DateAndTime ::=
     DisplayString


vmwEnvIndicationTime OBJECT-TYPE
    SYNTAX     DateAndTime
    MAX-ACCESS accessible-for-notify
    STATUS     current
    DESCRIPTION
      "The time and date of creation of the underlying Indication received by the snmp agent. The
       property may be set to the time SNMP agent received the notification if the entity creating the
       Indication is not capable of determining this
       information and delivers a null IndicationTime property. Note that IndicationTime may be the same
       for two Indications that are generated in rapid succession."
    REFERENCE
      "http://www.dmtf.org/standards/cim/cim_schema_v2240 : file CIM_AlertIndication.mof : property IndicationTime"
    ::= { vmwEnvCIM 3 }


vmwCimOmHeartbeat NOTIFICATION-TYPE
    OBJECTS     { vmwEnvIndicationTime }
    STATUS      current 
    DESCRIPTION
        "This notification, if the agent is so configured, will be sent 
         on a periodic basis to indicate cimom indication delivery is functioning."
    ::= { vmwCimOmNotifications 401 }

-- conformance information
vmwCimOmMIBConformance
OBJECT IDENTIFIER ::= { vmwCimOm 2 }
vmwCimOmMIBCompliances
OBJECT IDENTIFIER ::= { vmwCimOmMIBConformance 1 }
vmwCimOmMIBGroups  OBJECT IDENTIFIER ::= { vmwCimOmMIBConformance 2 }

-- compliance statements

-- vmwCimOmMIBBasicCompliance MODULE-COMPLIANCE
-- STATUS  current
-- DESCRIPTION
--     "The compliance statement for entities which implement the 
--     VMWARE-CIMOM-MIB."
-- MODULE  -- this module
-- MANDATORY-GROUPS { vmwCimOmNotificationGroup }
-- GROUP  vmwCimOmNotificationGroup
-- DESCRIPTION
--     "This group is mandatory for systems with CIM object manager."
-- ::= { vmwCimOmMIBCompliances 4 }

vmwCimOmNotificationGroup NOTIFICATION-GROUP
       NOTIFICATIONS {
       vmwCimOmHeartbeat
       }
       STATUS      current
       DESCRIPTION
           "Notifications related to CIM Object Manager subsystem."
       ::= { vmwCimOmMIBGroups 2 }


END
