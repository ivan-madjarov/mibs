MMB-COM-MIB DEFINITIONS ::= BEGIN

--PRIMEQUEST system management MIB for MMB
--
--
--$Copyright$
--Copyright Fujitsu Limited 2004 - 2013
--All rights reserved
--
--
--MIB Revision: 03000001
--

IMPORTS
	OBJECT-TYPE								FROM RFC-1212
	TRAP-TYPE								FROM RFC-1215
	mib-2, DisplayString, PhysAddress		FROM RFC1213-MIB
	TimeTicks, Counter, Gauge, IpAddress	FROM RFC1155-SMI
	mgmt, enterprises						FROM RFC1155-SMI
	InetAddressType, InetAddress			FROM INET-ADDRESS-MIB;


--
-- Textual conventions
--

  TrueFalse ::= INTEGER
  {

      false(1),
      true(2)
  }

  TrueFalseUnknown ::= INTEGER
  {

      false(1),
      true(2),
      unknown(3)
  }

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    mmb:                    1.3.6.1.4.1.211.1.31.1.1
--     sysInfo:               1.3.6.1.4.1.211.1.31.1.1.1
--    partition:              1.3.6.1.4.1.211.1.31.1.2
--
--FUJITSU PRIMEQUEST system management MIB nodes for MMB
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   mmb           OBJECT IDENTIFIER  ::={ primequest 1 }
   partition     OBJECT IDENTIFIER  ::={ primequest 2 }
    sysInfo	OBJECT IDENTIFIER	::={ mmb	1 }
     agentInfo	OBJECT IDENTIFIER	::={ sysInfo 1 }
     unitInformation	OBJECT IDENTIFIER	::={ sysInfo 2 }
     management	OBJECT IDENTIFIER	::={ sysInfo 3 }
     serverInformation	OBJECT IDENTIFIER	::={ sysInfo 4 }
     environment	OBJECT IDENTIFIER	::={ sysInfo 5 }
     hardware	OBJECT IDENTIFIER	::={ sysInfo 6 }
     recovery	OBJECT IDENTIFIER	::={ sysInfo 7 }
     status	OBJECT IDENTIFIER	::={ sysInfo 8 }
     maintenance	OBJECT IDENTIFIER	::={ sysInfo 9 }
     deployment	OBJECT IDENTIFIER	::={ sysInfo 10 }

--FUJITSU PRIMEQUEST system management MIB objects for MMB


--agentInfo-MIB groups

agentId OBJECT-TYPE
   SYNTAX   DisplayString
   ACCESS   read-only
   STATUS   mandatory
   DESCRIPTION "Agent identification string; Not supported."
   ::= { agentInfo 1 }

agentCompany OBJECT-TYPE
   SYNTAX   DisplayString
   ACCESS   read-only
   STATUS   mandatory
   DESCRIPTION "Agent's company name (e.g. Fujitsu Siemens Computers); Not supported."
   ::= { agentInfo 2 }

agentVersion OBJECT-TYPE
   SYNTAX   DisplayString
   ACCESS   read-only
   STATUS   mandatory
   DESCRIPTION "Agent's version string (e.g. 1.05); Not supported."
   ::= { agentInfo 3 }

agentBuild OBJECT-TYPE
   SYNTAX   DisplayString
   ACCESS   read-only
   STATUS   mandatory
   DESCRIPTION "Compilation time and date of agent program; Not supported."
   ::= { agentInfo 4 }

agentWriteAllowed OBJECT-TYPE
   SYNTAX   INTEGER{
      unknown(1),
      write-not-allowed(2),
      write-allowed(3)
   }
   ACCESS   read-only
   STATUS   mandatory
   DESCRIPTION "Defines whether writable objects can be written
                (except shutdown/power-off operations); Not supported."
   ::= { agentInfo 5 }

agentShutdownAllowed OBJECT-TYPE
   SYNTAX   INTEGER{
      unknown(1),
      shutdown-not-allowed(2),
      shutdown-allowed(3)
   }
   ACCESS   read-only
   STATUS   mandatory
   DESCRIPTION "Defines whether shutdown/power-off objects can be written; Not supported."
   ::= { agentInfo 6 }


--unitInformation-MIB groups

localServerUnitId OBJECT-TYPE
   SYNTAX   INTEGER
   ACCESS   read-only
   STATUS   mandatory
   DESCRIPTION "Unit identifier number of the local server (usually is ID 1).
                This ID can be used as index into the units table."
   ::= { unitInformation 1 }

numberUnits OBJECT-TYPE
   SYNTAX   INTEGER
   ACCESS   read-only
   STATUS   mandatory
   DESCRIPTION "Number of available units (size of units table)."
   ::= { unitInformation 2 }


-- ----------------------------------------------------------------------------
-- TABLE: unitTable
--
--	unitTable :	.1.3.6.1.4.1.211.1.31.1.1.1.2.3
--
--Implementation of this table is mandatory
-- ----------------------------------------------------------------------------
unitTable OBJECT-TYPE
   SYNTAX   SEQUENCE OF Units
   ACCESS   not-accessible
   STATUS   mandatory
   DESCRIPTION "Description of all units in this MIB"
   ::= { unitInformation 3 }

units OBJECT-TYPE
   SYNTAX   Units
   ACCESS   not-accessible
   STATUS   mandatory
   DESCRIPTION " "
   INDEX   { uUnitId }
   ::= { unitTable 1 }

Units ::=
   SEQUENCE {
      uUnitId
         INTEGER,
      unitClass
         INTEGER,
      unitCainetNr
         INTEGER,
      unitDesignation
         DisplayString,
      unitModelName
         DisplayString,
      unitManufacturer
         DisplayString,
      unitSerialNumber
         DisplayString,
      unitLocation
         DisplayString,
      unitContact
         DisplayString,
      unitAdminURL
         DisplayString,
      frontDoorStatus
         INTEGER,
      housingOpenStatus
         INTEGER,
      msgLogLanguages
         DisplayString,
      unitWorldWideName
         DisplayString,
      remcsId
         DisplayString,
      assetTag
         DisplayString,
      unitManagementIpAddress
         DisplayString,
      unitManagementIpAddressV6
         DisplayString
   }

uUnitId OBJECT-TYPE
   SYNTAX   INTEGER
   ACCESS   read-only
   STATUS   mandatory
   DESCRIPTION "Unit identifier (index: 1..n)"
   ::= { units 1 }

unitClass OBJECT-TYPE
   SYNTAX   INTEGER{
      chassis(1),
      partition(2),
      free-pool(3),
      sb(4),
      iou(7),
      iou-divided(8),
      iou-nodivided(9),
      pci-box(10),
      fan-tray(17),
      op-panel(20),
      mmb(21),
      gspb(28),
      gspb-divided(29),
      gspb-nodivided(30),
      sas-unit(31),
      psu(32),
      dvdb(33),
      lpci-box(34),
      fan(35),
      du(36)
   }
   ACCESS   read-only
   STATUS   mandatory
   DESCRIPTION "Unit classification (type)"
   ::= { units 2 }

unitCainetNr OBJECT-TYPE
   SYNTAX   INTEGER
   ACCESS   read-only
   STATUS   mandatory
   DESCRIPTION "Physical identification number or partition identification number of units. 
                The ID of the 'chassis' is usually 0."
   ::= { units 3 }

unitDesignation OBJECT-TYPE
   SYNTAX   DisplayString
   ACCESS   read-only
   STATUS   mandatory
   DESCRIPTION "Unit identification name. (e.g. 'SB#1')
                This object returns 'Part Number'; if the index shows chassis."
   ::= { units 4 }

unitModelName OBJECT-TYPE
   SYNTAX   DisplayString
   ACCESS   read-only
   STATUS   mandatory
   DESCRIPTION "Unit model name (e.g. 'PRIMERGY PRIMEQUEST 3200 model xxx')"
   ::= { units 5 }

unitManufacturer OBJECT-TYPE
   SYNTAX   DisplayString
   ACCESS   read-only
   STATUS   mandatory
   DESCRIPTION "Unit manufacturer name (e.g. 'Fujitsu')"
   ::= { units 6 }

unitSerialNumber OBJECT-TYPE
   SYNTAX   DisplayString
   ACCESS   read-only
   STATUS   mandatory
   DESCRIPTION "Unit serial number (e.g. '0202456123')"
   ::= { units 7 }

unitLocation OBJECT-TYPE
   SYNTAX   DisplayString
   ACCESS   read-only
   STATUS   mandatory
   DESCRIPTION "Unit location string (e.g. 'ServerCenter Room 17; Rack 9')"
   ::= { units 8 }

unitContact OBJECT-TYPE
   SYNTAX   DisplayString
   ACCESS   read-only
   STATUS   mandatory
   DESCRIPTION "Unit contact name (e.g. 'Mr. Bond')"
   ::= { units 9 }

unitAdminURL OBJECT-TYPE
   SYNTAX   DisplayString
   ACCESS   read-only
   STATUS   mandatory
   DESCRIPTION "URL of administration HTML interface(MMB-GUI) (e.g. 'http://MyServer/admin')"
   ::= { units 10 }

frontDoorStatus OBJECT-TYPE
   SYNTAX   INTEGER{
      unknown(1),
      open(2),
      close(3)
   }
   ACCESS   read-only
   STATUS   mandatory
   DESCRIPTION "Status describing whether the front door is open or closed; Not supported."
   ::= { units 11 }

housingOpenStatus OBJECT-TYPE
   SYNTAX   INTEGER{
      unknown(1),
      open(2),
      close(3),
      opened-and-closed(4)
   }
   ACCESS   read-only
   STATUS   mandatory
   DESCRIPTION "Status describing whether the housing is open or closed; Not supported."
   ::= { units 12 }

msgLogLanguages OBJECT-TYPE
   SYNTAX   DisplayString
   ACCESS   read-only
   STATUS   mandatory
   DESCRIPTION "Supported languages of text message log (comma-seperated list of decimal language codes; 
                see sc2MessageTextLogTable). e.g. '1031;1033' means German and English are supported.
                English (1033) is the default language and is always available; Not supported."
   ::= { units 13 }

unitWorldWideName OBJECT-TYPE
   SYNTAX   DisplayString
   ACCESS   read-only
   STATUS   mandatory
   DESCRIPTION "Unit World Wide Name. A 64-bit sized address for storage devices (e.g. '6661E2B0A00B88FB'); Not supported."
   ::= { units 14 }

remcsId OBJECT-TYPE
   SYNTAX   DisplayString
   ACCESS   read-only
   STATUS   mandatory
   DESCRIPTION "REMCS system identification string (binary data); Not supported.
                   Format of Fujitsu REMCS ID (40byte)
                   Format = TTMMMMMMMMMMMMmmmmmmmmmmmmCCnnnnnnnnnnnn
                   TT     :  2byte : Type ID for Company Name
                   MM...M : 12byte : Model Name
                   mm...m : 12byte : Device Name
                   CC     :  2byte : Checksum
                   nn...n : 12byte : Serial number"
   ::= { units 15 }

assetTag OBJECT-TYPE
   SYNTAX   DisplayString
   ACCESS   read-only
   STATUS   mandatory
   DESCRIPTION "Customer specific asset tag (40 bytes)"
   ::= { units 16 }

unitManagementIpAddress OBJECT-TYPE
   SYNTAX   DisplayString
   ACCESS   read-only
   STATUS   mandatory
   DESCRIPTION "IPv4 address of the partition for management purpose (e.g. '192.168.0.140')"
   ::= { units 18 }

unitManagementIpAddressV6 OBJECT-TYPE
   SYNTAX   DisplayString
   ACCESS   read-only
   STATUS   mandatory
   DESCRIPTION "IPv6 address of the partition for management purpose (e.g. '2001:0db8:0000:85a3:0000:0000:ac1f:8001')"
   ::= { units 20 }

unitTableUpdateCount OBJECT-TYPE
   SYNTAX   INTEGER
   ACCESS   read-only
   STATUS   mandatory
   DESCRIPTION "Counter defining the update revision of the unit table.
                This counter is incremented with every table contents change/update."
   ::= { unitInformation 4 }


-- ----------------------------------------------------------------------------
-- TABLE: unitParentTable
--
--	unitParentTable :	.1.3.6.1.4.1.211.1.31.1.1.1.2.5
--
--Implementation of this table is mandatory
-- ----------------------------------------------------------------------------
unitParentTable OBJECT-TYPE
   SYNTAX   SEQUENCE OF UnitParents
   ACCESS   not-accessible
   STATUS   mandatory
   DESCRIPTION "Parent-child relationship of all units"
   ::= { unitInformation 5 }

unitParents OBJECT-TYPE
   SYNTAX   UnitParents
   ACCESS   not-accessible
   STATUS   mandatory
   DESCRIPTION " "
   INDEX   { pUnitId,
	     pParentNr }
   ::= { unitParentTable 1 }

UnitParents ::=
   SEQUENCE {
      pUnitId
         INTEGER,
      pParentNr
         INTEGER,
      parentUnit
         INTEGER,
      parentUnitClass
         INTEGER
   }

pUnitId OBJECT-TYPE
   SYNTAX   INTEGER
   ACCESS   read-only
   STATUS   mandatory
   DESCRIPTION "Unit identifier (index: 1..n)"
   ::= { unitParents 1 }

pParentNr OBJECT-TYPE
   SYNTAX   INTEGER
   ACCESS   read-only
   STATUS   mandatory
   DESCRIPTION "Parent number (index: 1..n)"
   ::= { unitParents 2 }

parentUnit OBJECT-TYPE
   SYNTAX   INTEGER
   ACCESS   read-only
   STATUS   mandatory
   DESCRIPTION "Parent unit. This is the same value as in the object of 'pParentNr'."
   ::= { unitParents 3 }

parentUnitClass OBJECT-TYPE
   SYNTAX   INTEGER{
      chassis(1),
      partition(2),
      free-pool(3),
      sb(4),
      iou(7),
      iou-divided(8),
      iou-nodivided(9),
      pci-box(10),
      fan-tray(17),
      op-panel(20),
      mmb(21),
      gspb(28),
      gspb-divided(29),
      gspb-nodivided(30),
      sas-unit(31),
      psu(32),
      dvdb(33),
      lpci-box(34),
      fan(35),
      du(36)
   }
   ACCESS   read-only
   STATUS   mandatory
   DESCRIPTION "Unit classification (type). This is the same value as in units table."
   ::= { unitParents 4 }


-- ----------------------------------------------------------------------------
-- TABLE: unitChildTable
--
--	unitChildTable :	.1.3.6.1.4.1.211.1.31.1.1.1.2.6
--
--Implementation of this table is mandatory
-- ----------------------------------------------------------------------------
unitChildTable OBJECT-TYPE
   SYNTAX   SEQUENCE OF UnitChilds
   ACCESS   not-accessible
   STATUS   mandatory
   DESCRIPTION "Parent-child relationship of all units"
   ::= { unitInformation 6 }

unitChilds OBJECT-TYPE
   SYNTAX   UnitChilds
   ACCESS   not-accessible
   STATUS   mandatory
   DESCRIPTION " "
   INDEX   { cUnitId,
	     cChildNr }
   ::= { unitChildTable 1 }

UnitChilds ::=
   SEQUENCE {
      cUnitId
         INTEGER,
      cChildNr
         INTEGER,
      childUnit
         INTEGER,
      childUnitClass
         INTEGER
   }

cUnitId OBJECT-TYPE
   SYNTAX   INTEGER
   ACCESS   read-only
   STATUS   mandatory
   DESCRIPTION "Unit identifier (index: 1..n)"
   ::= { unitChilds 1 }

cChildNr OBJECT-TYPE
   SYNTAX   INTEGER
   ACCESS   read-only
   STATUS   mandatory
   DESCRIPTION "Child number (index: 1..n)"
   ::= { unitChilds 2 }

childUnit OBJECT-TYPE
   SYNTAX   INTEGER
   ACCESS   read-only
   STATUS   mandatory
   DESCRIPTION "Child unit. This is the same value as in the object of 'cChildNr'."
   ::= { unitChilds 3 }

childUnitClass OBJECT-TYPE
   SYNTAX   INTEGER{
      chassis(1),
      partition(2),
      free-pool(3),
      sb(4),
      iou(7),
      iou-divided(8),
      iou-nodivided(9),
      pci-box(10),
      fan-tray(17),
      op-panel(20),
      mmb(21),
      gspb(28),
      gspb-divided(29),
      gspb-nodivided(30),
      sas-unit(31),
      psu(32),
      dvdb(33),
      lpci-box(34),
      fan(35),
      du(36)
   }
   ACCESS   read-only
   STATUS   mandatory
   DESCRIPTION "Unit classification (type). This is the same value as in units table."
   ::= { unitChilds 4 }

parentChildTableUpdateCount OBJECT-TYPE
   SYNTAX   INTEGER
   ACCESS   read-only
   STATUS   mandatory
   DESCRIPTION "Counter defining the update revision of the parent-child unit table.
                This counter is incremented with every table contents change/update."
   ::= { unitInformation 7 }


--management-MIB groups


-- ----------------------------------------------------------------------------
-- TABLE: managementNodeTable
--
--	managementNodeTable :	.1.3.6.1.4.1.211.1.31.1.1.1.3.1
--
--Implementation of this table is mandatory
-- ----------------------------------------------------------------------------
managementNodeTable OBJECT-TYPE
   SYNTAX   SEQUENCE OF ManagementNodes
   ACCESS   not-accessible
   STATUS   mandatory
   DESCRIPTION "SNMP management node addresses (how to address the units)"
   ::= { management 1 }

managementNodes OBJECT-TYPE
   SYNTAX   ManagementNodes
   ACCESS   not-accessible
   STATUS   mandatory
   DESCRIPTION " "
   INDEX   { mnUnitId,
	     mnNodeNr }
   ::= { managementNodeTable 1 }

ManagementNodes ::=
   SEQUENCE {
      mnUnitId
         INTEGER,
      mnNodeNr
         INTEGER,
      unitNodeIfType
         INTEGER,
      unitNodeAddress
         DisplayString,
      unitNodeIpNetmask
         DisplayString,
      unitNodeGateway
         DisplayString,
      unitNodeName
         DisplayString,
      unitNodeClass
         INTEGER,
      unitNodeMacAddress
         PhysAddress,
      unitNodeUseDHCP
         INTEGER,
      unitNodeControllerType
         DisplayString,
      unitNodeControllerModel
         DisplayString,
      unitNodeControllerFWVersion
         DisplayString
   }

mnUnitId OBJECT-TYPE
   SYNTAX   INTEGER
   ACCESS   read-only
   STATUS   mandatory
   DESCRIPTION "Unit identifier (index: 1..n)"
   ::= { managementNodes 1 }

mnNodeNr OBJECT-TYPE
   SYNTAX   INTEGER
   ACCESS   read-only
   STATUS   mandatory
   DESCRIPTION "Management node address number (index: 1..n)"
   ::= { managementNodes 2 }

unitNodeIfType OBJECT-TYPE
   SYNTAX   INTEGER{
      unknown(1),
      ip(2),
      ipx(3),
      ipv6-ip(4),
      virtual-ip(5),
      ipv6-virtual-ip(6)
   }
   ACCESS   read-only
   STATUS   mandatory
   DESCRIPTION "Management node interface type"
   ::= { managementNodes 3 }

unitNodeAddress OBJECT-TYPE
   SYNTAX   DisplayString
   ACCESS   read-only
   STATUS   mandatory
   DESCRIPTION "Management node address (e.g. 192.168.0.100)"
   ::= { managementNodes 4 }

unitNodeIpNetmask OBJECT-TYPE
   SYNTAX   DisplayString
   ACCESS   read-only
   STATUS   mandatory
   DESCRIPTION "Management node address (e.g. 255.255.255.128)"
   ::= { managementNodes 5 }

unitNodeGateway OBJECT-TYPE
   SYNTAX   DisplayString
   ACCESS   read-only
   STATUS   mandatory
   DESCRIPTION "Management node address (e.g. 192.168.0.126)"
   ::= { managementNodes 6 }

unitNodeName OBJECT-TYPE
   SYNTAX   DisplayString
   ACCESS   read-only
   STATUS   mandatory
   DESCRIPTION "Management node name (e.g. 'primequest-no1')"
   ::= { managementNodes 7 }

unitNodeClass OBJECT-TYPE
   SYNTAX   INTEGER{
      unknown(1),
      primery(2),
      secondary(3),
      manegement-blade(4),
      secondary-remote(5),
      secondary-remote-backup(6),
      baseboard-controller(7),
      secondary-manegement-blade(8)
   }
   ACCESS   read-only
   STATUS   mandatory
   DESCRIPTION "Management node class:
                      primary:          operating system interface
                      secondary:        remote management controller interface
                      management-blade: management blade in blade server
                      secondary-backup: backup remote management controller interface"
   ::= { managementNodes 8 }

unitNodeMacAddress OBJECT-TYPE
   SYNTAX   PhysAddress
   ACCESS   read-only
   STATUS   mandatory
   DESCRIPTION "Management node hardware (MAC) address; ff:ff:ff:ff:ff:ff if value not available"
   ::= { managementNodes 9 }

unitNodeUseDHCP OBJECT-TYPE
   SYNTAX   INTEGER{
      unknown(1),
      use-fixed-address(2),
      use-dhcp(3)
   }
   ACCESS   read-only
   STATUS   mandatory
   DESCRIPTION "Management node uses DHCP to obtain its address"
   ::= { managementNodes 10 }

unitNodeControllerType OBJECT-TYPE
   SYNTAX   DisplayString
   ACCESS   read-only
   STATUS   mandatory
   DESCRIPTION "The type of the remote management controller (for identification); like 'RSB'; 'RSB S2'; 'RSB S2 LP'... 
                These names will not be changed if defined once; Not supported."
   ::= { managementNodes 11 }

unitNodeControllerModel OBJECT-TYPE
   SYNTAX   DisplayString
   ACCESS   read-only
   STATUS   mandatory
   DESCRIPTION "The model name of the remote management controller (for displaying); like 'Remote Service Board'; 
                RemoteView Service Board S2'… This name should not be used for identification; only for displaying
                (can be changed in different firmware versions)! Not supported."
   ::= { managementNodes 12 }

unitNodeControllerFWVersion OBJECT-TYPE
   SYNTAX   DisplayString
   ACCESS   read-only
   STATUS   mandatory
   DESCRIPTION "The FW version of the remote management controller; Not supported."
   ::= { managementNodes 13 }

nodeTableUpdateCount OBJECT-TYPE
   SYNTAX   INTEGER
   ACCESS   read-only
   STATUS   mandatory
   DESCRIPTION "Counter defining the update revision of the management node table.
                This counter is incremented with every table contents change/update."
   ::= { management 2 }

managementChannelType OBJECT-TYPE
   SYNTAX   INTEGER{
      unknown(1),
      primery(2),
      secondary(3)
   }
   ACCESS   read-only
   STATUS   mandatory
   DESCRIPTION "The type of the management channel currently used (this MIB instance)."
   ::= { management 3 }


-- ----------------------------------------------------------------------------
-- TABLE: managementProcessorTable
--
--	managementProcessorTable :	.1.3.6.1.4.1.211.1.31.1.1.1.3.4
--
--Implementation of this table is mandatory
-- ----------------------------------------------------------------------------
managementProcessorTable OBJECT-TYPE
   SYNTAX   SEQUENCE OF ManagementProcessors
   ACCESS   not-accessible
   STATUS   mandatory
   DESCRIPTION "System management service processors"
   ::= { management 4 }

managementProcessors OBJECT-TYPE
   SYNTAX   ManagementProcessors
   ACCESS   not-accessible
   STATUS   mandatory
   DESCRIPTION " "
   INDEX   { spUnitId,
	     spProcessorNr }
   ::= { managementProcessorTable 1 }

ManagementProcessors ::=
   SEQUENCE {
      spUnitId
         INTEGER,
      spProcessorNr
         INTEGER,
      spModelName
         DisplayString,
      spFirmwareVersion
         DisplayString,
      spBatteryStatus
         INTEGER,
      spBatteryDischargeTime
         INTEGER,
      spTimeOnBattery
         Counter,
      spDoBatteryChargeCycle
         INTEGER,
      spBatteryChargeLevel
         Gauge
   }

spUnitId OBJECT-TYPE
   SYNTAX   INTEGER
   ACCESS   read-only
   STATUS   mandatory
   DESCRIPTION "Unit identifier (index: 1..n)"
   ::= { managementProcessors 1 }

spProcessorNr OBJECT-TYPE
   SYNTAX   INTEGER
   ACCESS   read-only
   STATUS   mandatory
   DESCRIPTION "Service processor number (index: 1..n)"
   ::= { managementProcessors 2 }

spModelName OBJECT-TYPE
   SYNTAX   DisplayString
   ACCESS   read-only
   STATUS   mandatory
   DESCRIPTION "Service processor model name"
   ::= { managementProcessors 3 }

spFirmwareVersion OBJECT-TYPE
   SYNTAX   DisplayString
   ACCESS   read-only
   STATUS   mandatory
   DESCRIPTION "Service processor firmware version / revision"
   ::= { managementProcessors 4 }

spBatteryStatus OBJECT-TYPE
   SYNTAX   INTEGER{
      unknown(1),
      not-present(2),
      ok(3),
      on-battery(4),
      recharging(5),
      failed(6),
      discharging(7)
   }
   ACCESS   read-only
   STATUS   mandatory
   DESCRIPTION "Service processor backup battery status"
   ::= { managementProcessors 5 }

spBatteryDischargeTime OBJECT-TYPE
   SYNTAX   INTEGER
   ACCESS   read-only
   STATUS   mandatory
   DESCRIPTION "Maximum time (in seconds) this backup battery can discharged.
                after that a shutdown will be performed (-1 = unknown); Not supported."
   ::= { managementProcessors 6 }

spTimeOnBattery OBJECT-TYPE
   SYNTAX   Counter
   ACCESS   read-only
   STATUS   mandatory
   DESCRIPTION "Time (in seconds) the service processor is running on battery
                since power fail (will be cleared on power recovery); Not supported."
   ::= { managementProcessors 7 }

spDoBatteryChargeCycle OBJECT-TYPE
   SYNTAX   INTEGER
   ACCESS   read-write
   STATUS   mandatory
   DESCRIPTION "Perform a discharge/charge cycle on the backup battery by writing
                a non-zero value. Reading this object just returns the value 0; Not supported."
   ::= { managementProcessors 8 }

spBatteryChargeLevel OBJECT-TYPE
   SYNTAX   Gauge
   ACCESS   read-only
   STATUS   mandatory
   DESCRIPTION "Reads the current charge level of the rechargeable battery
                (in percent of the maximum capacity); Not supported."
   ::= { managementProcessors 9 }


-- ----------------------------------------------------------------------------
-- TABLE: managedUpsNodeTable
--
--	managedUpsNodeTable :	.1.3.6.1.4.1.211.1.31.1.1.1.3.5
--
--Implementation of this table is mandatory
-- ----------------------------------------------------------------------------
managedUpsNodeTable OBJECT-TYPE
   SYNTAX   SEQUENCE OF ManagementUpsNodes
   ACCESS   not-accessible
   STATUS   mandatory
   DESCRIPTION "UPS nodes managed by the units; Not supported."
   ::= { management 5 }

managedUpsNodes OBJECT-TYPE
   SYNTAX   ManagementUpsNodes
   ACCESS   not-accessible
   STATUS   mandatory
   DESCRIPTION " "
   INDEX   { upsUnitId,
	     upsNr }
   ::= { managedUpsNodeTable 1 }

ManagementUpsNodes ::=
   SEQUENCE {
      upsUnitId
         INTEGER,
      upsNr
         INTEGER,
      upsVendorName
         DisplayString,
      upsModelName
         DisplayString,
      upsIpAddress
         DisplayString,
      upsMibRoot
         DisplayString,
      upsSnmpCommunity
         DisplayString,
      upsHttpPort
         INTEGER
   }

upsUnitId OBJECT-TYPE
   SYNTAX   INTEGER
   ACCESS   read-only
   STATUS   mandatory
   DESCRIPTION "Unit identifier (index: 1..n); Not supported."
   ::= { managedUpsNodes 1 }

upsNr OBJECT-TYPE
   SYNTAX   INTEGER
   ACCESS   read-only
   STATUS   mandatory
   DESCRIPTION "UPS number (index: 1..n); Not supported."
   ::= { managedUpsNodes 2 }

upsVendorName OBJECT-TYPE
   SYNTAX   DisplayString
   ACCESS   read-only
   STATUS   mandatory
   DESCRIPTION "UPS vendor name; Not supported."
   ::= { managedUpsNodes 3 }

upsModelName OBJECT-TYPE
   SYNTAX   DisplayString
   ACCESS   read-only
   STATUS   mandatory
   DESCRIPTION "UPS model name; Not supported."
   ::= { managedUpsNodes 4 }

upsIpAddress OBJECT-TYPE
   SYNTAX   DisplayString
   ACCESS   read-only
   STATUS   mandatory
   DESCRIPTION "UPS IP address (represented as string; may also contain an IP V6 address); Not supported."
   ::= { managedUpsNodes 5 }

upsMibRoot OBJECT-TYPE
   SYNTAX   DisplayString
   ACCESS   read-only
   STATUS   mandatory
   DESCRIPTION "UPS MIB root OID; specifies the root OID of the MIB to be used to
                query UPS via SNMP (empty string if no SNMP agent available); Not supported."
   ::= { managedUpsNodes 6 }

upsSnmpCommunity OBJECT-TYPE
   SYNTAX   DisplayString
   ACCESS   read-only
   STATUS   mandatory
   DESCRIPTION "UPS SNMP community name (empty string if no SNMP agent available); Not supported."
   ::= { managedUpsNodes 7 }

upsHttpPort OBJECT-TYPE
   SYNTAX   INTEGER
   ACCESS   read-only
   STATUS   mandatory
   DESCRIPTION "UPS HTTP interface port; specifies the TCP port number for accessing
                the UPS management interface via HTTP (0 if no HTTP server available); Not supported."
   ::= { managedUpsNodes 8 }

managementTimeZone OBJECT-TYPE
   SYNTAX   DisplayString
   ACCESS   read-only
   STATUS   mandatory
   DESCRIPTION "Management node timezone (e.g. '2004-9-22 12:15:18+09:00')"
   ::= { management 6 }


--serverInformation-MIB groups


-- ----------------------------------------------------------------------------
-- TABLE: serverTable
--
--	serverTable :	.1.3.6.1.4.1.211.1.31.1.1.1.4.1
--
--Implementation of this table is mandatory
-- ----------------------------------------------------------------------------
serverTable OBJECT-TYPE
   SYNTAX   SEQUENCE OF Servers
   ACCESS   not-accessible
   STATUS   mandatory
   DESCRIPTION "Table containing information about the available servers"
   ::= { serverInformation 1 }

servers OBJECT-TYPE
   SYNTAX   Servers
   ACCESS   not-accessible
   STATUS   mandatory
   DESCRIPTION " "
   INDEX   { srvUnitId }
   ::= { serverTable 1 }

Servers ::=
   SEQUENCE {
      srvUnitId
         INTEGER,
      srvPhysicalMemory
         INTEGER,
      srvLastBootResult
         INTEGER,
      srvCurrentBootStatus
         INTEGER,
      srvShutdownCommand
         INTEGER,
      srvShutdownDelay
         INTEGER,
      srvUUID
         DisplayString,
      srvPhysicalMemoryOs
         INTEGER,
      srvTpmMode
         INTEGER,
      srvManagementIP
         DisplayString
   }

srvUnitId OBJECT-TYPE
   SYNTAX   INTEGER
   ACCESS   read-only
   STATUS   mandatory
   DESCRIPTION "Unit identifier (index: 1..n)"
   ::= { servers 1 }

srvPhysicalMemory OBJECT-TYPE
   SYNTAX   INTEGER
   ACCESS   read-only
   STATUS   mandatory
   DESCRIPTION "Size of physical main memory installed (MBytes); Not supported."
   ::= { servers 2 }

srvLastBootResult OBJECT-TYPE
   SYNTAX   INTEGER{
      unknown(1),
      os-boot-successful(2),
      diagnostic-boot-successful(3),
      no-boot-cpu(4),
      no-bootable-media(5),
      os-failed-load(6),
      diagnostic-boot-failed(7),
      hardware-failure(8)
   }
   ACCESS   read-only
   STATUS   mandatory
   DESCRIPTION "Result of last system boot; Not supported."
   ::= { servers 3 }

srvCurrentBootStatus OBJECT-TYPE
   SYNTAX   INTEGER{
      unknown(1),
      off(2),
      no-boot-cpu(3),
      self-test(4),
      setup(5),
      os-boot(6),
      diagnostic-boot(7),
      os-running(8),
      diagnostic-running(9),
      os-shutdown(10),
      diagnostic-shutdown(11),
      reset(12),
      panic(13),
      check-stop(14),
      dumping(15),
      halt(16),
      xpar-firm-running(17)
   }
   ACCESS   read-only
   STATUS   mandatory
   DESCRIPTION "Status of the current boot
                unknown(1)' returns; during the Power-on->POST and the shutdown->Power-off."
   ::= { servers 4 }

srvShutdownCommand OBJECT-TYPE
   SYNTAX   INTEGER{
      unknown(1),
      power-off(2),
      power-on(3),
      power-cycle(4),
      shutdown-and-off(5),
      shutdown-and-reset(6),
      shutdown-and-power-cycle(7),
      raise-nmi(8),
      abort-pending-command(9),
      reset(10)
   }
   ACCESS   read-write
   STATUS   mandatory
   DESCRIPTION "Shutdown the server and switch off or reset; a delay (see object below)
                can be defined before the command is being executed;
                on reading that value you get the currently pending or executing command value;
                argument tells what kind of action:
                        power-on: switch power on
                        power-off: switch power off
                        power-cycle: switch power off and switch power on again.
                        shutdown-and-off: execute a shutdown then power off
                        shutdown-and-reset: execute a shutdown then reset
                        shutdown-and-power-cycle: execute a shutdown then power off and on again
                        raise-nmi: raise an NMI (normally causes debugger to start)
                The value unknown(1) cannot be set; Not supported."
   ::= { servers 5 }

srvShutdownDelay OBJECT-TYPE
   SYNTAX   INTEGER
   ACCESS   read-write
   STATUS   mandatory
   DESCRIPTION "Delay time (seconds) the agent waits before executing the shutdown command
                (see previous command).
                  0 = immediate action; no delay
                 -1 = unknown (delay not supported)
                The value unknown(-1) cannot be set; Not supported."
   ::= { servers 6 }

srvUUID OBJECT-TYPE
   SYNTAX   DisplayString
   ACCESS   read-only
   STATUS   mandatory
   DESCRIPTION "Universal Unique ID (UUID) number - this is a world wide unique ID number of the server. Can be used for 
                identifying a server. The format is like this: 157E465A-A4AC-D711-A847-DD85CECD12EC."
   ::= { servers 7 }

srvPhysicalMemoryOs OBJECT-TYPE
   SYNTAX   INTEGER
   ACCESS   read-only
   STATUS   mandatory
   DESCRIPTION "Size of physical main memory available to the operating system (MBytes). This value is similar to 
                sc2srvPhysicalMemory'; but may be less if the system has mirror or hot spare memory modules; Not supported."
   ::= { servers 8 }

srvTpmMode OBJECT-TYPE
   SYNTAX   INTEGER{
      disable(1),
      enable(2)
   }
   ACCESS   read-only
   STATUS   mandatory
   DESCRIPTION "Trusted Platform Module(TPM) setting."
   ::= { servers 9 }

srvManagementIP OBJECT-TYPE
   SYNTAX   DisplayString
   ACCESS   read-only
   STATUS   mandatory
   DESCRIPTION "BMC management address (e.g. 192.168.0.150)"
   ::= { servers 10 }


-- ----------------------------------------------------------------------------
-- TABLE: unitPowerOnOffTable
--
--	unitPowerOnOffTable :	.1.3.6.1.4.1.211.1.31.1.1.1.4.2
--
--Implementation of this table is mandatory
-- ----------------------------------------------------------------------------
unitPowerOnOffTable OBJECT-TYPE
   SYNTAX   SEQUENCE OF UnitPowerOnOff
   ACCESS   not-accessible
   STATUS   mandatory
   DESCRIPTION "Unit power-on and -off information"
   ::= { serverInformation 2 }

unitPowerOnOff OBJECT-TYPE
   SYNTAX   UnitPowerOnOff
   ACCESS   not-accessible
   STATUS   mandatory
   DESCRIPTION " "
   INDEX   { ooUnitId }
   ::= { unitPowerOnOffTable 1 }

UnitPowerOnOff ::=
   SEQUENCE {
      ooUnitId
         INTEGER,
      powerOnOffStatus
         INTEGER,
      lastPowerOffSource
         INTEGER,
      lastPowerOnSource
         INTEGER,
      lastPowerOnTime
         INTEGER,
      powerOnCounts
         INTEGER,
      powerOnDuration
         INTEGER,
      powerOffDuration
         INTEGER,
      powerFailRecovery
         INTEGER,
      powerCommand
         INTEGER,
      powerSupplyRedundancy
         INTEGER
   }

ooUnitId OBJECT-TYPE
   SYNTAX   INTEGER
   ACCESS   read-only
   STATUS   mandatory
   DESCRIPTION "Unit identifier (index: 1..n)"
   ::= { unitPowerOnOff 1 }

powerOnOffStatus OBJECT-TYPE
   SYNTAX   INTEGER{
      unknown(1),
      off(2),
      on(3)
   }
   ACCESS   read-only
   STATUS   mandatory
   DESCRIPTION "Current power on/off status"
   ::= { unitPowerOnOff 2 }

lastPowerOffSource OBJECT-TYPE
   SYNTAX   INTEGER{
      unknown(1),
      swoff-command(2),
      power-button(3),
      ac-fail(4),
      clock(5),
      fan-fail(6),
      temperature-critical(7),
      temperature-damage(8),
      power-supply-failure(9),
      watchdog(10),
      remote-off(11),
      hardware-fail(12),
      peripheral-bus-error(13),
      cpu-error(14),
      nmi(20),
      hardware-reset(23),
      warmstart(24),
      reset-button(25),
      ac-fail-reboot(26),
      keyboard(29),
      remote-manager(31),
      remote-manager-reset(32),
      power-limiting(35),
      mmb-continuous-operation(36),
      watchdog-power-cycle(37),
      firmware-restart(242),
      housing-opened(243)
   }
   ACCESS   read-only
   STATUS   mandatory
   DESCRIPTION "Reason why the system was switched off last time; Not supported."
   ::= { unitPowerOnOff 3 }

lastPowerOnSource OBJECT-TYPE
   SYNTAX   INTEGER{
      unknown(1),
      swoff-command(2),
      power-button(3),
      ac-fail(4),
      clock(5),
      fan-fail(6),
      temperature-critical(7),
      temperature-damage(8),
      power-supply-failure(9),
      watchdog(10),
      remote-on(11),
      hardware-fail(12),
      peripheral-bus-error(13),
      cpu-error(14),
      nmi(20),
      hardware-reset(23),
      warmstart(24),
      reset-button(25),
      ac-fail-reboot(26),
      mgmt-processor-fail(27),
      pci-pme(28),
      keyboard(29),
      chipcard-reader(30),
      remote-manager(31),
      remote-manager-reset(32),
      power-cycle(33),
      firmware-restart(242),
      housing-opened(243)
   }
   ACCESS   read-only
   STATUS   mandatory
   DESCRIPTION "Source the system was switched on from; Not supported."
   ::= { unitPowerOnOff 4 }

lastPowerOnTime OBJECT-TYPE
   SYNTAX   INTEGER
   ACCESS   read-only
   STATUS   mandatory
   DESCRIPTION "Time and Date the system was booted (seconds since 1/1/1970; -1 = unknown); Not supported."
   ::= { unitPowerOnOff 5 }

powerOnCounts OBJECT-TYPE
   SYNTAX   INTEGER
   ACCESS   read-only
   STATUS   mandatory
   DESCRIPTION "Tells how often the server was switched on in its life (-1 = unknown); Not supported."
   ::= { unitPowerOnOff 6 }

powerOnDuration OBJECT-TYPE
   SYNTAX   INTEGER
   ACCESS   read-only
   STATUS   mandatory
   DESCRIPTION "Tells how long the system has stayed ON in its life (in hours; -1 = unknown); Not supported."
   ::= { unitPowerOnOff 7 }

powerOffDuration OBJECT-TYPE
   SYNTAX   INTEGER
   ACCESS   read-only
   STATUS   mandatory
   DESCRIPTION "Tells how long the system has stayed OFF in its life (in hours; -1 = unknown); Not supported."
   ::= { unitPowerOnOff 8 }

powerFailRecovery OBJECT-TYPE
   SYNTAX   INTEGER{
      unknown(1),
      not-available(2),
      as-before(3),
      remain-off(4),
      switch-on(5),
      schedule-sync(6)
   }
   ACCESS   read-only
   STATUS   mandatory
   DESCRIPTION "Action on AC power recovery after AC has failed.
                     not-available(2) : function not available; behavior is hardware-defined.
                     as-before(3)     : server gets the same power state as before the AC fail.
                     remain-off(4)    : server remains off on power resume.
                     switch-on(5)     : server is always switched on on power resume.
                     schedule-sync(6)     : server synchronizes the power state with the schedule setting."
   ::= { unitPowerOnOff 9 }

powerCommand OBJECT-TYPE
   SYNTAX   INTEGER{
      unknown(1),
      off(2),
      on(3),
      power-cycle(4)
   }
   ACCESS   read-write
   STATUS   mandatory
   DESCRIPTION "Switch the unit on or off; argument tells what kind of action:
                    on:          switch power on
                    off:         switch power off
                    power-cycle: switch power off and switch power on again.
                The value unknown(1) cannot be set; Not supported."
   ::= { unitPowerOnOff 10 }

powerSupplyRedundancy OBJECT-TYPE
   SYNTAX   INTEGER
   ACCESS   read-only
   STATUS   mandatory
   DESCRIPTION "Specifies whether the power supply system contains redundant power supplies:
                  0   : no redundant power supplies available
                  1   : redundant power supplies available"
   ::= { unitPowerOnOff 11 }


-- ----------------------------------------------------------------------------
-- TABLE: performanceTable
--
--	performanceTable :	.1.3.6.1.4.1.211.1.31.1.1.1.4.3
--
--Implementation of this table is mandatory
-- ----------------------------------------------------------------------------
performanceTable OBJECT-TYPE
   SYNTAX   SEQUENCE OF Performance
   ACCESS   not-accessible
   STATUS   mandatory
   DESCRIPTION "Server performance and utilization information; Not supported."
   ::= { serverInformation 3 }

performance OBJECT-TYPE
   SYNTAX   Performance
   ACCESS   not-accessible
   STATUS   mandatory
   DESCRIPTION " "
   INDEX   { perfUnitId,
	     perfNr }
   ::= { performanceTable 1 }

Performance ::=
   SEQUENCE {
      perfUnitId
         INTEGER,
      perfNr
         INTEGER,
      perfType
         INTEGER,
      performanceValue
         Gauge,
      performanceName
         DisplayString
   }

perfUnitId OBJECT-TYPE
   SYNTAX   INTEGER
   ACCESS   read-only
   STATUS   mandatory
   DESCRIPTION "Unit identifier (index; 1..n); Not supported."
   ::= { performance 1 }

perfNr OBJECT-TYPE
   SYNTAX   INTEGER
   ACCESS   read-only
   STATUS   mandatory
   DESCRIPTION "Server performance entry number (index; 1..n)"
   ::= { performance 2 }

perfType OBJECT-TYPE
   SYNTAX   INTEGER{
      cpu(1),
      cpu-pverall(2),
      pci-load(3),
      pci-efficiency(4),
      pci-transfer(5),
      memory-physical(6),
      memory-total(7),
      memory-percent(8)
   }
   ACCESS   read-only
   STATUS   mandatory
   DESCRIPTION "Server performance object type (description see below); Not supported."
   ::= { performance 3 }

performanceValue OBJECT-TYPE
   SYNTAX   Gauge
   ACCESS   read-only
   STATUS   mandatory
   DESCRIPTION "Server performance value (value interpretation depending on type):; Not supported.
                   cpu:             Load of a single CPU in percent
                   cpu-overall:     Overall CPU load in percent
                   pci-load:        PCI bus load in percent
                   pci-efficiency:  PCI bus efficiency in percent (100% is optimum)
                   pci-transfer:    PCI bus transfer rate in MBytes/sec.
                   memory-physical: Physical memory usage in MBytes
                   memory-total:    Total memory usage (physical + virtual) in MBytes
                   memory-percent:  Physical memory usage in percent"
   ::= { performance 4 }

performanceName OBJECT-TYPE
   SYNTAX   DisplayString
   ACCESS   read-only
   STATUS   mandatory
   DESCRIPTION "Name (short description) of the performance value (e.g. 'CPU1').
                Can be used for displaying a list of performance values in the management frontend; Not supported."
   ::= { performance 5 }


-- ----------------------------------------------------------------------------
-- TABLE: timerOnOffTable
--
--	timerOnOffTable :	.1.3.6.1.4.1.211.1.31.1.1.1.4.4
--
--Implementation of this table is mandatory
-- ----------------------------------------------------------------------------
timerOnOffTable OBJECT-TYPE
   SYNTAX   SEQUENCE OF TimerOnOff
   ACCESS   not-accessible
   STATUS   mandatory
   DESCRIPTION "Power on/off timer table; Not supported."
   ::= { serverInformation 4 }

timerOnOff OBJECT-TYPE
   SYNTAX   TimerOnOff
   ACCESS   not-accessible
   STATUS   mandatory
   DESCRIPTION " "
   INDEX   { tooUnitId,
	     tooDayOfWeek }
   ::= { timerOnOffTable 1 }

TimerOnOff ::=
   SEQUENCE {
      tooUnitId
         INTEGER,
      tooDayOfWeek
         INTEGER,
      onTime
         INTEGER,
      offTime
         INTEGER
   }

tooUnitId OBJECT-TYPE
   SYNTAX   INTEGER
   ACCESS   read-only
   STATUS   mandatory
   DESCRIPTION "Unit identifier (index: 1..n); Not supported."
   ::= { timerOnOff 1 }

tooDayOfWeek OBJECT-TYPE
   SYNTAX   INTEGER
   ACCESS   read-only
   STATUS   mandatory
   DESCRIPTION "Day of the week the times should act upon (index); 1=Sunday 2=Monday... ; Not supported."
   ::= { timerOnOff 2 }

onTime OBJECT-TYPE
   SYNTAX   INTEGER
   ACCESS   read-write
   STATUS   mandatory
   DESCRIPTION "Time the system should be switched on (by the real-time clock;
                in minutes since midnight; -1 = disabled; no on time).
                Only values -1 and 0..1439 are allowed; Not supported."
   ::= { timerOnOff 3 }

offTime OBJECT-TYPE
   SYNTAX   INTEGER
   ACCESS   read-write
   STATUS   mandatory
   DESCRIPTION "Time the system should be switched off (by the real-time clock of software;
                in minutes since midnight; -1 = disabled; no on time).
                Only values -1 and 0..1439 are allowed; Not supported."
   ::= { timerOnOff 4 }


-- ----------------------------------------------------------------------------
-- TABLE: powerMonitoringTable
--
--	powerMonitoringTable :	.1.3.6.1.4.1.211.1.31.1.1.1.4.5
--
--Implementation of this table is mandatory
-- ----------------------------------------------------------------------------
powerMonitoringTable OBJECT-TYPE
   SYNTAX   SEQUENCE OF PowerMonitoring
   ACCESS   not-accessible
   STATUS   mandatory
   DESCRIPTION "Power monitoring table"
   ::= { serverInformation 5 }

powerMonitoring OBJECT-TYPE
   SYNTAX   PowerMonitoring
   ACCESS   not-accessible
   STATUS   mandatory
   DESCRIPTION " "
   INDEX   { pmUnitId }
   ::= { powerMonitoringTable 1 }

PowerMonitoring ::=
   SEQUENCE {
      pmUnitId
         INTEGER,
      pmCurrentPowerMonitoringAvailable
         TrueFalse,
      pmCurrentPowerMonitoringEnabled
         TrueFalse,
      pmNominalPowerConsumption
         INTEGER,
      pmCurrentPowerConsumption
         Gauge,
      pmCurrentPowerControl
         INTEGER
   }

pmUnitId OBJECT-TYPE
   SYNTAX   INTEGER
   ACCESS   read-only
   STATUS   mandatory
   DESCRIPTION "Unit identifier (index: 1..n)"
   ::= { powerMonitoring 1 }

pmCurrentPowerMonitoringAvailable OBJECT-TYPE
   SYNTAX   TrueFalse
   ACCESS   read-only
   STATUS   mandatory
   DESCRIPTION "Power monitoring and control available on this server:
                   true:  Power monitoring and power control is available
                   false: Power monitoring and power control is not available"
   ::= { powerMonitoring 2 }

pmCurrentPowerMonitoringEnabled OBJECT-TYPE
   SYNTAX   TrueFalse
   ACCESS   read-only
   STATUS   mandatory
   DESCRIPTION "Power monitoring enable value:
                   true:  Power monitoring and data gathering is enabled
                   false: Power monitoring and data gathering is disabled or not available"
   ::= { powerMonitoring 3 }

pmNominalPowerConsumption OBJECT-TYPE
   SYNTAX   INTEGER
   ACCESS   read-only
   STATUS   mandatory
   DESCRIPTION "Nominal (maximum) value of the system's power consumption (in Watts; -1 if value not available)"
   ::= { powerMonitoring 4 }

pmCurrentPowerConsumption OBJECT-TYPE
   SYNTAX   Gauge
   ACCESS   read-only
   STATUS   mandatory
   DESCRIPTION "Current value of the system's power consumption (in Watts; 4294967295(0xffffffff) if value not available)"
   ::= { powerMonitoring 5 }

pmCurrentPowerControl OBJECT-TYPE
   SYNTAX   INTEGER{
      unknown(1),
      disabled(2),
      best-performance(3),
      minimum-power(4),
      automatic(5),
      scheduled(6),
      limited(7)
   }
   ACCESS   read-only
   STATUS   mandatory
   DESCRIPTION "Power mode control value; Not supported.
                   disabled:         The baseboard management controller does not control the power saving behaviour
                   best-performance: The baseboard management controller gives best performance to the system 
                                            (power consumption may be increased)
                   minimum-power:    The baseboard management controller controls the system in way to consume 
                                               minimum power (performance may be reduced)
                   automatic:        The baseboard management controller automatically controls power consumption 
                                         between good performance and low power consumption
                   scheduled:        The baseboard management controller controls power consumption by schedule"
   ::= { powerMonitoring 6 }

pmPowerLimitThreshold OBJECT-TYPE
   SYNTAX   INTEGER
   ACCESS   read-only
   STATUS   mandatory
   DESCRIPTION "Maximum limit value of the system's power consumption (in Watts; -1 if value not available; only valid if limiting enabled)"
   ::= { powerMonitoring 8 }

pmPowerControlMode OBJECT-TYPE
   SYNTAX   INTEGER{
      unknown(1),
      disabled(2),
      best-performance(3),
      minimum-power(4),
      automatic(5),
      scheduled(6),
      limited(7),
      low-noise(8)
   }
   ACCESS   read-only
   STATUS   mandatory
   DESCRIPTION "Configured power control mode value:
                   disabled:         The management controller does not control the power saving behaviour
                   best-performance: The management controller gives best performance to the system 
                                            (power consumption may be increased)
                   minimum-power:    The management controller controls the system in way to consume 
                                               minimum power (performance may be reduced)
                   automatic:        The management controller automatically controls power consumption 
                                         between good performance and low power consumption
                   scheduled:        The management controller controls power consumption by schedule
                   limited:          The management controller controls power consumption by power limit
                   low-noise:        The management controller controls the power to ensure running"
   ::= { powerMonitoring 11 }

pmPowerDisplayUnit OBJECT-TYPE
   SYNTAX   INTEGER{
      unknown(1),
      watt(2),
      btu(3)
   }
   ACCESS   read-only
   STATUS   mandatory
   DESCRIPTION "Configurd unit for the display of power consumption values:
                   Watt:   Power consumption values are displayed in Watts
                   Btu/h:  Power consumption values are displyed in Btu"
   ::= { powerMonitoring 12 }


-- ----------------------------------------------------------------------------
-- TABLE: utilizationHistoryTable
--
--	utilizationHistoryTable :	.1.3.6.1.4.1.211.1.31.1.1.1.4.6
--
--Implementation of this table is mandatory
-- ----------------------------------------------------------------------------
utilizationHistoryTable OBJECT-TYPE
   SYNTAX   SEQUENCE OF UtilizationHistory
   ACCESS   not-accessible
   STATUS   mandatory
   DESCRIPTION "Utilization history table (for power consumption); table only contains existing
                values (no values for non-existing values); Not supported."
   ::= { serverInformation 6 }

utilizationHistory OBJECT-TYPE
   SYNTAX   UtilizationHistory
   ACCESS   not-accessible
   STATUS   mandatory
   DESCRIPTION " "
   INDEX   { uthUnitId,
	     uthEntity,
	     uthTimeStamp }
   ::= { utilizationHistoryTable 1 }

UtilizationHistory ::=
   SEQUENCE {
      uthUnitId
         INTEGER,
      uthEntity
         INTEGER,
      uthTimeStamp
         INTEGER,
      uthHardwareUUID
         DisplayString,
      uthAverageValue
         Gauge,
      uthMinValue
         Gauge,
      uthMaxValue
         Gauge
   }

uthUnitId OBJECT-TYPE
   SYNTAX   INTEGER
   ACCESS   read-only
   STATUS   mandatory
   DESCRIPTION "Unit identifier (index; 1..n); Not supported."
   ::= { utilizationHistory 1 }

uthEntity OBJECT-TYPE
   SYNTAX   INTEGER{
      powerConsumptionDay(1),
      powerConsumptionMonth(2),
      powerConsumptionYear(3)
   }
   ACCESS   read-only
   STATUS   mandatory
   DESCRIPTION "Utilization value entity; describes what kind of value to be requested; Not supported.
                  powerConsumptionDay:   power consumption values of the last 24 hours; one value (Watts) per minute
                  powerConsumptionMonth: power consumption values of the last month; one value (Watts) per hour
                   powerConsumptionYear:  power consumption values of the last year; one value (Watts) per day"
   ::= { utilizationHistory 2 }

uthTimeStamp OBJECT-TYPE
   SYNTAX   INTEGER
   ACCESS   read-only
   STATUS   mandatory
   DESCRIPTION "Time stamp of the currenty history entry (time_t = seconds since 1/1/1970; 0:00 AM); Not supported."
   ::= { utilizationHistory 3 }

uthHardwareUUID OBJECT-TYPE
   SYNTAX   DisplayString
   ACCESS   read-only
   STATUS   mandatory
   DESCRIPTION "UUID of the hardware instance that delivered the value (from object sc2srvUUID);
                may change if an installation is migrated to another hardware (e.g. in blade environments); Not supported."
   ::= { utilizationHistory 4 }

uthAverageValue OBJECT-TYPE
   SYNTAX   Gauge
   ACCESS   read-only
   STATUS   mandatory
   DESCRIPTION "Average value (in Watts) within the monitored time period (minute; hour; day); Not supported."
   ::= { utilizationHistory 5 }

uthMinValue OBJECT-TYPE
   SYNTAX   Gauge
   ACCESS   read-only
   STATUS   mandatory
   DESCRIPTION "Minimum (lowest) value within the monitored time period; Not supported."
   ::= { utilizationHistory 6 }

uthMaxValue OBJECT-TYPE
   SYNTAX   Gauge
   ACCESS   read-only
   STATUS   mandatory
   DESCRIPTION "Maximum (highest) value within the monitored time period; Not supported."
   ::= { utilizationHistory 7 }


-- ----------------------------------------------------------------------------
-- TABLE: powerSourceInformationTable
--
--	powerSourceInformationTable :	.1.3.6.1.4.1.211.1.31.1.1.1.4.7
--
--Implementation of this table is mandatory
-- ----------------------------------------------------------------------------
powerSourceInformationTable OBJECT-TYPE
   SYNTAX   SEQUENCE OF PowerSourceInformation
   ACCESS   not-accessible
   STATUS   mandatory
   DESCRIPTION "Power source information table"
   ::= { serverInformation 7 }

powerSourceInformation OBJECT-TYPE
   SYNTAX   PowerSourceInformation
   ACCESS   not-accessible
   STATUS   mandatory
   DESCRIPTION " "
   INDEX   { psiUnitId }
   ::= { powerSourceInformationTable 1 }

PowerSourceInformation ::=
   SEQUENCE {
      psiUnitId
         INTEGER,
      psiPowerSourceType
         DisplayString,
      psiPowerSourcePhase
         INTEGER,
      psiPowerSourceVoltage
         INTEGER
   }

psiUnitId OBJECT-TYPE
   SYNTAX   INTEGER
   ACCESS   read-only
   STATUS   mandatory
   DESCRIPTION "Unit identifier (index; 1..n)"
   ::= { powerSourceInformation 1 }

psiPowerSourceType OBJECT-TYPE
   SYNTAX   DisplayString
   ACCESS   read-only
   STATUS   mandatory
   DESCRIPTION "System input power source type (e.g. 'AC'; 'DC')"
   ::= { powerSourceInformation 2 }

psiPowerSourcePhase OBJECT-TYPE
   SYNTAX   INTEGER{
      unknown(1),
      single-phase(2),
      three-phase(3)
   }
   ACCESS   read-only
   STATUS   mandatory
   DESCRIPTION "System input phase of power source."
   ::= { powerSourceInformation 3 }

psiPowerSourceVoltage OBJECT-TYPE
   SYNTAX   INTEGER
   ACCESS   read-only
   STATUS   mandatory
   DESCRIPTION "System nominal input voltage of power source (in Volts; -1 if value not available)."
   ::= { powerSourceInformation 4 }


--environment-MIB groups


-- ----------------------------------------------------------------------------
-- TABLE: temperatureSensorTable
--
--	temperatureSensorTable :	.1.3.6.1.4.1.211.1.31.1.1.1.5.1
--
--Implementation of this table is mandatory
-- ----------------------------------------------------------------------------
temperatureSensorTable OBJECT-TYPE
   SYNTAX   SEQUENCE OF TemperatureSensors
   ACCESS   not-accessible
   STATUS   mandatory
   DESCRIPTION "Temperature sensors"
   ::= { environment 1 }

temperatureSensors OBJECT-TYPE
   SYNTAX   TemperatureSensors
   ACCESS   not-accessible
   STATUS   mandatory
   DESCRIPTION " "
   INDEX   { tempUnitId,
	     tempSensorNr }
   ::= { temperatureSensorTable 1 }

TemperatureSensors ::=
   SEQUENCE {
      tempUnitId
         INTEGER,
      tempSensorNr
         INTEGER,
      tempSensorDesignation
         DisplayString,
      tempSensorIdentifier
         DisplayString,
      tempSensorStatus
         INTEGER,
      tempCurrentTemperature
         INTEGER,
      tempWarningLevel
         INTEGER,
      tempCriticalLevel
         INTEGER,
      tempCriticalReaction
         INTEGER
   }

tempUnitId OBJECT-TYPE
   SYNTAX   INTEGER
   ACCESS   read-only
   STATUS   mandatory
   DESCRIPTION "Unit identifier (index: 1..n)"
   ::= { temperatureSensors 1 }

tempSensorNr OBJECT-TYPE
   SYNTAX   INTEGER
   ACCESS   read-only
   STATUS   mandatory
   DESCRIPTION "Temperature sensor number (index: 0..n)"
   ::= { temperatureSensors 2 }

tempSensorDesignation OBJECT-TYPE
   SYNTAX   DisplayString
   ACCESS   read-only
   STATUS   mandatory
   DESCRIPTION "Temperature sensor designation (e.g. SB#0-CPU#A0 Temp.)"
   ::= { temperatureSensors 3 }

tempSensorIdentifier OBJECT-TYPE
   SYNTAX   DisplayString
   ACCESS   read-only
   STATUS   mandatory
   DESCRIPTION "Temperature sensor identification string (e.g. TEMP-RSB1); Not supported."
   ::= { temperatureSensors 4 }

tempSensorStatus OBJECT-TYPE
   SYNTAX   INTEGER{
      unknown(1),
      not-available(2),
      ok(3),
      failed(5),
      temperature-warning(6),
      temperature-critical(7)
   }
   ACCESS   read-only
   STATUS   mandatory
   DESCRIPTION "Status of the temperature sensor
                Status mapping.
                 SEL level        MIB Value
                Warning          temperature-warning(6)
                Error              temperature-critical(7)
                Error              failed(5)"
   ::= { temperatureSensors 5 }

tempCurrentTemperature OBJECT-TYPE
   SYNTAX   INTEGER
   ACCESS   read-only
   STATUS   mandatory
   DESCRIPTION "Current temperature at this sensor (degrees Celsius).
                This object returns 0; if the agent can not get the value."
   ::= { temperatureSensors 6 }

tempWarningLevel OBJECT-TYPE
   SYNTAX   INTEGER
   ACCESS   read-only
   STATUS   mandatory
   DESCRIPTION "Maximum temperature - warning level (degrees Celsius)"
   ::= { temperatureSensors 7 }

tempCriticalLevel OBJECT-TYPE
   SYNTAX   INTEGER
   ACCESS   read-only
   STATUS   mandatory
   DESCRIPTION "Maximum temperature - critical level (degrees Celsius). system shutdown may occur if this level is exceeded."
   ::= { temperatureSensors 8 }

tempCriticalReaction OBJECT-TYPE
   SYNTAX   INTEGER{
      unknown(1),
      continue(2),
      shutdown-and-poweroff(3)
   }
   ACCESS   read-only
   STATUS   mandatory
   DESCRIPTION "Reaction if temperature exceeds the critical level."
   ::= { temperatureSensors 9 }


-- ----------------------------------------------------------------------------
-- TABLE: fanTable
--
--	fanTable :	.1.3.6.1.4.1.211.1.31.1.1.1.5.2
--
--Implementation of this table is mandatory
-- ----------------------------------------------------------------------------
fanTable OBJECT-TYPE
   SYNTAX   SEQUENCE OF Fans
   ACCESS   not-accessible
   STATUS   mandatory
   DESCRIPTION "Fans"
   ::= { environment 2 }

fans OBJECT-TYPE
   SYNTAX   Fans
   ACCESS   not-accessible
   STATUS   mandatory
   DESCRIPTION " "
   INDEX   { fanUnitId,
	     fanNr }
   ::= { fanTable 1 }

Fans ::=
   SEQUENCE {
      fanUnitId
         INTEGER,
      fanNr
         INTEGER,
      fanDesignation
         DisplayString,
      fanIdentifier
         DisplayString,
      fanStatus
         INTEGER,
      fanCurrentSpeed
         INTEGER,
      fanQuality
         INTEGER,
      fanFailReaction
         INTEGER,
      fanFailShutdownDelay
         INTEGER
   }

fanUnitId OBJECT-TYPE
   SYNTAX   INTEGER
   ACCESS   read-only
   STATUS   mandatory
   DESCRIPTION "Unit identifier (index: 1..n)"
   ::= { fans 1 }

fanNr OBJECT-TYPE
   SYNTAX   INTEGER
   ACCESS   read-only
   STATUS   mandatory
   DESCRIPTION "Fan number (index: 0..n)"
   ::= { fans 2 }

fanDesignation OBJECT-TYPE
   SYNTAX   DisplayString
   ACCESS   read-only
   STATUS   mandatory
   DESCRIPTION "Fan designation (e.g. FAN-TRAY#00-Fan#00-1)"
   ::= { fans 3 }

fanIdentifier OBJECT-TYPE
   SYNTAX   DisplayString
   ACCESS   read-only
   STATUS   mandatory
   DESCRIPTION "Fan identification string (e.g. FAN-1-POWERSUPPLY); Not supported."
   ::= { fans 4 }

fanStatus OBJECT-TYPE
   SYNTAX   INTEGER{
      unknown(1),
      disabled(2),
      ok(3),
      failed(4),
      prefailed-predicted(5),
      redundant-fan-failed(6),
      not-manageable(7),
      not-present(8)
   }
   ACCESS   read-only
   STATUS   mandatory
   DESCRIPTION "Status of the fan
                Status mapping.
                 SEL level        MIB Value
                Error              failed(5)"
   ::= { fans 5 }

fanCurrentSpeed OBJECT-TYPE
   SYNTAX   INTEGER
   ACCESS   read-only
   STATUS   mandatory
   DESCRIPTION "Current fan speed (revolutions per minute). This object returns 0; if the agent can not get the value."
   ::= { fans 6 }

fanQuality OBJECT-TYPE
   SYNTAX   INTEGER
   ACCESS   read-only
   STATUS   mandatory
   DESCRIPTION "Quality of fan (in percent of nominal speed - measured at full speed); Not supported."
   ::= { fans 7 }

fanFailReaction OBJECT-TYPE
   SYNTAX   INTEGER{
      unknown(1),
      continue(2),
      shutdown-and-poweroff(3)
   }
   ACCESS   read-only
   STATUS   mandatory
   DESCRIPTION "Reaction if the fan fails."
   ::= { fans 8 }

fanFailShutdownDelay OBJECT-TYPE
   SYNTAX   INTEGER
   ACCESS   read-write
   STATUS   mandatory
   DESCRIPTION "Delay time (in seconds) when shutdown should commit on fan fail
                (if shutdown-and-off is configured; 0 = immediately
                 -1 = unknown; cannot be set); Not supported."
   ::= { fans 9 }


-- ----------------------------------------------------------------------------
-- TABLE: airflowTable
--
--	airflowTable :	.1.3.6.1.4.1.211.1.31.1.1.1.5.3
--
--Implementation of this table is mandatory
-- ----------------------------------------------------------------------------
airflowTable OBJECT-TYPE
   SYNTAX   SEQUENCE OF Airflow
   ACCESS   not-accessible
   STATUS   mandatory
   DESCRIPTION "Exhaust airflow volume table"
   ::= { environment 3 }

airflow OBJECT-TYPE
   SYNTAX   Airflow
   ACCESS   not-accessible
   STATUS   mandatory
   DESCRIPTION " "
   INDEX   { afUnitId }
   ::= { airflowTable 1 }

Airflow ::=
   SEQUENCE {
      afUnitId
         INTEGER,
      afExhaustAirflowVolume
         INTEGER,
      afExhaustAirflowVolumeUnit
         DisplayString
   }

afUnitId OBJECT-TYPE
   SYNTAX   INTEGER
   ACCESS   read-only
   STATUS   mandatory
   DESCRIPTION "Unit identifier (index; 1..n)"
   ::= { airflow 1 }

afExhaustAirflowVolume OBJECT-TYPE
   SYNTAX   INTEGER
   ACCESS   read-only
   STATUS   mandatory
   DESCRIPTION "System exhaust airflow volume ('-1' if value not available)"
   ::= { airflow 2 }

afExhaustAirflowVolumeUnit OBJECT-TYPE
   SYNTAX   DisplayString
   ACCESS   read-only
   STATUS   mandatory
   DESCRIPTION "System exhaust airflow volume unit (e.g. 'cbm/h'; 'ccm/min'; ...)"
   ::= { airflow 3 }


--hardware-MIB groups


-- ----------------------------------------------------------------------------
-- TABLE: systemBoardTable
--
--	systemBoardTable :	.1.3.6.1.4.1.211.1.31.1.1.1.6.1
--
--Implementation of this table is mandatory
-- ----------------------------------------------------------------------------
systemBoardTable OBJECT-TYPE
   SYNTAX   SEQUENCE OF SystemBoard
   ACCESS   not-accessible
   STATUS   mandatory
   DESCRIPTION "System board (main board) information"
   ::= { hardware 1 }

systemBoard OBJECT-TYPE
   SYNTAX   SystemBoard
   ACCESS   not-accessible
   STATUS   mandatory
   DESCRIPTION " "
   INDEX   { sbUnitId }
   ::= { systemBoardTable 1 }

SystemBoard ::=
   SEQUENCE {
      sbUnitId
         INTEGER,
      systemBoardModelName
         DisplayString,
      systemBoardProductNumber
         DisplayString,
      systemBoardRevision
         DisplayString,
      systemBoardSerialNumber
         DisplayString
   }

sbUnitId OBJECT-TYPE
   SYNTAX   INTEGER
   ACCESS   read-only
   STATUS   mandatory
   DESCRIPTION "Unit identifier (index: 1..n)"
   ::= { systemBoard 1 }

systemBoardModelName OBJECT-TYPE
   SYNTAX   DisplayString
   ACCESS   read-only
   STATUS   mandatory
   DESCRIPTION "Model name (e.g. 'System Board')"
   ::= { systemBoard 2 }

systemBoardProductNumber OBJECT-TYPE
   SYNTAX   DisplayString
   ACCESS   read-only
   STATUS   mandatory
   DESCRIPTION "Product number (may be identical to ModelName)"
   ::= { systemBoard 3 }

systemBoardRevision OBJECT-TYPE
   SYNTAX   DisplayString
   ACCESS   read-only
   STATUS   mandatory
   DESCRIPTION "Revision string (e.g. 'WGS1 GS3')"
   ::= { systemBoard 4 }

systemBoardSerialNumber OBJECT-TYPE
   SYNTAX   DisplayString
   ACCESS   read-only
   STATUS   mandatory
   DESCRIPTION "Serial number (not available for all boards)"
   ::= { systemBoard 5 }


-- ----------------------------------------------------------------------------
-- TABLE: powerSupplyTable
--
--	powerSupplyTable :	.1.3.6.1.4.1.211.1.31.1.1.1.6.2
--
--Implementation of this table is mandatory
-- ----------------------------------------------------------------------------
powerSupplyTable OBJECT-TYPE
   SYNTAX   SEQUENCE OF PowerSupply
   ACCESS   not-accessible
   STATUS   mandatory
   DESCRIPTION "Power supplies"
   ::= { hardware 2 }

powerSupply OBJECT-TYPE
   SYNTAX   PowerSupply
   ACCESS   not-accessible
   STATUS   mandatory
   DESCRIPTION " "
   INDEX   { psUnitId,
	     psPowerSupplyNr }
   ::= { powerSupplyTable 1 }

PowerSupply ::=
   SEQUENCE {
      psUnitId
         INTEGER,
      psPowerSupplyNr
         INTEGER,
      powerSupplyDesignation
         DisplayString,
      powerSupplyIdentifier
         DisplayString,
      powerSupplyStatus
         INTEGER
   }

psUnitId OBJECT-TYPE
   SYNTAX   INTEGER
   ACCESS   read-only
   STATUS   mandatory
   DESCRIPTION "Unit identifier (index: 1..n)"
   ::= { powerSupply 1 }

psPowerSupplyNr OBJECT-TYPE
   SYNTAX   INTEGER
   ACCESS   read-only
   STATUS   mandatory
   DESCRIPTION "Power supply (bay) number (index: 0..n)"
   ::= { powerSupply 2 }

powerSupplyDesignation OBJECT-TYPE
   SYNTAX   DisplayString
   ACCESS   read-only
   STATUS   mandatory
   DESCRIPTION "Power supply designation (e.g. PWRSYS#1-FEP#0)"
   ::= { powerSupply 3 }

powerSupplyIdentifier OBJECT-TYPE
   SYNTAX   DisplayString
   ACCESS   read-only
   STATUS   mandatory
   DESCRIPTION "Power supply identification string (e.g. PS1); Not supported."
   ::= { powerSupply 4 }

powerSupplyStatus OBJECT-TYPE
   SYNTAX   INTEGER{
      unknown(1),
      not-present(2),
      ok(3),
      failed(4),
      ac-fail(5),
      dc-fail(6),
      critical-temperature(7),
      not-manageable(8),
      predictive-fail(9)
   }
   ACCESS   read-only
   STATUS   mandatory
   DESCRIPTION "Power supply status
                Status mapping.
                 SEL level        MIB Value
                Warning          ac-fail(5)
                Warning          predictive-fail(9)
                Error              failed(4)
                Error              not-manageable(8)"
   ::= { powerSupply 5 }

psPowerSupplyLoad OBJECT-TYPE
   SYNTAX   INTEGER
   ACCESS   read-only
   STATUS   mandatory
   DESCRIPTION "Actual power supply output load in Watts (0 = not available); Not supported."
   ::= { localServerUnitId 6 }


-- ----------------------------------------------------------------------------
-- TABLE: voltageTable
--
--	voltageTable :	.1.3.6.1.4.1.211.1.31.1.1.1.6.3
--
--Implementation of this table is mandatory
-- ----------------------------------------------------------------------------
voltageTable OBJECT-TYPE
   SYNTAX   SEQUENCE OF Voltages
   ACCESS   not-accessible
   STATUS   mandatory
   DESCRIPTION "Voltages - all voltage values are in 1/100th Volts;
                a value of 330 means 3.30 Volts (0xffffffff = unknown)"
   ::= { hardware 3 }

voltages OBJECT-TYPE
   SYNTAX   Voltages
   ACCESS   not-accessible
   STATUS   mandatory
   DESCRIPTION " "
   INDEX   { voUnitId,
	     voSensorNr }
   ::= { voltageTable 1 }

Voltages ::=
   SEQUENCE {
      voUnitId
         INTEGER,
      voSensorNr
         INTEGER,
      voltageDesignation
         DisplayString,
      voltageStatus
         INTEGER,
      voltageCurrentValue
         INTEGER,
      voltageNominalValue
         INTEGER,
      voltageMinimumLevel
         INTEGER,
      voltageMaximumLevel
         INTEGER,
      voltageCurrentLoad
         Gauge
   }

voUnitId OBJECT-TYPE
   SYNTAX   INTEGER
   ACCESS   read-only
   STATUS   mandatory
   DESCRIPTION "Unit identifier (index: 1..n)"
   ::= { voltages 1 }

voSensorNr OBJECT-TYPE
   SYNTAX   INTEGER
   ACCESS   read-only
   STATUS   mandatory
   DESCRIPTION "Voltage sensor number (index: 0..n)"
   ::= { voltages 2 }

voltageDesignation OBJECT-TYPE
   SYNTAX   DisplayString
   ACCESS   read-only
   STATUS   mandatory
   DESCRIPTION "Voltage designation string (e.g. SB#1-+5V#1)"
   ::= { voltages 3 }

voltageStatus OBJECT-TYPE
   SYNTAX   INTEGER{
      unknown(1),
      not-available(2),
      ok(3),
      too-low(4),
      too-high(5),
      sensor-failed(6),
      low-warning(7),
      high-warning(8)
   }
   ACCESS   read-only
   STATUS   mandatory
   DESCRIPTION "Voltage status
                Status mapping.
                 SEL level        MIB Value
                Warning          low-warning(7)
                Warning          high-warning(8)
                Error              too-low(4)
                Error              too-high(5)"
   ::= { voltages 4 }

voltageCurrentValue OBJECT-TYPE
   SYNTAX   INTEGER
   ACCESS   read-only
   STATUS   mandatory
   DESCRIPTION "Voltage current value. This object returns 0; if the agent can not get the value.(1/100V)"
   ::= { voltages 5 }

voltageNominalValue OBJECT-TYPE
   SYNTAX   INTEGER
   ACCESS   read-only
   STATUS   mandatory
   DESCRIPTION "Voltage nominal value; Not supported."
   ::= { voltages 6 }

voltageMinimumLevel OBJECT-TYPE
   SYNTAX   INTEGER
   ACCESS   read-only
   STATUS   mandatory
   DESCRIPTION "Voltage minimum level (1/100V)"
   ::= { voltages 7 }

voltageMaximumLevel OBJECT-TYPE
   SYNTAX   INTEGER
   ACCESS   read-only
   STATUS   mandatory
   DESCRIPTION "Voltage maximum level (1/100V)"
   ::= { voltages 8 }

voltageCurrentLoad OBJECT-TYPE
   SYNTAX   Gauge
   ACCESS   read-only
   STATUS   mandatory
   DESCRIPTION "Current output load on this voltage line.
                in percent of the maximum load (0xffffffff = unknown); Not supported."
   ::= { voltages 9 }


-- ----------------------------------------------------------------------------
-- TABLE: cpuTable
--
--	cpuTable :	.1.3.6.1.4.1.211.1.31.1.1.1.6.4
--
--Implementation of this table is mandatory
-- ----------------------------------------------------------------------------
cpuTable OBJECT-TYPE
   SYNTAX   SEQUENCE OF Cpus
   ACCESS   not-accessible
   STATUS   mandatory
   DESCRIPTION "CPU description table"
   ::= { hardware 4 }

cpus OBJECT-TYPE
   SYNTAX   Cpus
   ACCESS   not-accessible
   STATUS   mandatory
   DESCRIPTION " "
   INDEX   { cpuUnitId,
	     cpuNr }
   ::= { cpuTable 1 }

Cpus ::=
   SEQUENCE {
      cpuUnitId
         INTEGER,
      cpuNr
         INTEGER,
      cpuDesignation
         DisplayString,
      cpuStatus
         INTEGER,
      cpuModelName
         DisplayString,
      cpuManufacturer
         DisplayString,
      cpuStep
         DisplayString,
      cpuCurrentSpeed
         INTEGER,
      cpuNumberLogicals
         INTEGER,
      cpuCacheL1Size
         INTEGER,
      cpuCacheL2Size
         INTEGER,
      cpuCacheL3Size
         INTEGER,
      cpuNumberCores
         INTEGER,
      cpuFamily
         INTEGER,
      cpuEnabledCores
         INTEGER
   }

cpuUnitId OBJECT-TYPE
   SYNTAX   INTEGER
   ACCESS   read-only
   STATUS   mandatory
   DESCRIPTION "Unit identifier (index: 1..n)"
   ::= { cpus 1 }

cpuNr OBJECT-TYPE
   SYNTAX   INTEGER
   ACCESS   read-only
   STATUS   mandatory
   DESCRIPTION "CPU (socket) number (index: 0..n)"
   ::= { cpus 2 }

cpuDesignation OBJECT-TYPE
   SYNTAX   DisplayString
   ACCESS   read-only
   STATUS   mandatory
   DESCRIPTION "CPU designation (e.g. SB#0-CPU#A0)"
   ::= { cpus 3 }

cpuStatus OBJECT-TYPE
   SYNTAX   INTEGER{
      unknown(1),
      not-present(2),
      ok(3),
      disabled(4),
      error(5),
      failed(6),
      missing-termination(7),
      prefailed-warning(8)
   }
   ACCESS   read-only
   STATUS   mandatory
   DESCRIPTION "CPU status
                Status mapping.
                 SEL level        MIB Value
                Warning          disabled(4)
                Warning          prefailed-warning(8)
                Error              failed(6)"
   ::= { cpus 4 }

cpuModelName OBJECT-TYPE
   SYNTAX   DisplayString
   ACCESS   read-only
   STATUS   mandatory
   DESCRIPTION "CPU model name (e.g. Itanium2 Processor)"
   ::= { cpus 5 }

cpuManufacturer OBJECT-TYPE
   SYNTAX   DisplayString
   ACCESS   read-only
   STATUS   mandatory
   DESCRIPTION "CPU manufacturer name (e.g. Intel); Not supported."
   ::= { cpus 6 }

cpuStep OBJECT-TYPE
   SYNTAX   DisplayString
   ACCESS   read-only
   STATUS   mandatory
   DESCRIPTION "CPU step / revision"
   ::= { cpus 7 }

cpuCurrentSpeed OBJECT-TYPE
   SYNTAX   INTEGER
   ACCESS   read-only
   STATUS   mandatory
   DESCRIPTION "CPU speed (frequency in MHz)"
   ::= { cpus 8 }

cpuNumberLogicals OBJECT-TYPE
   SYNTAX   INTEGER
   ACCESS   read-only
   STATUS   mandatory
   DESCRIPTION "Number of (physically available) logical CPUs within one physical CPU (for hyper-threading and multi-core CPUs).
                This is the sum of all cores and all logical CPUs of a hyper-threading CPU; Not supported."
   ::= { cpus 9 }

cpuCacheL1Size OBJECT-TYPE
   SYNTAX   INTEGER
   ACCESS   read-only
   STATUS   mandatory
   DESCRIPTION "Size of first level cache (in kBytes; -1 if unknown); Not supported."
   ::= { cpus 10 }

cpuCacheL2Size OBJECT-TYPE
   SYNTAX   INTEGER
   ACCESS   read-only
   STATUS   mandatory
   DESCRIPTION "Size of second level cache (in kBytes; -1 if unknown); Not supported."
   ::= { cpus 11 }

cpuCacheL3Size OBJECT-TYPE
   SYNTAX   INTEGER
   ACCESS   read-only
   STATUS   mandatory
   DESCRIPTION "Size of third level cache (in kBytes; -1 if unknown)"
   ::= { cpus 12 }

cpuNumberCores OBJECT-TYPE
   SYNTAX   INTEGER
   ACCESS   read-only
   STATUS   mandatory
   DESCRIPTION "Number of (physically available) cores within one physical CPU (for multi-core CPUs; platform dependent)"
   ::= { cpus 13 }

cpuFamily OBJECT-TYPE
   SYNTAX   INTEGER
   ACCESS   read-only
   STATUS   mandatory
   DESCRIPTION "CPU family code. This enumerated value is specified by the DMTF SMBIOS specification 
                (processor information; type 4); Not supported."
   ::= { cpus 14 }

cpuEnabledCores OBJECT-TYPE
   SYNTAX   INTEGER
   ACCESS   read-only
   STATUS   mandatory
   DESCRIPTION "Number of effectively enabled cores within one physical CPU (for multi-core CPUs; 0 if unknown)"
   ::= { cpus 15 }


-- ----------------------------------------------------------------------------
-- TABLE: memoryModuleTable
--
--	memoryModuleTable :	.1.3.6.1.4.1.211.1.31.1.1.1.6.5
--
--Implementation of this table is mandatory
-- ----------------------------------------------------------------------------
memoryModuleTable OBJECT-TYPE
   SYNTAX   SEQUENCE OF MemoryModules
   ACCESS   not-accessible
   STATUS   mandatory
   DESCRIPTION "Main memory module table"
   ::= { hardware 5 }

memoryModules OBJECT-TYPE
   SYNTAX   MemoryModules
   ACCESS   not-accessible
   STATUS   mandatory
   DESCRIPTION " "
   INDEX   { memUnitId,
	     memModuleNr }
   ::= { memoryModuleTable 1 }

MemoryModules ::=
   SEQUENCE {
      memUnitId
         INTEGER,
      memModuleNr
         INTEGER,
      memModuleDesignation
         DisplayString,
      memModuleStatus
         INTEGER,
      memModuleBank
         INTEGER,
      memModuleCapacity
         INTEGER,
      memModuleStartAddress
         INTEGER,
      memModuleForm
         DisplayString,
      memModuleType
         DisplayString,
      memModuleCorrErrors
         Counter,
      memModuleUncorrErrors
         Counter,
      memModuleApproved
         INTEGER,
      memModuleConfiguration
         INTEGER,
      memModuleFrequency
         INTEGER,
      memModuleMaxFrequency
         INTEGER,
      memModuleVoltInterface
         DisplayString
   }

memUnitId OBJECT-TYPE
   SYNTAX   INTEGER
   ACCESS   read-only
   STATUS   mandatory
   DESCRIPTION "Unit identifier (index: 1..n)"
   ::= { memoryModules 1 }

memModuleNr OBJECT-TYPE
   SYNTAX   INTEGER
   ACCESS   read-only
   STATUS   mandatory
   DESCRIPTION "Memory module (socket) number (index: 0..n)"
   ::= { memoryModules 2 }

memModuleDesignation OBJECT-TYPE
   SYNTAX   DisplayString
   ACCESS   read-only
   STATUS   mandatory
   DESCRIPTION "Memory module designation (e.g. SB#0-DIMM#0A0)"
   ::= { memoryModules 3 }

memModuleStatus OBJECT-TYPE
   SYNTAX   INTEGER{
      unknown(1),
      not-present(2),
      ok(3),
      failed-disabled(4),
      error(5),
      warning(7),
      hot-spare(8),
      configuration-error(9)
   }
   ACCESS   read-only
   STATUS   mandatory
   DESCRIPTION "Memory module status
                Status mapping.
                 SEL level        MIB Value
                Warning          failed-disabled(4)
                Warning          warning(7)
                Error              error(5)
                Error              configuration-error(9)"
   ::= { memoryModules 4 }

memModuleBank OBJECT-TYPE
   SYNTAX   INTEGER
   ACCESS   read-only
   STATUS   mandatory
   DESCRIPTION "Memory module bank number (-1 if unknown); Not supported."
   ::= { memoryModules 5 }

memModuleCapacity OBJECT-TYPE
   SYNTAX   INTEGER
   ACCESS   read-only
   STATUS   mandatory
   DESCRIPTION "Memory module size (capacity in MBytes; -1 if unknown)"
   ::= { memoryModules 6 }

memModuleStartAddress OBJECT-TYPE
   SYNTAX   INTEGER
   ACCESS   read-only
   STATUS   mandatory
   DESCRIPTION "Memory module start address (in MBytes; -1 if unknown); Not supported."
   ::= { memoryModules 7 }

memModuleForm OBJECT-TYPE
   SYNTAX   DisplayString
   ACCESS   read-only
   STATUS   mandatory
   DESCRIPTION "Memory module form (SIMM  DIMM  ...); Not supported."
   ::= { memoryModules 8 }

memModuleType OBJECT-TYPE
   SYNTAX   DisplayString
   ACCESS   read-only
   STATUS   mandatory
   DESCRIPTION "Memory module type (SDRAM  DDRAM  DDR2  DDR3 ...); Not supported."
   ::= { memoryModules 9 }

memModuleCorrErrors OBJECT-TYPE
   SYNTAX   Counter
   ACCESS   read-only
   STATUS   mandatory
   DESCRIPTION "Number of memory module correctable errors (-1 if unknown); Not supported."
   ::= { memoryModules 10 }

memModuleUncorrErrors OBJECT-TYPE
   SYNTAX   Counter
   ACCESS   read-only
   STATUS   mandatory
   DESCRIPTION "Number of memory module uncorrectable errors (-1 if unknown); Not supported."
   ::= { memoryModules 11 }

memModuleApproved OBJECT-TYPE
   SYNTAX   INTEGER{
      unknown(1),
      no(2),
      yes(3)
   }
   ACCESS   read-only
   STATUS   mandatory
   DESCRIPTION "Memory module approved for this machine; Not supported."
   ::= { memoryModules 12 }

memModuleConfiguration OBJECT-TYPE
   SYNTAX   INTEGER{
      unknown(1),
      normal(2),
      disabled(3),
      hotSpare(4),
      mirror(5),
      raid(6),
      notUsable(7)
   }
   ACCESS   read-only
   STATUS   mandatory
   DESCRIPTION "Memory module configuration; Not supported.
                  unknown(1):     Module configuration could not be evaluated
                  normal(2):      Module is in normal non-redundant configuration or slot is empty
                  disabled(3):    Module is disabled (manually through BIOS setup)
                  hotSpare(4):    Module is a hot-spare (standby) module; which will be used as a run-time-replacement for failed modules
                  mirror(5):      Module is part of a mirror configuration
                  raid(6):        Module is part of a RAID configuration
                  notUsable(7):   Module is not usable in the actual configuration because of architectural restrictions
                This object replaces the previous redundancy status values hot-spare and mirror in sc2memModuleStatus."
   ::= { memoryModules 13 }

memModuleFrequency OBJECT-TYPE
   SYNTAX   INTEGER
   ACCESS   read-only
   STATUS   mandatory
   DESCRIPTION "Memory module actual front side bus frequency (in MHz; -1 if unknown). 
                This value is based on the BIOS settings; Not supported."
   ::= { memoryModules 14 }

memModuleMaxFrequency OBJECT-TYPE
   SYNTAX   INTEGER
   ACCESS   read-only
   STATUS   mandatory
   DESCRIPTION "Memory module maximum front side bus frequency (in MHz; -1 if unknown). This value is based on 
                memory module SPD data; Not supported."
   ::= { memoryModules 15 }

memModuleVoltInterface OBJECT-TYPE
   SYNTAX   DisplayString
   ACCESS   read-only
   STATUS   mandatory
   DESCRIPTION "Memory module interface voltage interface description; Not supported."
   ::= { memoryModules 16 }

cpuMultithreadEnable OBJECT-TYPE
   SYNTAX   INTEGER{
      unknown(1),
      disabled(2),
      enabled(3)
   }
   ACCESS   read-only
   STATUS   mandatory
   DESCRIPTION "Multithreading of CPU enabled; Not supported."
   ::= { hardware 6 }


-- ----------------------------------------------------------------------------
-- TABLE: componentPowerConsumptionTable
--
--	componentPowerConsumptionTable :	.1.3.6.1.4.1.211.1.31.1.1.1.6.7
--
--Implementation of this table is mandatory
-- ----------------------------------------------------------------------------
componentPowerConsumptionTable OBJECT-TYPE
   SYNTAX   SEQUENCE OF ComponentPowerConsumption
   ACCESS   not-accessible
   STATUS   mandatory
   DESCRIPTION "Table of component power consumption data; Not supported."
   ::= { hardware 7 }

componentPowerConsumption OBJECT-TYPE
   SYNTAX   ComponentPowerConsumption
   ACCESS   not-accessible
   STATUS   mandatory
   DESCRIPTION " "
   INDEX   { cpcUnitId,
	     cpcComponentClass,
	     cpcComponentIndex }
   ::= { componentPowerConsumptionTable 1 }

ComponentPowerConsumption ::=
   SEQUENCE {
      cpcUnitId
         INTEGER,
      cpcComponentClass
         INTEGER,
      cpcComponentIndex
         INTEGER,
      cpcDesignation
         DisplayString,
      cpcCurrentValue
         INTEGER
   }

cpcUnitId OBJECT-TYPE
   SYNTAX   INTEGER
   ACCESS   read-only
   STATUS   mandatory
   DESCRIPTION "Unit identifier (index; 1..n); Not supported."
   ::= { componentPowerConsumption 1 }

cpcComponentClass OBJECT-TYPE
   SYNTAX   INTEGER{
      processor(3),
      disk(4),
      memory-unit(8),
      processor-module(9),
      chassis(23),
      sub-chassis(24),
      disk-bay(26),
      cooling-device(29),
      cooling-unit(30),
      memory-device(32)
   }
   ACCESS   read-write
   STATUS   mandatory
   DESCRIPTION "Component class enumeration (based on IPMI v1.0 entity ID); Not supported."
   ::= { componentPowerConsumption 2 }

cpcComponentIndex OBJECT-TYPE
   SYNTAX   INTEGER
   ACCESS   read-only
   STATUS   mandatory
   DESCRIPTION "Component index within class (1..n); Not supported."
   ::= { componentPowerConsumption 3 }

cpcDesignation OBJECT-TYPE
   SYNTAX   DisplayString
   ACCESS   read-only
   STATUS   mandatory
   DESCRIPTION "Component designation; Not supported."
   ::= { componentPowerConsumption 4 }

cpcCurrentValue OBJECT-TYPE
   SYNTAX   INTEGER
   ACCESS   read-only
   STATUS   mandatory
   DESCRIPTION "Current component power consumption in Watts; Not supported."
   ::= { componentPowerConsumption 5 }


-- ----------------------------------------------------------------------------
-- TABLE: trustedPlatformModuleTable
--
--	trustedPlatformModuleTable :	.1.3.6.1.4.1.211.1.31.1.1.1.6.8
--
--Implementation of this table is mandatory
-- ----------------------------------------------------------------------------
trustedPlatformModuleTable OBJECT-TYPE
   SYNTAX   SEQUENCE OF TrustedPlatformModule
   ACCESS   not-accessible
   STATUS   mandatory
   DESCRIPTION "Trusted Platform Module (TPM) status information (see corresponding TPM specification for detailed description of these states)"
   ::= { hardware 8 }

trustedPlatformModule OBJECT-TYPE
   SYNTAX   TrustedPlatformModule
   ACCESS   not-accessible
   STATUS   mandatory
   DESCRIPTION " "
   INDEX   { tpmUnitId }
   ::= { trustedPlatformModuleTable 1 }

TrustedPlatformModule ::=
   SEQUENCE {
      tpmUnitId
         INTEGER,
      tpmHardwareAvailable
         TrueFalseUnknown,
      tpmBiosEnabled
         TrueFalseUnknown,
      tpmEnabled
         TrueFalseUnknown,
      tpmActivated
         TrueFalseUnknown,
      tpmOwnership
         TrueFalseUnknown
   }

tpmUnitId OBJECT-TYPE
   SYNTAX   INTEGER
   ACCESS   read-only
   STATUS   mandatory
   DESCRIPTION "Unit identifier (index: 1..n)"
   ::= { trustedPlatformModuleTable 1 }

tpmHardwareAvailable OBJECT-TYPE
   SYNTAX   TrueFalseUnknown
   ACCESS   read-only
   STATUS   mandatory
   DESCRIPTION "TPM hardware is available ('unknown' if hardware availability cannot be detected; no interface found)"
   ::= { trustedPlatformModuleTable 2 }

tpmBiosEnabled OBJECT-TYPE
   SYNTAX   TrueFalseUnknown
   ACCESS   read-only
   STATUS   mandatory
   DESCRIPTION "TPM hardware is enabled by BIOS ('unknown' if hardware is not available; a reboot is required to change this value)"
   ::= { trustedPlatformModuleTable 3 }

tpmEnabled OBJECT-TYPE
   SYNTAX   TrueFalseUnknown
   ACCESS   read-only
   STATUS   mandatory
   DESCRIPTION "TPM is enabled (by software; cannot take ownership if disabled; 'unknown' if hardware is not available or disabled)"
   ::= { trustedPlatformModuleTable 4 }

tpmActivated OBJECT-TYPE
   SYNTAX   TrueFalseUnknown
   ACCESS   read-only
   STATUS   mandatory
   DESCRIPTION "TPM is activated (by software; 'unknown' if hardware is not available or disabled)"
   ::= { trustedPlatformModuleTable 5 }

tpmOwnership OBJECT-TYPE
   SYNTAX   TrueFalseUnknown
   ACCESS   read-only
   STATUS   mandatory
   DESCRIPTION "TPM ownership is established (valid endorsement key is existing; 'unknown' if hardware is not available or disabled)"
   ::= { trustedPlatformModuleTable 6 }


--recovery-MIB groups


-- ----------------------------------------------------------------------------
-- TABLE: messageLogTable
--
--	messageLogTable :	.1.3.6.1.4.1.211.1.31.1.1.1.7.1
--
--Implementation of this table is mandatory
-- ----------------------------------------------------------------------------
messageLogTable OBJECT-TYPE
   SYNTAX   SEQUENCE OF MessageLogs
   ACCESS   not-accessible
   STATUS   mandatory
   DESCRIPTION "Error and event message handling; Not supported."
   ::= { recovery 1 }

messageLogs OBJECT-TYPE
   SYNTAX   MessageLogs
   ACCESS   not-accessible
   STATUS   mandatory
   DESCRIPTION " "
   INDEX   { msgUnitId,
	     msgLogEntryNr }
   ::= { messageLogTable 1 }

MessageLogs ::=
   SEQUENCE {
      msgUnitId
         INTEGER,
      msgLogEntryNr
         INTEGER,
      msgLogEntryData
         OCTET STRING
   }

msgUnitId OBJECT-TYPE
   SYNTAX   INTEGER
   ACCESS   read-only
   STATUS   mandatory
   DESCRIPTION "Unit identifier (index: 1..n); Not supported.."
   ::= { messageLogs 1 }

msgLogEntryNr OBJECT-TYPE
   SYNTAX   INTEGER
   ACCESS   read-only
   STATUS   mandatory
   DESCRIPTION "Message log entry number (index: 0..n); Not supported.."
   ::= { messageLogs 2 }

msgLogEntryData OBJECT-TYPE
   SYNTAX   OCTET STRING
   ACCESS   read-only
   STATUS   mandatory
   DESCRIPTION "Message log entry data (binary; one message per table entry); Not supported.."
   ::= { messageLogs 3 }


-- ----------------------------------------------------------------------------
-- TABLE: watchdogTable
--
--	watchdogTable :	.1.3.6.1.4.1.211.1.31.1.1.1.7.2
--
--Implementation of this table is mandatory
-- ----------------------------------------------------------------------------
watchdogTable OBJECT-TYPE
   SYNTAX   SEQUENCE OF Watchdogs
   ACCESS   not-accessible
   STATUS   mandatory
   DESCRIPTION "Watchdogs"
   ::= { recovery 2 }

watchdogs OBJECT-TYPE
   SYNTAX   Watchdogs
   ACCESS   not-accessible
   STATUS   mandatory
   DESCRIPTION " "
   INDEX   { wdUnitId,
	     watchdogType }
   ::= { watchdogTable 1 }

Watchdogs ::=
   SEQUENCE {
      wdUnitId
         INTEGER,
      watchdogType
         INTEGER,
      watchdogStatus
         INTEGER,
      watchdogEnable
         INTEGER,
      watchdogTime
         INTEGER,
      watchdogAction
         INTEGER
   }

wdUnitId OBJECT-TYPE
   SYNTAX   INTEGER
   ACCESS   read-only
   STATUS   mandatory
   DESCRIPTION "Unit identifier (index: 1..n)"
   ::= { watchdogs 1 }

watchdogType OBJECT-TYPE
   SYNTAX   INTEGER{
      other(1),
      hardware(2),
      software(3),
      bios(4),
      boot(5),
      management-controller(6),
      remote-management-controller(7),
      management-soft(8)
   }
   ACCESS   read-only
   STATUS   mandatory
   DESCRIPTION "Watchdog type"
   ::= { watchdogs 2 }

watchdogStatus OBJECT-TYPE
   SYNTAX   INTEGER{
      unknown(1),
      disable(2),
      enable(3),
      not-available(4)
   }
   ACCESS   read-only
   STATUS   mandatory
   DESCRIPTION "Watchdog status"
   ::= { watchdogs 3 }

watchdogEnable OBJECT-TYPE
   SYNTAX   INTEGER{
      unknown(1),
      disable(2),
      enable(3)
   }
   ACCESS   read-only
   STATUS   mandatory
   DESCRIPTION "Enable/disable watchdog"
   ::= { watchdogs 4 }

watchdogTime OBJECT-TYPE
   SYNTAX   INTEGER
   ACCESS   read-only
   STATUS   mandatory
   DESCRIPTION "Watchdog timeout period in seconds"
   ::= { watchdogs 5 }

watchdogAction OBJECT-TYPE
   SYNTAX   INTEGER{
      unknown(1),
      continue(2),
      reboot(3),
      nmi(4),
      power-cycle(5),
      power-down(6),
      hardware-reset(7)
   }
   ACCESS   read-only
   STATUS   mandatory
   DESCRIPTION "Watchdog timeout action"
   ::= { watchdogs 6 }


-- ----------------------------------------------------------------------------
-- TABLE: recoverySettingTable
--
--	recoverySettingTable :	.1.3.6.1.4.1.211.1.31.1.1.1.7.3
--
--Implementation of this table is mandatory
-- ----------------------------------------------------------------------------
recoverySettingTable OBJECT-TYPE
   SYNTAX   SEQUENCE OF RecoverySettings
   ACCESS   not-accessible
   STATUS   mandatory
   DESCRIPTION "ASR&R (Automatic server recovery and restart) settings; Not supported."
   ::= { recovery 3 }

recoverySettings OBJECT-TYPE
   SYNTAX   RecoverySettings
   ACCESS   not-accessible
   STATUS   mandatory
   DESCRIPTION " "
   INDEX   { asrUnitId }
   ::= { recoverySettingTable 1 }

RecoverySettings ::=
   SEQUENCE {
      asrUnitId
         INTEGER,
      asrNrRebootRetries
         INTEGER,
      asrDefaultRebootRetries
         INTEGER,
      asrNextBootSource
         INTEGER,
      asrRebootFailAction
         INTEGER,
      asrRestartDelay
         INTEGER,
      asrPostErrorHalt
         INTEGER
   }

asrUnitId OBJECT-TYPE
   SYNTAX   INTEGER
   ACCESS   read-only
   STATUS   mandatory
   DESCRIPTION "Unit identifier (index: 1..n); Not supported."
   ::= { recoverySettings 1 }

asrNrRebootRetries OBJECT-TYPE
   SYNTAX   INTEGER
   ACCESS   read-write
   STATUS   mandatory
   DESCRIPTION "Current number of retries to reboot/restart the server when a failure shutdown
                (and power-off) had occurred. After this number of retries the action
                defined in 'sc2asrRebootFailAction' will be executed
                (-1 = unknown; no retries).
                The value unknown(1) cannot be set; a SET will deliver 'badValue'; Not supported."
   ::= { recoverySettings 2 }

asrDefaultRebootRetries OBJECT-TYPE
   SYNTAX   INTEGER
   ACCESS   read-write
   STATUS   mandatory
   DESCRIPTION "Default number of retries for server failure reboot. The previous
                object sc2asrNrRebootRetries will be set to this value after the server
                is working properly for a certain amount of time; Not supported."
   ::= { recoverySettings 3 }

asrNextBootSource OBJECT-TYPE
   SYNTAX   INTEGER{
      unknown(1),
      operating-system(2),
      reserved(3),
      diag-system(4),
      remote-disk(5)
   }
   ACCESS   read-write
   STATUS   mandatory
   DESCRIPTION "Source medium to boot from (next time):
                   operating-system: boot from floppy or hard disk
                   diag-system:     boot from alternate diagnostic system (only for SCSI systems;
                                           load diagnostic system from alternate IDE disk).
                   remote-disk:      boot from remote network disk
                The value unknown(1) cannot be set; a SET will deliver 'badValue'; Not supported."
   ::= { recoverySettings 4 }

asrRebootFailAction OBJECT-TYPE
   SYNTAX   INTEGER{
      unknown(1),
      switch-off(2),
      boot-diag-system(3),
      no-diag-system(4)
   }
   ACCESS   read-write
   STATUS   mandatory
   DESCRIPTION "Specifies the action after a specified number of failed reboot retries
                (the object 'sc2asrNrRebootRetries' has reached zero).The value
                no-diag-system(4) means that a diagnostic system is not available; no other value can be set.
                The values unknown(1) and reserved(3) cannot be set; a SET will deliver 'badValue'; Not supported."
   ::= { recoverySettings 5 }

asrRestartDelay OBJECT-TYPE
   SYNTAX   INTEGER
   ACCESS   read-write
   STATUS   mandatory
   DESCRIPTION "Delay (in minutes) when the system should be automatically switched on
                again (by real-time clock) after an error power-off.
                Setting this value to zero means immediate restart (power-cycle only).
                You can disable automatic restart by setting the 'sc2asrRebootFailAction'
                to 'switch-off' and the 'sc2asrDefaultRebootRetries' to zero; Not supported."
   ::= { recoverySettings 6 }

asrPostErrorHalt OBJECT-TYPE
   SYNTAX   INTEGER{
      unknown(1),
      halt-on-any-error(2),
      no-halt-on-any-error(3),
      other(4)
   }
   ACCESS   read-write
   STATUS   mandatory
   DESCRIPTION "Describes what to do when a POST error has occurred (halt on any error; no halt on any error...).
                The values unknown(1) and other(9) cannot be set; a SET will deliver 'badValue'; Not supported."
   ::= { recoverySettings 7 }


-- ----------------------------------------------------------------------------
-- TABLE: messageTextLogTable
--
--	messageTextLogTable :	.1.3.6.1.4.1.211.1.31.1.1.1.7.4
--
--Implementation of this table is mandatory
-- ----------------------------------------------------------------------------
messageTextLogTable OBJECT-TYPE
   SYNTAX   SEQUENCE OF MessageTextLogs
   ACCESS   not-accessible
   STATUS   mandatory
   DESCRIPTION "Error and event message handling; reported as text strings; Not supported."
   ::= { recovery 4 }

messageTextLogs OBJECT-TYPE
   SYNTAX   MessageTextLogs
   ACCESS   not-accessible
   STATUS   mandatory
   DESCRIPTION " "
   INDEX   { msgTextLogUnitId,
	     msgTextLogLanguage,
	     msgTextLogSeqNr }
   ::= { messageTextLogTable 1 }

MessageTextLogs ::=
   SEQUENCE {
      msgTextLogUnitId
         INTEGER,
      msgTextLogLanguage
         INTEGER,
      msgTextLogSeqNr
         INTEGER,
      msgTextLogTimestamp
         INTEGER,
      msgTextLogMessage
         DisplayString,
      msgTextLogErrorCode
         INTEGER,
      msgTextLogSeverity
         INTEGER,
      msgTextLogCSSComponent
         TrueFalse
   }

msgTextLogUnitId OBJECT-TYPE
   SYNTAX   INTEGER
   ACCESS   read-only
   STATUS   mandatory
   DESCRIPTION "Unit identifier (index: 1..n); Not supported."
   ::= { messageTextLogs 1 }

msgTextLogLanguage OBJECT-TYPE
   SYNTAX   INTEGER
   ACCESS   read-only
   STATUS   mandatory
   DESCRIPTION "Message log entry language (index; Windows language code); Not supported.
                e.g. 1031; 1033 for German; English (default; always available)"
   ::= { messageTextLogs 2 }

msgTextLogSeqNr OBJECT-TYPE
   SYNTAX   INTEGER
   ACCESS   read-only
   STATUS   mandatory
   DESCRIPTION "Message log entry sequence number (index; 0..n); Not supported."
   ::= { messageTextLogs 3 }

msgTextLogTimestamp OBJECT-TYPE
   SYNTAX   INTEGER
   ACCESS   read-only
   STATUS   mandatory
   DESCRIPTION "Message log entry time stamp (time_t = seconds since 1/1/1970; 0:00 AM); Not supported."
   ::= { messageTextLogs 4 }

msgTextLogMessage OBJECT-TYPE
   SYNTAX   DisplayString
   ACCESS   read-only
   STATUS   mandatory
   DESCRIPTION "Message log entry message string (multi-byte string; multi-language; not every language may be implemented); Not supported."
   ::= { messageTextLogs 5 }

msgTextLogErrorCode OBJECT-TYPE
   SYNTAX   INTEGER
   ACCESS   read-only
   STATUS   mandatory
   DESCRIPTION "Message log entry error code; Not supported."
   ::= { messageTextLogs 6 }

msgTextLogSeverity OBJECT-TYPE
   SYNTAX   INTEGER{
      informational(1),
      minor(2),
      major(3),
      critical(4)
   }
   ACCESS   read-only
   STATUS   mandatory
   DESCRIPTION "Message log entry severity; Not supported."
   ::= { messageTextLogs 7 }

msgTextLogCSSComponent OBJECT-TYPE
   SYNTAX   TrueFalse
   ACCESS   read-only
   STATUS   mandatory
   DESCRIPTION "Component which caused the log message may be replaced by the customer (CSS=Customer Self Service); Not supported."
   ::= { messageTextLogs 8 }


-- ----------------------------------------------------------------------------
-- TABLE: messageLogActionHintTable
--
--	messageLogActionHintTable :	.1.3.6.1.4.1.211.1.31.1.1.1.7.5
--
--Implementation of this table is mandatory
-- ----------------------------------------------------------------------------
messageLogActionHintTable OBJECT-TYPE
   SYNTAX   SEQUENCE OF MessageLogActionHints
   ACCESS   not-accessible
   STATUS   mandatory
   DESCRIPTION "Action text strings for error and event messages; Not supported."
   ::= { recovery 5 }

messageLogActionHints OBJECT-TYPE
   SYNTAX   MessageLogActionHints
   ACCESS   not-accessible
   STATUS   mandatory
   DESCRIPTION " "
   INDEX   { mlaLanguage,
	     mlaErrorCode,
	     mlaType,
	     mlaIndex }
   ::= { messageLogActionHintTable 1 }

MessageLogActionHints ::=
   SEQUENCE {
      mlaLanguage
         INTEGER,
      mlaErrorCode
         INTEGER,
      mlaType
         INTEGER,
      mlaIndex
         INTEGER,
      mlaMessage
         DisplayString
   }

mlaLanguage OBJECT-TYPE
   SYNTAX   INTEGER
   ACCESS   read-only
   STATUS   mandatory
   DESCRIPTION "Action text language (index; Windows language code) e.g. 1031; 1033 for German; English; Not supported."
   ::= { messageLogActionHints 1 }

mlaErrorCode OBJECT-TYPE
   SYNTAX   INTEGER
   ACCESS   read-only
   STATUS   mandatory
   DESCRIPTION "Action text error code (index); Not supported."
   ::= { messageLogActionHints 2 }

mlaType OBJECT-TYPE
   SYNTAX   INTEGER{
      summary(1),
      cause(2),
      resolution(3)
   }
   ACCESS   read-only
   STATUS   mandatory
   DESCRIPTION "Message log entry severity; Not supported."
   ::= { messageLogActionHints 3 }

mlaIndex OBJECT-TYPE
   SYNTAX   INTEGER
   ACCESS   read-only
   STATUS   mandatory
   DESCRIPTION "Action text entry string index (index; 1..n); Not supported."
   ::= { messageLogActionHints 4 }

mlaMessage OBJECT-TYPE
   SYNTAX   DisplayString
   ACCESS   read-only
   STATUS   mandatory
   DESCRIPTION "Action message string; Not supported."
   ::= { messageLogActionHints 5 }


--status-MIB groups

agentStatus OBJECT-TYPE
   SYNTAX   INTEGER{
      ok(1),
      degraded(2),
      error(3),
      failed(4),
      unknown(5)
   }
   ACCESS   read-only
   STATUS   mandatory
   DESCRIPTION "Overall status of all monitored components in this agent
                ok(1):       all subsystems and components working properly; no failure
                degraded(2): at least one component has a problem; system may still work properly
                error(3):    severe problem; system will not work properly
                failed(4):   one or more managed components have failed
                unknown(5):  none of the subsystems had a valid status (e.g. during initialization)"
   ::= { status 1 }


-- ----------------------------------------------------------------------------
-- TABLE: statusComponentTable
--
--	statusComponentTable :	.1.3.6.1.4.1.211.1.31.1.1.1.8.2
--
--Implementation of this table is mandatory
-- ----------------------------------------------------------------------------
statusComponentTable OBJECT-TYPE
   SYNTAX   SEQUENCE OF StatusComponents
   ACCESS   not-accessible
   STATUS   mandatory
   DESCRIPTION "Table with status values of the components in this agent. The table
                summarizes all instances of one component to one status value."
   ::= { status 2 }

statusComponents OBJECT-TYPE
   SYNTAX   StatusComponents
   ACCESS   not-accessible
   STATUS   mandatory
   DESCRIPTION " "
   INDEX   { csUnitId,
	     csType }
   ::= { statusComponentTable 1 }

StatusComponents ::=
   SEQUENCE {
      csUnitId
         INTEGER,
      csType
         INTEGER,
      componentStatusValue
         INTEGER
   }

csUnitId OBJECT-TYPE
   SYNTAX   INTEGER
   ACCESS   read-only
   STATUS   mandatory
   DESCRIPTION "Unit identifier (index: 1..n)"
   ::= { statusComponents 1 }

csType OBJECT-TYPE
   SYNTAX   INTEGER{
      system-boot(1),
      power(2),
      temperatures(3),
      fans(4),
      power-supplies(5),
      voltages(6),
      cpus(7),
      memory-modules(8),
      total(9),
      fan-redundancy(10),
      power-supply-redundancy(11)
   }
   ACCESS   read-only
   STATUS   mandatory
   DESCRIPTION "Component status type"
   ::= { statusComponents 2 }

componentStatusValue OBJECT-TYPE
   SYNTAX   INTEGER{
      ok(1),
      degraded(2),
      error(3),
      failed(4),
      unknown(5)
   }
   ACCESS   read-only
   STATUS   mandatory
   DESCRIPTION "Component status value (for description of status values see previous object)
                Status mapping.
                 SEL level        MIB Value
                Warning          degraded(2)
                Warning          failed(4)
                Error              error(5)"
   ::= { statusComponents 3 }


-- ----------------------------------------------------------------------------
-- TABLE: componentStatusSensorTable
--
--	componentStatusSensorTable :	.1.3.6.1.4.1.211.1.31.1.1.1.8.3
--
--Implementation of this table is mandatory
-- ----------------------------------------------------------------------------
componentStatusSensorTable OBJECT-TYPE
   SYNTAX   SEQUENCE OF ComponentStatusSensors
   ACCESS   not-accessible
   STATUS   mandatory
   DESCRIPTION "This table contains the component status sensor table of the BMC (baseboard management
                controller). Additionally it also holds the CSS (Customer Self Service) information; Not supported."
   ::= { status 3 }

componentStatusSensors OBJECT-TYPE
   SYNTAX   ComponentStatusSensors
   ACCESS   not-accessible
   STATUS   mandatory
   DESCRIPTION " "
   INDEX   { cssUnitId,
	     cssSensorNumber }
   ::= { componentStatusSensorTable 1 }

ComponentStatusSensors ::=
   SEQUENCE {
      cssUnitId
         INTEGER,
      cssSensorNumber
         INTEGER,
      cssSensorDesignation
         DisplayString,
      cssSensorDevice
         DisplayString,
      cssSensorDeviceInstance
         INTEGER,
      cssSensorPhysicalLed
         TrueFalse,
      cssSensorCssComponent
         TrueFalse,
      cssSensorStatus
         INTEGER,
      cssComponentServicePartId
         DisplayString
   }

cssUnitId OBJECT-TYPE
   SYNTAX   INTEGER
   ACCESS   read-only
   STATUS   mandatory
   DESCRIPTION "Unit identifier (index: 1..n); Not supported."
   ::= { componentStatusSensors 1 }

cssSensorNumber OBJECT-TYPE
   SYNTAX   INTEGER
   ACCESS   read-only
   STATUS   mandatory
   DESCRIPTION "BMC component status sensor number (index; 1..n); Not supported."
   ::= { componentStatusSensors 2 }

cssSensorDesignation OBJECT-TYPE
   SYNTAX   DisplayString
   ACCESS   read-only
   STATUS   mandatory
   DESCRIPTION "Component status sensor designation string; Not supported."
   ::= { componentStatusSensors 3 }

cssSensorDevice OBJECT-TYPE
   SYNTAX   DisplayString
   ACCESS   read-only
   STATUS   mandatory
   DESCRIPTION "Name of device (entity) the component status sensor belongs to; Not supported."
   ::= { componentStatusSensors 4 }

cssSensorDeviceInstance OBJECT-TYPE
   SYNTAX   INTEGER
   ACCESS   read-only
   STATUS   mandatory
   DESCRIPTION "Instance number of device (entity) the component status sensor belongs to; Not supported."
   ::= { componentStatusSensors 5 }

cssSensorPhysicalLed OBJECT-TYPE
   SYNTAX   TrueFalse
   ACCESS   read-only
   STATUS   mandatory
   DESCRIPTION "If set; component has a physical status LED showing the sensor status; Not supported."
   ::= { componentStatusSensors 6 }

cssSensorCssComponent OBJECT-TYPE
   SYNTAX   TrueFalse
   ACCESS   read-only
   STATUS   mandatory
   DESCRIPTION "If set; component may be replaced by the customer (CSS component); Not supported."
   ::= { componentStatusSensors 7 }

cssSensorStatus OBJECT-TYPE
   SYNTAX   INTEGER{
      unknown(1),
      ok(2),
      identify(3),
      prefailure-warning(4),
      failure(5),
      not-present(6)
   }
   ACCESS   read-only
   STATUS   mandatory
   DESCRIPTION "Status returned by the component status sensor; Not supported."
   ::= { componentStatusSensors 8 }

cssComponentServicePartId OBJECT-TYPE
   SYNTAX   DisplayString
   ACCESS   read-only
   STATUS   mandatory
   DESCRIPTION "Spare part number of the replaceable component; used to create a link to the spare part list on the service's spare part 
                catalogue. This usually is the component's designation string; with blanks substituted by underscores; Not supported."
   ::= { componentStatusSensors 9 }

cssTableSize OBJECT-TYPE
   SYNTAX   INTEGER
   ACCESS   read-only
   STATUS   mandatory
   DESCRIPTION "Number of entries in the component status sensor table; Not supported."
   ::= { status 4 }


--maintenance-MIB groups


-- ----------------------------------------------------------------------------
-- TABLE: maintenanceObjectTable
--
--	maintenanceObjectTable :	.1.3.6.1.4.1.211.1.31.1.1.1.9.1
--
--Implementation of this table is mandatory
-- ----------------------------------------------------------------------------
maintenanceObjectTable OBJECT-TYPE
   SYNTAX   SEQUENCE OF MaintenanceObjects
   ACCESS   not-accessible
   STATUS   mandatory
   DESCRIPTION "Table containing some other maintenance objects."
   ::= { maintenance 1 }

maintenanceObjects OBJECT-TYPE
   SYNTAX   MaintenanceObjects
   ACCESS   not-accessible
   STATUS   mandatory
   DESCRIPTION " "
   INDEX   { mtUnitId }
   ::= { maintenanceObjectTable 1 }

MaintenanceObjects ::=
   SEQUENCE {
      mtUnitId
         INTEGER,
      errorCounterStartTime
         INTEGER,
      sendTestTrap
         INTEGER,
      addTrapDestination
         IpAddress,
      mtMaintenanceStatus
         INTEGER
   }

mtUnitId OBJECT-TYPE
   SYNTAX   INTEGER
   ACCESS   read-only
   STATUS   mandatory
   DESCRIPTION "Unit identifier (index: 1..n)."
   ::= { maintenanceObjects 1 }

errorCounterStartTime OBJECT-TYPE
   SYNTAX   INTEGER
   ACCESS   read-only
   STATUS   mandatory
   DESCRIPTION "Memory module error counter start time (seconds since 1/1/1970; -1 if unknown).
                This is the time when the error counters were started or reset last time; Not supported."
   ::= { maintenanceObjects 2 }

sendTestTrap OBJECT-TYPE
   SYNTAX   INTEGER
   ACCESS   read-write
   STATUS   mandatory
   DESCRIPTION "Send a test trap (test alarm) to the manager application(s) to test connection and trap
                configuration; trap cannot be disabled.
                Initiate test trap sending by writing a non-zero value.
                Reading this object just returns the value 0; Not supported."
   ::= { maintenanceObjects 3 }

addTrapDestination OBJECT-TYPE
   SYNTAX   IpAddress
   ACCESS   read-write
   STATUS   mandatory
   DESCRIPTION "Add the specified IP address (of the management station) to
                the trap destination list of this server. That client will become an alarm
                receiver for traps of this server; Not supported."
   ::= { maintenanceObjects 4 }

mtMaintenanceStatus OBJECT-TYPE
   SYNTAX   INTEGER{
      off(1),
      on(2)
   }
   ACCESS   read-only
   STATUS   mandatory
   DESCRIPTION "maitenance status"
   ::= { maintenanceObjects 5 }


-- ----------------------------------------------------------------------------
-- TABLE: firmwareVersionTable
--
--	firmwareVersionTable :	.1.3.6.1.4.1.211.1.31.1.1.1.9.2
--
--Implementation of this table is mandatory
-- ----------------------------------------------------------------------------
firmwareVersionTable OBJECT-TYPE
   SYNTAX   SEQUENCE OF FirmwareVersions
   ACCESS   not-accessible
   STATUS   mandatory
   DESCRIPTION "Controller firmware version table"
   ::= { maintenance 2 }

firmwareVersions OBJECT-TYPE
   SYNTAX   FirmwareVersions
   ACCESS   not-accessible
   STATUS   mandatory
   DESCRIPTION " "
   INDEX   { fwUnitId,
	     fwType }
   ::= { firmwareVersionTable 1 }

FirmwareVersions ::=
   SEQUENCE {
      fwUnitId
         INTEGER,
      fwType
         INTEGER,
      fwModelName
         DisplayString,
      fwVersion
         DisplayString,
      fwLocation
         INTEGER
   }

fwUnitId OBJECT-TYPE
   SYNTAX   INTEGER
   ACCESS   read-only
   STATUS   mandatory
   DESCRIPTION "Unit identifier (index: 1..n)"
   ::= { firmwareVersions 1 }

fwType OBJECT-TYPE
   SYNTAX   INTEGER{
      bios(1),
      management-controller(2),
      remote-management-controller(3),
      pal(4),
      sal(5),
      efi(6),
      baseboard-management-controller(7),
      gswb-offline0(8),
      gswb-offline1(9),
      gswb-online0(10),
      gswb-online1(11),
      total(20)
   }
   ACCESS   read-only
   STATUS   mandatory
   DESCRIPTION "Controller/firmware type"
   ::= { firmwareVersions 2 }

fwModelName OBJECT-TYPE
   SYNTAX   DisplayString
   ACCESS   read-only
   STATUS   mandatory
   DESCRIPTION "Controller/firmware model name (e.g. 'Copernicus'...)
                TOTAL' shows all firmware version in system (including BIOS; BMC; MMB)."
   ::= { firmwareVersions 3 }

fwVersion OBJECT-TYPE
   SYNTAX   DisplayString
   ACCESS   read-only
   STATUS   mandatory
   DESCRIPTION "Controller/firmware version string (e.g. '3.81.02')"
   ::= { firmwareVersions 4 }

fwLocation OBJECT-TYPE
   SYNTAX   INTEGER
   ACCESS   read-only
   STATUS   mandatory
   DESCRIPTION "BMM physical number of controller/firmware on IOU."
   ::= { firmwareVersions 5 }


--deployment-MIB groups


-- ----------------------------------------------------------------------------
-- TABLE: deployInfoTable
--
--	deployInfoTable :	.1.3.6.1.4.1.211.1.31.1.1.1.10.1
--
--Implementation of this table is mandatory
-- ----------------------------------------------------------------------------
deployInfoTable OBJECT-TYPE
   SYNTAX   SEQUENCE OF DeployInfo
   ACCESS   not-accessible
   STATUS   mandatory
   DESCRIPTION "Table with data of deployment information; Not supported."
   ::= { deployment 1 }

deployInfo OBJECT-TYPE
   SYNTAX   DeployInfo
   ACCESS   not-accessible
   STATUS   mandatory
   DESCRIPTION " "
   INDEX   { dplInfoUnitId }
   ::= { deployInfoTable 1 }

DeployInfo ::=
   SEQUENCE {
      dplInfoUnitId
         INTEGER,
      deployInfoChassisId
         DisplayString,
      deployInfoMacAddr1
         PhysAddress,
      deployInfoMacAddr2
         PhysAddress,
      deployInfoMacAddr3
         PhysAddress,
      deployInfoMacAddr4
         PhysAddress,
      deployInfoIpAddr1
         IpAddress,
      deployInfoIpAddr2
         IpAddress,
      deployInfoIpAddr3
         IpAddress,
      deployInfoIpAddr4
         IpAddress,
      deployInfoNetMask1
         IpAddress,
      deployInfoNetMask2
         IpAddress,
      deployInfoNetMask3
         IpAddress,
      deployInfoNetMask4
         IpAddress,
      deployInfoGateway1
         IpAddress,
      deployInfoGateway2
         IpAddress,
      deployInfoGateway3
         IpAddress,
      deployInfoGateway4
         IpAddress,
      deployInfoHostname
         DisplayString,
      deployInfoMasterImageReference
         DisplayString,
      deployInfoStatusOfBlade
         INTEGER,
      deployInfoLanStatusOfSlot
         INTEGER,
      deployInfoAutomaticRecovery
         INTEGER,
      deployInfoStatusOfCloning
         INTEGER,
      deployInfoBootMode
         INTEGER
   }

dplInfoUnitId OBJECT-TYPE
   SYNTAX   INTEGER
   ACCESS   read-only
   STATUS   mandatory
   DESCRIPTION "Unit identifier (index: 1..n); Not supported."
   ::= { deployInfo 1 }

deployInfoChassisId OBJECT-TYPE
   SYNTAX   DisplayString
   ACCESS   read-only
   STATUS   mandatory
   DESCRIPTION "Chassis serial number; Not supported."
   ::= { deployInfo 2 }

deployInfoMacAddr1 OBJECT-TYPE
   SYNTAX   PhysAddress
   ACCESS   read-only
   STATUS   mandatory
   DESCRIPTION "MAC address 1; Not supported."
   ::= { deployInfo 3 }

deployInfoMacAddr2 OBJECT-TYPE
   SYNTAX   PhysAddress
   ACCESS   read-only
   STATUS   mandatory
   DESCRIPTION "MAC address 2; Not supported."
   ::= { deployInfo 4 }

deployInfoMacAddr3 OBJECT-TYPE
   SYNTAX   PhysAddress
   ACCESS   read-only
   STATUS   mandatory
   DESCRIPTION "MAC address 3; Not supported."
   ::= { deployInfo 5 }

deployInfoMacAddr4 OBJECT-TYPE
   SYNTAX   PhysAddress
   ACCESS   read-only
   STATUS   mandatory
   DESCRIPTION "MAC address 4; Not supported."
   ::= { deployInfo 6 }

deployInfoIpAddr1 OBJECT-TYPE
   SYNTAX   IpAddress
   ACCESS   read-write
   STATUS   mandatory
   DESCRIPTION "IP address 1; Not supported."
   ::= { deployInfo 7 }

deployInfoIpAddr2 OBJECT-TYPE
   SYNTAX   IpAddress
   ACCESS   read-write
   STATUS   mandatory
   DESCRIPTION "IP address 2; Not supported."
   ::= { deployInfo 8 }

deployInfoIpAddr3 OBJECT-TYPE
   SYNTAX   IpAddress
   ACCESS   read-write
   STATUS   mandatory
   DESCRIPTION "IP address 3; Not supported."
   ::= { deployInfo 9 }

deployInfoIpAddr4 OBJECT-TYPE
   SYNTAX   IpAddress
   ACCESS   read-write
   STATUS   mandatory
   DESCRIPTION "IP address 4; Not supported."
   ::= { deployInfo 10 }

deployInfoNetMask1 OBJECT-TYPE
   SYNTAX   IpAddress
   ACCESS   read-write
   STATUS   mandatory
   DESCRIPTION "IP subnet mask 1; Not supported."
   ::= { deployInfo 11 }

deployInfoNetMask2 OBJECT-TYPE
   SYNTAX   IpAddress
   ACCESS   read-write
   STATUS   mandatory
   DESCRIPTION "IP subnet mask 2; Not supported."
   ::= { deployInfo 12 }

deployInfoNetMask3 OBJECT-TYPE
   SYNTAX   IpAddress
   ACCESS   read-write
   STATUS   mandatory
   DESCRIPTION "IP subnet mask 3; Not supported."
   ::= { deployInfo 13 }

deployInfoNetMask4 OBJECT-TYPE
   SYNTAX   IpAddress
   ACCESS   read-write
   STATUS   mandatory
   DESCRIPTION "IP subnet mask 4; Not supported."
   ::= { deployInfo 14 }

deployInfoGateway1 OBJECT-TYPE
   SYNTAX   IpAddress
   ACCESS   read-write
   STATUS   mandatory
   DESCRIPTION "IP gateway 1; Not supported."
   ::= { deployInfo 15 }

deployInfoGateway2 OBJECT-TYPE
   SYNTAX   IpAddress
   ACCESS   read-write
   STATUS   mandatory
   DESCRIPTION "IP gateway 2; Not supported."
   ::= { deployInfo 16 }

deployInfoGateway3 OBJECT-TYPE
   SYNTAX   IpAddress
   ACCESS   read-write
   STATUS   mandatory
   DESCRIPTION "IP gateway 3; Not supported."
   ::= { deployInfo 17 }

deployInfoGateway4 OBJECT-TYPE
   SYNTAX   IpAddress
   ACCESS   read-write
   STATUS   mandatory
   DESCRIPTION "IP gateway 4; Not supported."
   ::= { deployInfo 18 }

deployInfoHostname OBJECT-TYPE
   SYNTAX   DisplayString
   ACCESS   read-write
   STATUS   mandatory
   DESCRIPTION "Host name; Not supported."
   ::= { deployInfo 19 }

deployInfoMasterImageReference OBJECT-TYPE
   SYNTAX   DisplayString
   ACCESS   read-write
   STATUS   mandatory
   DESCRIPTION "URL in UNC notification (but in ASCII) to remote image file
                (with the extensions of *.img; *.cfg; *.txt); Not supported."
   ::= { deployInfo 20 }

deployInfoStatusOfBlade OBJECT-TYPE
   SYNTAX   INTEGER{
      unknown(1),
      power-down(2),
      standby(3),
      system-boot-failure(4),
      bios-setup(5),
      booting(6)
   }
   ACCESS   read-write
   STATUS   mandatory
   DESCRIPTION "Status of this server:
                 power-down(2):          waiting for boot
                 standby(3):             power management mode
                 system-boot-failure(4): system boot failure
                 bios-setup(5):          BIOS setup or boot phase
                 booting(6):             ACPI OS currently booting
                ; Not supported."
   ::= { deployInfo 21 }

deployInfoLanStatusOfSlot OBJECT-TYPE
   SYNTAX   INTEGER{
      unknown(1),
      false(2),
      true(3)
   }
   ACCESS   read-write
   STATUS   mandatory
   DESCRIPTION "Defines whether the IP-LAN definitions are valid or not; Not supported."
   ::= { deployInfo 22 }

deployInfoAutomaticRecovery OBJECT-TYPE
   SYNTAX   INTEGER{
      unknown(1),
      false(2),
      true(3)
   }
   ACCESS   read-write
   STATUS   mandatory
   DESCRIPTION "Defines if this server blade should be provided automatic recovery; Not supported."
   ::= { deployInfo 23 }

deployInfoStatusOfCloning OBJECT-TYPE
   SYNTAX   INTEGER{
      unknown(1),
      not-cloned(2),
      cloning(3),
      cloned(4)
   }
   ACCESS   read-write
   STATUS   mandatory
   DESCRIPTION "Status of current cloning process; Not supported."
   ::= { deployInfo 24 }

deployInfoBootMode OBJECT-TYPE
   SYNTAX   INTEGER{
      unknown(1),
      normal(2),
      pxeBiosSetup(3),
      pxeLan0(4),
      pxeLan1(5),
      pxeLan2(6),
      pxeLan3(7)
   }
   ACCESS   read-write
   STATUS   mandatory
   DESCRIPTION "Boot mode of the server for remote deployment:
                  normal(2):       boot from standard disk subsystem
                  pxeBiosSetup(3): boot from PXE according to BIOS setup settings (for OEM systems)
                  pxeLanx(y):      boot from PXE LAN interface x (0..3)
                ; Not supported."
   ::= { deployInfo 25 }


-- ----------------------------------------------------------------------------
-- TABLE: oemDeployInfoTable
--
--	oemDeployInfoTable :	.1.3.6.1.4.1.211.1.31.1.1.1.10.2
--
--Implementation of this table is mandatory
-- ----------------------------------------------------------------------------
oemDeployInfoTable OBJECT-TYPE
   SYNTAX   SEQUENCE OF OemDeployInfo
   ACCESS   not-accessible
   STATUS   mandatory
   DESCRIPTION "Table with data of server OEM information; Not supported."
   ::= { deployment 2 }

oemDeployInfo OBJECT-TYPE
   SYNTAX   OemDeployInfo
   ACCESS   not-accessible
   STATUS   mandatory
   DESCRIPTION " "
   INDEX   { odplInfoUnitId,
	     odplParamId }
   ::= { oemDeployInfoTable 1 }

OemDeployInfo ::=
   SEQUENCE {
      odplInfoUnitId
         INTEGER,
      odplParamId
         INTEGER,
      oemDeployInfoParamData
         DisplayString
   }

odplInfoUnitId OBJECT-TYPE
   SYNTAX   INTEGER
   ACCESS   read-only
   STATUS   mandatory
   DESCRIPTION "Unit identifier (index: 1..n); Not supported."
   ::= { oemDeployInfo 1 }

odplParamId OBJECT-TYPE
   SYNTAX   INTEGER
   ACCESS   read-only
   STATUS   mandatory
   DESCRIPTION "OEM parameter ID (index: 1..10); Not supported."
   ::= { oemDeployInfo 2 }

oemDeployInfoParamData OBJECT-TYPE
   SYNTAX   DisplayString
   ACCESS   read-write
   STATUS   mandatory
   DESCRIPTION "OEM parameter data; Not supported."
   ::= { oemDeployInfo 3 }


-- ----------------------------------------------------------------------------
-- TABLE: deployLanInterfaceTable
--
--	deployLanInterfaceTable :	.1.3.6.1.4.1.211.1.31.1.1.1.10.3
--
--Implementation of this table is mandatory
-- ----------------------------------------------------------------------------
deployLanInterfaceTable OBJECT-TYPE
   SYNTAX   SEQUENCE OF DeployLanInterfaces
   ACCESS   not-accessible
   STATUS   mandatory
   DESCRIPTION "Table with system LAN interfaces information:
                This table lists all real LAN interfaces in same physical order as the BIOS uses it for PXE boot.
                Only on-board interfaces are listed; no virtual interfaces."
   ::= { deployment 3 }

deployLanInterfaces OBJECT-TYPE
   SYNTAX   DeployLanInterfaces
   ACCESS   not-accessible
   STATUS   mandatory
   DESCRIPTION " "
   INDEX   { dplLanUnitId,
	     dplLanInterfaceNr }
   ::= { deployLanInterfaceTable 1 }

DeployLanInterfaces ::=
   SEQUENCE {
      dplLanUnitId
         INTEGER,
      dplLanInterfaceNr
         INTEGER,
      dplLanMacAddress
         PhysAddress
   }

dplLanUnitId OBJECT-TYPE
   SYNTAX   INTEGER
   ACCESS   read-only
   STATUS   mandatory
   DESCRIPTION "Unit identifier (index; 1..n)"
   ::= { deployLanInterfaces 1 }

dplLanInterfaceNr OBJECT-TYPE
   SYNTAX   INTEGER
   ACCESS   read-only
   STATUS   mandatory
   DESCRIPTION "LAN interface number (index; 0..n)"
   ::= { deployLanInterfaces 2 }

dplLanMacAddress OBJECT-TYPE
   SYNTAX   PhysAddress
   ACCESS   read-only
   STATUS   mandatory
   DESCRIPTION "LAN interface hardware (MAC) address; ff:ff:ff:ff:ff:ff if value not available"
   ::= { deployLanInterfaces 3 }


END
