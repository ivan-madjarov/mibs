FSC-RAID-MIB DEFINITIONS ::= BEGIN

-- MibName=fscRAIDMIB
-- 
-- ServerView RAID Manager MIB - Unified RAID system monitoring for internal RAID controllers
-- 
-- MIB Revision: 1.6.20
-- 
-- Copyright (c) Fujitsu Technology Solutions 2009 - 2013
-- All rights reserved
-- 

   IMPORTS
        OBJECT-TYPE                 FROM RFC-1212
        TRAP-TYPE                   FROM RFC-1215
        DisplayString               FROM RFC1213-MIB
        Counter, Gauge, enterprises FROM RFC1155-SMI;

-- The Windows MIB compiler doesn't support IMPORTS.
-- In this case uncomment the next few lines.
-- 
-- DisplayString ::= OCTET STRING
-- enterprises       OBJECT IDENTIFIER   ::= { iso org(3) dod(6) internet(1) private(4) 1 }

   sni                   OBJECT IDENTIFIER ::= { enterprises 231 }
   sniProductMibs        OBJECT IDENTIFIER ::= { sni 2 }

   fscRAIDMIB OBJECT IDENTIFIER   ::= { sniProductMibs 49 }
   svrObjects OBJECT IDENTIFIER   ::= { fscRAIDMIB 1 }
   svrNotifications OBJECT IDENTIFIER   ::= { fscRAIDMIB 2 }

   --
   -- Textual conventions
   --

   CompStatus ::= INTEGER
   {
      ok(1),
      prefailure(2),
      failure(3)
   }

   TrueFalse ::= INTEGER
   {
      false(1),
      true(2)
   }

   Index ::= INTEGER (0..2147483647)


-- **********************************************************************************************
--
-- GROUP        svrAgentInfo
-- DESCRIPTION  "This group defines agent specific objects like agent name,
--               vendor name and versions"
--
--      svrAgentInfo group: 1.3.6.1.4.1.231.2.49.1.1
--
-- **********************************************************************************************

svrAgentInfo OBJECT IDENTIFIER		::= { svrObjects 1 }

svrAgentId OBJECT-TYPE
    SYNTAX       DisplayString
    ACCESS       read-only
    STATUS       mandatory
    DESCRIPTION  "Agent identification string"
    ::= { svrAgentInfo 1 }

svrAgentCompany OBJECT-TYPE
    SYNTAX       DisplayString
    ACCESS       read-only
    STATUS       mandatory
    DESCRIPTION  "Agent's company name (e.g. Fujitsu)"
    ::= { svrAgentInfo 2 }

svrAgentVersion OBJECT-TYPE
    SYNTAX       DisplayString
    ACCESS       read-only
    STATUS       mandatory
    DESCRIPTION  "Agent's version string (e.g. 1.05)"
    ::= { svrAgentInfo 3 }

svrAgentBuild OBJECT-TYPE
    SYNTAX       DisplayString
    ACCESS       read-only
    STATUS       mandatory
    DESCRIPTION  "Compilation time and date of agent program"
    ::= { svrAgentInfo 4 }


-- **********************************************************************************************
--
-- GROUP        svrAgentOptions
-- DESCRIPTION  "This group defines global agent options - currently not used"
--
--      svrAgentOptions group: 1.3.6.1.4.1.231.2.49.1.2
--
-- **********************************************************************************************

svrAgentOptions OBJECT IDENTIFIER		::= { svrObjects 2 }


-- **********************************************************************************************
--
-- GROUP        svrStatus
-- DESCRIPTION  "This group defines status summary values"
--
--      svrStatus group: 1.3.6.1.4.1.231.2.49.1.3
--
-- **********************************************************************************************

svrStatus OBJECT IDENTIFIER		::= { svrObjects 3 }

svrStatusLogicalDrives OBJECT-TYPE
    SYNTAX       CompStatus
    ACCESS       read-only
    STATUS       mandatory
    DESCRIPTION  "Logical drive status (summary status of all logical drives at all controllers)"
    ::= { svrStatus 1 }

svrStatusPhysicalDevices OBJECT-TYPE
    SYNTAX       CompStatus
    ACCESS       read-only
    STATUS       mandatory
    DESCRIPTION  "Device status (summary status of all devices at all controllers)"
    ::= { svrStatus 2 }

svrStatusControllers OBJECT-TYPE
    SYNTAX       CompStatus
    ACCESS       read-only
    STATUS       mandatory
    DESCRIPTION  "Controller status (summary status of all controllers, including status
                  of all devices and logical drives of this controller)"
    ::= { svrStatus 3 }

svrStatusOverall OBJECT-TYPE
    SYNTAX       CompStatus
    ACCESS       read-only
    STATUS       mandatory
    DESCRIPTION  "Overall status (overall summary status)"
    ::= { svrStatus 4 }


-- **********************************************************************************************
--
-- GROUP        svrControllerInfo
-- DESCRIPTION  "This group describes the available RAID controllers and their capabilities"
--
--      svrControllerInfo group: 1.3.6.1.4.1.231.2.49.1.4
--
-- **********************************************************************************************

svrControllerInfo OBJECT IDENTIFIER		::= { svrObjects 4 }

svrNumberRaidControllers OBJECT-TYPE
    SYNTAX       INTEGER
    ACCESS       read-only
    STATUS       mandatory
    DESCRIPTION  "Number of available ServerView RAID Manager managed RAID controllers/adapters (number of entries in svrCtrlTable)"
    ::= { svrControllerInfo 1 }

-- ----------------------------------------------------------------------------------------------
--
-- TABLE        svrCtrlTable
-- STATUS       mandatory
-- DESCRIPTION  "Available RAID adapters (supported by ServerView RAID Manager)"
--
--      svrCtrlTable: 1.3.6.1.4.1.231.2.49.1.4.2
--
-- ----------------------------------------------------------------------------------------------

svrCtrlTable OBJECT-TYPE
    SYNTAX       SEQUENCE OF SvrCtrlEntry
    ACCESS       not-accessible
    STATUS       mandatory
    DESCRIPTION  "Available RAID adapters (supported by ServerView RAID Manager)"
    ::= { svrControllerInfo 2 }

svrCtrlEntry OBJECT-TYPE
    SYNTAX       SvrCtrlEntry
    ACCESS       not-accessible
    STATUS       mandatory
    DESCRIPTION  ""
    INDEX   { svrCtrlNr }
    ::= { svrCtrlTable 1 }

SvrCtrlEntry ::= SEQUENCE
{
    svrCtrlNr
        Index,
    svrCtrlModelName
        DisplayString,
    svrCtrlManufacturerName
        DisplayString,
    svrCtrlBusLocation
        DisplayString,
    svrCtrlBusLocationText
        DisplayString,
    svrCtrlHardwareRevision
        DisplayString,
    svrCtrlFirmwareRevision
        DisplayString,
    svrCtrlBiosRevision
        DisplayString,
    svrCtrlNumberChannels
        INTEGER,
    svrCtrlMaxChannelInUse
        INTEGER,
    svrCtrlNumberPhysDisks
        INTEGER,
    svrCtrlNumberLogicalDrives
        INTEGER,
    svrCtrlCacheSize
        INTEGER,
    svrCtrlBBUStatus
        INTEGER,
    svrCtrlStatus
        CompStatus,
    svrCtrlInterface
        INTEGER,
    svrCtrlBusLocationBus
        INTEGER,
    svrCtrlBusLocationDevice
        INTEGER,
    svrCtrlBusLocationFunction
        INTEGER,
    svrCtrlBusLocationSlot
        INTEGER,
    svrCtrlSerialNo
        DisplayString,
    svrCtrlDriverName
        DisplayString,
    svrCtrlDriverRevision
        DisplayString,
    svrCtrlBBUStatusEx
        INTEGER,
    svrCtrlDisplayName
        DisplayString,
    svrCtrlHostName
        DisplayString,
    svrCtrlUEFIDriverRevision
        DisplayString,
    svrCtrlBusLocationSegment
        INTEGER
}

svrCtrlNr OBJECT-TYPE
    SYNTAX       Index
    ACCESS       read-only
    STATUS       mandatory
    DESCRIPTION  "Unique controller number (index; starts with 1)"
    ::= { svrCtrlEntry 1 }

svrCtrlModelName OBJECT-TYPE
    SYNTAX       DisplayString
    ACCESS       read-only
    STATUS       mandatory
    DESCRIPTION  "Controller model name"
    ::= { svrCtrlEntry 2 }

svrCtrlManufacturerName OBJECT-TYPE
    SYNTAX       DisplayString
    ACCESS       read-only
    STATUS       mandatory
    DESCRIPTION  "Controller manufacturer name"
    ::= { svrCtrlEntry 3 }

svrCtrlBusLocation OBJECT-TYPE
    SYNTAX       DisplayString
    ACCESS       read-only
    STATUS       mandatory
    DESCRIPTION  "String describing the location of a RAID controller on PCI or SCSI bus
                  (e.g. 'PCI:Bus=1&Device=6&Function=1&Slot=4', 'SCSI:Host=0&Channel=1&Target=2&LUN=3' or 'LAN:IP=10.0.0.33:5566'...)"
    ::= { svrCtrlEntry 4 }

svrCtrlBusLocationText OBJECT-TYPE
    SYNTAX       DisplayString
    ACCESS       read-only
    STATUS       mandatory
    DESCRIPTION  "String describing the bus location of a RAID controller as a human readable text
                  (e.g. 'PCI Bus 1, Device 6'...)"
    ::= { svrCtrlEntry 5 }

svrCtrlHardwareRevision OBJECT-TYPE
    SYNTAX       DisplayString
    ACCESS       read-only
    STATUS       mandatory
    DESCRIPTION  "Controller hardware version/revision"
    ::= { svrCtrlEntry 6 }

svrCtrlFirmwareRevision OBJECT-TYPE
    SYNTAX       DisplayString
    ACCESS       read-only
    STATUS       mandatory
    DESCRIPTION  "Controller firmware version/revision"
    ::= { svrCtrlEntry 7 }

svrCtrlBiosRevision OBJECT-TYPE
    SYNTAX       DisplayString
    ACCESS       read-only
    STATUS       mandatory
    DESCRIPTION  "Controller BIOS option ROM version/revision"
    ::= { svrCtrlEntry 8 }

svrCtrlNumberChannels OBJECT-TYPE
    SYNTAX       INTEGER
    ACCESS       read-only
    STATUS       mandatory
    DESCRIPTION  "Number of channels/ports at the controller"
    ::= { svrCtrlEntry 9 }

svrCtrlMaxChannelInUse OBJECT-TYPE
    SYNTAX       INTEGER
    ACCESS       read-only
    STATUS       mandatory
    DESCRIPTION  "Number of the hightest channel/port that is in use"
    ::= { svrCtrlEntry 10 }

svrCtrlNumberPhysDisks OBJECT-TYPE
    SYNTAX       INTEGER
    ACCESS       read-only
    STATUS       mandatory
    DESCRIPTION  "Current number of disks"
    ::= { svrCtrlEntry 11 }

svrCtrlNumberLogicalDrives OBJECT-TYPE
    SYNTAX       INTEGER
    ACCESS       read-only
    STATUS       mandatory
    DESCRIPTION  "Current number of logical drives"
    ::= { svrCtrlEntry 12 }

svrCtrlCacheSize OBJECT-TYPE
    SYNTAX       INTEGER
    ACCESS       read-only
    STATUS       mandatory
    DESCRIPTION  "Size of onboard cache on the controller (in MBytes)"
    ::= { svrCtrlEntry 13 }

svrCtrlBBUStatus OBJECT-TYPE
    SYNTAX       INTEGER
    {
        notAvailable(1),
        onLine(2),
        onBattery(3),
        onBatteryLow(4),
        charging(5),
        discharging(6),
        failed(7)
    }
    ACCESS       read-only
    STATUS       mandatory
    DESCRIPTION  "Status of onboard battery backup unit (deprecated)"
    ::= { svrCtrlEntry 14 }

svrCtrlStatus OBJECT-TYPE
    SYNTAX       CompStatus
    ACCESS       read-only
    STATUS       mandatory
    DESCRIPTION  "Overall controller status (including status of all disks and logical drives)"
    ::= { svrCtrlEntry 15 }

svrCtrlInterface OBJECT-TYPE
    SYNTAX       INTEGER
    {
        other(1),
        scsi(2),
        ide(3),
        ieee1394(4),
        sata(5),
        sas(6),
        fc(7)
    }
    ACCESS       read-only
    STATUS       mandatory
    DESCRIPTION  "Disk connection interface"
    ::= { svrCtrlEntry 16 }

svrCtrlBusLocationBus OBJECT-TYPE
    SYNTAX       INTEGER
    ACCESS       read-only
    STATUS       mandatory
    DESCRIPTION  "Bus number of a RAID controller on PCI or SCSI bus"
    ::= { svrCtrlEntry 17 }

svrCtrlBusLocationDevice OBJECT-TYPE
    SYNTAX       INTEGER
    ACCESS       read-only
    STATUS       mandatory
    DESCRIPTION  "Device number of a RAID controller on PCI or SCSI bus"
    ::= { svrCtrlEntry 18 }

svrCtrlBusLocationFunction OBJECT-TYPE
    SYNTAX       INTEGER
    ACCESS       read-only
    STATUS       mandatory
    DESCRIPTION  "Function number of a RAID controller on PCI or SCSI bus"
    ::= { svrCtrlEntry 19 }

svrCtrlBusLocationSlot OBJECT-TYPE
    SYNTAX       INTEGER
    ACCESS       read-only
    STATUS       mandatory
    DESCRIPTION  "Slot number of a RAID controller on PCI or SCSI bus"
    ::= { svrCtrlEntry 20 }

svrCtrlSerialNo OBJECT-TYPE
    SYNTAX       DisplayString
    ACCESS       read-only
    STATUS       mandatory
    DESCRIPTION  "Controller serial number"
    ::= { svrCtrlEntry 21 }

svrCtrlDriverName OBJECT-TYPE
    SYNTAX       DisplayString
    ACCESS       read-only
    STATUS       mandatory
    DESCRIPTION  "Controller driver name"
    ::= { svrCtrlEntry 22 }

svrCtrlDriverRevision OBJECT-TYPE
    SYNTAX       DisplayString
    ACCESS       read-only
    STATUS       mandatory
    DESCRIPTION  "Controller driver version/revision"
    ::= { svrCtrlEntry 23 }

svrCtrlBBUStatusEx OBJECT-TYPE
    SYNTAX       INTEGER
    {
        unknown(1),
        notInstalled(2),
        normal(3),
        charging(4),
        discharging(5),
        warning(6),
        failed(7)
    }
    ACCESS       read-only
    STATUS       mandatory
    DESCRIPTION  "Status of onboard battery backup unit"
    ::= { svrCtrlEntry 24 }

svrCtrlDisplayName OBJECT-TYPE
    SYNTAX       DisplayString
    ACCESS       read-only
    STATUS       mandatory
    DESCRIPTION  "Controller display name"
    ::= { svrCtrlEntry 25 }

svrCtrlHostName OBJECT-TYPE
    SYNTAX       DisplayString
    ACCESS       read-only
    STATUS       mandatory
    DESCRIPTION  "Name or IP address of server where controller is hosted, empty for local host"
    ::= { svrCtrlEntry 26 }

svrCtrlUEFIDriverRevision OBJECT-TYPE
    SYNTAX       DisplayString
    ACCESS       read-only
    STATUS       mandatory
    DESCRIPTION  "Controller UEFI driver version/revision"
    ::= { svrCtrlEntry 27 }

svrCtrlBusLocationSegment OBJECT-TYPE
    SYNTAX       INTEGER
    ACCESS       read-only
    STATUS       mandatory
    DESCRIPTION  "Segment number of a RAID controller on PCI bus"
    ::= { svrCtrlEntry 28 }



-- **********************************************************************************************
--
-- GROUP        svrPhysicalDeviceInfo
-- DESCRIPTION  "This group contains information about devices"
--
--      svrPhysicalDeviceInfo group: 1.3.6.1.4.1.231.2.49.1.5
--
-- **********************************************************************************************

svrPhysicalDeviceInfo OBJECT IDENTIFIER		::= { svrObjects 5 }

svrNumberPhysicalDevices OBJECT-TYPE
    SYNTAX       INTEGER
    ACCESS       read-only
    STATUS       mandatory
    DESCRIPTION  "Number of available devices (number of entries in svrPhysicalDeviceTable)"
    ::= { svrPhysicalDeviceInfo 1 }

-- ----------------------------------------------------------------------------------------------
--
-- TABLE        svrPhysicalDeviceTable
-- STATUS       mandatory
-- DESCRIPTION  "Table containing devices (disks)"
--
--      svrPhysicalDeviceTable: 1.3.6.1.4.1.231.2.49.1.5.2
--
-- ----------------------------------------------------------------------------------------------

svrPhysicalDeviceTable OBJECT-TYPE
    SYNTAX       SEQUENCE OF SvrPhysicalDeviceEntry
    ACCESS       not-accessible
    STATUS       mandatory
    DESCRIPTION  "Table containing devices (disks)"
    ::= { svrPhysicalDeviceInfo 2 }

svrPhysicalDeviceEntry OBJECT-TYPE
    SYNTAX       SvrPhysicalDeviceEntry
    ACCESS       not-accessible
    STATUS       mandatory
    DESCRIPTION  ""
    INDEX   { svrPhysicalDeviceCtrlNr, svrPhysicalDeviceChannel, svrPhysicalDeviceTarget, svrPhysicalDeviceLUN }
    ::= { svrPhysicalDeviceTable 1 }

SvrPhysicalDeviceEntry ::= SEQUENCE
{
    svrPhysicalDeviceCtrlNr
        Index,
    svrPhysicalDeviceChannel
        Index,
    svrPhysicalDeviceTarget
        Index,
    svrPhysicalDeviceLUN
        Index,
    svrPhysicalDeviceModelName
        DisplayString,
    svrPhysicalDeviceVendorName
        DisplayString,
    svrPhysicalDeviceCapacity
        INTEGER,
    svrPhysicalDeviceMaxTransferRate
        INTEGER,
    svrPhysicalDeviceType
        INTEGER,
    svrPhysicalDeviceConfiguredDisk
        TrueFalse,
    svrPhysicalDeviceInterface
        INTEGER,
    svrPhysicalDeviceErrors
        Counter,
    svrPhysicalDeviceNrBadBlocks
        Counter,
    svrPhysicalDeviceSmartStatus
        INTEGER,
    svrPhysicalDeviceStatus
        INTEGER,
    svrPhysicalDeviceFirmwareRevision
        DisplayString,
    svrPhysicalDeviceSerialNumber
        DisplayString,
    svrPhysicalDeviceForeignConfig
        TrueFalse,
    svrPhysicalDeviceIdx
        INTEGER,
    svrPhysicalDeviceStatusEx
        INTEGER,
    svrPhysicalDeviceCapacityMB
        INTEGER,
    svrPhysicalDeviceEnclosureNumber
        INTEGER,
    svrPhysicalDeviceSlot
        INTEGER,
    svrPhysicalDeviceDisplayName
        DisplayString,
    svrPhysicalDevicePowerStatus
        INTEGER
}

svrPhysicalDeviceCtrlNr OBJECT-TYPE
    SYNTAX       Index
    ACCESS       read-only
    STATUS       mandatory
    DESCRIPTION  "Controller number (same as index in svrCtrlTable)"
    ::= { svrPhysicalDeviceEntry 1 }

svrPhysicalDeviceChannel OBJECT-TYPE
    SYNTAX       Index
    ACCESS       read-only
    STATUS       mandatory
    DESCRIPTION  "Channel/Port number (index)
                    SCSI: bus (channel) number
                    SAS/SATA: port number
                  a value >= 65000 means unknown/invalid (e.g. missing device)"
    ::= { svrPhysicalDeviceEntry 2 }

svrPhysicalDeviceTarget OBJECT-TYPE
    SYNTAX       Index
    ACCESS       read-only
    STATUS       mandatory
    DESCRIPTION  "Device target number (index)
                    SCSI: target number (SCSI ID)
                    SAS/SATA: device number
                  a value >= 65000 means unknown/invalid (e.g. missing device)"
    ::= { svrPhysicalDeviceEntry 3 }

svrPhysicalDeviceLUN OBJECT-TYPE
    SYNTAX       Index
    ACCESS       read-only
    STATUS       mandatory
    DESCRIPTION  "Device logical unit number (index)
                    SCSI: logical unit number (SCSI LUN)
                    SAS/SATA: not used (0)"
    ::= { svrPhysicalDeviceEntry 4 }

svrPhysicalDeviceModelName OBJECT-TYPE
    SYNTAX       DisplayString
    ACCESS       read-only
    STATUS       mandatory
    DESCRIPTION  "Device model name"
    ::= { svrPhysicalDeviceEntry 5 }

svrPhysicalDeviceVendorName OBJECT-TYPE
    SYNTAX       DisplayString
    ACCESS       read-only
    STATUS       mandatory
    DESCRIPTION  "Device vendor (manufacturer) name"
    ::= { svrPhysicalDeviceEntry 6 }

svrPhysicalDeviceCapacity OBJECT-TYPE
    SYNTAX       INTEGER
    ACCESS       read-only
    STATUS       mandatory
    DESCRIPTION  "Disk capacity (GBytes)"
    ::= { svrPhysicalDeviceEntry 7 }

svrPhysicalDeviceMaxTransferRate OBJECT-TYPE
    SYNTAX       INTEGER
    ACCESS       read-only
    STATUS       mandatory
    DESCRIPTION  "Maximum transfer rate (MBytes/second) of the disk interface"
    ::= { svrPhysicalDeviceEntry 8 }

svrPhysicalDeviceType OBJECT-TYPE
    SYNTAX       INTEGER
    {
        other(1),
        disk(2),
        tape(3),
        printer(4),
        processor(5),
        writeOnce(6),
        cdRomDvd(7),
        scanner(8),
        optical(9),
        jukebox(10),
        communicationDevice(11),
        host(98),
        unknown(99)
    }
    ACCESS       read-only
    STATUS       mandatory
    DESCRIPTION  "Device type"
    ::= { svrPhysicalDeviceEntry 9 }

svrPhysicalDeviceConfiguredDisk OBJECT-TYPE
    SYNTAX       TrueFalse
    ACCESS       read-only
    STATUS       mandatory
    DESCRIPTION  "This disk is a configured part of RAID array"
    ::= { svrPhysicalDeviceEntry 10 }

svrPhysicalDeviceInterface OBJECT-TYPE
    SYNTAX       INTEGER
    {
        other(1),
        scsi(2),
        ide(3),
        ieee1394(4),
        sata(5),
        sas(6),
        fc(7)
    }
    ACCESS       read-only
    STATUS       mandatory
    DESCRIPTION  "Disk connection interface"
    ::= { svrPhysicalDeviceEntry 11 }

svrPhysicalDeviceErrors OBJECT-TYPE
    SYNTAX       Counter
    ACCESS       read-only
    STATUS       mandatory
    DESCRIPTION  "Number of read/write/seek or other errors (summary of all error counters)"
    ::= { svrPhysicalDeviceEntry 12 }

svrPhysicalDeviceNrBadBlocks OBJECT-TYPE
    SYNTAX       Counter
    ACCESS       read-only
    STATUS       mandatory
    DESCRIPTION  "Number of detected bad blocks (0 = unknown or no bad blocks)"
    ::= { svrPhysicalDeviceEntry 13 }

svrPhysicalDeviceSmartStatus OBJECT-TYPE
    SYNTAX       INTEGER
    {
        ok(1),
        failurePredicted(2),
        smartNotAvailable(3),
        smartMonitoringDisabled(4)
    }
    ACCESS       read-only
    STATUS       mandatory
    DESCRIPTION  "SMART status"
    ::= { svrPhysicalDeviceEntry 14 }

svrPhysicalDeviceStatus OBJECT-TYPE
    SYNTAX       INTEGER
    {
        unknown(1),
        noDisk(2),
        online(3),
        ready(4),
        failed(5),
        rebuilding(6),
        hotspareGlobal(7),
        hotspareDedicated(8),
        offline(9),
        unconfiguredFailed(10),
        formatting(11),
        dead(12)
    }
    ACCESS       read-only
    STATUS       mandatory
    DESCRIPTION  "Device status (deprecated):
                    noDisk(2):               device is not a hard disk
                    online(3):               device is available and working properly
                    ready(4):                device can be used for new configuration
                    failed(5):               device is available but no longer working
                    rebuilding(6):           device is restoring fault tolerance
                    hotspareGlobal(7):       device is a hot spare device for use in any array
                    hotspareDedicated(8):    device is a hot spare device for use in a dedicated array
                    offline(9):              device is set to non-working state
                    unconfiguredFailed(10):  device is not configured but a failure has occurred
                    formatting(15):          device is currently being formatted
                    dead(12):                device is not available or not responding"
    ::= { svrPhysicalDeviceEntry 15 }

svrPhysicalDeviceFirmwareRevision OBJECT-TYPE
    SYNTAX       DisplayString
    ACCESS       read-only
    STATUS       mandatory
    DESCRIPTION  "Device firmware version/revision"
    ::= { svrPhysicalDeviceEntry 16 }

svrPhysicalDeviceSerialNumber OBJECT-TYPE
    SYNTAX       DisplayString
    ACCESS       read-only
    STATUS       mandatory
    DESCRIPTION  "Device serial number"
    ::= { svrPhysicalDeviceEntry 17 }

svrPhysicalDeviceForeignConfig OBJECT-TYPE
    SYNTAX       TrueFalse
    ACCESS       read-only
    STATUS       mandatory
    DESCRIPTION  "This device has a foreign configuration"
    ::= { svrPhysicalDeviceEntry 18 }

svrPhysicalDeviceIdx OBJECT-TYPE
    SYNTAX       INTEGER
    ACCESS       read-only
    STATUS       mandatory
    DESCRIPTION  "Device SVRAID object index"
    ::= { svrPhysicalDeviceEntry 19 }

svrPhysicalDeviceStatusEx OBJECT-TYPE
    SYNTAX       INTEGER
    {
        unknown(1),
        noDisk(2),
        available(3),
        operational(4),
        failed(5),
        rebuilding(6),
        globalHotSpare(7),
        dedicatedHotSpare(8),
        offline(9),
        unconfiguredFailed(10),
        failedMissing(11),
        copyBack(12),
        redundantCopy(13),
        waiting(14),
        preparing(15),
        migrating(16),
        jbod(17),
        shielded(18),
        clearing(19),
        erasing(20)
    }
    ACCESS       read-only
    STATUS       mandatory
    DESCRIPTION  "Device status:
                    noDisk(2):                device is not a hard disk
                    available(3):             device is unconfigured and working properly
                    operational(4):           device is configured and working properly
                    failed(5):                device is configured but is no longer working
                    rebuilding(6):            device is restoring fault tolerance
                    globalHotSpare(7):        device is a hot spare device for use in any array
                    dedicatedHotSpare(8):     device is a hot spare device for use in a dedicated array
                    offline(9):               device is set to non-working state
                    unconfiguredFailed(10):   device is not configured but is no longer working
                    failedMissing(11):        device is not available anymore
                    copyBack(12):             device is target for copyback operation
                    redundantCopy(13):        device is target for redundant copy operation
                    waiting(14):              device is waiting for copyback to start
                    preparing(15):            device is starting up
                    migrating(16):            device is part of migration process
                    jbod(17):                 device is exposed to operating system
                    shielded(18):             device is under diagnostic test
                    clearing(19):             device is being cleared
                    erasing(20):              device is begin erased"
    ::= { svrPhysicalDeviceEntry 20 }

svrPhysicalDeviceCapacityMB OBJECT-TYPE
    SYNTAX       INTEGER
    ACCESS       read-only
    STATUS       mandatory
    DESCRIPTION  "Disk capacity (MBytes)"
    ::= { svrPhysicalDeviceEntry 21 }

svrPhysicalDeviceEnclosureNumber OBJECT-TYPE
    SYNTAX       INTEGER
    ACCESS       read-only
    STATUS       mandatory
    DESCRIPTION  "Device enclosure number (-1 unknown or not in an enclosure)"
    ::= { svrPhysicalDeviceEntry 22 }

svrPhysicalDeviceSlot OBJECT-TYPE
    SYNTAX       INTEGER
    ACCESS       read-only
    STATUS       mandatory
    DESCRIPTION  "Device slot number (-1 unknown)"
    ::= { svrPhysicalDeviceEntry 23 }

svrPhysicalDeviceDisplayName OBJECT-TYPE
    SYNTAX       DisplayString
    ACCESS       read-only
    STATUS       mandatory
    DESCRIPTION  "Device display name"
    ::= { svrPhysicalDeviceEntry 24 }

svrPhysicalDevicePowerStatus OBJECT-TYPE
    SYNTAX       INTEGER
    {
        active(1),
        stopped(2),
        transition(3)
    }
    ACCESS       read-only
    STATUS       mandatory
    DESCRIPTION  "Device power status:
                    active(1):                device is active
                    stopped(2):               device is powered down
                    transition(3):            device changes its power status"
    ::= { svrPhysicalDeviceEntry 25 }



-- **********************************************************************************************
--
-- GROUP        svrLogicalDriveInfo
-- DESCRIPTION  "This group contains information about logical RAID drives"
--
--      svrLogicalDriveInfo group: 1.3.6.1.4.1.231.2.49.1.6
--
-- **********************************************************************************************

svrLogicalDriveInfo OBJECT IDENTIFIER		::= { svrObjects 6 }

svrNumberLogicalDrives OBJECT-TYPE
    SYNTAX       INTEGER
    ACCESS       read-only
    STATUS       mandatory
    DESCRIPTION  "Number of available logical drives (number of entries in 
                    svrLogicalDriveTable and svrLogicalDriveContentsTable)"
    ::= { svrLogicalDriveInfo 1 }

-- ----------------------------------------------------------------------------------------------
--
-- TABLE        svrLogicalDriveTable
-- STATUS       mandatory
-- DESCRIPTION  "Table containing logical drives (system drives)"
--
--      svrLogicalDriveTable: 1.3.6.1.4.1.231.2.49.1.6.2
--
-- ----------------------------------------------------------------------------------------------

svrLogicalDriveTable OBJECT-TYPE
    SYNTAX       SEQUENCE OF SvrLogicalDriveEntry
    ACCESS       not-accessible
    STATUS       mandatory
    DESCRIPTION  "Table containing logical drives (system drives)"
    ::= { svrLogicalDriveInfo 2 }

svrLogicalDriveEntry OBJECT-TYPE
    SYNTAX       SvrLogicalDriveEntry
    ACCESS       not-accessible
    STATUS       mandatory
    DESCRIPTION  ""
    INDEX   { svrLogicalDriveCtrlNr, svrLogicalDriveNr }
    ::= { svrLogicalDriveTable 1 }

SvrLogicalDriveEntry ::= SEQUENCE
{
    svrLogicalDriveCtrlNr
        Index,
    svrLogicalDriveNr
        Index,
    svrLogicalDriveArraySize
        INTEGER,
    svrLogicalDriveTotalSize
        INTEGER,
    svrLogicalDriveRaidLevel
        INTEGER,
    svrLogicalDriveRaidLevelStr
        DisplayString,
    svrLogicalDriveStripeSize
        INTEGER,
    svrLogicalDriveWriteMode
        INTEGER,
    svrLogicalDriveProgress
        Gauge,
    svrLogicalDriveStatus
        INTEGER,
    svrLogicalDriveName
        DisplayString,
    svrLogicalDriveArraySizeMB
        INTEGER,
    svrLogicalDriveTotalSizeMB
        INTEGER,
    svrLogicalDriveOSDeviceName
        DisplayString,
    svrLogicalDriveReadMode
        INTEGER,
    svrLogicalDriveCacheMode
        INTEGER,
    svrLogicalDriveDiskCacheMode
        INTEGER,
    svrLogicalDriveInitStatus
        INTEGER,
    svrLogicalDriveStatusEx
        INTEGER,
    svrLogicalDriveDisplayName
        DisplayString
}

svrLogicalDriveCtrlNr OBJECT-TYPE
    SYNTAX       Index
    ACCESS       read-only
    STATUS       mandatory
    DESCRIPTION  "Controller number (same as index in svrCtrlTable); if 0, logical drive is not attached to any controller"
    ::= { svrLogicalDriveEntry 1 }

svrLogicalDriveNr OBJECT-TYPE
    SYNTAX       Index
    ACCESS       read-only
    STATUS       mandatory
    DESCRIPTION  "Unique logical drive number on the specified controller (index; starts with 1)"
    ::= { svrLogicalDriveEntry 2 }

svrLogicalDriveArraySize OBJECT-TYPE
    SYNTAX       INTEGER
    ACCESS       read-only
    STATUS       mandatory
    DESCRIPTION  "Size (GBytes) of the logical drive (usable space)"
    ::= { svrLogicalDriveEntry 3 }

svrLogicalDriveTotalSize OBJECT-TYPE
    SYNTAX       INTEGER
    ACCESS       read-only
    STATUS       mandatory
    DESCRIPTION  "Size (GBytes) of the logical drive (physical disk space, size of all drives)"
    ::= { svrLogicalDriveEntry 4 }

svrLogicalDriveRaidLevel OBJECT-TYPE
    SYNTAX       INTEGER
    {
        unknown(1),
        raid0(2),
        raid01(3),
        raid1(4),
        raid1e(5),
        raid10(6),
        raid3(7),
        raid4(8),
        raid5(9),
        raid50(10),
        raid5e(11),
        raid5ee(12),
        raid6(13),
        concat(14),
        single(15),
        raid60(16),
        raid1e0(17),
        raid0CC(18),
        raid1CC(19),
        raid1ECC(20),
        raid5CC(21),
        raid00(22)
    }
    ACCESS       read-only
    STATUS       mandatory
    DESCRIPTION  "RAID level"
    ::= { svrLogicalDriveEntry 5 }

svrLogicalDriveRaidLevelStr OBJECT-TYPE
    SYNTAX       DisplayString
    ACCESS       read-only
    STATUS       mandatory
    DESCRIPTION  "RAID level (as string, e.g. 'Single', 'Mirror'...)"
    ::= { svrLogicalDriveEntry 6 }

svrLogicalDriveStripeSize OBJECT-TYPE
    SYNTAX       INTEGER
    ACCESS       read-only
    STATUS       mandatory
    DESCRIPTION  "RAID stripe size (in bytes) of the logical drive"
    ::= { svrLogicalDriveEntry 7 }

svrLogicalDriveWriteMode OBJECT-TYPE
    SYNTAX       INTEGER
    {
        unknown(1),
        writeBack(2),
        writeThrough(3),
        adaptive(4),
        writeBackBadBBU(5),
        readOnly(6),
        readWrite(7),
        alwaysReadWrite(8),
        notAvailable(9)
    }
    ACCESS       read-only
    STATUS       mandatory
    DESCRIPTION  "Logical drive write mode:
                    writeBack(2): cached
                    writeThrough(3): not cached
                    adaptive(4): cached if BBU is working properly, else un-cached
                    writeBackBadBBU(5): remain cached even if BBU fails
                    readOnly(6): cache read operations only
                    readWrite(7): cache read and write operations
                    alwaysReadWrite(8): always cache read and write operations"
    ::= { svrLogicalDriveEntry 8 }

svrLogicalDriveProgress OBJECT-TYPE
    SYNTAX       Gauge
    ACCESS       read-only
    STATUS       mandatory
    DESCRIPTION  "Logical drive task progress rate (in percent 0..100) of a rebuild / verify / initialize task.
                  This rate is only valid if the drive is performing a longer task like rebuild,
                  verify (consistency check) or initialization and is 100 if no task is in progress or task
                  is finished."
    ::= { svrLogicalDriveEntry 9 }

svrLogicalDriveStatus OBJECT-TYPE
    SYNTAX       INTEGER
    {
        unknown(1),
        online(2),
        degraded(3),
        offline(4),
        rebuilding(5),
        verifying(6),
        initializing(7),
        morphing(8),
        partialDegraded(9)
    }
    ACCESS       read-only
    STATUS       mandatory
    DESCRIPTION  "Status of the logical drive (deprecated):
                    online(2):       drive is OK, all disks working properly
                    degraded(3):     one disk in this array failed, redundancy lost
                    offline(4):      too many disks in this array failed, drive no longer available
                    rebuilding(5):   drive is currently rebuilding (new disk added)
                    verifying(6):    drive is currently executing a consistency check
                    initializing(7): drive was just created and is currently being initialized
                    morphing(8):     drive is currently being modified (online RAID extension)
                    partialDegraded(9): one disk in this array failed, reduced redundancy still available"
    ::= { svrLogicalDriveEntry 10 }

svrLogicalDriveName OBJECT-TYPE
    SYNTAX       DisplayString
    ACCESS       read-only
    STATUS       mandatory
    DESCRIPTION  "Logical drive name"
    ::= { svrLogicalDriveEntry 11 }

svrLogicalDriveArraySizeMB OBJECT-TYPE
    SYNTAX       INTEGER
    ACCESS       read-only
    STATUS       mandatory
    DESCRIPTION  "Size (MBytes) of the logical drive (usable space)"
    ::= { svrLogicalDriveEntry 12 }

svrLogicalDriveTotalSizeMB OBJECT-TYPE
    SYNTAX       INTEGER
    ACCESS       read-only
    STATUS       mandatory
    DESCRIPTION  "Size (MBytes) of the logical drive (physical disk space, size of all drives)"
    ::= { svrLogicalDriveEntry 13 }

svrLogicalDriveOSDeviceName OBJECT-TYPE
    SYNTAX       DisplayString
    ACCESS       read-only
    STATUS       mandatory
    DESCRIPTION  "Operating system device name"
    ::= { svrLogicalDriveEntry 14 }

svrLogicalDriveReadMode OBJECT-TYPE
    SYNTAX       INTEGER
    {
        unknown(1),
        readAhead(2),
        noReadAhead(3),
        adaptive(4),
        notAvailable(5)
    }
    ACCESS       read-only
    STATUS       mandatory
    DESCRIPTION  "Logical drive read mode"
    ::= { svrLogicalDriveEntry 15 }

svrLogicalDriveCacheMode OBJECT-TYPE
    SYNTAX       INTEGER
    {
        unknown(1),
        cached(2),
        direct(3),
        notAvailable(4)
    }
    ACCESS       read-only
    STATUS       mandatory
    DESCRIPTION  "Logical drive cache mode"
    ::= { svrLogicalDriveEntry 16 }

svrLogicalDriveDiskCacheMode OBJECT-TYPE
    SYNTAX       INTEGER
    {
        unknown(1),
        enabled(2),
        disabled(3),
        unchanged(4),
        notAvailable(5)
    }
    ACCESS       read-only
    STATUS       mandatory
    DESCRIPTION  "Logical drive disk cache mode"
    ::= { svrLogicalDriveEntry 17 }

svrLogicalDriveInitStatus OBJECT-TYPE
    SYNTAX       INTEGER
    {
        unknown(1),
        initialized(2),
        notInitialized(3)
    }
    ACCESS       read-only
    STATUS       mandatory
    DESCRIPTION  "Logical drive initialization status"
    ::= { svrLogicalDriveEntry 18 }

svrLogicalDriveStatusEx OBJECT-TYPE
    SYNTAX       INTEGER
    {
        unknown(1),
        operational(2),
        partiallyDegraded(3),
        degraded(4),
        failed(5),
        rebuilding(6),
        checking(7),
        mdcing(8),
        initializing(9),
        backgroundInitializing(10),
        migrating(11),
        copying(12),
        offline(13),
        spareInUse(14),
        erasing(15)
    }
    ACCESS       read-only
    STATUS       mandatory
    DESCRIPTION  "Status of the logical drive:
                    operational(2):   drive is OK, all disks working properly
                    partiallyDegraded(3): one disk in this array failed, reduced redundancy still available
                    degraded(4):      one disk in this array failed, redundancy lost
                    failed(5):        too many disks in this array failed, drive no longer available
                    rebuilding(6):    drive is currently rebuilding
                    checking(7):      drive is currently executing a consistency check
                    mdcing(8):        drive is currently executing a consistency check and fixes inconsistencies
                    initializing(9):  drive is currently being initialized
                    backgroundInitializing(10): drive is currently being initialized in background
                    migrating(11):    drive is currently being modified (online RAID extension)
                    copying(12):      drive is currently executing a copyback or redundant copy operation
                    offline(13):      drive is temporarily not operational
                    spareInUse(14):   drive is using a hot spare
                    erasing(15):      drive is being erased"
    ::= { svrLogicalDriveEntry 19 }

svrLogicalDriveDisplayName OBJECT-TYPE
    SYNTAX       DisplayString
    ACCESS       read-only
    STATUS       mandatory
    DESCRIPTION  "Logical drive display name"
    ::= { svrLogicalDriveEntry 20 }


-- ----------------------------------------------------------------------------------------------
--
-- TABLE        svrLogicalDriveContentsTable
-- STATUS       mandatory
-- DESCRIPTION  "Table containing the devices belonging to a logical drive
--               (logical to device mapping);
--               the same device can be member of more than one logical drive."
--
--      svrLogicalDriveContentsTable: 1.3.6.1.4.1.231.2.49.1.6.3
--
-- ----------------------------------------------------------------------------------------------

svrLogicalDriveContentsTable OBJECT-TYPE
    SYNTAX       SEQUENCE OF SvrLogicalDriveContentsEntry
    ACCESS       not-accessible
    STATUS       mandatory
    DESCRIPTION  "Table containing the devices belonging to a logical drive
                  (logical to device mapping);
                  the same device can be member of more than one logical drive."
    ::= { svrLogicalDriveInfo 3 }

svrLogicalDriveContentsEntry OBJECT-TYPE
    SYNTAX       SvrLogicalDriveContentsEntry
    ACCESS       not-accessible
    STATUS       mandatory
    DESCRIPTION  ""
    INDEX   { svrLogicalDriveContentsCtrlNr, svrLogicalDriveContentsLogicalDriveNr, svrLogicalDriveContentsNr, svrLogicalDriveContentsIdx }
    ::= { svrLogicalDriveContentsTable 1 }

SvrLogicalDriveContentsEntry ::= SEQUENCE
{
    svrLogicalDriveContentsCtrlNr
        Index,
    svrLogicalDriveContentsLogicalDriveNr
        Index,
    svrLogicalDriveContentsNr
        Index,
    svrLogicalDriveContentsChannel
        INTEGER,
    svrLogicalDriveContentsTarget
        INTEGER,
    svrLogicalDriveContentsLUN
        INTEGER,
    svrLogicalDriveContentsIdx
        Index,
    svrLogicalDriveContentsSpanNr
        INTEGER
}

svrLogicalDriveContentsCtrlNr OBJECT-TYPE
    SYNTAX       Index
    ACCESS       read-only
    STATUS       mandatory
    DESCRIPTION  "Controller number (same as index in svrCtrlTable)"
    ::= { svrLogicalDriveContentsEntry 1 }

svrLogicalDriveContentsLogicalDriveNr OBJECT-TYPE
    SYNTAX       Index
    ACCESS       read-only
    STATUS       mandatory
    DESCRIPTION  "Logical drive number (same as index in svrLogicalDriveTable)"
    ::= { svrLogicalDriveContentsEntry 2 }

svrLogicalDriveContentsNr OBJECT-TYPE
    SYNTAX       Index
    ACCESS       read-only
    STATUS       mandatory
    DESCRIPTION  "Device index (index; starts with 1 for each logical drive)"
    ::= { svrLogicalDriveContentsEntry 3 }

svrLogicalDriveContentsChannel OBJECT-TYPE
    SYNTAX       INTEGER
    ACCESS       read-only
    STATUS       mandatory
    DESCRIPTION  "Device channel number (same as index in svrPhysicalDeviceTable)"
    ::= { svrLogicalDriveContentsEntry 4 }

svrLogicalDriveContentsTarget OBJECT-TYPE
    SYNTAX       INTEGER
    ACCESS       read-only
    STATUS       mandatory
    DESCRIPTION  "Device target number (same as index in svrPhysicalDeviceTable)"
    ::= { svrLogicalDriveContentsEntry 5 }

svrLogicalDriveContentsLUN OBJECT-TYPE
    SYNTAX       INTEGER
    ACCESS       read-only
    STATUS       mandatory
    DESCRIPTION  "Device logical unit number (same as index in svrPhysicalDeviceTable)"
    ::= { svrLogicalDriveContentsEntry 6 }

svrLogicalDriveContentsIdx OBJECT-TYPE
    SYNTAX       Index
    ACCESS       read-only
    STATUS       mandatory
    DESCRIPTION  "Device SVRAID object index (same as Idx in svrPhysicalDeviceTable)"
    ::= { svrLogicalDriveContentsEntry 7 }

svrLogicalDriveContentsSpanNr OBJECT-TYPE
    SYNTAX       INTEGER
    ACCESS       read-only
    STATUS       mandatory
    DESCRIPTION  "Logical drive span number (starts with 1)"
    ::= { svrLogicalDriveContentsEntry 8 }



-- **********************************************************************************************
--
-- GROUP        svrNotificationsInfo
-- DESCRIPTION  "This group defines the trap parameter variables. They are not accessible directly,
--               but sent together with traps."
--
--      svrNotificationsInfo group: 1.3.6.1.4.1.231.2.49.2.1
--
-- **********************************************************************************************

svrNotificationsInfo OBJECT IDENTIFIER		::= { svrNotifications 1 }

svrTrapInfoServerName OBJECT-TYPE
    SYNTAX       DisplayString
    ACCESS       read-only
    STATUS       mandatory
    DESCRIPTION  "Name of the server the trap comes from"
    ::= { svrNotificationsInfo 1 }

svrTrapInfoTime OBJECT-TYPE
    SYNTAX       INTEGER
    ACCESS       read-only
    STATUS       mandatory
    DESCRIPTION  "Time when the trap occurred (in seconds since 01/01/1970 00:00h)"
    ::= { svrNotificationsInfo 2 }

svrTrapInfoPlaceHolder1 OBJECT-TYPE
    SYNTAX       DisplayString
    ACCESS       read-only
    STATUS       mandatory
    DESCRIPTION  "Text to replace %? in trap descriptions"
    ::= { svrNotificationsInfo 3 }

svrTrapInfoPlaceHolder2 OBJECT-TYPE
    SYNTAX       DisplayString
    ACCESS       read-only
    STATUS       mandatory
    DESCRIPTION  "Text to replace %? in trap descriptions"
    ::= { svrNotificationsInfo 4 }

svrTrapInfoPlaceHolder3 OBJECT-TYPE
    SYNTAX       DisplayString
    ACCESS       read-only
    STATUS       mandatory
    DESCRIPTION  "Text to replace %? in trap descriptions"
    ::= { svrNotificationsInfo 5 }

svrTrapInfoPlaceHolder4 OBJECT-TYPE
    SYNTAX       DisplayString
    ACCESS       read-only
    STATUS       mandatory
    DESCRIPTION  "Text to replace %? in trap descriptions"
    ::= { svrNotificationsInfo 6 }

svrTrapInfoPlaceHolder5 OBJECT-TYPE
    SYNTAX       DisplayString
    ACCESS       read-only
    STATUS       mandatory
    DESCRIPTION  "Text to replace %? in trap descriptions"
    ::= { svrNotificationsInfo 7 }

svrTrapInfoPlaceHolder6 OBJECT-TYPE
    SYNTAX       DisplayString
    ACCESS       read-only
    STATUS       mandatory
    DESCRIPTION  "Text to replace %? in trap descriptions"
    ::= { svrNotificationsInfo 8 }


-- **********************************************************************************************
--
-- GROUP        svrNotificationsTraps
-- DESCRIPTION  "This group defines the traps."
--
--     Trap enterprise: svrNotifications (1.3.6.1.4.1.231.2.49.2)
--
-- **********************************************************************************************

-- EVT_UNDEFINED

svrTrapUndefinedEvent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Undefined event."
    --#TYPE            "Undefined event"
    --#SUMMARY         "Undefined event (Server %s)"
    --#ARGUMENTS       { 0 }
    --#SEVERITY        INFORMATIONAL
    --#TIMEINDEX       1
    --#HELP            "If there are errors directly before or after this event, perform the proper recovery action for that error."
    --#STATE           OPERATIONAL
    ::= 1

-- EVT_CONNECTED

svrTrapConnectedEvent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Connection to ServerView RAID Manager established."
    --#TYPE            "Connection to ServerView RAID Manager established"
    --#SUMMARY         "Connection to ServerView RAID Manager established (Server %s)"
    --#ARGUMENTS       { 0 }
    --#SEVERITY        INFORMATIONAL
    --#TIMEINDEX       1
    --#HELP            ""
    --#STATE           OPERATIONAL
    ::= 2

-- EVT_DISCONNECTED

svrTrapDisconnectedEvent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disconnected from ServerView RAID Manager."
    --#TYPE            "Disconnected from ServerView RAID Manager"
    --#SUMMARY         "Disconnected from ServerView RAID Manager (Server %s)"
    --#ARGUMENTS       { 0 }
    --#SEVERITY        INFORMATIONAL
    --#TIMEINDEX       1
    --#HELP            ""
    --#STATE           NONOPERATIONAL
    ::= 3

-- EVT_UNEXPECTED_DISCONNECT

svrTrapUnexpectedDisconnectEvent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unexpected disconnect from ServerView RAID Manager."
    --#TYPE            "Unexpected disconnect from ServerView RAID Manager"
    --#SUMMARY         "Unexpected disconnect from ServerView RAID Manager (Server %s)"
    --#ARGUMENTS       { 0 }
    --#SEVERITY        CRITICAL
    --#TIMEINDEX       1
    --#HELP            "If problem persists after reboot, call your local Fujitsu Helpdesk."
    --#STATE           NONOPERATIONAL
    ::= 4

-- EVT_TEST_TRAP

svrTrapTestEvent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Test event."
    --#TYPE            "Test event"
    --#SUMMARY         "Test event (Server %s)"
    --#ARGUMENTS       { 0 }
    --#SEVERITY        INFORMATIONAL
    --#TIMEINDEX       1
    --#HELP            ""
    --#STATE           OPERATIONAL
    ::= 5

-- EVT_UNKNOWN

svrTrapUnknownEvent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unknown event."
    --#TYPE            "Unknown event"
    --#SUMMARY         "Unknown event (Server %s)"
    --#ARGUMENTS       { 0 }
    --#SEVERITY        INFORMATIONAL
    --#TIMEINDEX       1
    --#HELP            "If there are errors directly before or after this event, perform the proper recovery action for that error."
    --#STATE           OPERATIONAL
    ::= 10000

-- EVT_INTERNAL

svrTrapInternalEvent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal event."
    --#TYPE            "Internal event"
    --#SUMMARY         "Internal event (Server %s)"
    --#ARGUMENTS       { 0 }
    --#SEVERITY        INFORMATIONAL
    --#TIMEINDEX       1
    --#HELP            "For information only."
    --#STATE           OPERATIONAL
    ::= 10001

-- EVT_WRITEACCESS_REVOKED

svrTrapWriteAccessRevoked TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write access of the ServerView RAID Manager revoked."
    --#TYPE            "Write access of the ServerView RAID Manager revoked"
    --#SUMMARY         "Write access of the ServerView RAID Manager revoked by user %s (%s) (Server %s)"
    --#ARGUMENTS       { 2, 3, 0 }
    --#SEVERITY        MINOR
    --#TIMEINDEX       1
    --#HELP            "For information only."
    --#STATE           OPERATIONAL
    ::= 10002

-- EVT_BATTERY_TEMPERATURE_OUT_OF_RANGE

svrTrapBatteryTempOutOfRange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU temperature out of range."
    --#TYPE            "BBU temperature out of range"
    --#SUMMARY         "Adapter %s: BBU temperature out of range (Server %s)"
    --#ARGUMENTS       { 2, 0 }
    --#SEVERITY        MAJOR
    --#TIMEINDEX       1
    --#HELP            "1) Check installation of all air flow channels, closed housing, and unblocked louvers. 2) Check environmental temperature. 3) Check version of RAID controller/iRMC firmware, and BIOS."
    --#STATE           OPERATIONAL
    ::= 10003

-- EVT_BATTERY_TEMPERATURE_UNSTABLE

svrTrapBatteryTempUnstable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU temperature unstable."
    --#TYPE            "BBU temperature unstable"
    --#SUMMARY         "Adapter %s: BBU temperature unstable (Server %s)"
    --#ARGUMENTS       { 2, 0 }
    --#SEVERITY        MAJOR
    --#TIMEINDEX       1
    --#HELP            "1) Check version of RAID controller/iRMC firmware, and BIOS. 2) If problem persists replace BBU."
    --#STATE           OPERATIONAL
    ::= 10004

-- EVT_BATTERY_TEMPERATURE_HIGH

svrTrapBatteryTempAboveTheshold TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU temperature above threshold."
    --#TYPE            "BBU temperature above threshold"
    --#SUMMARY         "Adapter %s: BBU temperature above threshold (Server %s)"
    --#ARGUMENTS       { 2, 0 }
    --#SEVERITY        MAJOR
    --#TIMEINDEX       1
    --#HELP            "1) Check installation of all air flow channels, closed housing, and unblocked louvers. 2) Check environmental temperature. 3) Check version of RAID controller/iRMC firmware, and BIOS."
    --#STATE           OPERATIONAL
    ::= 10005

-- EVT_BATTERY_VOLTAGE_OUT_OF_RANGE

svrTrapBatteryVoltageOutOfRange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU voltage out of range."
    --#TYPE            "BBU voltage out of range"
    --#SUMMARY         "Adapter %s: BBU voltage out of range (Server %s)"
    --#ARGUMENTS       { 2, 0 }
    --#SEVERITY        MAJOR
    --#TIMEINDEX       1
    --#HELP            "1) Check connection between BBU data/power cable and RAID controller. 2) Check version of RAID controller/iRMC firmware, and BIOS. 3) If problem persists replace BBU."
    --#STATE           OPERATIONAL
    ::= 10006

-- EVT_BATTERY_VOLTAGE_UNSTABLE

svrTrapBatteryVoltageUnstable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU voltage unstable."
    --#TYPE            "BBU voltage unstable"
    --#SUMMARY         "Adapter %s: BBU voltage unstable (Server %s)"
    --#ARGUMENTS       { 2, 0 }
    --#SEVERITY        MAJOR
    --#TIMEINDEX       1
    --#HELP            "1) Check connection between BBU data/power cable and RAID controller. 2) Check version of RAID controller/iRMC firmware, and BIOS. 3) If problem persists replace BBU."
    --#STATE           OPERATIONAL
    ::= 10007

-- EVT_BATTERY_VOLTAGE_LOW

svrTrapBatteryVoltageLow TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU voltage below threshold."
    --#TYPE            "BBU voltage below threshold"
    --#SUMMARY         "Adapter %s: BBU voltage below threshold (Server %s)"
    --#ARGUMENTS       { 2, 0 }
    --#SEVERITY        MAJOR
    --#TIMEINDEX       1
    --#HELP            "1) Check connection between BBU data/power cable and RAID controller. 2) Check version of RAID controller/iRMC firmware, and BIOS. 3) If problem persists replace BBU."
    --#STATE           OPERATIONAL
    ::= 10008

-- EVT_BATTERY_COMMUNICATION_ERROR

svrTrapBatteryCommunicationError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU communication error."
    --#TYPE            "BBU communication error"
    --#SUMMARY         "Adapter %s: BBU communication error (Server %s)"
    --#ARGUMENTS       { 2, 0 }
    --#SEVERITY        MAJOR
    --#TIMEINDEX       1
    --#HELP            "1) Check connection between BBU data/power cable and RAID controller. 2) Check version of RAID controller/iRMC firmware, and BIOS. 3) If problem persists replace BBU."
    --#STATE           OPERATIONAL
    ::= 10009

-- EVT_BATTERY_RECONDITION_STARTED

svrTrapBatteryReconditionStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU reconditioning started."
    --#TYPE            "BBU reconditioning started"
    --#SUMMARY         "Adapter %s: BBU reconditioning started (Server %s)"
    --#ARGUMENTS       { 2, 0 }
    --#SEVERITY        INFORMATIONAL
    --#TIMEINDEX       1
    --#HELP            ""
    --#STATE           OPERATIONAL
    ::= 10010

-- EVT_BATTERY_NORMAL

svrTrapBatteryStatusNormal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU status becomes normal."
    --#TYPE            "BBU status becomes normal"
    --#SUMMARY         "Adapter %s: BBU status becomes normal (Server %s)"
    --#ARGUMENTS       { 2, 0 }
    --#SEVERITY        INFORMATIONAL
    --#TIMEINDEX       1
    --#HELP            ""
    --#STATE           OPERATIONAL
    ::= 10011

-- EVT_BATTERY_GOOD

svrTrapBatteryGood TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU good."
    --#TYPE            "BBU good"
    --#SUMMARY         "Adapter %s: BBU good (Server %s)"
    --#ARGUMENTS       { 2, 0 }
    --#SEVERITY        INFORMATIONAL
    --#TIMEINDEX       1
    --#HELP            ""
    --#STATE           OPERATIONAL
    ::= 10012

-- EVT_BATTERY_FAILED

svrTrapBatteryFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU failed."
    --#TYPE            "BBU failed"
    --#SUMMARY         "Adapter %s: BBU failed (Server %s)"
    --#ARGUMENTS       { 2, 0 }
    --#SEVERITY        CRITICAL
    --#TIMEINDEX       1
    --#HELP            "Note: Only informational during recalibration process. 1) Check connection between BBU data/power cable and RAID controller. 2) Check version of RAID controller/iRMC firmware, and BIOS. 3) If problem persists replace BBU."
    --#STATE           NONOPERATIONAL
    ::= 10013

-- EVT_BATTERY_FAST_CHARGE_FAILED

svrTrapBatteryFastChargingFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU fast charging failed."
    --#TYPE            "BBU fast charging failed"
    --#SUMMARY         "Adapter %s: BBU fast charging failed (Server %s)"
    --#ARGUMENTS       { 2, 0 }
    --#SEVERITY        MAJOR
    --#TIMEINDEX       1
    --#HELP            "Note: Do not interrupt the charging process by reboots or shutdowns. 1) Check version of RAID controller/iRMC firmware, and BIOS. 2) If problem persists replace BBU."
    --#STATE           OPERATIONAL
    ::= 10014

-- EVT_BATTERY_CHARGE_COUNT_EXCEEDED

svrTrapBatteryChargeCountExceeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU charge count exceeded."
    --#TYPE            "BBU charge count exceeded"
    --#SUMMARY         "Adapter %s: BBU charge count exceeded (Server %s)"
    --#ARGUMENTS       { 2, 0 }
    --#SEVERITY        MINOR
    --#TIMEINDEX       1
    --#HELP            "1) Initiate manual recalibration process (e.g. via ServerView RAID Manager). Note: Do not interrupt the charging process by reboots or shutdowns. 2) If problem persists replace BBU."
    --#STATE           OPERATIONAL
    ::= 10015

-- EVT_BATTERY_NEEDS_RECONDITION

svrTrapBatteryNeedsRecondition TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU needs reconditioning."
    --#TYPE            "BBU needs reconditioning"
    --#SUMMARY         "Adapter %s: BBU needs reconditioning (Server %s)"
    --#ARGUMENTS       { 2, 0 }
    --#SEVERITY        MINOR
    --#TIMEINDEX       1
    --#HELP            "Note: By default BBU recalibration is automatically initiated every 30 days. 1) If scheduled BBU recalibration is disabled initiate manual recalibration process (e.g. via ServerView RAID Manager)."
    --#STATE           OPERATIONAL
    ::= 10016

-- EVT_SCSI_SENSE_DATA

svrTrapSCSISenseAvailable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SCSI sense data available."
    --#TYPE            "SCSI sense data available"
    --#SUMMARY         "Adapter %s: SCSI sense data on disk (%s) available: %s (Server %s)"
    --#ARGUMENTS       { 2, 3, 4, 0 }
    --#SEVERITY        INFORMATIONAL
    --#TIMEINDEX       1
    --#HELP            ""
    --#STATE           OPERATIONAL
    ::= 10017

-- EVT_ASYNCHRONOUS_COMMAND_COMPLETED

svrTrapAsyncCommandCompleted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Asynchronous command finished."
    --#TYPE            "Asynchronous command finished"
    --#SUMMARY         "Adapter %s: Asynchronous command finished (Server %s)"
    --#ARGUMENTS       { 2, 0 }
    --#SEVERITY        INFORMATIONAL
    --#TIMEINDEX       1
    --#HELP            ""
    --#STATE           OPERATIONAL
    ::= 10018

-- EVT_ADAPTER_PAUSED

svrTrapAdapterPaused TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter suspended."
    --#TYPE            "Adapter suspended"
    --#SUMMARY         "Adapter %s suspended (Server %s)"
    --#ARGUMENTS       { 2, 0 }
    --#SEVERITY        INFORMATIONAL
    --#TIMEINDEX       1
    --#HELP            ""
    --#STATE           NONOPERATIONAL
    ::= 10019

-- EVT_ADAPTER_CONTINUED

svrTrapAdapterContinued TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter resumed."
    --#TYPE            "Adapter resumed"
    --#SUMMARY         "Adapter %s resumed (Server %s)"
    --#ARGUMENTS       { 2, 0 }
    --#SEVERITY        INFORMATIONAL
    --#TIMEINDEX       1
    --#HELP            ""
    --#STATE           OPERATIONAL
    ::= 10020

-- EVT_DISK_ONLINE

svrTrapPDMarkedOnline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk marked online."
    --#TYPE            "Disk marked online"
    --#SUMMARY         "Adapter %s: Disk (%s) marked online (Server %s)"
    --#ARGUMENTS       { 2, 3, 0 }
    --#SEVERITY        INFORMATIONAL
    --#TIMEINDEX       1
    --#HELP            ""
    --#STATE           OPERATIONAL
    ::= 10021

-- EVT_DISK_OFFLINE

svrTrapPDMarkedOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk marked offline."
    --#TYPE            "Disk marked offline"
    --#SUMMARY         "Adapter %s: Disk (%s) marked offline (Server %s)"
    --#ARGUMENTS       { 2, 3, 0 }
    --#SEVERITY        CRITICAL
    --#TIMEINDEX       1
    --#HELP            "Note: Only informational if affected disk was manually set offline otherwise: 1) If offline disk is member of an array initiate a rebuild to the offline disk. 2) If problem persists replace affected disk."
    --#STATE           NONOPERATIONAL
    ::= 10022

-- EVT_DISK_TIME_OUT

svrTrapPDTimedOut TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk timed out."
    --#TYPE            "Disk timed out"
    --#SUMMARY         "Adapter %s: Disk (%s) timed out (Server %s)"
    --#ARGUMENTS       { 2, 3, 0 }
    --#SEVERITY        MAJOR
    --#TIMEINDEX       1
    --#HELP            "Note: In general additional error messages should occur. If there are no other actions defined call your local Fujitsu Helpdesk."
    --#STATE           OPERATIONAL
    ::= 10023

-- EVT_GLOBAL_HOTSPARE_CREATED

svrTrapPDCreatedGlobalHotspare TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Global hot spare created on disk."
    --#TYPE            "Global hot spare created on disk"
    --#SUMMARY         "Adapter %s: Global hot spare created on disk (%s) (Server %s)"
    --#ARGUMENTS       { 2, 3, 0 }
    --#SEVERITY        INFORMATIONAL
    --#TIMEINDEX       1
    --#HELP            ""
    --#STATE           OPERATIONAL
    ::= 10024

-- EVT_GLOBAL_HOTSPARE_DELETED

svrTrapPDDeletedGlobalHotspare TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Global hot spare deleted on disk."
    --#TYPE            "Global hot spare deleted on disk"
    --#SUMMARY         "Adapter %s: Global hot spare deleted on disk (%s) (Server %s)"
    --#ARGUMENTS       { 2, 3, 0 }
    --#SEVERITY        MINOR
    --#TIMEINDEX       1
    --#HELP            "For information only."
    --#STATE           OPERATIONAL
    ::= 10025

-- EVT_DEDICATED_HOTSPARE_CREATED

svrTrapPDCreatedDedicatedHotspare TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Dedicated hot spare created on disk."
    --#TYPE            "Dedicated hot spare created on disk"
    --#SUMMARY         "Adapter %s: Dedicated hot spare created on disk (%s) (Server %s)"
    --#ARGUMENTS       { 2, 3, 0 }
    --#SEVERITY        INFORMATIONAL
    --#TIMEINDEX       1
    --#HELP            ""
    --#STATE           OPERATIONAL
    ::= 10026

-- EVT_DEDICATED_HOTSPARE_DELETED

svrTrapPDDeletedDedicatedHotspare TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Dedicated hot spare deleted on disk."
    --#TYPE            "Dedicated hot spare deleted on disk"
    --#SUMMARY         "Adapter %s: Dedicated hot spare deleted on disk (%s) (Server %s)"
    --#ARGUMENTS       { 2, 3, 0 }
    --#SEVERITY        MINOR
    --#TIMEINDEX       1
    --#HELP            "For information only."
    --#STATE           OPERATIONAL
    ::= 10027

-- EVT_DISK_AVAILABLE

svrTrapPDMarkedAvailable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk marked available."
    --#TYPE            "Disk marked available"
    --#SUMMARY         "Adapter %s: Disk (%s) marked available (Server %s)"
    --#ARGUMENTS       { 2, 3, 0 }
    --#SEVERITY        INFORMATIONAL
    --#TIMEINDEX       1
    --#HELP            ""
    --#STATE           OPERATIONAL
    ::= 10028

-- EVT_DISK_REBUILDING

svrTrapPDRebuildStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild on disk started."
    --#TYPE            "Rebuild on disk started"
    --#SUMMARY         "Adapter %s: Rebuild on disk (%s) started (Server %s)"
    --#ARGUMENTS       { 2, 3, 0 }
    --#SEVERITY        INFORMATIONAL
    --#TIMEINDEX       1
    --#HELP            ""
    --#STATE           DEGRADED
    ::= 10029

-- EVT_DISK_REBUILD_FAILED

svrTrapPDRebuildFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild on disk failed."
    --#TYPE            "Rebuild on disk failed"
    --#SUMMARY         "Adapter %s: Rebuild on disk (%s) failed (Server %s)"
    --#ARGUMENTS       { 2, 3, 0 }
    --#SEVERITY        MAJOR
    --#TIMEINDEX       1
    --#HELP            "1) Manually initiate a second rebuild (e.g. via ServerView RAID Manager). 2) If problem persists replace affected disk."
    --#STATE           DEGRADED
    ::= 10030

-- EVT_DISK_BAD_BLOCK

svrTrapPDBadBlockDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block on disk detected."
    --#TYPE            "Bad block on disk detected"
    --#SUMMARY         "Adapter %s: Bad block on disk (%s) LBA %s detected (Server %s)"
    --#ARGUMENTS       { 2, 3, 4, 0 }
    --#SEVERITY        MAJOR
    --#TIMEINDEX       1
    --#HELP            "Replace affected disk."
    --#STATE           DEGRADED
    ::= 10031

-- EVT_PNPADD

svrTrapNewPDDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "New disk detected."
    --#TYPE            "New disk detected"
    --#SUMMARY         "Adapter %s: New disk (%s) detected (Server %s)"
    --#ARGUMENTS       { 2, 3, 0 }
    --#SEVERITY        INFORMATIONAL
    --#TIMEINDEX       1
    --#HELP            ""
    --#STATE           OPERATIONAL
    ::= 10032

-- EVT_PNPREMOVE

svrTrapPDRemoved TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk removed."
    --#TYPE            "Disk removed"
    --#SUMMARY         "Adapter %s: Disk (%s) removed (Server %s)"
    --#ARGUMENTS       { 2, 3, 0 }
    --#SEVERITY        MINOR
    --#TIMEINDEX       1
    --#HELP            "Note: Only informational if affected disk has been removed otherwise: 1) Unplug affected disk, wait 30 seconds, reinsert it. 2) Replace affected disk. 3) Replace affected backplane or the data cable."
    --#STATE           OPERATIONAL
    ::= 10033

-- EVT_BAD_SECTOR_CLEARED

svrTrapPDBadSectorLogEntryCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad sector log entry on disk cleared."
    --#TYPE            "Bad sector log entry on disk cleared"
    --#SUMMARY         "Adapter %s: Bad sector log entry on disk (%s) cleared (Server %s)"
    --#ARGUMENTS       { 2, 3, 0 }
    --#SEVERITY        INFORMATIONAL
    --#TIMEINDEX       1
    --#HELP            ""
    --#STATE           OPERATIONAL
    ::= 10034

-- EVT_BAD_SECTOR_UPDATED

svrTrapPDBadSectorLogUpdated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad sector log on disk updated."
    --#TYPE            "Bad sector log on disk updated"
    --#SUMMARY         "Adapter %s: Bad sector log on disk (%s) updated (Server %s)"
    --#ARGUMENTS       { 2, 3, 0 }
    --#SEVERITY        INFORMATIONAL
    --#TIMEINDEX       1
    --#HELP            ""
    --#STATE           OPERATIONAL
    ::= 10035

-- EVT_BAD_SECTOR

svrTrapPDBadSectorDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad sector on disk detected."
    --#TYPE            "Bad sector on disk detected"
    --#SUMMARY         "Adapter %s: Bad sector on disk (%s) detected (Server %s)"
    --#ARGUMENTS       { 2, 3, 0 }
    --#SEVERITY        MAJOR
    --#TIMEINDEX       1
    --#HELP            "Replace affected disk."
    --#STATE           DEGRADED
    ::= 10036

-- EVT_COD_ERROR

svrTrapPDCODIOError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "COD I/O error on disk."
    --#TYPE            "COD I/O error on disk"
    --#SUMMARY         "Adapter %s: COD I/O error on disk (%s) (Server %s)"
    --#ARGUMENTS       { 2, 3, 0 }
    --#SEVERITY        MAJOR
    --#TIMEINDEX       1
    --#HELP            "1) Manually initiate a rebuild (e.g. via ServerView RAID Manager) of affected disk. 2) If problem persists replace affected disk."
    --#STATE           OPERATIONAL
    ::= 10037

-- EVT_TASK_ERROR

svrTrapPDErrorDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Error on disk detected."
    --#TYPE            "Error on disk detected"
    --#SUMMARY         "Adapter %s: Error on disk (%s) detected (Server %s)"
    --#ARGUMENTS       { 2, 3, 0 }
    --#SEVERITY        MAJOR
    --#TIMEINDEX       1
    --#HELP            "Replace affected disk."
    --#STATE           OPERATIONAL
    ::= 10038

-- EVT_RESET_CHANNEL

svrTrapChannelReset TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Channel was reset."
    --#TYPE            "Channel was reset"
    --#SUMMARY         "Adapter %s: Channel %s was reset (Server %s)"
    --#ARGUMENTS       { 2, 3, 0 }
    --#SEVERITY        INFORMATIONAL
    --#TIMEINDEX       1
    --#HELP            ""
    --#STATE           OPERATIONAL
    ::= 10039

-- EVT_IO_RETRY

svrTrapPDRetryIO TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Retry I/O on disk."
    --#TYPE            "Retry I/O on disk"
    --#SUMMARY         "Adapter %s: Retry I/O on disk (%s) (Server %s)"
    --#ARGUMENTS       { 2, 3, 0 }
    --#SEVERITY        MAJOR
    --#TIMEINDEX       1
    --#HELP            "If the problem occurs repeatedly replace affected disk."
    --#STATE           OPERATIONAL
    ::= 10040

-- EVT_ECC_ERROR

svrTrapPDECCError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "ECC error on disk."
    --#TYPE            "ECC error on disk"
    --#SUMMARY         "Adapter %s: ECC error on disk (%s) (Server %s)"
    --#ARGUMENTS       { 2, 3, 0 }
    --#SEVERITY        MAJOR
    --#TIMEINDEX       1
    --#HELP            "If the problem occurs repeatedly replace affected disk."
    --#STATE           OPERATIONAL
    ::= 10041

-- EVT_WRITE_MODE_SWITCH

svrTrapAdapterWriteModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write mode changed."
    --#TYPE            "Write mode changed"
    --#SUMMARY         "Adapter %s: Write modes changed (Server %s)"
    --#ARGUMENTS       { 2, 0 }
    --#SEVERITY        INFORMATIONAL
    --#TIMEINDEX       1
    --#HELP            ""
    --#STATE           OPERATIONAL
    ::= 10042

-- EVT_MEDIA_ERROR

svrTrapPDMediaError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Media error on disk."
    --#TYPE            "Media error on disk"
    --#SUMMARY         "Adapter %s: Media error on disk (%s) (Server %s)"
    --#ARGUMENTS       { 2, 3, 0 }
    --#SEVERITY        MAJOR
    --#TIMEINDEX       1
    --#HELP            "Replace affected disk."
    --#STATE           OPERATIONAL
    ::= 10043

-- EVT_SMART_WARNING

svrTrapPDSMARTWarning TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SMART warning on disk."
    --#TYPE            "SMART warning on disk"
    --#SUMMARY         "Adapter %s: SMART warning on disk (%s) (Server %s)"
    --#ARGUMENTS       { 2, 3, 0 }
    --#SEVERITY        MINOR
    --#TIMEINDEX       1
    --#HELP            "Note: Disk reports a prefailure. The affected disk might fail soon. 1) Replace the disk during next maintenance."
    --#STATE           OPERATIONAL
    ::= 10044

-- EVT_SMART_ERROR

svrTrapPDSMARTError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SMART error on disk."
    --#TYPE            "SMART error on disk"
    --#SUMMARY         "Adapter %s: SMART error on disk (%s) (Server %s)"
    --#ARGUMENTS       { 2, 3, 0 }
    --#SEVERITY        MINOR
    --#TIMEINDEX       1
    --#HELP            "Replace affected disk."
    --#STATE           OPERATIONAL
    ::= 10045

-- EVT_SWAP_BAD_SWAP

svrTrapEnclosureBadPDInserted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad disk inserted in enclosure."
    --#TYPE            "Bad disk inserted in enclosure"
    --#SUMMARY         "Adapter %s: Bad disk inserted in enclosure %s (Server %s)"
    --#ARGUMENTS       { 2, 3, 0 }
    --#SEVERITY        MAJOR
    --#TIMEINDEX       1
    --#HELP            "Replace affected disk."
    --#STATE           NONOPERATIONAL
    ::= 10046

-- EVT_SWAP_POWER_DOWN

svrTrapEnclosurePoweredDown TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure powered down."
    --#TYPE            "Enclosure powered down"
    --#SUMMARY         "Adapter %s: Enclosure %s powered down (Server %s)"
    --#ARGUMENTS       { 2, 3, 0 }
    --#SEVERITY        MAJOR
    --#TIMEINDEX       1
    --#HELP            "If this error message is not a result of a planned power off of the external storage subsystem: 1) Check the power cable(s). 2) Check the mains voltage. 3) Replace affected power supply(s)."
    --#STATE           NONOPERATIONAL
    ::= 10047

-- EVT_SWAP_POWER_UP

svrTrapEnclosurePoweredUp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure powered up."
    --#TYPE            "Enclosure powered up"
    --#SUMMARY         "Adapter %s: Enclosure %s powered up (Server %s)"
    --#ARGUMENTS       { 2, 3, 0 }
    --#SEVERITY        INFORMATIONAL
    --#TIMEINDEX       1
    --#HELP            ""
    --#STATE           OPERATIONAL
    ::= 10048

-- EVT_FAN_FAILED

svrTrapEnclosureFanFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Fan in enclosure failed."
    --#TYPE            "Fan in enclosure failed"
    --#SUMMARY         "Adapter %s: Fan %s in enclosure %s failed (Server %s)"
    --#ARGUMENTS       { 2, 3, 4, 0 }
    --#SEVERITY        CRITICAL
    --#TIMEINDEX       1
    --#HELP            "Replace affected fan within the external storage subsystem."
    --#STATE           OPERATIONAL
    ::= 10049

-- EVT_TEMPERATURE_SENSOR_ALERT

svrTrapEnclosureTempSensAboveThreshold TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Temperature sensor in enclosure above threshold."
    --#TYPE            "Temperature sensor in enclosure above threshold"
    --#SUMMARY         "Adapter %s: Temperature sensor %s in enclosure %s above threshold (Server %s)"
    --#ARGUMENTS       { 2, 3, 4, 0 }
    --#SEVERITY        MAJOR
    --#TIMEINDEX       1
    --#HELP            "1) Check installation of all air flow channels, closed housing, and unblocked louvers. 2) Check environmental temperature."
    --#STATE           OPERATIONAL
    ::= 10050

-- EVT_POWER_SUPPLY_FAILED

svrTrapEnclosurePowerSupplyFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power supply in enclosure failed."
    --#TYPE            "Power supply in enclosure failed"
    --#SUMMARY         "Adapter %s: Power supply %s in enclosure %s failed (Server %s)"
    --#ARGUMENTS       { 2, 3, 4, 0 }
    --#SEVERITY        CRITICAL
    --#TIMEINDEX       1
    --#HELP            "1) Check the power cable. 2) Check the mains voltage. 3) Replace affected power supply."
    --#STATE           OPERATIONAL
    ::= 10051

-- EVT_POWER_SUPPLY_FAILED_3

svrTrapPD33VPowerFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "3.3V power failed for disk."
    --#TYPE            "3.3V power failed for disk"
    --#SUMMARY         "Adapter %s: 3.3V power failed for disk (%s) (Server %s)"
    --#ARGUMENTS       { 2, 3, 0 }
    --#SEVERITY        CRITICAL
    --#TIMEINDEX       1
    --#HELP            "1) Check whether all cables are correctly connected to the disk backplane connectors. 2) Replace affected disk."
    --#STATE           OPERATIONAL
    ::= 10052

-- EVT_POWER_SUPPLY_FAILED_5

svrTrapPD50VPowerFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "5.0V power failed for disk."
    --#TYPE            "5.0V power failed for disk"
    --#SUMMARY         "Adapter %s: 5.0V power failed for disk (%s) (Server %s)"
    --#ARGUMENTS       { 2, 3, 0 }
    --#SEVERITY        CRITICAL
    --#TIMEINDEX       1
    --#HELP            "1) Check whether all cables are correctly connected to the disk backplane connectors. 2) Replace affected disk."
    --#STATE           OPERATIONAL
    ::= 10053

-- EVT_POWER_SUPPLY_FAILED_12

svrTrapPD12VPowerFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "12V power failed for disk."
    --#TYPE            "12V power failed for disk"
    --#SUMMARY         "Adapter %s: 12V power failed for disk (%s) (Server %s)"
    --#ARGUMENTS       { 2, 3, 0 }
    --#SEVERITY        CRITICAL
    --#TIMEINDEX       1
    --#HELP            "1) Check whether all cables are correctly connected to the disk backplane connectors. 2) Replace affected disk."
    --#STATE           NONOPERATIONAL
    ::= 10054

-- EVT_REBUILD_STARTED

svrTrapLDRebuildStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild started on logical drive."
    --#TYPE            "Rebuild started on logical drive"
    --#SUMMARY         "Adapter %s: Rebuild started on logical drive %s (Server %s)"
    --#ARGUMENTS       { 2, 3, 0 }
    --#SEVERITY        INFORMATIONAL
    --#TIMEINDEX       1
    --#HELP            ""
    --#STATE           DEGRADED
    ::= 10055

-- EVT_REBUILD_FINISHED

svrTrapLDRebuildFinished TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild finished on logical drive."
    --#TYPE            "Rebuild finished on logical drive"
    --#SUMMARY         "Adapter %s: Rebuild finished on logical drive %s (Server %s)"
    --#ARGUMENTS       { 2, 3, 0 }
    --#SEVERITY        INFORMATIONAL
    --#TIMEINDEX       1
    --#HELP            ""
    --#STATE           OPERATIONAL
    ::= 10056

-- EVT_REBUILD_FAILED

svrTrapLDRebuildFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild failed on logical drive."
    --#TYPE            "Rebuild failed on logical drive"
    --#SUMMARY         "Adapter %s: Rebuild failed on logical drive %s (Server %s)"
    --#ARGUMENTS       { 2, 3, 0 }
    --#SEVERITY        MAJOR
    --#TIMEINDEX       1
    --#HELP            "1) Manually initiate a second rebuild (e.g. via ServerView RAID Manager)."
    --#STATE           DEGRADED
    ::= 10057

-- EVT_REBUILD_CANCELED

svrTrapLDRebuildAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild aborted on logical drive."
    --#TYPE            "Rebuild aborted on logical drive"
    --#SUMMARY         "Adapter %s: Rebuild aborted on logical drive %s (Server %s)"
    --#ARGUMENTS       { 2, 3, 0 }
    --#SEVERITY        MINOR
    --#TIMEINDEX       1
    --#HELP            "Note: Rebuild was probably aborted by user. Attention: The affected RAID array is still degraded. 1) The rebuild should be started again as soon as possible."
    --#STATE           DEGRADED
    ::= 10058

-- EVT_REBUILD_PAUSED

svrTrapLDRebuildPaused TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild suspended on logical drive."
    --#TYPE            "Rebuild suspended on logical drive"
    --#SUMMARY         "Adapter %s: Rebuild suspended on logical drive %s (Server %s)"
    --#ARGUMENTS       { 2, 3, 0 }
    --#SEVERITY        INFORMATIONAL
    --#TIMEINDEX       1
    --#HELP            ""
    --#STATE           DEGRADED
    ::= 10059

-- EVT_CHECK_STARTED

svrTrapLDConCheckStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check started on logical drive."
    --#TYPE            "Consistency check started on logical drive"
    --#SUMMARY         "Adapter %s: Consistency check started on logical drive %s (Server %s)"
    --#ARGUMENTS       { 2, 3, 0 }
    --#SEVERITY        INFORMATIONAL
    --#TIMEINDEX       1
    --#HELP            ""
    --#STATE           OPERATIONAL
    ::= 10060

-- EVT_CHECK_FINISHED

svrTrapLDConCheckFinished TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check finished on logical drive."
    --#TYPE            "Consistency check finished on logical drive"
    --#SUMMARY         "Adapter %s: Consistency check finished on logical drive %s (Server %s)"
    --#ARGUMENTS       { 2, 3, 0 }
    --#SEVERITY        INFORMATIONAL
    --#TIMEINDEX       1
    --#HELP            ""
    --#STATE           OPERATIONAL
    ::= 10061

-- EVT_CHECK_FAILED

svrTrapLDConCheckFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check failed on logical drive."
    --#TYPE            "Consistency check failed on logical drive"
    --#SUMMARY         "Adapter %s: Consistency check failed on logical drive %s (Server %s)"
    --#ARGUMENTS       { 2, 3, 0 }
    --#SEVERITY        MAJOR
    --#TIMEINDEX       1
    --#HELP            "Failure happens only if a disk out of the logical drive failed. 1) Check state of logical drive. 2) If logical drive is not operational, check state of affected disk. 3) Check for additional error messages for affected disk."
    --#STATE           OPERATIONAL
    ::= 10062

-- EVT_CHECK_CANCELED

svrTrapLDConCheckAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check aborted on logical drive."
    --#TYPE            "Consistency check aborted on logical drive"
    --#SUMMARY         "Adapter %s: Consistency check aborted on logical drive %s (Server %s)"
    --#ARGUMENTS       { 2, 3, 0 }
    --#SEVERITY        MINOR
    --#TIMEINDEX       1
    --#HELP            "Note: Consistency check was probably aborted by user. 1) The consistency check should be started again as soon as possible."
    --#STATE           OPERATIONAL
    ::= 10063

-- EVT_CHECK_PAUSED

svrTrapLDConCheckPaused TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check suspended on logical drive."
    --#TYPE            "Consistency check suspended on logical drive"
    --#SUMMARY         "Adapter %s: Consistency check suspended on logical drive %s (Server %s)"
    --#ARGUMENTS       { 2, 3, 0 }
    --#SEVERITY        INFORMATIONAL
    --#TIMEINDEX       1
    --#HELP            ""
    --#STATE           OPERATIONAL
    ::= 10064

-- EVT_CHECK_STARTED_UNINITIALIZED

svrTrapLDUninitialisedConCheckStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check started on uninitialized logical drive."
    --#TYPE            "Consistency check started on uninitialized logical drive"
    --#SUMMARY         "Adapter %s: Consistency check started on uninitialized logical drive %s (Server %s)"
    --#ARGUMENTS       { 2, 3, 0 }
    --#SEVERITY        INFORMATIONAL
    --#TIMEINDEX       1
    --#HELP            ""
    --#STATE           OPERATIONAL
    ::= 10065

-- EVT_CHECK_ERROR

svrTrapLDConCheckFinishedWithErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check finished with errors on logical drive."
    --#TYPE            "Consistency check finished with errors on logical drive"
    --#SUMMARY         "Adapter %s: Consistency check finished with errors on logical drive %s (Server %s)"
    --#ARGUMENTS       { 2, 3, 0 }
    --#SEVERITY        MAJOR
    --#TIMEINDEX       1
    --#HELP            "1) Manually initiate second consistency check (MDC). 2) If problem persists backup data from affected logical drive. 3) Delete and recreate affected logical drive. 4) Restore data."
    --#STATE           OPERATIONAL
    ::= 10066

-- EVT_INCONSISTENT_LBA

svrTrapLDInconsistencyDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Inconsistency detected on logical drive."
    --#TYPE            "Inconsistency detected on logical drive"
    --#SUMMARY         "Adapter %s: Inconsistency detected on logical drive %s at LBA %s (Server %s)"
    --#ARGUMENTS       { 2, 3, 4, 0 }
    --#SEVERITY        MAJOR
    --#TIMEINDEX       1
    --#HELP            "Check if logical drive is initialized. If initialized check the following: 1) Backup your data. 2) Start a consistency check with fix. 3) Compare backup data with data on logical drive. 4) If different (data lost), restore last good data."
    --#STATE           OPERATIONAL
    ::= 10067

-- EVT_MIGRATION_STARTED

svrTrapLDMigrationStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Migration started on logical drive."
    --#TYPE            "Migration started on logical drive"
    --#SUMMARY         "Adapter %s: Migration started on logical drive %s (Server %s)"
    --#ARGUMENTS       { 2, 3, 0 }
    --#SEVERITY        INFORMATIONAL
    --#TIMEINDEX       1
    --#HELP            ""
    --#STATE           OPERATIONAL
    ::= 10068

-- EVT_MIGRATION_FINISHED

svrTrapLDMigrationFinished TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Migration finished on logical drive."
    --#TYPE            "Migration finished on logical drive"
    --#SUMMARY         "Adapter %s: Migration finished on logical drive %s (Server %s)"
    --#ARGUMENTS       { 2, 3, 0 }
    --#SEVERITY        INFORMATIONAL
    --#TIMEINDEX       1
    --#HELP            ""
    --#STATE           OPERATIONAL
    ::= 10069

-- EVT_MIGRATION_FAILED

svrTrapLDMigrationFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Migration failed on logical drive."
    --#TYPE            "Migration failed on logical drive"
    --#SUMMARY         "Adapter %s: Migration failed on logical drive %s (Server %s)"
    --#ARGUMENTS       { 2, 3, 0 }
    --#SEVERITY        MAJOR
    --#TIMEINDEX       1
    --#HELP            "Note: The logical drive is failed (multi dead). 1) Replace broken drives. 2) Create new configuration and restore last good data."
    --#STATE           OPERATIONAL
    ::= 10070

-- EVT_MIGRATION_ABORTED

svrTrapLDMigrationAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Migration aborted on logical drive."
    --#TYPE            "Migration aborted on logical drive"
    --#SUMMARY         "Adapter %s: Migration aborted on logical drive %s (Server %s)"
    --#ARGUMENTS       { 2, 3, 0 }
    --#SEVERITY        MINOR
    --#TIMEINDEX       1
    --#HELP            "Note: Migration was probably aborted by user. For information only."
    --#STATE           OPERATIONAL
    ::= 10071

-- EVT_PATROL_READ_STARTED

svrTrapAdapterPatrolReadStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read started."
    --#TYPE            "Patrol Read started"
    --#SUMMARY         "Adapter %s: Patrol Read started (Server %s)"
    --#ARGUMENTS       { 2, 0 }
    --#SEVERITY        INFORMATIONAL
    --#TIMEINDEX       1
    --#HELP            ""
    --#STATE           OPERATIONAL
    ::= 10072

-- EVT_PATROL_READ_FINISHED

svrTrapAdapterPatrolReadCompleted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read finished."
    --#TYPE            "Patrol Read finished"
    --#SUMMARY         "Adapter %s: Patrol Read finished (Server %s)"
    --#ARGUMENTS       { 2, 0 }
    --#SEVERITY        INFORMATIONAL
    --#TIMEINDEX       1
    --#HELP            ""
    --#STATE           OPERATIONAL
    ::= 10073

-- EVT_PATROL_READ_CANCELED

svrTrapAdapterPatrolReadAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read aborted."
    --#TYPE            "Patrol Read aborted"
    --#SUMMARY         "Adapter %s: Patrol Read aborted (Server %s)"
    --#ARGUMENTS       { 2, 0 }
    --#SEVERITY        MINOR
    --#TIMEINDEX       1
    --#HELP            "Note: Patrol read was probably aborted by user. For information only."
    --#STATE           OPERATIONAL
    ::= 10074

-- EVT_PATROL_READ_STOPPED

svrTrapAdapterPatrolReadStopped TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read stopped."
    --#TYPE            "Patrol Read stopped"
    --#SUMMARY         "Adapter %s: Patrol Read stopped (Server %s)"
    --#ARGUMENTS       { 2, 0 }
    --#SEVERITY        INFORMATIONAL
    --#TIMEINDEX       1
    --#HELP            ""
    --#STATE           OPERATIONAL
    ::= 10075

-- EVT_PATROL_READ_PAUSED

svrTrapAdapterPatrolReadPaused TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read suspended."
    --#TYPE            "Patrol Read suspended"
    --#SUMMARY         "Adapter %s: Patrol Read suspended (Server %s)"
    --#ARGUMENTS       { 2, 0 }
    --#SEVERITY        INFORMATIONAL
    --#TIMEINDEX       1
    --#HELP            ""
    --#STATE           OPERATIONAL
    ::= 10076

-- EVT_PATROL_READ_CONTINUED

svrTrapAdapterPatrolReadContinued TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read resumed."
    --#TYPE            "Patrol Read resumed"
    --#SUMMARY         "Adapter %s: Patrol Read resumed (Server %s)"
    --#ARGUMENTS       { 2, 0 }
    --#SEVERITY        INFORMATIONAL
    --#TIMEINDEX       1
    --#HELP            ""
    --#STATE           OPERATIONAL
    ::= 10077

-- EVT_LOGICALDRIVE_DEGRADED

svrTrapLDDegraded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive degraded."
    --#TYPE            "Logical drive degraded"
    --#SUMMARY         "Adapter %s: Logical drive %s degraded (Server %s)"
    --#ARGUMENTS       { 2, 3, 0 }
    --#SEVERITY        MAJOR
    --#TIMEINDEX       1
    --#HELP            "1) Manually initiate a rebuild of affected disk (e.g. via ServerView RAID Manager). 2) If problem persists replace affected disk."
    --#STATE           DEGRADED
    ::= 10078

-- EVT_LOGICALDRIVE_FAILED

svrTrapLDFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive failed."
    --#TYPE            "Logical drive failed"
    --#SUMMARY         "Adapter %s: Logical drive %s failed (Server %s)"
    --#ARGUMENTS       { 2, 3, 0 }
    --#SEVERITY        CRITICAL
    --#TIMEINDEX       1
    --#HELP            "Note: Sometimes it is possible to recover without data loss. Further investigation is needed."
    --#STATE           NONOPERATIONAL
    ::= 10079

-- EVT_LOGICALDRIVE_CREATED

svrTrapLDCreated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive created."
    --#TYPE            "Logical drive created"
    --#SUMMARY         "Adapter %s: Logical drive %s created (Server %s)"
    --#ARGUMENTS       { 2, 3, 0 }
    --#SEVERITY        INFORMATIONAL
    --#TIMEINDEX       1
    --#HELP            ""
    --#STATE           OPERATIONAL
    ::= 10080

-- EVT_LOGICALDRIVE_DELETED

svrTrapLDDeleted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive deleted."
    --#TYPE            "Logical drive deleted"
    --#SUMMARY         "Adapter %s: Logical drive %s deleted (Server %s)"
    --#ARGUMENTS       { 2, 3, 0 }
    --#SEVERITY        MINOR
    --#TIMEINDEX       1
    --#HELP            "For information only."
    --#STATE           OPERATIONAL
    ::= 10081

-- EVT_LOGICALDRIVE_OPERATIONAL

svrTrapLDOperational TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive operational."
    --#TYPE            "Logical drive operational"
    --#SUMMARY         "Adapter %s: Logical drive %s operational (Server %s)"
    --#ARGUMENTS       { 2, 3, 0 }
    --#SEVERITY        INFORMATIONAL
    --#TIMEINDEX       1
    --#HELP            ""
    --#STATE           OPERATIONAL
    ::= 10082

-- EVT_LOGICALDRIVE_DISKERROR

svrTrapLDPDError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive error on disk."
    --#TYPE            "Logical drive error on disk"
    --#SUMMARY         "Adapter %s: Logical drive %s: Error on disk (%s) (Server %s)"
    --#ARGUMENTS       { 2, 3, 4, 0 }
    --#SEVERITY        MAJOR
    --#TIMEINDEX       1
    --#HELP            "Replace affected disk."
    --#STATE           OPERATIONAL
    ::= 10083

-- EVT_LOGICALDRIVE_BAD_BLOCK

svrTrapLDBadBlockDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive bad block detected."
    --#TYPE            "Logical drive bad block detected"
    --#SUMMARY         "Adapter %s: Logical drive %s: Bad block at LBA %s detected (Server %s)"
    --#ARGUMENTS       { 2, 3, 4, 0 }
    --#SEVERITY        MAJOR
    --#TIMEINDEX       1
    --#HELP            "1) Try to rewrite data. 2) If problem persists replace affected disk."
    --#STATE           OPERATIONAL
    ::= 10084

-- EVT_INITIALIZATION_STARTED

svrTrapLDInitStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization started on logical drive."
    --#TYPE            "Initialization started on logical drive"
    --#SUMMARY         "Adapter %s: Initialization started on logical drive %s (Server %s)"
    --#ARGUMENTS       { 2, 3, 0 }
    --#SEVERITY        INFORMATIONAL
    --#TIMEINDEX       1
    --#HELP            ""
    --#STATE           OPERATIONAL
    ::= 10085

-- EVT_INITIALIZATION_FINISHED

svrTrapLDInitFinished TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization finished on logical drive."
    --#TYPE            "Initialization finished on logical drive"
    --#SUMMARY         "Adapter %s: Initialization finished on logical drive %s (Server %s)"
    --#ARGUMENTS       { 2, 3, 0 }
    --#SEVERITY        INFORMATIONAL
    --#TIMEINDEX       1
    --#HELP            ""
    --#STATE           OPERATIONAL
    ::= 10086

-- EVT_BGI_STARTED

svrTrapLDBackInitStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI started on logical drive."
    --#TYPE            "BGI started on logical drive"
    --#SUMMARY         "Adapter %s: BGI started on logical drive %s (Server %s)"
    --#ARGUMENTS       { 2, 3, 0 }
    --#SEVERITY        INFORMATIONAL
    --#TIMEINDEX       1
    --#HELP            ""
    --#STATE           OPERATIONAL
    ::= 10087

-- EVT_BGI_FINISHED

svrTrapLDBackInitFinished TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI finished on logical drive."
    --#TYPE            "BGI finished on logical drive"
    --#SUMMARY         "Adapter %s: BGI finished on logical drive %s (Server %s)"
    --#ARGUMENTS       { 2, 3, 0 }
    --#SEVERITY        INFORMATIONAL
    --#TIMEINDEX       1
    --#HELP            ""
    --#STATE           OPERATIONAL
    ::= 10088

-- EVT_BGI_CANCELED

svrTrapLDBackInitCanceled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI canceled on logical drive."
    --#TYPE            "BGI canceled on logical drive"
    --#SUMMARY         "Adapter %s: BGI canceled on logical drive %s (Server %s)"
    --#ARGUMENTS       { 2, 3, 0 }
    --#SEVERITY        MINOR
    --#TIMEINDEX       1
    --#HELP            "Background initialization (BGI) resumes automatically after a certain period of time. For information only."
    --#STATE           OPERATIONAL
    ::= 10089

-- EVT_INITIALIZATION_CANCELED

svrTrapLDInitCanceled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization canceled on logical drive."
    --#TYPE            "Initialization canceled on logical drive"
    --#SUMMARY         "Adapter %s: Initialization canceled on logical drive %s (Server %s)"
    --#ARGUMENTS       { 2, 3, 0 }
    --#SEVERITY        MINOR
    --#TIMEINDEX       1
    --#HELP            "For information only."
    --#STATE           OPERATIONAL
    ::= 10090

-- EVT_DRIVELETTER_CHANGED

svrTrapLDDriveLetterChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Drive letter changed for logical drive."
    --#TYPE            "Drive letter changed for logical drive"
    --#SUMMARY         "Adapter %s: Drive letter changed for logical drive %s (Server %s)"
    --#ARGUMENTS       { 2, 3, 0 }
    --#SEVERITY        INFORMATIONAL
    --#TIMEINDEX       1
    --#HELP            ""
    --#STATE           OPERATIONAL
    ::= 10091

-- EVT_HOTSPARE_OPERATION_STARTED

svrTrapLDHotspareOperationStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hot spare operation on logical drive started."
    --#TYPE            "Hot spare operation on logical drive started"
    --#SUMMARY         "Adapter %s: Hot spare operation on logical drive %s started (Server %s)"
    --#ARGUMENTS       { 2, 3, 0 }
    --#SEVERITY        INFORMATIONAL
    --#TIMEINDEX       1
    --#HELP            ""
    --#STATE           OPERATIONAL
    ::= 10092

-- EVT_HOTSPARE_OPERATION_FAILED

svrTrapLDHotspareOperationFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hot spare operation on logical drive failed."
    --#TYPE            "Hot spare operation on logical drive failed"
    --#SUMMARY         "Adapter %s: Hot spare operation on logical drive %s failed (Server %s)"
    --#ARGUMENTS       { 2, 3, 0 }
    --#SEVERITY        MAJOR
    --#TIMEINDEX       1
    --#HELP            "1) Unplug affected disk, wait 30 seconds, reinsert it. 2) Replace affected disk."
    --#STATE           OPERATIONAL
    ::= 10093

-- EVT_TEMPORARY_OFFLINE

svrTrapLDForcedFromFailedToDegraded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive forced from failed to degraded."
    --#TYPE            "Logical drive forced from failed to degraded"
    --#SUMMARY         "Adapter %s: Logical drive %s forced from failed to degraded (Server %s)"
    --#ARGUMENTS       { 2, 3, 0 }
    --#SEVERITY        MAJOR
    --#TIMEINDEX       1
    --#HELP            "1) Temporary offline case. 2) Try to rebuild remaining defect drive."
    --#STATE           DEGRADED
    ::= 10094

-- EVT_ALARM_ENABLED

svrTrapAdapterAlarmEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Alarm enabled."
    --#TYPE            "Alarm enabled"
    --#SUMMARY         "Adapter %s: Alarm enabled (Server %s)"
    --#ARGUMENTS       { 2, 0 }
    --#SEVERITY        INFORMATIONAL
    --#TIMEINDEX       1
    --#HELP            ""
    --#STATE           OPERATIONAL
    ::= 10095

-- EVT_ALARM_DISABLED

svrTrapAdapterAlarmDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Alarm disabled."
    --#TYPE            "Alarm disabled"
    --#SUMMARY         "Adapter %s: Alarm disabled (Server %s)"
    --#ARGUMENTS       { 2, 0 }
    --#SEVERITY        MINOR
    --#TIMEINDEX       1
    --#HELP            "For information only."
    --#STATE           OPERATIONAL
    ::= 10096

-- EVT_AUTO_CHECK_ENABLED

svrTrapAdapterAutomaticCheckEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic inconsistency handling enabled."
    --#TYPE            "Automatic inconsistency handling enabled"
    --#SUMMARY         "Adapter %s: Automatic inconsistency handling enabled (Server %s)"
    --#ARGUMENTS       { 2, 0 }
    --#SEVERITY        INFORMATIONAL
    --#TIMEINDEX       1
    --#HELP            ""
    --#STATE           OPERATIONAL
    ::= 10097

-- EVT_AUTO_CHECK_DISABLED

svrTrapAdapterAutomaticCheckDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic inconsistency handling disabled."
    --#TYPE            "Automatic inconsistency handling disabled"
    --#SUMMARY         "Adapter %s: Automatic inconsistency handling disabled (Server %s)"
    --#ARGUMENTS       { 2, 0 }
    --#SEVERITY        INFORMATIONAL
    --#TIMEINDEX       1
    --#HELP            ""
    --#STATE           OPERATIONAL
    ::= 10098

-- EVT_CHECK_INTERVAL_CHANGED

svrTrapAdapterCheckIntervalChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic inconsistency handling Interval changed."
    --#TYPE            "Automatic inconsistency handling Interval changed"
    --#SUMMARY         "Adapter %s: Inconsistency handling interval changed (Server %s)"
    --#ARGUMENTS       { 2, 0 }
    --#SEVERITY        INFORMATIONAL
    --#TIMEINDEX       1
    --#HELP            ""
    --#STATE           OPERATIONAL
    ::= 10099

-- EVT_REBUILD_RATE_CHANGED

svrTrapAdapterRebuildRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild rate changed."
    --#TYPE            "Rebuild rate changed"
    --#SUMMARY         "Adapter %s: Rebuild rate changed (Server %s)"
    --#ARGUMENTS       { 2, 0 }
    --#SEVERITY        INFORMATIONAL
    --#TIMEINDEX       1
    --#HELP            ""
    --#STATE           OPERATIONAL
    ::= 10100

-- EVT_PATROLREAD_DISABLED

svrTrapAdapterPatrolReadDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read disabled."
    --#TYPE            "Patrol Read disabled"
    --#SUMMARY         "Adapter %s: Patrol Read disabled (Server %s)"
    --#ARGUMENTS       { 2, 0 }
    --#SEVERITY        INFORMATIONAL
    --#TIMEINDEX       1
    --#HELP            ""
    --#STATE           OPERATIONAL
    ::= 10101

-- EVT_PATROLREAD_AUTO

svrTrapAdapterPatrolReadAutomatic TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read set to automatic."
    --#TYPE            "Patrol Read set to automatic"
    --#SUMMARY         "Adapter %s: Patrol Read set to automatic (Server %s)"
    --#ARGUMENTS       { 2, 0 }
    --#SEVERITY        INFORMATIONAL
    --#TIMEINDEX       1
    --#HELP            ""
    --#STATE           OPERATIONAL
    ::= 10102

-- EVT_PATROLREAD_MANUAL

svrTrapAdapterPatrolReadManual TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read set to manual."
    --#TYPE            "Patrol Read set to manual"
    --#SUMMARY         "Adapter %s: Patrol Read set to manual (Server %s)"
    --#ARGUMENTS       { 2, 0 }
    --#SEVERITY        INFORMATIONAL
    --#TIMEINDEX       1
    --#HELP            ""
    --#STATE           OPERATIONAL
    ::= 10103

-- EVT_PATROLREAD_DELAY_CHANGED

svrTrapAdapterPatrolReadDelayChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read delay changed."
    --#TYPE            "Patrol Read delay changed"
    --#SUMMARY         "Adapter %s: Patrol Read delay changed (Server %s)"
    --#ARGUMENTS       { 2, 0 }
    --#SEVERITY        INFORMATIONAL
    --#TIMEINDEX       1
    --#HELP            ""
    --#STATE           OPERATIONAL
    ::= 10104

-- EVT_NORMAL_INITIALIZATION

svrTrapAdapterInitNormal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization set to normal."
    --#TYPE            "Initialization set to normal"
    --#SUMMARY         "Adapter %s: Initialization set to normal (Server %s)"
    --#ARGUMENTS       { 2, 0 }
    --#SEVERITY        INFORMATIONAL
    --#TIMEINDEX       1
    --#HELP            ""
    --#STATE           OPERATIONAL
    ::= 10105

-- EVT_FAST_INITIALIZATION

svrTrapAdapterInitFast TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization set to fast."
    --#TYPE            "Initialization set to fast"
    --#SUMMARY         "Adapter %s: Initialization set to fast (Server %s)"
    --#ARGUMENTS       { 2, 0 }
    --#SEVERITY        INFORMATIONAL
    --#TIMEINDEX       1
    --#HELP            ""
    --#STATE           OPERATIONAL
    ::= 10106

-- EVT_INITIATOR_ID_CHANGED

svrTrapAdapterInitiatorIDChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initiator ID changed."
    --#TYPE            "Initiator ID changed"
    --#SUMMARY         "Adapter %s: Initiator ID changed (Server %s)"
    --#ARGUMENTS       { 2, 0 }
    --#SEVERITY        INFORMATIONAL
    --#TIMEINDEX       1
    --#HELP            ""
    --#STATE           OPERATIONAL
    ::= 10107

-- EVT_AUTO_REBUILD_ENABLED

svrTrapAdapterAutomaticeRebuildEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic rebuild enabled."
    --#TYPE            "Automatic rebuild enabled"
    --#SUMMARY         "Adapter %s: Automatic rebuild enabled (Server %s)"
    --#ARGUMENTS       { 2, 0 }
    --#SEVERITY        INFORMATIONAL
    --#TIMEINDEX       1
    --#HELP            ""
    --#STATE           OPERATIONAL
    ::= 10108

-- EVT_AUTO_REBUILD_DISABLED

svrTrapAdapterAutomaticeRebuildDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic rebuild disabled."
    --#TYPE            "Automatic rebuild disabled"
    --#SUMMARY         "Adapter %s: Automatic rebuild disabled (Server %s)"
    --#ARGUMENTS       { 2, 0 }
    --#SEVERITY        INFORMATIONAL
    --#TIMEINDEX       1
    --#HELP            ""
    --#STATE           OPERATIONAL
    ::= 10109

-- EVT_NEW_DEVICE_AUTO

svrTrapAdapterNewDeviceAutomatic TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "New device set to automatic."
    --#TYPE            "New device set to automatic"
    --#SUMMARY         "Adapter %s: New device set to automatic (Server %s)"
    --#ARGUMENTS       { 2, 0 }
    --#SEVERITY        INFORMATIONAL
    --#TIMEINDEX       1
    --#HELP            ""
    --#STATE           OPERATIONAL
    ::= 10110

-- EVT_NEW_DEVICE_CTRL_M

svrTrapAdapterNewDeviceCTRLM TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "New device set to CTRL-M."
    --#TYPE            "New device set to CTRL-M"
    --#SUMMARY         "Adapter %s: New device set to CtrlM (Server %s)"
    --#ARGUMENTS       { 2, 0 }
    --#SEVERITY        INFORMATIONAL
    --#TIMEINDEX       1
    --#HELP            ""
    --#STATE           OPERATIONAL
    ::= 10111

-- EVT_MDC_RATE_CHANGED

svrTrapAdapterMDCRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC rate changed."
    --#TYPE            "MDC rate changed"
    --#SUMMARY         "Adapter %s: MDC rate changed (Server %s)"
    --#ARGUMENTS       { 2, 0 }
    --#SEVERITY        INFORMATIONAL
    --#TIMEINDEX       1
    --#HELP            ""
    --#STATE           OPERATIONAL
    ::= 10112

-- EVT_MDC_RATE_CHANGED_EX

svrTrapAdapterMDCRateChangedEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC rate changed."
    --#TYPE            "MDC rate changed"
    --#SUMMARY         "Adapter %s: MDC rate changed to %s percent (Server %s)"
    --#ARGUMENTS       { 2, 3, 0 }
    --#SEVERITY        INFORMATIONAL
    --#TIMEINDEX       1
    --#HELP            ""
    --#STATE           OPERATIONAL
    ::= 10113

-- EVT_BIOS_ENABLED

svrTrapAdapterBIOSEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BIOS enabled."
    --#TYPE            "BIOS enabled"
    --#SUMMARY         "Adapter %s: BIOS enabled (Server %s)"
    --#ARGUMENTS       { 2, 0 }
    --#SEVERITY        INFORMATIONAL
    --#TIMEINDEX       1
    --#HELP            ""
    --#STATE           OPERATIONAL
    ::= 10114

-- EVT_BIOS_DISABLED

svrTrapAdapterBIOSDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BIOS disabled."
    --#TYPE            "BIOS disabled"
    --#SUMMARY         "Adapter %s: BIOS disabled (Server %s)"
    --#ARGUMENTS       { 2, 0 }
    --#SEVERITY        INFORMATIONAL
    --#TIMEINDEX       1
    --#HELP            ""
    --#STATE           OPERATIONAL
    ::= 10115

-- EVT_STOP_ON_ERROR_ENABLED

svrTrapAdapterStopOnErrorEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BIOS stop on error enabled."
    --#TYPE            "BIOS stop on error enabled"
    --#SUMMARY         "Adapter %s: BIOS stop on error enabled (Server %s)"
    --#ARGUMENTS       { 2, 0 }
    --#SEVERITY        INFORMATIONAL
    --#TIMEINDEX       1
    --#HELP            ""
    --#STATE           OPERATIONAL
    ::= 10116

-- EVT_STOP_ON_ERROR_DISABLED

svrTrapAdapterStopOnErrorDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BIOS stop on error disabled."
    --#TYPE            "BIOS stop on error disabled"
    --#SUMMARY         "Adapter %s: BIOS stop on error disabled (Server %s)"
    --#ARGUMENTS       { 2, 0 }
    --#SEVERITY        INFORMATIONAL
    --#TIMEINDEX       1
    --#HELP            ""
    --#STATE           OPERATIONAL
    ::= 10117

-- EVT_DISK_WRITE_CACHE_ENABLED

svrTrapAdapterPDWriteCacheEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write cache on all disks enabled."
    --#TYPE            "Write cache on all disks enabled"
    --#SUMMARY         "Adapter %s: Write cache on all disks enabled (Server %s)"
    --#ARGUMENTS       { 2, 0 }
    --#SEVERITY        INFORMATIONAL
    --#TIMEINDEX       1
    --#HELP            ""
    --#STATE           OPERATIONAL
    ::= 10118

-- EVT_DISK_WRITE_CACHE_DISABLED

svrTrapAdapterPDWriteCacheDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write cache on all disks disabled."
    --#TYPE            "Write cache on all disks disabled"
    --#SUMMARY         "Adapter %s: Write cache on all disks disabled (Server %s)"
    --#ARGUMENTS       { 2, 0 }
    --#SEVERITY        INFORMATIONAL
    --#TIMEINDEX       1
    --#HELP            ""
    --#STATE           OPERATIONAL
    ::= 10119

-- EVT_READAHEAD_ENABLED

svrTrapAdapterPDReadAheadEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Read-ahead on all disks enabled."
    --#TYPE            "Read-ahead on all disks enabled"
    --#SUMMARY         "Adapter %s: Read-ahead on all disks enabled (Server %s)"
    --#ARGUMENTS       { 2, 0 }
    --#SEVERITY        INFORMATIONAL
    --#TIMEINDEX       1
    --#HELP            ""
    --#STATE           OPERATIONAL
    ::= 10120

-- EVT_READAHEAD_DISABLED

svrTrapAdapterPDReadAheadDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Read-ahead on all disks disabled."
    --#TYPE            "Read-ahead on all disks disabled"
    --#SUMMARY         "Adapter %s: Read-ahead on all disks disabled (Server %s)"
    --#ARGUMENTS       { 2, 0 }
    --#SEVERITY        INFORMATIONAL
    --#TIMEINDEX       1
    --#HELP            ""
    --#STATE           OPERATIONAL
    ::= 10121

-- EVT_AUTO_RESUME_ENABLED

svrTrapAdapterAutomaticResumeEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic resumption enabled."
    --#TYPE            "Automatic resumption enabled"
    --#SUMMARY         "Adapter %s: Automatic resumption enabled (Server %s)"
    --#ARGUMENTS       { 2, 0 }
    --#SEVERITY        INFORMATIONAL
    --#TIMEINDEX       1
    --#HELP            ""
    --#STATE           OPERATIONAL
    ::= 10122

-- EVT_AUTO_RESUME_DISABLED

svrTrapAdapterAutomaticResumeDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic resumption disabled."
    --#TYPE            "Automatic resumption disabled"
    --#SUMMARY         "Adapter %s: Automatic resumption disabled (Server %s)"
    --#ARGUMENTS       { 2, 0 }
    --#SEVERITY        INFORMATIONAL
    --#TIMEINDEX       1
    --#HELP            ""
    --#STATE           OPERATIONAL
    ::= 10123

-- EVT_DEVICES_PER_SPIN_CHANGED

svrTrapAdapterDevicesPerSpinChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Spinup drive count changed (after next reboot)."
    --#TYPE            "Spinup drive count changed (after next reboot)"
    --#SUMMARY         "Adapter %s: Spinup drive count changed (after next reboot) (Server %s)"
    --#ARGUMENTS       { 2, 0 }
    --#SEVERITY        INFORMATIONAL
    --#TIMEINDEX       1
    --#HELP            ""
    --#STATE           OPERATIONAL
    ::= 10124

-- EVT_DELAY_BETWEEN_SPINS_CHANGED

svrTrapAdapterDelayBetweenSpinsChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Spinup delay changed (after next reboot)."
    --#TYPE            "Spinup delay changed (after next reboot)"
    --#SUMMARY         "Adapter %s: Spinup delay changed (after next reboot) (Server %s)"
    --#ARGUMENTS       { 2, 0 }
    --#SEVERITY        INFORMATIONAL
    --#TIMEINDEX       1
    --#HELP            ""
    --#STATE           OPERATIONAL
    ::= 10125

-- EVT_CHECK_RATE_CHANGED

svrTrapAdapterConCheckRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check rate changed."
    --#TYPE            "Consistency check rate changed"
    --#SUMMARY         "Adapter %s: Consistency check rate changed (Server %s)"
    --#ARGUMENTS       { 2, 0 }
    --#SEVERITY        INFORMATIONAL
    --#TIMEINDEX       1
    --#HELP            ""
    --#STATE           OPERATIONAL
    ::= 10126

-- EVT_TEMPORARY_OFFLINE_ENABLED

svrTrapAdapterTempOfflineEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Temporary offline enabled."
    --#TYPE            "Temporary offline enabled"
    --#SUMMARY         "Adapter %s: Temporary offline enabled (Server %s)"
    --#ARGUMENTS       { 2, 0 }
    --#SEVERITY        INFORMATIONAL
    --#TIMEINDEX       1
    --#HELP            ""
    --#STATE           OPERATIONAL
    ::= 10127

-- EVT_TEMPORARY_OFFLINE_DISABLED

svrTrapAdapterTempOfflineDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Temporary offline disabled."
    --#TYPE            "Temporary offline disabled"
    --#SUMMARY         "Adapter %s: Temporary offline disabled (Server %s)"
    --#ARGUMENTS       { 2, 0 }
    --#SEVERITY        INFORMATIONAL
    --#TIMEINDEX       1
    --#HELP            ""
    --#STATE           OPERATIONAL
    ::= 10128

-- EVT_SMART_ENABLED

svrTrapAdapterSMARTEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SMART enabled."
    --#TYPE            "SMART enabled"
    --#SUMMARY         "Adapter %s: SMART enabled (Server %s)"
    --#ARGUMENTS       { 2, 0 }
    --#SEVERITY        INFORMATIONAL
    --#TIMEINDEX       1
    --#HELP            ""
    --#STATE           OPERATIONAL
    ::= 10129

-- EVT_SMART_DISABLED

svrTrapAdapterSMARTDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SMART disabled."
    --#TYPE            "SMART disabled"
    --#SUMMARY         "Adapter %s: SMART disabled (Server %s)"
    --#ARGUMENTS       { 2, 0 }
    --#SEVERITY        INFORMATIONAL
    --#TIMEINDEX       1
    --#HELP            ""
    --#STATE           OPERATIONAL
    ::= 10130

-- EVT_SMART_POLL_INTERVAL_CHANGED

svrTrapAdapterSMARTPollIntervalChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SMART poll interval changed."
    --#TYPE            "SMART poll interval changed"
    --#SUMMARY         "Adapter %s: SMART poll interval changed (Server %s)"
    --#ARGUMENTS       { 2, 0 }
    --#SEVERITY        INFORMATIONAL
    --#TIMEINDEX       1
    --#HELP            ""
    --#STATE           OPERATIONAL
    ::= 10131

-- EVT_SCAN_CONFIGURATION

svrTrapAdapterConfigChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Configuration rescanned."
    --#TYPE            "Configuration rescanned"
    --#SUMMARY         "Adapter %s: Configuration rescanned (Server %s)"
    --#ARGUMENTS       { 2, 0 }
    --#SEVERITY        INFORMATIONAL
    --#TIMEINDEX       1
    --#HELP            ""
    --#STATE           OPERATIONAL
    ::= 10132

-- EVT_CLEAR_CONFIGURATION

svrTrapAdapterConfigCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Configuration cleared."
    --#TYPE            "Configuration cleared"
    --#SUMMARY         "Adapter %s: Configuration cleared (Server %s)"
    --#ARGUMENTS       { 2, 0 }
    --#SEVERITY        INFORMATIONAL
    --#TIMEINDEX       1
    --#HELP            ""
    --#STATE           OPERATIONAL
    ::= 10133

-- EVT_ACTIVITY_CHANGED

svrTrapAdapterActivityChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Activity changed."
    --#TYPE            "Activity changed"
    --#SUMMARY         "Adapter %s: Activity changed (Server %s)"
    --#ARGUMENTS       { 2, 0 }
    --#SEVERITY        INFORMATIONAL
    --#TIMEINDEX       1
    --#HELP            ""
    --#STATE           OPERATIONAL
    ::= 10134

-- EVT_WIDE_TERMINATION

svrTrapChannelTerminationWide TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Channel termination set to wide."
    --#TYPE            "Channel termination set to wide"
    --#SUMMARY         "Adapter %s: Channel %s termination set to wide (Server %s)"
    --#ARGUMENTS       { 2, 3, 0 }
    --#SEVERITY        INFORMATIONAL
    --#TIMEINDEX       1
    --#HELP            ""
    --#STATE           OPERATIONAL
    ::= 10135

-- EVT_NARROW_TERMINATION

svrTrapChannelTerminationNarrow TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Channel termination set to narrow."
    --#TYPE            "Channel termination set to narrow"
    --#SUMMARY         "Adapter %s: Channel %s termination set to narrow (Server %s)"
    --#ARGUMENTS       { 2, 3, 0 }
    --#SEVERITY        INFORMATIONAL
    --#TIMEINDEX       1
    --#HELP            ""
    --#STATE           OPERATIONAL
    ::= 10136

-- EVT_TERMINATION_DISABLED

svrTrapChannelTerminationDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Channel termination disabled."
    --#TYPE            "Channel termination disabled"
    --#SUMMARY         "Adapter %s: Channel %s termination disabled (Server %s)"
    --#ARGUMENTS       { 2, 3, 0 }
    --#SEVERITY        INFORMATIONAL
    --#TIMEINDEX       1
    --#HELP            ""
    --#STATE           OPERATIONAL
    ::= 10137

-- EVT_ACTIVE_CHANNEL

svrTrapChannelActivated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Channel activated."
    --#TYPE            "Channel activated"
    --#SUMMARY         "Adapter %s: Channel %s activated (Server %s)"
    --#ARGUMENTS       { 2, 3, 0 }
    --#SEVERITY        INFORMATIONAL
    --#TIMEINDEX       1
    --#HELP            ""
    --#STATE           OPERATIONAL
    ::= 10138

-- EVT_QUIET_CHANNEL

svrTrapChannelDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Channel disabled."
    --#TYPE            "Channel disabled"
    --#SUMMARY         "Adapter %s: Channel %s disabled (Server %s)"
    --#ARGUMENTS       { 2, 3, 0 }
    --#SEVERITY        MINOR
    --#TIMEINDEX       1
    --#HELP            "1) Connection issue. 2) Check all of your cabling."
    --#STATE           NONOPERATIONAL
    ::= 10139

-- EVT_DEDICATED_CHANNEL

svrTrapChannelDedicated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Channel set to dedicated."
    --#TYPE            "Channel set to dedicated"
    --#SUMMARY         "Adapter %s: Channel %s set to dedicated (Server %s)"
    --#ARGUMENTS       { 2, 3, 0 }
    --#SEVERITY        INFORMATIONAL
    --#TIMEINDEX       1
    --#HELP            ""
    --#STATE           OPERATIONAL
    ::= 10140

-- EVT_SHARED_CHANNEL

svrTrapChannelShared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Channel set to shared."
    --#TYPE            "Channel set to shared"
    --#SUMMARY         "Adapter %s: Channel %s set to shared (Server %s)"
    --#ARGUMENTS       { 2, 3, 0 }
    --#SEVERITY        INFORMATIONAL
    --#TIMEINDEX       1
    --#HELP            ""
    --#STATE           OPERATIONAL
    ::= 10141

-- EVT_LOGICALDRIVE_READAHEAD_ENABLED

svrTrapLDReadAheadEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: Read-ahead enabled."
    --#TYPE            "Logical drive: Read-ahead enabled"
    --#SUMMARY         "Adapter %s: Logical drive %s: Read-ahead enabled (Server %s)"
    --#ARGUMENTS       { 2, 3, 0 }
    --#SEVERITY        INFORMATIONAL
    --#TIMEINDEX       1
    --#HELP            ""
    --#STATE           OPERATIONAL
    ::= 10142

-- EVT_LOGICALDRIVE_READAHEAD_DISABLED

svrTrapLDReadAheadDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: Read-ahead disabled."
    --#TYPE            "Logical drive: Read-ahead disabled"
    --#SUMMARY         "Adapter %s: Logical drive %s: Read-ahead disabled (Server %s)"
    --#ARGUMENTS       { 2, 3, 0 }
    --#SEVERITY        INFORMATIONAL
    --#TIMEINDEX       1
    --#HELP            ""
    --#STATE           OPERATIONAL
    ::= 10143

-- EVT_ADAPTIVE_READAHEAD_ENABLED

svrTrapLDAdaptiveReadAheadEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: Adaptive read-ahead enabled."
    --#TYPE            "Logical drive: Adaptive read-ahead enabled"
    --#SUMMARY         "Adapter %s: Logical drive %s: Adaptive read-ahead enabled (Server %s)"
    --#ARGUMENTS       { 2, 3, 0 }
    --#SEVERITY        INFORMATIONAL
    --#TIMEINDEX       1
    --#HELP            ""
    --#STATE           OPERATIONAL
    ::= 10144

-- EVT_WRITE_THROUGH

svrTrapLDWriteModeWriteThrough TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: Write mode set to Write-through."
    --#TYPE            "Logical drive: Write mode set to Write-through"
    --#SUMMARY         "Adapter %s: Logical drive %s: Write mode set to Write-through (Server %s)"
    --#ARGUMENTS       { 2, 3, 0 }
    --#SEVERITY        INFORMATIONAL
    --#TIMEINDEX       1
    --#HELP            ""
    --#STATE           OPERATIONAL
    ::= 10145

-- EVT_WRITE_BACK

svrTrapLDWriteModeWriteBack TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: Write mode set to Write-back."
    --#TYPE            "Logical drive: Write mode set to Write-back"
    --#SUMMARY         "Adapter %s: Logical drive %s: Write mode set to Write-back (Server %s)"
    --#ARGUMENTS       { 2, 3, 0 }
    --#SEVERITY        INFORMATIONAL
    --#TIMEINDEX       1
    --#HELP            ""
    --#STATE           OPERATIONAL
    ::= 10146

-- EVT_DIRECT

svrTrapLSIOModeDirect TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: I/O mode set to direct."
    --#TYPE            "Logical drive: I/O mode set to direct"
    --#SUMMARY         "Adapter %s: Logical drive %s: I/O mode set to direct (Server %s)"
    --#ARGUMENTS       { 2, 3, 0 }
    --#SEVERITY        INFORMATIONAL
    --#TIMEINDEX       1
    --#HELP            ""
    --#STATE           OPERATIONAL
    ::= 10147

-- EVT_CACHED

svrTrapLSIOModeCached TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: I/O mode set to cached."
    --#TYPE            "Logical drive: I/O mode set to cached"
    --#SUMMARY         "Adapter %s: Logical drive %s: I/O mode set to cached (Server %s)"
    --#ARGUMENTS       { 2, 3, 0 }
    --#SEVERITY        INFORMATIONAL
    --#TIMEINDEX       1
    --#HELP            ""
    --#STATE           OPERATIONAL
    ::= 10148

-- EVT_TRANSFER_SPEED

svrTrapPDTransferSpeedChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Max. transfer speed of disk changed (after next Reboot)."
    --#TYPE            "Max. transfer speed of disk changed (after next Reboot)"
    --#SUMMARY         "Adapter %s: Max. transfer speed of disk (%s) changed (after next reboot) (Server %s)"
    --#ARGUMENTS       { 2, 3, 0 }
    --#SEVERITY        INFORMATIONAL
    --#TIMEINDEX       1
    --#HELP            ""
    --#STATE           OPERATIONAL
    ::= 10149

-- EVT_BUS_WIDTH

svrTrapPDBusWidthChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bus width of disk changed (after next Reboot)."
    --#TYPE            "Bus width of disk changed (after next Reboot)"
    --#SUMMARY         "Adapter %s: Bus width of disk (%s) changed (after next reboot) (Server %s)"
    --#ARGUMENTS       { 2, 3, 0 }
    --#SEVERITY        INFORMATIONAL
    --#TIMEINDEX       1
    --#HELP            ""
    --#STATE           OPERATIONAL
    ::= 10150

-- EVT_BBU_VOLTAGE_PROBLEM

svrTrapBBUVoltageProblemDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU voltage problem detected."
    --#TYPE            "BBU voltage problem detected"
    --#SUMMARY         "Adapter %s: BBU voltage problem detected (Server %s)"
    --#ARGUMENTS       { 2, 0 }
    --#SEVERITY        MAJOR
    --#TIMEINDEX       1
    --#HELP            "1) Check connection between BBU data/power cable and RAID controller. 2) Check version of RAID controller/iRMC firmware, and BIOS. 3) If problem persists replace BBU."
    --#STATE           OPERATIONAL
    ::= 10151

-- EVT_BBU_TEMPATURE_PROBLEM

svrTrapBBUTempProblemDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU temperature problem detected."
    --#TYPE            "BBU temperature problem detected"
    --#SUMMARY         "Adapter %s: BBU temperature problem detected (Server %s)"
    --#ARGUMENTS       { 2, 0 }
    --#SEVERITY        MAJOR
    --#TIMEINDEX       1
    --#HELP            "1) Check installation of all air flow channels, closed housing, and unblocked louvers. 2) Check environmental temperature. 3) Check version of RAID controller/iRMC firmware, and BIOS."
    --#STATE           OPERATIONAL
    ::= 10152

-- EVT_BBU_CHARGING

svrTrapBBUCharging TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU charging."
    --#TYPE            "BBU charging"
    --#SUMMARY         "Adapter %s: BBU charging (Server %s)"
    --#ARGUMENTS       { 2, 0 }
    --#SEVERITY        INFORMATIONAL
    --#TIMEINDEX       1
    --#HELP            ""
    --#STATE           OPERATIONAL
    ::= 10153

-- EVT_BBU_FAILED

svrTrapBBUFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU failed."
    --#TYPE            "BBU failed"
    --#SUMMARY         "Adapter %s: BBU failed (Server %s)"
    --#ARGUMENTS       { 2, 0 }
    --#SEVERITY        CRITICAL
    --#TIMEINDEX       1
    --#HELP            "Note: Only informational during recalibration process. 1) Check connection between BBU data/power cable and RAID controller. 2) Check version of RAID controller/iRMC firmware, and BIOS. 3) If problem persists replace BBU."
    --#STATE           NONOPERATIONAL
    ::= 10154

-- EVT_BBU_NORMAL

svrTrapBBUNormal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU normal."
    --#TYPE            "BBU normal"
    --#SUMMARY         "Adapter %s: BBU normal (Server %s)"
    --#ARGUMENTS       { 2, 0 }
    --#SEVERITY        INFORMATIONAL
    --#TIMEINDEX       1
    --#HELP            ""
    --#STATE           OPERATIONAL
    ::= 10155

-- EVT_BBU_DISCHARGING

svrTrapBBUDischarging TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU discharging."
    --#TYPE            "BBU discharging"
    --#SUMMARY         "Adapter %s: BBU discharging (Server %s)"
    --#ARGUMENTS       { 2, 0 }
    --#SEVERITY        INFORMATIONAL
    --#TIMEINDEX       1
    --#HELP            ""
    --#STATE           OPERATIONAL
    ::= 10156

-- EVT_DISK_ERROR_FIXED

svrTrapAdapterDiskErrorFixed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk error fixed."
    --#TYPE            "Disk error fixed"
    --#SUMMARY         "Adapter %s: Disk error fixed (Server %s)"
    --#ARGUMENTS       { 2, 0 }
    --#SEVERITY        MINOR
    --#TIMEINDEX       1
    --#HELP            "For information only."
    --#STATE           OPERATIONAL
    ::= 10157

-- EVT_DRIVER_WRITE_CACHE_ENABLED

svrTrapAdapterDriverWriteCacheEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Driver write cache enabled."
    --#TYPE            "Driver write cache enabled"
    --#SUMMARY         "Adapter %s: Driver write cache enabled (Server %s)"
    --#ARGUMENTS       { 2, 0 }
    --#SEVERITY        INFORMATIONAL
    --#TIMEINDEX       1
    --#HELP            ""
    --#STATE           OPERATIONAL
    ::= 10158

-- EVT_DRIVER_WRITE_CACHE_DISABLED

svrTrapAdapterDriverWriteCacheDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Driver write cache disabled."
    --#TYPE            "Driver write cache disabled"
    --#SUMMARY         "Adapter %s: Driver write cache disabled (Server %s)"
    --#ARGUMENTS       { 2, 0 }
    --#SEVERITY        INFORMATIONAL
    --#TIMEINDEX       1
    --#HELP            ""
    --#STATE           OPERATIONAL
    ::= 10159

-- EVT_GB_BOUNDARY_ENABLED

svrTrapAdapterDriveSizingEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Drive sizing (GB Boundary) enabled."
    --#TYPE            "Drive sizing (GB Boundary) enabled"
    --#SUMMARY         "Adapter %s: Drive sizing (GB boundary) enabled (Server %s)"
    --#ARGUMENTS       { 2, 0 }
    --#SEVERITY        INFORMATIONAL
    --#TIMEINDEX       1
    --#HELP            ""
    --#STATE           OPERATIONAL
    ::= 10160

-- EVT_GB_BOUNDARY_DISABLED

svrTrapAdapterDriveSizingDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Drive sizing (GB Boundary) disabled."
    --#TYPE            "Drive sizing (GB Boundary) disabled"
    --#SUMMARY         "Adapter %s: Drive sizing (GB boundary) disabled (Server %s)"
    --#ARGUMENTS       { 2, 0 }
    --#SEVERITY        INFORMATIONAL
    --#TIMEINDEX       1
    --#HELP            ""
    --#STATE           OPERATIONAL
    ::= 10161

-- EVT_HOTSPARE_REBUILD_ENABLED

svrTrapAdapterHotspareAndAutomaticRebuildEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hot spare support and automatic rebuild enabled."
    --#TYPE            "Hot spare support and automatic rebuild enabled"
    --#SUMMARY         "Adapter %s: Hot spare support and automatic rebuild enabled (Server %s)"
    --#ARGUMENTS       { 2, 0 }
    --#SEVERITY        INFORMATIONAL
    --#TIMEINDEX       1
    --#HELP            ""
    --#STATE           OPERATIONAL
    ::= 10162

-- EVT_HOTSPARE_REBUILD_DISABLED

svrTrapAdapterHotspareAndAutomaticRebuildDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hot spare support and automatic rebuild disabled."
    --#TYPE            "Hot spare support and automatic rebuild disabled"
    --#SUMMARY         "Adapter %s: Hot spare support and automatic rebuild disabled (Server %s)"
    --#ARGUMENTS       { 2, 0 }
    --#SEVERITY        INFORMATIONAL
    --#TIMEINDEX       1
    --#HELP            ""
    --#STATE           OPERATIONAL
    ::= 10163

-- EVT_TASK_RATE_CHANGED

svrTrapAdapterTaskRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Task rate changed."
    --#TYPE            "Task rate changed"
    --#SUMMARY         "Adapter %s: Task rate changed (Server %s)"
    --#ARGUMENTS       { 2, 0 }
    --#SEVERITY        INFORMATIONAL
    --#TIMEINDEX       1
    --#HELP            ""
    --#STATE           OPERATIONAL
    ::= 10164

-- EVT_INCONSISTENCY_POLICY_CHECK

svrTrapAdapterInonHandlingCheck TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Inconsistency handling set to consistency check."
    --#TYPE            "Inconsistency handling set to consistency check"
    --#SUMMARY         "Adapter %s: Inconsistency handling set to consistency check (Server %s)"
    --#ARGUMENTS       { 2, 0 }
    --#SEVERITY        INFORMATIONAL
    --#TIMEINDEX       1
    --#HELP            ""
    --#STATE           OPERATIONAL
    ::= 10165

-- EVT_INCONSISTENCY_POLICY_CHECK_ABORT

svrTrapAdapterInonHandlingCheckAbort TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Inconsistency handling set to consistency check (abort on first inconsistency)."
    --#TYPE            "Inconsistency handling set to consistency check (abort on first inconsistency)"
    --#SUMMARY         "Adapter %s: Inconsistency handling set to consistency check (abort on first inconsistency) (Server %s)"
    --#ARGUMENTS       { 2, 0 }
    --#SEVERITY        INFORMATIONAL
    --#TIMEINDEX       1
    --#HELP            ""
    --#STATE           OPERATIONAL
    ::= 10166

-- EVT_INCONSISTENCY_POLICY_MDC

svrTrapAdapterInonHandlingMDC TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Inconsistency handling set to MDC."
    --#TYPE            "Inconsistency handling set to MDC"
    --#SUMMARY         "Adapter %s: Inconsistency handling set to MDC (Server %s)"
    --#ARGUMENTS       { 2, 0 }
    --#SEVERITY        INFORMATIONAL
    --#TIMEINDEX       1
    --#HELP            ""
    --#STATE           OPERATIONAL
    ::= 10167

-- EVT_LOGICALDRIVE_NAME_CHANGED

svrTrapLDNameChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: Name changed."
    --#TYPE            "Logical drive: Name changed"
    --#SUMMARY         "Adapter %s: Logical drive %s: Name changed (Server %s)"
    --#ARGUMENTS       { 2, 3, 0 }
    --#SEVERITY        INFORMATIONAL
    --#TIMEINDEX       1
    --#HELP            ""
    --#STATE           OPERATIONAL
    ::= 10168

-- EVT_LOGICALDRIVE_WRITE_MODE_CHANGED

svrTrapLDCacheWriteModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive: Cache write mode changed."
    --#TYPE            "Logical drive: Cache write mode changed"
    --#SUMMARY         "Adapter %s: Logical drive %s: Cache write mode changed (Server %s)"
    --#ARGUMENTS       { 2, 3, 0 }
    --#SEVERITY        INFORMATIONAL
    --#TIMEINDEX       1
    --#HELP            ""
    --#STATE           OPERATIONAL
    ::= 10169

-- EVT_REBOOT_REQUIRED

svrTrapRebootRequired TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reboot required."
    --#TYPE            "Reboot required"
    --#SUMMARY         "Reboot required (Server %s)"
    --#ARGUMENTS       { 0 }
    --#SEVERITY        MAJOR
    --#TIMEINDEX       1
    --#HELP            "For information only."
    --#STATE           OPERATIONAL
    ::= 10170

-- EVT_LOGIN

svrTrapModuleLoggedIn TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Module logged in."
    --#TYPE            "Module logged in"
    --#SUMMARY         "User %s (%s) logged in (Server %s)"
    --#ARGUMENTS       { 2, 3, 0 }
    --#SEVERITY        INFORMATIONAL
    --#TIMEINDEX       1
    --#HELP            ""
    --#STATE           OPERATIONAL
    ::= 10171

-- EVT_LOGOUT

svrTrapModuleLoggedOut TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Module logged out."
    --#TYPE            "Module logged out"
    --#SUMMARY         "User %s (%s) logged out (Server %s)"
    --#ARGUMENTS       { 2, 3, 0 }
    --#SEVERITY        INFORMATIONAL
    --#TIMEINDEX       1
    --#HELP            ""
    --#STATE           OPERATIONAL
    ::= 10172

-- EVT_HOTSPARE_ENABLED

svrTrapAdapterHotspareEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hot spare enabled."
    --#TYPE            "Hot spare enabled"
    --#SUMMARY         "Adapter %s: Hot spare enabled (Server %s)"
    --#ARGUMENTS       { 2, 0 }
    --#SEVERITY        INFORMATIONAL
    --#TIMEINDEX       1
    --#HELP            ""
    --#STATE           OPERATIONAL
    ::= 10173

-- EVT_HOTSPARE_DISABLED

svrTrapAdapterHotspareDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hot spare disabled."
    --#TYPE            "Hot spare disabled"
    --#SUMMARY         "Adapter %s: Hot spare disabled (Server %s)"
    --#ARGUMENTS       { 2, 0 }
    --#SEVERITY        INFORMATIONAL
    --#TIMEINDEX       1
    --#HELP            ""
    --#STATE           OPERATIONAL
    ::= 10174

-- EVT_HOTSWAP_ENABLED

svrTrapAdapterHotswapEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hotswap enabled."
    --#TYPE            "Hotswap enabled"
    --#SUMMARY         "Adapter %s: Hot swap enabled (Server %s)"
    --#ARGUMENTS       { 2, 0 }
    --#SEVERITY        INFORMATIONAL
    --#TIMEINDEX       1
    --#HELP            ""
    --#STATE           OPERATIONAL
    ::= 10175

-- EVT_HOTSWAP_DISABLED

svrTrapAdapterHotswapDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hotswap disabled."
    --#TYPE            "Hotswap disabled"
    --#SUMMARY         "Adapter %s: Hot swap disabled (Server %s)"
    --#ARGUMENTS       { 2, 0 }
    --#SEVERITY        INFORMATIONAL
    --#TIMEINDEX       1
    --#HELP            ""
    --#STATE           OPERATIONAL
    ::= 10176

-- EVT_WRITE_MODE_BACK

svrTrapAdapterWriteModeWriteBack TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write mode set to Write-back."
    --#TYPE            "Write mode set to Write-back"
    --#SUMMARY         "Adapter %s: Write mode set to Write-back (Server %s)"
    --#ARGUMENTS       { 2, 0 }
    --#SEVERITY        INFORMATIONAL
    --#TIMEINDEX       1
    --#HELP            ""
    --#STATE           OPERATIONAL
    ::= 10177

-- EVT_WRITE_MODE_WRITETHROUGH

svrTrapAdapterWriteModeWriteThrough TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write mode set to Write-through."
    --#TYPE            "Write mode set to Write-through"
    --#SUMMARY         "Adapter %s: Write mode set to Write-through (Server %s)"
    --#ARGUMENTS       { 2, 0 }
    --#SEVERITY        INFORMATIONAL
    --#TIMEINDEX       1
    --#HELP            ""
    --#STATE           OPERATIONAL
    ::= 10178

-- EVT_WRITE_MODE_ADAPTIVE

svrTrapAdapterWriteModeAdaptive TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write mode set to adaptive."
    --#TYPE            "Write mode set to adaptive"
    --#SUMMARY         "Adapter %s: Write mode set to Adaptive (Server %s)"
    --#ARGUMENTS       { 2, 0 }
    --#SEVERITY        INFORMATIONAL
    --#TIMEINDEX       1
    --#HELP            ""
    --#STATE           OPERATIONAL
    ::= 10179

-- EVT_BATTERY_CHARGE_STARTED

svrTrapBatteryChargeStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU charging started."
    --#TYPE            "BBU charging started"
    --#SUMMARY         "Adapter %s: BBU charging started (Server %s)"
    --#ARGUMENTS       { 2, 0 }
    --#SEVERITY        INFORMATIONAL
    --#TIMEINDEX       1
    --#HELP            ""
    --#STATE           OPERATIONAL
    ::= 10180

-- EVT_RAID5_INIT_ENABLED

svrTrapAdapterAutomaticRAID5InitEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic initialization of RAID-5 enabled."
    --#TYPE            "Automatic initialization of RAID-5 enabled"
    --#SUMMARY         "Adapter %s: Automatic initialization of RAID-5 enabled (Server %s)"
    --#ARGUMENTS       { 2, 0 }
    --#SEVERITY        INFORMATIONAL
    --#TIMEINDEX       1
    --#HELP            ""
    --#STATE           OPERATIONAL
    ::= 10181

-- EVT_RAID5_INIT_DISABLED

svrTrapAdapterAutomaticRAID5InitDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic initialization of RAID-5 disabled."
    --#TYPE            "Automatic initialization of RAID-5 disabled"
    --#SUMMARY         "Adapter %s: Automatic initialization of RAID-5 disabled (Server %s)"
    --#ARGUMENTS       { 2, 0 }
    --#SEVERITY        INFORMATIONAL
    --#TIMEINDEX       1
    --#HELP            ""
    --#STATE           OPERATIONAL
    ::= 10182

-- EVT_COPY_BACK_ENABLED

svrTrapAdapterCopyBackEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback enabled."
    --#TYPE            "Copyback enabled"
    --#SUMMARY         "Adapter %s: Copyback enabled (Server %s)"
    --#ARGUMENTS       { 2, 0 }
    --#SEVERITY        INFORMATIONAL
    --#TIMEINDEX       1
    --#HELP            ""
    --#STATE           OPERATIONAL
    ::= 10183

-- EVT_COPY_BACK_DISABLED

svrTrapAdapterCopyBackDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback disabled."
    --#TYPE            "Copyback disabled"
    --#SUMMARY         "Adapter %s: Copyback disabled (Server %s)"
    --#ARGUMENTS       { 2, 0 }
    --#SEVERITY        INFORMATIONAL
    --#TIMEINDEX       1
    --#HELP            ""
    --#STATE           OPERATIONAL
    ::= 10184

-- EVT_CLEAR_INITIALIZATION

svrTrapAdapterInitClear TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization set to clear."
    --#TYPE            "Initialization set to clear"
    --#SUMMARY         "Adapter %s: Initialization set to clear (Server %s)"
    --#ARGUMENTS       { 2, 0 }
    --#SEVERITY        INFORMATIONAL
    --#TIMEINDEX       1
    --#HELP            ""
    --#STATE           OPERATIONAL
    ::= 10185

-- EVT_VERIFY_STARTED

svrTrapPDVerifyStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Verify started."
    --#TYPE            "Verify started"
    --#SUMMARY         "Adapter %s: Verification started on disk (%s) (Server %s)"
    --#ARGUMENTS       { 2, 3, 0 }
    --#SEVERITY        INFORMATIONAL
    --#TIMEINDEX       1
    --#HELP            ""
    --#STATE           OPERATIONAL
    ::= 10186

-- EVT_VERIFY_FINISHED

svrTrapPDVerifyFinished TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Verify finished."
    --#TYPE            "Verify finished"
    --#SUMMARY         "Adapter %s: Verification finished on disk (%s) (Server %s)"
    --#ARGUMENTS       { 2, 3, 0 }
    --#SEVERITY        INFORMATIONAL
    --#TIMEINDEX       1
    --#HELP            ""
    --#STATE           OPERATIONAL
    ::= 10187

-- EVT_LOGICALDRIVE_READ_MODE_CHANGED

svrTrapLDReadModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cache read mode changed."
    --#TYPE            "Cache read mode changed"
    --#SUMMARY         "Adapter %s: Logical drive %s: Cache read mode changed (Server %s)"
    --#ARGUMENTS       { 2, 3, 0 }
    --#SEVERITY        INFORMATIONAL
    --#TIMEINDEX       1
    --#HELP            ""
    --#STATE           OPERATIONAL
    ::= 10188

-- EVT_LOGICALDRIVE_CACHE_MODE_CHANGED

svrTrapLDCacheModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cache mode changed."
    --#TYPE            "Cache mode changed"
    --#SUMMARY         "Adapter %s: Logical drive %s: Cache mode changed (Server %s)"
    --#ARGUMENTS       { 2, 3, 0 }
    --#SEVERITY        INFORMATIONAL
    --#TIMEINDEX       1
    --#HELP            ""
    --#STATE           OPERATIONAL
    ::= 10189

-- EVT_LOGICALDRIVE_ACCESS_MODE_CHANGED

svrTrapLDAcessModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Access mode changed."
    --#TYPE            "Access mode changed"
    --#SUMMARY         "Adapter %s: Logical drive %s: Access mode changed (Server %s)"
    --#ARGUMENTS       { 2, 3, 0 }
    --#SEVERITY        INFORMATIONAL
    --#TIMEINDEX       1
    --#HELP            ""
    --#STATE           OPERATIONAL
    ::= 10190

-- EVT_LOGICALDRIVE_BGI_MODE_CHANGED

svrTrapLDBGIModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI mode changed."
    --#TYPE            "BGI mode changed"
    --#SUMMARY         "Adapter %s: Logical drive %s: BGI mode changed (Server %s)"
    --#ARGUMENTS       { 2, 3, 0 }
    --#SEVERITY        INFORMATIONAL
    --#TIMEINDEX       1
    --#HELP            ""
    --#STATE           OPERATIONAL
    ::= 10191

-- EVT_LOGICALDRIVE_DISK_CACHE_MODE_CHANGED

svrTrapLDDiskCacheModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk cache mode changed."
    --#TYPE            "Disk cache mode changed"
    --#SUMMARY         "Adapter %s: Logical drive %s: Disk cache mode changed (Server %s)"
    --#ARGUMENTS       { 2, 3, 0 }
    --#SEVERITY        INFORMATIONAL
    --#TIMEINDEX       1
    --#HELP            ""
    --#STATE           OPERATIONAL
    ::= 10192

-- EVT_BOOT

svrTrapBoot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware initialization started."
    --#TYPE            "Firmware initialization started"
    --#SUMMARY         "Adapter %s: Firmware initialization started (Server %s)"
    --#ARGUMENTS       { 2, 0 }
    --#SEVERITY        INFORMATIONAL
    --#TIMEINDEX       1
    --#HELP            ""
    --#STATE           OPERATIONAL
    ::= 10193

-- EVT_VERSION

svrTrapVersion TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware version."
    --#TYPE            "Firmware version"
    --#SUMMARY         "Adapter %s: Firmware version %s (Server %s)"
    --#ARGUMENTS       { 2, 3, 0 }
    --#SEVERITY        INFORMATIONAL
    --#TIMEINDEX       1
    --#HELP            ""
    --#STATE           OPERATIONAL
    ::= 10194

-- EVT_BBU_TBBU_DIRTY_CACHE_CONFIG_MISMATCH

svrTrapBBUTBBUDirtyCacheConfigMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unable to recover cache data from TBBU."
    --#TYPE            "Unable to recover cache data from TBBU"
    --#SUMMARY         "Adapter %s: Unable to recover cache data from TBBU (Server %s)"
    --#ARGUMENTS       { 2, 0 }
    --#SEVERITY        MAJOR
    --#TIMEINDEX       1
    --#HELP            "Call your local Fujitsu Helpdesk."
    --#STATE           OPERATIONAL
    ::= 10195

-- EVT_BBU_TBBU_DIRTY_CACHE_PROCESSED

svrTrapBBUTBBUDirtyCacheProcessed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cache data recovered from TBBU successfully."
    --#TYPE            "Cache data recovered from TBBU successfully"
    --#SUMMARY         "Adapter %s: Cache data recovered from TBBU successfully (Server %s)"
    --#ARGUMENTS       { 2, 0 }
    --#SEVERITY        INFORMATIONAL
    --#TIMEINDEX       1
    --#HELP            ""
    --#STATE           OPERATIONAL
    ::= 10196

-- EVT_CLUST_DOWN

svrTrapClustDown TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cluster down; communication with peer lost."
    --#TYPE            "Cluster down; communication with peer lost"
    --#SUMMARY         "Adapter %s: Cluster down; communication with peer lost (Server %s)"
    --#ARGUMENTS       { 2, 0 }
    --#SEVERITY        MAJOR
    --#TIMEINDEX       1
    --#HELP            "Call your local Fujitsu Helpdesk."
    --#STATE           OPERATIONAL
    ::= 10197

-- EVT_CLUST_OWNERSHIP_CHANGE

svrTrapClustOwnershipChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Ownership changed."
    --#TYPE            "Ownership changed"
    --#SUMMARY         "Adapter %s: %s ownership changed from %s to %s (Server %s)"
    --#ARGUMENTS       { 2, 3, 4, 5, 0 }
    --#SEVERITY        INFORMATIONAL
    --#TIMEINDEX       1
    --#HELP            ""
    --#STATE           OPERATIONAL
    ::= 10198

-- EVT_CTRL_BGI_RATE_CHANGED

svrTrapCtrlBGIRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Background initialization rate changed."
    --#TYPE            "Background initialization rate changed"
    --#SUMMARY         "Adapter %s: BGI rate changed to %s percent (Server %s)"
    --#ARGUMENTS       { 2, 3, 0 }
    --#SEVERITY        INFORMATIONAL
    --#TIMEINDEX       1
    --#HELP            ""
    --#STATE           OPERATIONAL
    ::= 10199

-- EVT_CTRL_CACHE_DISCARDED

svrTrapCtrlCacheDiscarded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Controller cache discarded."
    --#TYPE            "Controller cache discarded"
    --#SUMMARY         "Adapter %s: Adapter cache discarded due to memory/BBU problems (Server %s)"
    --#ARGUMENTS       { 2, 0 }
    --#SEVERITY        MAJOR
    --#TIMEINDEX       1
    --#HELP            ""
    --#STATE           OPERATIONAL
    ::= 10200

-- EVT_CTRL_CACHE_REBOOT_CANT_RECOVER

svrTrapCtrlCacheRebootCantRecover TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unable to recover cache data."
    --#TYPE            "Unable to recover cache data"
    --#SUMMARY         "Adapter %s: Unable to recover cache data due to configuration mismatch (Server %s)"
    --#ARGUMENTS       { 2, 0 }
    --#SEVERITY        MAJOR
    --#TIMEINDEX       1
    --#HELP            "Call your local Fujitsu Helpdesk."
    --#STATE           OPERATIONAL
    ::= 10201

-- EVT_CTRL_CACHE_REBOOT_RECOVER

svrTrapCtrlCacheRebootRecover TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cache data recovered successfully."
    --#TYPE            "Cache data recovered successfully"
    --#SUMMARY         "Adapter %s: Cache data recovered successfully (Server %s)"
    --#ARGUMENTS       { 2, 0 }
    --#SEVERITY        INFORMATIONAL
    --#TIMEINDEX       1
    --#HELP            ""
    --#STATE           OPERATIONAL
    ::= 10202

-- EVT_CTRL_CACHE_VERSION_MISMATCH

svrTrapCtrlCacheVersionMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Controller cache discarded."
    --#TYPE            "Controller cache discarded"
    --#SUMMARY         "Adapter %s: Adapter cache discarded due to firmware version IOncompatibility (Server %s)"
    --#ARGUMENTS       { 2, 0 }
    --#SEVERITY        MAJOR
    --#TIMEINDEX       1
    --#HELP            "1) Check version of RAID controller/iRMC firmware, and BIOS."
    --#STATE           OPERATIONAL
    ::= 10203

-- EVT_CTRL_CRASH

svrTrapCtrlCrash TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Fatal firmware error."
    --#TYPE            "Fatal firmware error"
    --#SUMMARY         "Adapter %s: Fatal firmware error: %s (Server %s)"
    --#ARGUMENTS       { 2, 3, 0 }
    --#SEVERITY        CRITICAL
    --#TIMEINDEX       1
    --#HELP            "1) Disconnect AC and wait 30 seconds before reconnect."
    --#STATE           NONOPERATIONAL
    ::= 10204

-- EVT_CTRL_FACTORY_DEFAULTS

svrTrapCtrlFactoryDefaults TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Factory defaults restored."
    --#TYPE            "Factory defaults restored"
    --#SUMMARY         "Adapter %s: Factory defaults restored (Server %s)"
    --#ARGUMENTS       { 2, 0 }
    --#SEVERITY        INFORMATIONAL
    --#TIMEINDEX       1
    --#HELP            ""
    --#STATE           OPERATIONAL
    ::= 10205

-- EVT_CTRL_FLASH_BAD_IMAGE

svrTrapCtrlFlashBadImage TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash downloaded image corrupt."
    --#TYPE            "Flash downloaded image corrupt"
    --#SUMMARY         "Adapter %s: Flash downloaded image corrupt (Server %s)"
    --#ARGUMENTS       { 2, 0 }
    --#SEVERITY        MAJOR
    --#TIMEINDEX       1
    --#HELP            "1) Download again. 2) Retry flash."
    --#STATE           OPERATIONAL
    ::= 10206

-- EVT_CTRL_FLASH_ERASE_ERROR

svrTrapCtrlFlashEraseError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash erase error."
    --#TYPE            "Flash erase error"
    --#SUMMARY         "Adapter %s: Flash erase error (Server %s)"
    --#ARGUMENTS       { 2, 0 }
    --#SEVERITY        MAJOR
    --#TIMEINDEX       1
    --#HELP            "1) Replace affected RAID controller."
    --#STATE           OPERATIONAL
    ::= 10207

-- EVT_CTRL_FLASH_ERASE_TIMEOUT

svrTrapCtrlFlashEraseTimeout TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash timeout during erase."
    --#TYPE            "Flash timeout during erase"
    --#SUMMARY         "Adapter %s: Flash timeout during erase (Server %s)"
    --#ARGUMENTS       { 2, 0 }
    --#SEVERITY        MAJOR
    --#TIMEINDEX       1
    --#HELP            "1) Retry flash. 2) Replace affected RAID controller."
    --#STATE           OPERATIONAL
    ::= 10208

-- EVT_CTRL_FLASH_GENERAL_ERROR

svrTrapCtrlFlashGeneralError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash error."
    --#TYPE            "Flash error"
    --#SUMMARY         "Adapter %s: Flash error (Server %s)"
    --#ARGUMENTS       { 2, 0 }
    --#SEVERITY        MAJOR
    --#TIMEINDEX       1
    --#HELP            "1) Retry flash. 2) Replace affected RAID controller."
    --#STATE           OPERATIONAL
    ::= 10209

-- EVT_CTRL_FLASH_IMAGE

svrTrapCtrlFlashImage TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flashing image."
    --#TYPE            "Flashing image"
    --#SUMMARY         "Adapter %s: Flashing image: %s (Server %s)"
    --#ARGUMENTS       { 2, 3, 0 }
    --#SEVERITY        INFORMATIONAL
    --#TIMEINDEX       1
    --#HELP            ""
    --#STATE           OPERATIONAL
    ::= 10210

-- EVT_CTRL_FLASH_OK

svrTrapCtrlFlashOK TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash complete."
    --#TYPE            "Flash complete"
    --#SUMMARY         "Adapter %s: Flash of new firmware image(s) complete (Server %s)"
    --#ARGUMENTS       { 2, 0 }
    --#SEVERITY        INFORMATIONAL
    --#TIMEINDEX       1
    --#HELP            ""
    --#STATE           OPERATIONAL
    ::= 10211

-- EVT_CTRL_FLASH_PROGRAM_ERROR

svrTrapCtrlFlashProgramError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash programming error."
    --#TYPE            "Flash programming error"
    --#SUMMARY         "Adapter %s: Flash programming error (Server %s)"
    --#ARGUMENTS       { 2, 0 }
    --#SEVERITY        MAJOR
    --#TIMEINDEX       1
    --#HELP            "1) Retry flash. 2) Replace affected RAID controller."
    --#STATE           OPERATIONAL
    ::= 10212

-- EVT_CTRL_FLASH_PROGRAM_TIMEOUT

svrTrapCtrlFlashProgramTimeout TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash timeout during programming."
    --#TYPE            "Flash timeout during programming"
    --#SUMMARY         "Adapter %s: Flash timeout during programming (Server %s)"
    --#ARGUMENTS       { 2, 0 }
    --#SEVERITY        MAJOR
    --#TIMEINDEX       1
    --#HELP            "1) Retry flash. 2) Replace affected RAID controller."
    --#STATE           OPERATIONAL
    ::= 10213

-- EVT_CTRL_FLASH_UNKNOWN_CHIP_TYPE

svrTrapCtrlFlashUnknownChipType TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash chip type unknown."
    --#TYPE            "Flash chip type unknown"
    --#SUMMARY         "Adapter %s: Flash chip type unknown (Server %s)"
    --#ARGUMENTS       { 2, 0 }
    --#SEVERITY        MINOR
    --#TIMEINDEX       1
    --#HELP            "1) Retry flash. 2) Replace affected RAID controller."
    --#STATE           OPERATIONAL
    ::= 10214

-- EVT_CTRL_FLASH_UNKNOWN_CMD_SET

svrTrapCtrlFlashUnknownCmdSet TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash command set unknown."
    --#TYPE            "Flash command set unknown"
    --#SUMMARY         "Adapter %s: Flash command set unknown (Server %s)"
    --#ARGUMENTS       { 2, 0 }
    --#SEVERITY        MAJOR
    --#TIMEINDEX       1
    --#HELP            "1) Retry flash. 2) Replace affected RAID controller."
    --#STATE           OPERATIONAL
    ::= 10215

-- EVT_CTRL_FLASH_VERIFY_FAILURE

svrTrapCtrlFlashVerifyFailure TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash verify failure."
    --#TYPE            "Flash verify failure"
    --#SUMMARY         "Adapter %s: Flash verification failure (Server %s)"
    --#ARGUMENTS       { 2, 0 }
    --#SEVERITY        MAJOR
    --#TIMEINDEX       1
    --#HELP            "1) Retry flash. 2) Replace affected RAID controller."
    --#STATE           OPERATIONAL
    ::= 10216

-- EVT_CTRL_FLUSH_RATE_CHANGED

svrTrapCtrlFlushRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flush rate changed."
    --#TYPE            "Flush rate changed"
    --#SUMMARY         "Adapter %s: Flush rate changed to %s seconds (Server %s)"
    --#ARGUMENTS       { 2, 3, 0 }
    --#SEVERITY        INFORMATIONAL
    --#TIMEINDEX       1
    --#HELP            ""
    --#STATE           OPERATIONAL
    ::= 10217

-- EVT_CTRL_HIBERNATE

svrTrapCtrlHibernate TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hibernate command received."
    --#TYPE            "Hibernate command received"
    --#SUMMARY         "Adapter %s: Hibernate command received from host (Server %s)"
    --#ARGUMENTS       { 2, 0 }
    --#SEVERITY        INFORMATIONAL
    --#TIMEINDEX       1
    --#HELP            ""
    --#STATE           OPERATIONAL
    ::= 10218

-- EVT_CTRL_LOG_CLEARED

svrTrapCtrlLogCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Event log cleared."
    --#TYPE            "Event log cleared"
    --#SUMMARY         "Adapter %s: Event log cleared (Server %s)"
    --#ARGUMENTS       { 2, 0 }
    --#SEVERITY        INFORMATIONAL
    --#TIMEINDEX       1
    --#HELP            ""
    --#STATE           OPERATIONAL
    ::= 10219

-- EVT_CTRL_LOG_WRAPPED

svrTrapCtrlLogWrapped TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Event log wrapped."
    --#TYPE            "Event log wrapped"
    --#SUMMARY         "Adapter %s: Event log wrapped (Server %s)"
    --#ARGUMENTS       { 2, 0 }
    --#SEVERITY        INFORMATIONAL
    --#TIMEINDEX       1
    --#HELP            ""
    --#STATE           OPERATIONAL
    ::= 10220

-- EVT_CTRL_MEM_ECC_MULTI_BIT

svrTrapCtrlMemECCMultiBit TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Multi-bit ECC error."
    --#TYPE            "Multi-bit ECC error"
    --#SUMMARY         "Adapter %s: Multi-bit ECC error: ECAR=%s, ELOG=%s, (%s) (Server %s)"
    --#ARGUMENTS       { 2, 3, 4, 5, 0 }
    --#SEVERITY        MAJOR
    --#TIMEINDEX       1
    --#HELP            "If the problem occurs repeatedly replace the RAID controller DIMM module (cache)."
    --#STATE           OPERATIONAL
    ::= 10221

-- EVT_CTRL_MEM_ECC_SINGLE_BIT

svrTrapCtrlMemECCSingleBit TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Single-bit ECC error."
    --#TYPE            "Single-bit ECC error"
    --#SUMMARY         "Adapter %s: Single-bit ECC error: ECAR=%s, ELOG=%s, (%s) (Server %s)"
    --#ARGUMENTS       { 2, 3, 4, 5, 0 }
    --#SEVERITY        MAJOR
    --#TIMEINDEX       1
    --#HELP            "If the problem occurs repeatedly replace the RAID controller DIMM module (cache)."
    --#STATE           OPERATIONAL
    ::= 10222

-- EVT_CTRL_NOT_ENOUGH_MEMORY

svrTrapCtrlNotEnoughMemory TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Not enough controller memory."
    --#TYPE            "Not enough controller memory"
    --#SUMMARY         "Adapter %s: Not enough adapter memory (Server %s)"
    --#ARGUMENTS       { 2, 0 }
    --#SEVERITY        MAJOR
    --#TIMEINDEX       1
    --#HELP            "1) Replace the RAID controller DIMM module (cache). 2) If problem persists replace RAID controller."
    --#STATE           OPERATIONAL
    ::= 10223

-- EVT_CTRL_PR_RATE_CHANGED

svrTrapCtrlPrRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read rate changed."
    --#TYPE            "Patrol Read rate changed"
    --#SUMMARY         "Adapter %s: Patrol Read rate changed to %s percent (Server %s)"
    --#ARGUMENTS       { 2, 3, 0 }
    --#SEVERITY        INFORMATIONAL
    --#TIMEINDEX       1
    --#HELP            ""
    --#STATE           OPERATIONAL
    ::= 10224

-- EVT_CTRL_RECON_RATE_CHANGED

svrTrapCtrlReconRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reconstruction rate changed."
    --#TYPE            "Reconstruction rate changed"
    --#SUMMARY         "Adapter %s: Migration rate changed to %s percent (Server %s)"
    --#ARGUMENTS       { 2, 3, 0 }
    --#SEVERITY        INFORMATIONAL
    --#TIMEINDEX       1
    --#HELP            ""
    --#STATE           OPERATIONAL
    ::= 10225

-- EVT_CTRL_SHUTDOWN

svrTrapCtrlShutdown TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Shutdown command received."
    --#TYPE            "Shutdown command received"
    --#SUMMARY         "Adapter %s: Shutdown command received from host (Server %s)"
    --#ARGUMENTS       { 2, 0 }
    --#SEVERITY        INFORMATIONAL
    --#TIMEINDEX       1
    --#HELP            ""
    --#STATE           OPERATIONAL
    ::= 10226

-- EVT_CTRL_TEST

svrTrapCtrlTest TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Test event."
    --#TYPE            "Test event"
    --#SUMMARY         "Adapter %s: Test event: '%s' (Server %s)"
    --#ARGUMENTS       { 2, 3, 0 }
    --#SEVERITY        INFORMATIONAL
    --#TIMEINDEX       1
    --#HELP            ""
    --#STATE           OPERATIONAL
    ::= 10227

-- EVT_CTRL_TIME_SET

svrTrapCTrlTimeSet TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Time established."
    --#TYPE            "Time established"
    --#SUMMARY         "Adapter %s: Time established as %s; (%s seconds since power on) (Server %s)"
    --#ARGUMENTS       { 2, 3, 4, 0 }
    --#SEVERITY        INFORMATIONAL
    --#TIMEINDEX       1
    --#HELP            ""
    --#STATE           OPERATIONAL
    ::= 10228

-- EVT_CTRL_USER_ENTERED_DEBUGGER

svrTrapCtrlUserEnteredDebugger TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "User entered firmware debugger."
    --#TYPE            "User entered firmware debugger"
    --#SUMMARY         "Adapter %s: User entered firmware debugger (Server %s)"
    --#ARGUMENTS       { 2, 0 }
    --#SEVERITY        INFORMATIONAL
    --#TIMEINDEX       1
    --#HELP            ""
    --#STATE           OPERATIONAL
    ::= 10229

-- EVT_LD_BGI_CORRECTED_MEDIUM_ERROR

svrTrapLDBGICorrectedMediumError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI corrected medium error."
    --#TYPE            "BGI corrected medium error"
    --#SUMMARY         "Adapter %s: BGI corrected medium error (logical drive %s at LBA %s on disk (%s) at LBA %s) (Server %s)"
    --#ARGUMENTS       { 2, 3, 4, 5, 6, 0 }
    --#SEVERITY        INFORMATIONAL
    --#TIMEINDEX       1
    --#HELP            ""
    --#STATE           OPERATIONAL
    ::= 10230

-- EVT_LD_BGI_DONE_ERRORS

svrTrapLDBGIDoneErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI finished with uncorrectable errors."
    --#TYPE            "BGI finished with uncorrectable errors"
    --#SUMMARY         "Adapter %s: BGI finished with uncorrectable errors on logical drive %s (Server %s)"
    --#ARGUMENTS       { 2, 3, 0 }
    --#SEVERITY        MAJOR
    --#TIMEINDEX       1
    --#HELP            "Initiate consistency check (e.g. via ServerView RAID Manager)."
    --#STATE           OPERATIONAL
    ::= 10231

-- EVT_LD_BGI_DOUBLE_MEDIUM_ERRORS

svrTrapLDBGIDoubleMediumErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI detected uncorrectable double medium errors."
    --#TYPE            "BGI detected uncorrectable double medium errors"
    --#SUMMARY         "Adapter %s: BGI detected uncorrectable multiple medium errors (disk (%s) at LBA %s on logical drive %s) (Server %s)"
    --#ARGUMENTS       { 2, 3, 4, 5, 0 }
    --#SEVERITY        MAJOR
    --#TIMEINDEX       1
    --#HELP            "Replace affected disk."
    --#STATE           OPERATIONAL
    ::= 10232

-- EVT_LD_BGI_FAILED

svrTrapLDBGIFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI failed."
    --#TYPE            "BGI failed"
    --#SUMMARY         "Adapter %s: BGI failed on logical drive %s (Server %s)"
    --#ARGUMENTS       { 2, 3, 0 }
    --#SEVERITY        MAJOR
    --#TIMEINDEX       1
    --#HELP            "1) Restart Background initialization (BGI). 2) Replace affected disk."
    --#STATE           OPERATIONAL
    ::= 10233

-- EVT_LD_BGI_PROGRESS

svrTrapLDBGIProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI progress."
    --#TYPE            "BGI progress"
    --#SUMMARY         "Adapter %s: BGI progress on logical drive %s is %s (Server %s)"
    --#ARGUMENTS       { 2, 3, 4, 0 }
    --#SEVERITY        INFORMATIONAL
    --#TIMEINDEX       1
    --#HELP            ""
    --#STATE           OPERATIONAL
    ::= 10234

-- EVT_LD_CACHE_POLICY_CHANGE

svrTrapLDCachePolicyChange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Policy change."
    --#TYPE            "Policy change"
    --#SUMMARY         "Adapter %s: Logical drive %s: %s changed (Server %s)"
    --#ARGUMENTS       { 2, 3, 4, 0 }
    --#SEVERITY        INFORMATIONAL
    --#TIMEINDEX       1
    --#HELP            ""
    --#STATE           OPERATIONAL
    ::= 10235

-- EVT_LD_MDC_CORRECTED_MEDIUM_ERROR

svrTrapLDMDCCorrectedMediumError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC corrected medium error."
    --#TYPE            "MDC corrected medium error"
    --#SUMMARY         "Adapter %s: MDC corrected medium error (logical drive %s at LBA %s on disk (%s) at LBA %s) (Server %s)"
    --#ARGUMENTS       { 2, 3, 4, 5, 6, 0 }
    --#SEVERITY        INFORMATIONAL
    --#TIMEINDEX       1
    --#HELP            ""
    --#STATE           OPERATIONAL
    ::= 10236

-- EVT_LD_CC_INCONSISTENT_PARITY

svrTrapLDCCInconsistentParity TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check found inconsistent parity."
    --#TYPE            "Consistency check found inconsistent parity"
    --#SUMMARY         "Adapter %s: Consistency check found inconsistent parity on logical drive %s at stripe %s (Server %s)"
    --#ARGUMENTS       { 2, 3, 4, 0 }
    --#SEVERITY        MAJOR
    --#TIMEINDEX       1
    --#HELP            "1) Start consistency check again. 2) If problem persists backup data from affected logical drive. 3) Delete and recreate affected logical drive. 4) Restore data."
    --#STATE           OPERATIONAL
    ::= 10237

-- EVT_LD_CC_INCONSISTENT_PARITY_LOGGING_DISABLED

svrTrapLDCCInconsistentParityLoggingDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check inconsistency logging disabled."
    --#TYPE            "Consistency check inconsistency logging disabled"
    --#SUMMARY         "Adapter %s: Consistency check logging disabled on logical drive %s (too many Inconsistencies) (Server %s)"
    --#ARGUMENTS       { 2, 3, 0 }
    --#SEVERITY        INFORMATIONAL
    --#TIMEINDEX       1
    --#HELP            ""
    --#STATE           OPERATIONAL
    ::= 10238

-- EVT_LD_CC_PROGRESS

svrTrapLDCCProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check progress."
    --#TYPE            "Consistency check progress"
    --#SUMMARY         "Adapter %s: Consistency check progress on %s is %s (Server %s)"
    --#ARGUMENTS       { 2, 3, 4, 0 }
    --#SEVERITY        INFORMATIONAL
    --#TIMEINDEX       1
    --#HELP            ""
    --#STATE           OPERATIONAL
    ::= 10239

-- EVT_LD_INIT_FAILED

svrTrapLDInitFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization failed."
    --#TYPE            "Initialization failed"
    --#SUMMARY         "Adapter %s: Initialization failed on logical drive %s (Server %s)"
    --#ARGUMENTS       { 2, 3, 0 }
    --#SEVERITY        MAJOR
    --#TIMEINDEX       1
    --#HELP            "1) Start initialization again."
    --#STATE           OPERATIONAL
    ::= 10240

-- EVT_LD_INIT_PROGRESS

svrTrapLDInitProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization progress."
    --#TYPE            "Initialization progress"
    --#SUMMARY         "Adapter %s: Initialization progress on logical drive %s is %s (Server %s)"
    --#ARGUMENTS       { 2, 3, 4, 0 }
    --#SEVERITY        INFORMATIONAL
    --#TIMEINDEX       1
    --#HELP            ""
    --#STATE           OPERATIONAL
    ::= 10241

-- EVT_LD_INIT_START_FAST

svrTrapLDInitStartFast TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Fast initialization started."
    --#TYPE            "Fast initialization started"
    --#SUMMARY         "Adapter %s: Fast initialization started on logical drive %s (Server %s)"
    --#ARGUMENTS       { 2, 3, 0 }
    --#SEVERITY        INFORMATIONAL
    --#TIMEINDEX       1
    --#HELP            ""
    --#STATE           OPERATIONAL
    ::= 10242

-- EVT_LD_INIT_START_FULL

svrTrapLDInitStartFull TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Full initialization started."
    --#TYPE            "Full initialization started"
    --#SUMMARY         "Adapter %s: Full initialization started on logical drive %s (Server %s)"
    --#ARGUMENTS       { 2, 3, 0 }
    --#SEVERITY        INFORMATIONAL
    --#TIMEINDEX       1
    --#HELP            ""
    --#STATE           OPERATIONAL
    ::= 10243

-- EVT_LD_PROP_CHANGE

svrTrapLDPropChange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Properties updated."
    --#TYPE            "Properties updated"
    --#SUMMARY         "Adapter %s: Logical drive %s: Property %s updated (Server %s)"
    --#ARGUMENTS       { 2, 3, 4, 0 }
    --#SEVERITY        INFORMATIONAL
    --#TIMEINDEX       1
    --#HELP            ""
    --#STATE           OPERATIONAL
    ::= 10244

-- EVT_LD_RECON_DOUBLE_MEDIUM_ERRORS

svrTrapLDReconDoubleMediumErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reconstruct detected uncorrectable double medium errors."
    --#TYPE            "Reconstruct detected uncorrectable double medium errors"
    --#SUMMARY         "Adapter %s: Migration detected uncorrectable multiple medium errors (logical drive %s at LBA %s on disk (%s) at LBA %s) (Server %s)"
    --#ARGUMENTS       { 2, 3, 4, 5, 6, 0 }
    --#SEVERITY        MAJOR
    --#TIMEINDEX       1
    --#HELP            "Replace affected disk."
    --#STATE           OPERATIONAL
    ::= 10245

-- EVT_LD_RECON_PROGRESS

svrTrapLDReconProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reconstruction progress."
    --#TYPE            "Reconstruction progress"
    --#SUMMARY         "Adapter %s: Migration progress on logical drive %s is %s (Server %s)"
    --#ARGUMENTS       { 2, 3, 4, 0 }
    --#SEVERITY        INFORMATIONAL
    --#TIMEINDEX       1
    --#HELP            ""
    --#STATE           OPERATIONAL
    ::= 10246

-- EVT_LD_RECON_RESUME

svrTrapLDReconResume TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reconstruction resumed."
    --#TYPE            "Reconstruction resumed"
    --#SUMMARY         "Adapter %s: Migration resumed on logical drive %s (Server %s)"
    --#ARGUMENTS       { 2, 3, 0 }
    --#SEVERITY        INFORMATIONAL
    --#TIMEINDEX       1
    --#HELP            ""
    --#STATE           OPERATIONAL
    ::= 10247

-- EVT_LD_RECON_RESUME_FAILED

svrTrapLDReconResumeFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reconstruction resume failed."
    --#TYPE            "Reconstruction resume failed"
    --#SUMMARY         "Adapter %s: Resume migration of logical drive %s failed due to Configuration Mismatch (Server %s)"
    --#ARGUMENTS       { 2, 3, 0 }
    --#SEVERITY        MAJOR
    --#TIMEINDEX       1
    --#HELP            "1) Check the RAID configuration and the event log for additional information. 2) Backup data from affected logical drive."
    --#STATE           OPERATIONAL
    ::= 10248

-- EVT_LD_STATE_CHANGE_OP_TO_OP

svrTrapLDStateChangedOpToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to operational."
    --#TYPE            "State change from operational to operational"
    --#SUMMARY         "Adapter %s: State change on logical drive %s from operational to operational (Server %s)"
    --#ARGUMENTS       { 2, 3, 0 }
    --#SEVERITY        INFORMATIONAL
    --#TIMEINDEX       1
    --#HELP            ""
    --#STATE           OPERATIONAL
    ::= 10249

-- EVT_PD_CLEAR_ABORTED

svrTrapPDClearAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Clear aborted."
    --#TYPE            "Clear aborted"
    --#SUMMARY         "Adapter %s: Clear aborted on disk (%s) (Server %s)"
    --#ARGUMENTS       { 2, 3, 0 }
    --#SEVERITY        MINOR
    --#TIMEINDEX       1
    --#HELP            "For information only."
    --#STATE           OPERATIONAL
    ::= 10250

-- EVT_PD_CLEAR_FAILED

svrTrapPDClearFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Clear failed."
    --#TYPE            "Clear failed"
    --#SUMMARY         "Adapter %s: Clear failed on disk (%s) (error %s) (Server %s)"
    --#ARGUMENTS       { 2, 3, 4, 0 }
    --#SEVERITY        MAJOR
    --#TIMEINDEX       1
    --#HELP            "1) Check version of RAID controller/iRMC firmware, and BIOS. 2) Verify that current RAID controller drivers are installed. 3) Disconnect AC and wait 30 seconds before reconnect."
    --#STATE           OPERATIONAL
    ::= 10251

-- EVT_PD_CLEAR_PROGRESS

svrTrapLDClearProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Clear progress."
    --#TYPE            "Clear progress"
    --#SUMMARY         "Adapter %s: Clear progress on disk (%s) is %s (Server %s)"
    --#ARGUMENTS       { 2, 3, 4, 0 }
    --#SEVERITY        INFORMATIONAL
    --#TIMEINDEX       1
    --#HELP            ""
    --#STATE           OPERATIONAL
    ::= 10252

-- EVT_PD_CLEAR_STARTED

svrTrapPDClearStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Clear started."
    --#TYPE            "Clear started"
    --#SUMMARY         "Adapter %s: Clear started on disk (%s) (Server %s)"
    --#ARGUMENTS       { 2, 3, 0 }
    --#SEVERITY        INFORMATIONAL
    --#TIMEINDEX       1
    --#HELP            ""
    --#STATE           OPERATIONAL
    ::= 10253

-- EVT_PD_CLEAR_SUCCESSFUL

svrTrapPDClearSuccessful TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Clear finished."
    --#TYPE            "Clear finished"
    --#SUMMARY         "Adapter %s: Clear finished on disk (%s) (Server %s)"
    --#ARGUMENTS       { 2, 3, 0 }
    --#SEVERITY        INFORMATIONAL
    --#TIMEINDEX       1
    --#HELP            ""
    --#STATE           OPERATIONAL
    ::= 10254

-- EVT_PD_ERR

svrTrapPDErr TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Error on disk."
    --#TYPE            "Error on disk"
    --#SUMMARY         "Adapter %s: Error on disk (%s) (error %s) (Server %s)"
    --#ARGUMENTS       { 2, 3, 4, 0 }
    --#SEVERITY        MAJOR
    --#TIMEINDEX       1
    --#HELP            "Replace affected disk."
    --#STATE           OPERATIONAL
    ::= 10255

-- EVT_PD_FORMAT_COMPLETE

svrTrapPDFormatComplete TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Format complete."
    --#TYPE            "Format complete"
    --#SUMMARY         "Adapter %s: Format complete on disk (%s) (Server %s)"
    --#ARGUMENTS       { 2, 3, 0 }
    --#SEVERITY        INFORMATIONAL
    --#TIMEINDEX       1
    --#HELP            ""
    --#STATE           OPERATIONAL
    ::= 10256

-- EVT_PD_FORMAT_STARTED

svrTrapPDFormatStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Format started."
    --#TYPE            "Format started"
    --#SUMMARY         "Adapter %s: Format started on disk (%s) (Server %s)"
    --#ARGUMENTS       { 2, 3, 0 }
    --#SEVERITY        INFORMATIONAL
    --#TIMEINDEX       1
    --#HELP            ""
    --#STATE           OPERATIONAL
    ::= 10257

-- EVT_PD_HS_SMART_POLL_FAILED

svrTrapPDHSSmartPollFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hot spare SMART polling failed."
    --#TYPE            "Hot spare SMART polling failed"
    --#SUMMARY         "Adapter %s: Hot spare SMART polling failed on disk (%s) (error %s) (Server %s)"
    --#ARGUMENTS       { 2, 3, 4, 0 }
    --#SEVERITY        MAJOR
    --#TIMEINDEX       1
    --#HELP            "Call your local Fujitsu Helpdesk."
    --#STATE           OPERATIONAL
    ::= 10258

-- EVT_PD_NOT_SUPPORTED

svrTrapPDNotSupported TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk not supported."
    --#TYPE            "Disk not supported"
    --#SUMMARY         "Adapter %s: Disk (%s) is not supported (Server %s)"
    --#ARGUMENTS       { 2, 3, 0 }
    --#SEVERITY        MAJOR
    --#TIMEINDEX       1
    --#HELP            "Install supported disk."
    --#STATE           OPERATIONAL
    ::= 10259

-- EVT_PD_PR_CORRECTED

svrTrapPDPRCorrected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read corrected medium error."
    --#TYPE            "Patrol Read corrected medium error"
    --#SUMMARY         "Adapter %s: Patrol Read corrected medium error on disk (%s) at LBA %s (Server %s)"
    --#ARGUMENTS       { 2, 3, 4, 0 }
    --#SEVERITY        INFORMATIONAL
    --#TIMEINDEX       1
    --#HELP            ""
    --#STATE           OPERATIONAL
    ::= 10260

-- EVT_PD_PR_PROGRESS

svrTrapPDPRProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read progress."
    --#TYPE            "Patrol Read progress"
    --#SUMMARY         "Adapter %s: Patrol Read progress on disk (%s) is %s (Server %s)"
    --#ARGUMENTS       { 2, 3, 4, 0 }
    --#SEVERITY        INFORMATIONAL
    --#TIMEINDEX       1
    --#HELP            ""
    --#STATE           OPERATIONAL
    ::= 10261

-- EVT_PD_PR_UNCORRECTABLE

svrTrapPDPRUncorrectable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read found an uncorrectable medium error."
    --#TYPE            "Patrol Read found an uncorrectable medium error"
    --#SUMMARY         "Adapter %s: Patrol Read found an uncorrectable medium error on disk (%s) at LBA %s (Server %s)"
    --#ARGUMENTS       { 2, 3, 4, 0 }
    --#SEVERITY        MAJOR
    --#TIMEINDEX       1
    --#HELP            "Replace affected disk."
    --#STATE           OPERATIONAL
    ::= 10262

-- EVT_PD_PREDICTIVE_THRESHOLD_EXCEEDED

svrTrapPDPredictiveThresholdExceeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Predictive failure."
    --#TYPE            "Predictive failure"
    --#SUMMARY         "Adapter %s: Predictive failure: Disk (%s) (Server %s)"
    --#ARGUMENTS       { 2, 3, 0 }
    --#SEVERITY        MINOR
    --#TIMEINDEX       1
    --#HELP            "Note: Disk reports a prefailure. The affected disk might fail soon. 1) Replace the disk during next maintenance."
    --#STATE           OPERATIONAL
    ::= 10263

-- EVT_PD_PUNCTURE

svrTrapPDPuncture TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Puncturing bad block."
    --#TYPE            "Puncturing bad block"
    --#SUMMARY         "Adapter %s: Puncturing bad block on disk (%s) at LBA %s (Server %s)"
    --#ARGUMENTS       { 2, 3, 4, 0 }
    --#SEVERITY        MAJOR
    --#TIMEINDEX       1
    --#HELP            "Replace affected disk."
    --#STATE           OPERATIONAL
    ::= 10264

-- EVT_PD_RBLD_ABORT_BY_USER

svrTrapPDRbldAbortByUser TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild aborted by user."
    --#TYPE            "Rebuild aborted by user"
    --#SUMMARY         "Adapter %s: Rebuild aborted by user on disk (%s) (Server %s)"
    --#ARGUMENTS       { 2, 3, 0 }
    --#SEVERITY        MINOR
    --#TIMEINDEX       1
    --#HELP            "For information only."
    --#STATE           DEGRADED
    ::= 10265

-- EVT_PD_RBLD_DONE_LD

svrTrapPDRbldDoneLD TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild complete on logical drive."
    --#TYPE            "Rebuild complete on logical drive"
    --#SUMMARY         "Adapter %s: Rebuild complete on logical drive %s (Server %s)"
    --#ARGUMENTS       { 2, 3, 0 }
    --#SEVERITY        INFORMATIONAL
    --#TIMEINDEX       1
    --#HELP            ""
    --#STATE           OPERATIONAL
    ::= 10266

-- EVT_PD_RBLD_DONE_PD

svrTrapPDRbldDonePD TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild complete on disk."
    --#TYPE            "Rebuild complete on disk"
    --#SUMMARY         "Adapter %s: Rebuild complete on disk (%s) (Server %s)"
    --#ARGUMENTS       { 2, 3, 0 }
    --#SEVERITY        INFORMATIONAL
    --#TIMEINDEX       1
    --#HELP            ""
    --#STATE           OPERATIONAL
    ::= 10267

-- EVT_PD_RBLD_PROGRESS

svrTrapPDRbldProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild progress."
    --#TYPE            "Rebuild progress"
    --#SUMMARY         "Adapter %s: Rebuild progress on disk (%s) is %s (Server %s)"
    --#ARGUMENTS       { 2, 3, 4, 0 }
    --#SEVERITY        INFORMATIONAL
    --#TIMEINDEX       1
    --#HELP            ""
    --#STATE           DEGRADED
    ::= 10268

-- EVT_PD_RBLD_RESUME

svrTrapPDRbldResume TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild resumed."
    --#TYPE            "Rebuild resumed"
    --#SUMMARY         "Adapter %s: Rebuild resumed on disk (%s) (Server %s)"
    --#ARGUMENTS       { 2, 3, 0 }
    --#SEVERITY        INFORMATIONAL
    --#TIMEINDEX       1
    --#HELP            ""
    --#STATE           DEGRADED
    ::= 10269

-- EVT_PD_RBLD_START_AUTO

svrTrapPDRbldStartAuto TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild automatically started."
    --#TYPE            "Rebuild automatically started"
    --#SUMMARY         "Adapter %s: Rebuild automatically started on disk (%s) (Server %s)"
    --#ARGUMENTS       { 2, 3, 0 }
    --#SEVERITY        INFORMATIONAL
    --#TIMEINDEX       1
    --#HELP            ""
    --#STATE           DEGRADED
    ::= 10270

-- EVT_PD_RBLD_STOP_BY_OWNERSHIP_LOSS

svrTrapPDRbldStopByOwnershipLoss TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild stopped."
    --#TYPE            "Rebuild stopped"
    --#SUMMARY         "Adapter %s: Rebuild stopped on disk (%s) due to loss of cluster ownership (Server %s)"
    --#ARGUMENTS       { 2, 3, 0 }
    --#SEVERITY        MAJOR
    --#TIMEINDEX       1
    --#HELP            "1) Restart rebuild."
    --#STATE           DEGRADED
    ::= 10271

-- EVT_PD_REASSIGN_WRITE_FAILED

svrTrapPDReassignWriteFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reassign write operation failed."
    --#TYPE            "Reassign write operation failed"
    --#SUMMARY         "Adapter %s: Reassign write operation failed on disk (%s) at LBA %s (Server %s)"
    --#ARGUMENTS       { 2, 3, 4, 0 }
    --#SEVERITY        MAJOR
    --#TIMEINDEX       1
    --#HELP            "Replace affected disk."
    --#STATE           OPERATIONAL
    ::= 10272

-- EVT_PD_REBUILD_MEDIUM_ERROR

svrTrapPDRebuildMediumError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unrecoverable medium error during rebuild."
    --#TYPE            "Unrecoverable medium error during rebuild"
    --#SUMMARY         "Adapter %s: Unrecoverable medium error during rebuild on disk (%s) at LBA %s (Server %s)"
    --#ARGUMENTS       { 2, 3, 4, 0 }
    --#SEVERITY        MAJOR
    --#TIMEINDEX       1
    --#HELP            "Replace affected disk."
    --#STATE           DEGRADED
    ::= 10273

-- EVT_PD_REC_CORRECTING

svrTrapPDRecCorrecting TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Corrected medium error during recovery."
    --#TYPE            "Corrected medium error during recovery"
    --#SUMMARY         "Adapter %s: Corrected medium error during recovery on disk (%s) at LBA %s (Server %s)"
    --#ARGUMENTS       { 2, 3, 4, 0 }
    --#SEVERITY        INFORMATIONAL
    --#TIMEINDEX       1
    --#HELP            ""
    --#STATE           OPERATIONAL
    ::= 10274

-- EVT_PD_RECOVER_MEDIUM_ERROR

svrTrapPDRecoverMediumError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unrecoverable medium error during recovery."
    --#TYPE            "Unrecoverable medium error during recovery"
    --#SUMMARY         "Adapter %s: Unrecoverable medium error during recovery on disk (%s) at LBA %s (Server %s)"
    --#ARGUMENTS       { 2, 3, 4, 0 }
    --#SEVERITY        MAJOR
    --#TIMEINDEX       1
    --#HELP            "Replace affected disk."
    --#STATE           OPERATIONAL
    ::= 10275

-- EVT_PD_SENSE

svrTrapPDSense TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unexpected sense."
    --#TYPE            "Unexpected sense"
    --#SUMMARY         "Adapter %s: Unexpected sense: Disk (%s), Key/ASC/ASCQ: %s: %s (Server %s)"
    --#ARGUMENTS       { 2, 3, 4, 5, 0 }
    --#SEVERITY        INFORMATIONAL
    --#TIMEINDEX       1
    --#HELP            ""
    --#STATE           OPERATIONAL
    ::= 10276

-- EVT_PD_STATE_CHANGE_AVAIL_TO_AVAIL

svrTrapPDStateChangeAvailToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to available."
    --#TYPE            "State change from available to available"
    --#SUMMARY         "Adapter %s: State change on disk (%s) from available to available (Server %s)"
    --#ARGUMENTS       { 2, 3, 0 }
    --#SEVERITY        INFORMATIONAL
    --#TIMEINDEX       1
    --#HELP            ""
    --#STATE           OPERATIONAL
    ::= 10277

-- EVT_PD_STATE_CHANGE_BY_USER_AVAIL_TO_AVAIL

svrTrapPDStateChangeByUserAvailToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to available."
    --#TYPE            "State change by user from available to available"
    --#SUMMARY         "Adapter %s: State change by user on disk (%s) from available to available (Server %s)"
    --#ARGUMENTS       { 2, 3, 0 }
    --#SEVERITY        INFORMATIONAL
    --#TIMEINDEX       1
    --#HELP            ""
    --#STATE           OPERATIONAL
    ::= 10278

-- EVT_PD_REDUNDANT_PATH_BROKEN

svrTrapPDRedundantPathBroken TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundant path broken."
    --#TYPE            "Redundant path broken"
    --#SUMMARY         "Adapter %s: Redundant path to disk (%s) broken (Server %s)"
    --#ARGUMENTS       { 2, 3, 0 }
    --#SEVERITY        MAJOR
    --#TIMEINDEX       1
    --#HELP            "Call your local Fujitsu Helpdesk."
    --#STATE           OPERATIONAL
    ::= 10279

-- EVT_PD_REDUNDANT_PATH_RESTORED

svrTrapPDRedundantPathRestored TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundant path restored."
    --#TYPE            "Redundant path restored"
    --#SUMMARY         "Adapter %s: Redundant path to disk (%s) restored (Server %s)"
    --#ARGUMENTS       { 2, 3, 0 }
    --#SEVERITY        INFORMATIONAL
    --#TIMEINDEX       1
    --#HELP            ""
    --#STATE           OPERATIONAL
    ::= 10280

-- EVT_PD_DEDICATED_SPARE_NO_LONGER_USEFUL

svrTrapPDDedicatedSpareNoLongerUseful TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Dedicated hot spare no longer useful."
    --#TYPE            "Dedicated hot spare no longer useful"
    --#SUMMARY         "Adapter %s: Dedicated hot spare (%s) no longer useful due to deleted array (Server %s)"
    --#ARGUMENTS       { 2, 3, 0 }
    --#SEVERITY        MINOR
    --#TIMEINDEX       1
    --#HELP            "For information only."
    --#STATE           OPERATIONAL
    ::= 10281

-- EVT_SAS_TOPOLOGY_LOOP_DETECTED

svrTrapSASTolologyLoopDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Loop detected."
    --#TYPE            "SAS topology error: Loop detected"
    --#SUMMARY         "Adapter %s: SAS topology error: Loop detected (Server %s)"
    --#ARGUMENTS       { 2, 0 }
    --#SEVERITY        MAJOR
    --#TIMEINDEX       1
    --#HELP            "Check the SAS configuration and cabling."
    --#STATE           OPERATIONAL
    ::= 10282

-- EVT_SAS_TOPOLOGY_UNADDRESSABLE_DEVICE

svrTrapSASTopologyUnaddressableDevice TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Unaddressable device."
    --#TYPE            "SAS topology error: Unaddressable device"
    --#SUMMARY         "Adapter %s: SAS topology error: Unaddressable device (Server %s)"
    --#ARGUMENTS       { 2, 0 }
    --#SEVERITY        MAJOR
    --#TIMEINDEX       1
    --#HELP            "Check the SAS configuration and cabling."
    --#STATE           OPERATIONAL
    ::= 10283

-- EVT_SAS_TOPOLOGY_MULTIPLE_PORTS_TO_SAME_ADDR

svrTrapSASTopologyMultiplePortsToSameAddr TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Multiple ports to the same SAS address."
    --#TYPE            "SAS topology error: Multiple ports to the same SAS address"
    --#SUMMARY         "Adapter %s: SAS topology error: Multiple ports to the same SAS address (Server %s)"
    --#ARGUMENTS       { 2, 0 }
    --#SEVERITY        MAJOR
    --#TIMEINDEX       1
    --#HELP            "Check the SAS configuration and cabling."
    --#STATE           OPERATIONAL
    ::= 10284

-- EVT_SAS_TOPOLOGY_EXPANDER_ERR

svrTrapSASTopologyExpanderErr TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Expander error."
    --#TYPE            "SAS topology error: Expander error"
    --#SUMMARY         "Adapter %s: SAS topology error: Expander error (Server %s)"
    --#ARGUMENTS       { 2, 0 }
    --#SEVERITY        MAJOR
    --#TIMEINDEX       1
    --#HELP            "1) Check the SAS configuration and cabling. 2) If problem persists replace affected backplane."
    --#STATE           OPERATIONAL
    ::= 10285

-- EVT_SAS_TOPOLOGY_SMP_TIMEOUT

svrTrapSASTopologySMPTimeout TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: SMP timeout."
    --#TYPE            "SAS topology error: SMP timeout"
    --#SUMMARY         "Adapter %s: SAS topology error: SMP timeout (Server %s)"
    --#ARGUMENTS       { 2, 0 }
    --#SEVERITY        MAJOR
    --#TIMEINDEX       1
    --#HELP            "Check the SAS configuration and cabling."
    --#STATE           OPERATIONAL
    ::= 10286

-- EVT_SAS_TOPOLOGY_OUT_OF_ROUTE_ENTRIES

svrTrapSASTopologyOutOfRouteEntries TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Out of route entries."
    --#TYPE            "SAS topology error: Out of route entries"
    --#SUMMARY         "Adapter %s: SAS topology error: Out of route entries (Server %s)"
    --#ARGUMENTS       { 2, 0 }
    --#SEVERITY        MAJOR
    --#TIMEINDEX       1
    --#HELP            "Check the SAS configuration and cabling."
    --#STATE           OPERATIONAL
    ::= 10287

-- EVT_SAS_TOPOLOGY_INDEX_NOT_FOUND

svrTrapSASTopologyIndexNotFound TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Index not found."
    --#TYPE            "SAS topology error: Index not found"
    --#SUMMARY         "Adapter %s: SAS topology error: Index not found (Server %s)"
    --#ARGUMENTS       { 2, 0 }
    --#SEVERITY        MAJOR
    --#TIMEINDEX       1
    --#HELP            "Check the SAS configuration and cabling."
    --#STATE           OPERATIONAL
    ::= 10288

-- EVT_SAS_TOPOLOGY_SMP_FUNCTION_FAILED

svrTrapSASTopologySMPFunctionFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: SMP function failed."
    --#TYPE            "SAS topology error: SMP function failed"
    --#SUMMARY         "Adapter %s: SAS topology error: SMP function failed (Server %s)"
    --#ARGUMENTS       { 2, 0 }
    --#SEVERITY        MAJOR
    --#TIMEINDEX       1
    --#HELP            "Check the SAS configuration and cabling."
    --#STATE           OPERATIONAL
    ::= 10289

-- EVT_SAS_TOPOLOGY_SMP_CRC_ERROR

svrTrapSASTopologySMPCRCError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: SMP CRC error."
    --#TYPE            "SAS topology error: SMP CRC error"
    --#SUMMARY         "Adapter %s: SAS topology error: SMP CRC error (Server %s)"
    --#ARGUMENTS       { 2, 0 }
    --#SEVERITY        MAJOR
    --#TIMEINDEX       1
    --#HELP            "Check the SAS configuration and cabling."
    --#STATE           OPERATIONAL
    ::= 10290

-- EVT_SAS_TOPOLOGY_MULITPLE_SUBTRACTIVE

svrTrapSASTopologyMultipleSubtractive TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Multiple subtractive."
    --#TYPE            "SAS topology error: Multiple subtractive"
    --#SUMMARY         "Adapter %s: SAS topology error: Multiple subtractive (Server %s)"
    --#ARGUMENTS       { 2, 0 }
    --#SEVERITY        MAJOR
    --#TIMEINDEX       1
    --#HELP            "Check the SAS configuration and cabling."
    --#STATE           OPERATIONAL
    ::= 10291

-- EVT_SAS_TOPOLOGY_TABLE_TO_TABLE

svrTrapSASTopologyTableToTable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Table to table."
    --#TYPE            "SAS topology error: Table to table"
    --#SUMMARY         "Adapter %s: SAS topology error: Table to table (Server %s)"
    --#ARGUMENTS       { 2, 0 }
    --#SEVERITY        MAJOR
    --#TIMEINDEX       1
    --#HELP            "Check the SAS configuration and cabling."
    --#STATE           OPERATIONAL
    ::= 10292

-- EVT_SAS_TOPOLOGY_MULTIPLE_PATHS

svrTrapSASTopologyMultiplePaths TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error: Multiple paths."
    --#TYPE            "SAS topology error: Multiple paths"
    --#SUMMARY         "Adapter %s: SAS topology error: Multiple paths (Server %s)"
    --#ARGUMENTS       { 2, 0 }
    --#SEVERITY        MAJOR
    --#TIMEINDEX       1
    --#HELP            "Check the SAS configuration and cabling."
    --#STATE           OPERATIONAL
    ::= 10293

-- EVT_PD_UNUSABLE

svrTrapPDUnusable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unable to access disk."
    --#TYPE            "Unable to access disk"
    --#SUMMARY         "Adapter %s: Unable to access disk (%s) (Server %s)"
    --#ARGUMENTS       { 2, 3, 0 }
    --#SEVERITY        MAJOR
    --#TIMEINDEX       1
    --#HELP            "1) Unplug affected disk, wait 30 seconds, reinsert it. 2) Replace affected disk. 3) Replace affected backplane."
    --#STATE           OPERATIONAL
    ::= 10294

-- EVT_PD_SPARE_DEDICATED_NOT_USEFUL_FOR_ALL_ARRAYS

svrTrapPDSpareDedicatedNotUsefulForAllArrays TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Dedicated hot spare not useful for all arrays."
    --#TYPE            "Dedicated hot spare not useful for all arrays"
    --#SUMMARY         "Adapter %s: Dedicated hot spare not useful for all arrays (Server %s)"
    --#ARGUMENTS       { 2, 0 }
    --#SEVERITY        MINOR
    --#TIMEINDEX       1
    --#HELP            "For information only."
    --#STATE           OPERATIONAL
    ::= 10295

-- EVT_PD_SPARE_GLOBAL_NOT_COVERING_ALL_ARRAYS

svrTrapPDSpareGlobalNotCoveringAllArrays TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Global hot spare does not cover all arrays."
    --#TYPE            "Global hot spare does not cover all arrays"
    --#SUMMARY         "Adapter %s: Global hot spare does not cover all arrays (Server %s)"
    --#ARGUMENTS       { 2, 0 }
    --#SEVERITY        MINOR
    --#TIMEINDEX       1
    --#HELP            "Note: The size of the global hot spare is not sufficient to secure all arrays."
    --#STATE           OPERATIONAL
    ::= 10296

-- EVT_LD_INCONSISTENT_DUE_AT_STARTUP

svrTrapLDInconsistentDueAtStartup TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Marking inconsistent."
    --#TYPE            "Marking inconsistent"
    --#SUMMARY         "Adapter %s: Marking logical drive %s inconsistent due to active writes at shutdown (Server %s)"
    --#ARGUMENTS       { 2, 3, 0 }
    --#SEVERITY        MINOR
    --#TIMEINDEX       1
    --#HELP            "Initiate consistency check (e.g. via ServerView RAID Manager)."
    --#STATE           OPERATIONAL
    ::= 10297

-- EVT_BBU_PRESENT

svrTrapBBUPresent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU present."
    --#TYPE            "BBU present"
    --#SUMMARY         "Adapter %s: BBU present (Server %s)"
    --#ARGUMENTS       { 2, 0 }
    --#SEVERITY        INFORMATIONAL
    --#TIMEINDEX       1
    --#HELP            ""
    --#STATE           OPERATIONAL
    ::= 10298

-- EVT_BBU_NOT_PRESENT

svrTrapBBUNotPresent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU not present."
    --#TYPE            "BBU not present"
    --#SUMMARY         "Adapter %s: BBU not present (Server %s)"
    --#ARGUMENTS       { 2, 0 }
    --#SEVERITY        INFORMATIONAL
    --#TIMEINDEX       1
    --#HELP            "If the system does not have a BBU this is for information only. If the system does have a BBU replace the BBU."
    --#STATE           OPERATIONAL
    ::= 10299

-- EVT_BBU_NEW_BATTERY_DETECTED

svrTrapBBUNewBatteryDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "New BBU detected."
    --#TYPE            "New BBU detected"
    --#SUMMARY         "Adapter %s: New BBU detected (Server %s)"
    --#ARGUMENTS       { 2, 0 }
    --#SEVERITY        INFORMATIONAL
    --#TIMEINDEX       1
    --#HELP            ""
    --#STATE           OPERATIONAL
    ::= 10300

-- EVT_BBU_REPLACED

svrTrapBBUReplaced TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU has been replaced."
    --#TYPE            "BBU has been replaced"
    --#SUMMARY         "Adapter %s: BBU has been replaced (Server %s)"
    --#ARGUMENTS       { 2, 0 }
    --#SEVERITY        INFORMATIONAL
    --#TIMEINDEX       1
    --#HELP            ""
    --#STATE           OPERATIONAL
    ::= 10301

-- EVT_BBU_TEMPERATURE_NORMAL

svrTrapBBUTemperatureNormal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU temperature is normal."
    --#TYPE            "BBU temperature is normal"
    --#SUMMARY         "Adapter %s: BBU temperature is normal (Server %s)"
    --#ARGUMENTS       { 2, 0 }
    --#SEVERITY        INFORMATIONAL
    --#TIMEINDEX       1
    --#HELP            ""
    --#STATE           OPERATIONAL
    ::= 10302

-- EVT_BBU_REPLACEMENT_NEEDED_SOH_BAD

svrTrapBBUReplacementNeededSOHBad TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU has failed and cannot support data retention."
    --#TYPE            "BBU needs replacement"
    --#SUMMARY         "Adapter %s: BBU has failed and cannot support data retention (Server %s)"
    --#ARGUMENTS       { 2, 0 }
    --#SEVERITY        MAJOR
    --#TIMEINDEX       1
    --#HELP            "If the error message occurs right after replacement of the BBU it can be safely ignored. The situation can occur due to the insufficient BBU charge. If the error message occurs during regular operation replace the BBU."
    --#STATE           OPERATIONAL
    ::= 10303

-- EVT_BBU_RELEARN_STARTED

svrTrapBBURelearnStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn started."
    --#TYPE            "BBU relearn started"
    --#SUMMARY         "Adapter %s: BBU relearn started (Server %s)"
    --#ARGUMENTS       { 2, 0 }
    --#SEVERITY        INFORMATIONAL
    --#TIMEINDEX       1
    --#HELP            ""
    --#STATE           OPERATIONAL
    ::= 10304

-- EVT_BBU_RELEARN_IN_PROGRESS

svrTrapBBURelearnInProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn in progress."
    --#TYPE            "BBU relearn in progress"
    --#SUMMARY         "Adapter %s: BBU relearn in progress (Server %s)"
    --#ARGUMENTS       { 2, 0 }
    --#SEVERITY        INFORMATIONAL
    --#TIMEINDEX       1
    --#HELP            ""
    --#STATE           OPERATIONAL
    ::= 10305

-- EVT_BBU_RELEARN_COMPLETE

svrTrapBBURelearnComplete TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn finished."
    --#TYPE            "BBU relearn finished"
    --#SUMMARY         "Adapter %s: BBU relearn finished (Server %s)"
    --#ARGUMENTS       { 2, 0 }
    --#SEVERITY        INFORMATIONAL
    --#TIMEINDEX       1
    --#HELP            ""
    --#STATE           OPERATIONAL
    ::= 10306

-- EVT_BBU_RELEARN_TIMEOUT

svrTrapBBURelearnTimeout TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn timed out."
    --#TYPE            "BBU relearn timed out"
    --#SUMMARY         "Adapter %s: BBU relearn timed out (Server %s)"
    --#ARGUMENTS       { 2, 0 }
    --#SEVERITY        MINOR
    --#TIMEINDEX       1
    --#HELP            "1) Initiate manual recalibration process (e.g. via ServerView RAID Manager). Note: Do not interrupt the charging process by reboots or shutdowns. 2) If problem persists replace BBU."
    --#STATE           OPERATIONAL
    ::= 10307

-- EVT_BBU_RELEARN_PENDING

svrTrapBBURelearnPending TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn pending."
    --#TYPE            "BBU relearn pending"
    --#SUMMARY         "Adapter %s: BBU relearn pending: BBU is under charge (Server %s)"
    --#ARGUMENTS       { 2, 0 }
    --#SEVERITY        INFORMATIONAL
    --#TIMEINDEX       1
    --#HELP            ""
    --#STATE           OPERATIONAL
    ::= 10308

-- EVT_BBU_RELEARN_POSTPONED

svrTrapBBUrelearnPostponed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn postponed."
    --#TYPE            "BBU relearn postponed"
    --#SUMMARY         "Adapter %s: BBU relearn postponed (Server %s)"
    --#ARGUMENTS       { 2, 0 }
    --#SEVERITY        INFORMATIONAL
    --#TIMEINDEX       1
    --#HELP            ""
    --#STATE           OPERATIONAL
    ::= 10309

-- EVT_BBU_RELEARN_WILL_START_IN_4_DAYS

svrTrapBBURelearnWillStartIn4Days TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn will start in 4 days."
    --#TYPE            "BBU relearn will start in 4 days"
    --#SUMMARY         "Adapter %s: BBU relearn will start in 4 days (Server %s)"
    --#ARGUMENTS       { 2, 0 }
    --#SEVERITY        INFORMATIONAL
    --#TIMEINDEX       1
    --#HELP            ""
    --#STATE           OPERATIONAL
    ::= 10310

-- EVT_BBU_RELEARN_WILL_START_IN_2_DAYS

svrTrapBBURelearnWillStartIn2Days TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn will start in 2 days."
    --#TYPE            "BBU relearn will start in 2 days"
    --#SUMMARY         "Adapter %s: BBU relearn will start in 2 days (Server %s)"
    --#ARGUMENTS       { 2, 0 }
    --#SEVERITY        INFORMATIONAL
    --#TIMEINDEX       1
    --#HELP            ""
    --#STATE           OPERATIONAL
    ::= 10311

-- EVT_BBU_RELEARN_WILL_START_IN_1_DAYS

svrTrapBBURelearnWillStartIn1Days TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn will start in 1 day."
    --#TYPE            "BBU relearn will start in 1 day"
    --#SUMMARY         "Adapter %s: BBU relearn will start in 1 day (Server %s)"
    --#ARGUMENTS       { 2, 0 }
    --#SEVERITY        INFORMATIONAL
    --#TIMEINDEX       1
    --#HELP            ""
    --#STATE           OPERATIONAL
    ::= 10312

-- EVT_BBU_RELEARN_WILL_START_IN_5_HOURS

svrTrapBBURelearnWillStartIn5Hours TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU relearn will start in 5 hours."
    --#TYPE            "BBU relearn will start in 5 hours"
    --#SUMMARY         "Adapter %s: BBU Relearn will start in 5 hours (Server %s)"
    --#ARGUMENTS       { 2, 0 }
    --#SEVERITY        INFORMATIONAL
    --#TIMEINDEX       1
    --#HELP            ""
    --#STATE           OPERATIONAL
    ::= 10313

-- EVT_BBU_BATTERY_REMOVED

svrTrapBBUBatteryRemoved TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU removed."
    --#TYPE            "BBU removed"
    --#SUMMARY         "Adapter %s: BBU removed (Server %s)"
    --#ARGUMENTS       { 2, 0 }
    --#SEVERITY        MINOR
    --#TIMEINDEX       1
    --#HELP            "For information only."
    --#STATE           OPERATIONAL
    ::= 10314

-- EVT_ENCL_DISCOVERED_SES

svrTrapEnclDiscoveredSES TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure (SES) discovered."
    --#TYPE            "Enclosure (SES) discovered"
    --#SUMMARY         "Adapter %s: Enclosure (SES) discovered on %s (Server %s)"
    --#ARGUMENTS       { 2, 3, 0 }
    --#SEVERITY        INFORMATIONAL
    --#TIMEINDEX       1
    --#HELP            ""
    --#STATE           OPERATIONAL
    ::= 10315

-- EVT_ENCL_DISCOVERED_SAFTE

svrTrapEnclDiscoveredSAFTE TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure (SAF-TE) discovered."
    --#TYPE            "Enclosure (SAF-TE) discovered"
    --#SUMMARY         "Adapter %s: Enclosure (SAF-TE) discovered on %s (Server %s)"
    --#ARGUMENTS       { 2, 3, 0 }
    --#SEVERITY        INFORMATIONAL
    --#TIMEINDEX       1
    --#HELP            ""
    --#STATE           OPERATIONAL
    ::= 10316

-- EVT_ENCL_COMMUNICATION_LOST

svrTrapEnclCommunicationLost TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure communication lost."
    --#TYPE            "Enclosure communication lost"
    --#SUMMARY         "Adapter %s: Enclosure %s communication lost (Server %s)"
    --#ARGUMENTS       { 2, 3, 0 }
    --#SEVERITY        MINOR
    --#TIMEINDEX       1
    --#HELP            "1) Check data cable(s) to enclosure. 2) Check if enclosure is running."
    --#STATE           OPERATIONAL
    ::= 10317

-- EVT_ENCL_COMMUNICATION_RESTORED

svrTrapEnclCommunicationRestored TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure communication restored."
    --#TYPE            "Enclosure communication restored"
    --#SUMMARY         "Adapter %s: Enclosure %s communication restored (Server %s)"
    --#ARGUMENTS       { 2, 3, 0 }
    --#SEVERITY        INFORMATIONAL
    --#TIMEINDEX       1
    --#HELP            ""
    --#STATE           OPERATIONAL
    ::= 10318

-- EVT_ENCL_FAN_INSERTED

svrTrapEnclFanInserted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure fan inserted."
    --#TYPE            "Enclosure fan inserted"
    --#SUMMARY         "Adapter %s: Enclosure %s fan %s inserted (Server %s)"
    --#ARGUMENTS       { 2, 3, 4, 0 }
    --#SEVERITY        INFORMATIONAL
    --#TIMEINDEX       1
    --#HELP            ""
    --#STATE           OPERATIONAL
    ::= 10319

-- EVT_ENCL_FAN_REMOVED

svrTrapEnclFanRemoved TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure fan removed."
    --#TYPE            "Enclosure fan removed"
    --#SUMMARY         "Adapter %s: Enclosure %s fan %s removed (Server %s)"
    --#ARGUMENTS       { 2, 3, 4, 0 }
    --#SEVERITY        MINOR
    --#TIMEINDEX       1
    --#HELP            "For information only."
    --#STATE           OPERATIONAL
    ::= 10320

-- EVT_ENCL_SIM_FAILED

svrTrapEnclSIMFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure I/O module failed."
    --#TYPE            "Enclosure I/O module failed"
    --#SUMMARY         "Adapter %s: Enclosure %s I/O module %s failed (Server %s)"
    --#ARGUMENTS       { 2, 3, 4, 0 }
    --#SEVERITY        MAJOR
    --#TIMEINDEX       1
    --#HELP            "Call your local Fujitsu Helpdesk."
    --#STATE           OPERATIONAL
    ::= 10321

-- EVT_ENCL_SIM_INSERTED

svrTrapEnclSIMInserted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure I/O module inserted."
    --#TYPE            "Enclosure I/O module inserted"
    --#SUMMARY         "Adapter %s: Enclosure %s I/O module %s inserted (Server %s)"
    --#ARGUMENTS       { 2, 3, 4, 0 }
    --#SEVERITY        INFORMATIONAL
    --#TIMEINDEX       1
    --#HELP            ""
    --#STATE           OPERATIONAL
    ::= 10322

-- EVT_ENCL_SIM_REMOVED

svrTrapEnclSimRemoved TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure I/O module removed."
    --#TYPE            "Enclosure I/O module removed"
    --#SUMMARY         "Adapter %s: Enclosure %s I/O module %s removed (Server %s)"
    --#ARGUMENTS       { 2, 3, 4, 0 }
    --#SEVERITY        MAJOR
    --#TIMEINDEX       1
    --#HELP            "For information only."
    --#STATE           OPERATIONAL
    ::= 10323

-- EVT_ENCL_SHUTDOWN

svrTrapEnclShutdown TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure shutdown."
    --#TYPE            "Enclosure shutdown"
    --#SUMMARY         "Adapter %s: Enclosure %s shutdown (Server %s)"
    --#ARGUMENTS       { 2, 3, 0 }
    --#SEVERITY        MAJOR
    --#TIMEINDEX       1
    --#HELP            "For information only."
    --#STATE           OPERATIONAL
    ::= 10324

-- EVT_ENCL_MAX_PER_PORT_EXCEEDED

svrTrapEnclMaxPerPortExceeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure not supported; too many enclosures connected to port."
    --#TYPE            "Enclosure not supported; too many enclosures connected to port"
    --#SUMMARY         "Adapter %s: Enclosure %s not supported; too many enclosures connected to port (Server %s)"
    --#ARGUMENTS       { 2, 3, 0 }
    --#SEVERITY        MINOR
    --#TIMEINDEX       1
    --#HELP            "Check your enclosure configuration."
    --#STATE           OPERATIONAL
    ::= 10325

-- EVT_ENCL_FIRMWARE_MISMATCH

svrTrapEnclFirmwareMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure firmware mismatch."
    --#TYPE            "Enclosure firmware mismatch"
    --#SUMMARY         "Adapter %s: Enclosure %s firmware mismatch (I/O module %s) (Server %s)"
    --#ARGUMENTS       { 2, 3, 4, 0 }
    --#SEVERITY        MAJOR
    --#TIMEINDEX       1
    --#HELP            "Call your local Fujitsu Helpdesk."
    --#STATE           OPERATIONAL
    ::= 10326

-- EVT_ENCL_BAD_SENSOR

svrTrapEnclBadSensor TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure sensor bad."
    --#TYPE            "Enclosure sensor bad"
    --#SUMMARY         "Adapter %s: Enclosure %s sensor %s bad (Server %s)"
    --#ARGUMENTS       { 2, 3, 4, 0 }
    --#SEVERITY        MAJOR
    --#TIMEINDEX       1
    --#HELP            "Call your local Fujitsu Helpdesk."
    --#STATE           OPERATIONAL
    ::= 10327

-- EVT_ENCL_BAD_PHY

svrTrapEnclBadPhy TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure PHY bad."
    --#TYPE            "Enclosure PHY bad"
    --#SUMMARY         "Adapter %s: Enclosure %s PHY bad for slot %s (Server %s)"
    --#ARGUMENTS       { 2, 3, 4, 0 }
    --#SEVERITY        MAJOR
    --#TIMEINDEX       1
    --#HELP            "Replace affected disk."
    --#STATE           OPERATIONAL
    ::= 10328

-- EVT_ENCL_UNSTABLE

svrTrapEnclUnstable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure is unstable."
    --#TYPE            "Enclosure is unstable"
    --#SUMMARY         "Adapter %s: Enclosure %s is unstable (Server %s)"
    --#ARGUMENTS       { 2, 3, 0 }
    --#SEVERITY        MAJOR
    --#TIMEINDEX       1
    --#HELP            "Call your local Fujitsu Helpdesk."
    --#STATE           OPERATIONAL
    ::= 10329

-- EVT_ENCL_HARDWARE_ERROR

svrTrapEnclHardwareError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure hardware error."
    --#TYPE            "Enclosure hardware error"
    --#SUMMARY         "Adapter %s: Enclosure %s hardware error (Server %s)"
    --#ARGUMENTS       { 2, 3, 0 }
    --#SEVERITY        MAJOR
    --#TIMEINDEX       1
    --#HELP            "1) Check data cable(s) to enclosure. 2) Check if enclosure is running."
    --#STATE           OPERATIONAL
    ::= 10330

-- EVT_ENCL_NOT_RESPONDING

svrTrapEnclNotResponding TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure not responding."
    --#TYPE            "Enclosure not responding"
    --#SUMMARY         "Adapter %s: Enclosure %s not responding (Server %s)"
    --#ARGUMENTS       { 2, 3, 0 }
    --#SEVERITY        MAJOR
    --#TIMEINDEX       1
    --#HELP            "1) Check data cable(s) to enclosure. 2) Check if enclosure is running."
    --#STATE           OPERATIONAL
    ::= 10331

-- EVT_ENCL_SAS_SATA_MIXING_DETECTED

svrTrapEnclSASSATAMixingDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS/SATA mixing not supported in enclosure."
    --#TYPE            "SAS/SATA mixing not supported in enclosure"
    --#SUMMARY         "Adapter %s: SAS/SATA mixing not supported in enclosure; %s disabled (Server %s)"
    --#ARGUMENTS       { 2, 3, 0 }
    --#SEVERITY        MINOR
    --#TIMEINDEX       1
    --#HELP            "Check your disk configuration within enclosure."
    --#STATE           OPERATIONAL
    ::= 10332

-- EVT_ENCL_SES_HOTPLUG_DETECTED

svrTrapEnclSESHotplugDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure (SES) hotplug not supported."
    --#TYPE            "Enclosure (SES) hotplug not supported"
    --#SUMMARY         "Adapter %s: Enclosure (SES) hot plug on %s was detected, but is not supported (Server %s)"
    --#ARGUMENTS       { 2, 3, 0 }
    --#SEVERITY        INFORMATIONAL
    --#TIMEINDEX       1
    --#HELP            ""
    --#STATE           OPERATIONAL
    ::= 10333

-- EVT_CLUSTER_ENABLED

svrTrapClusterEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Clustering enabled."
    --#TYPE            "Clustering enabled"
    --#SUMMARY         "Adapter %s: Clustering enabled (Server %s)"
    --#ARGUMENTS       { 2, 0 }
    --#SEVERITY        INFORMATIONAL
    --#TIMEINDEX       1
    --#HELP            ""
    --#STATE           OPERATIONAL
    ::= 10334

-- EVT_CLUSTER_DISABLED

svrTrapClusterDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Clustering disabled."
    --#TYPE            "Clustering disabled"
    --#SUMMARY         "Adapter %s: Clustering disabled (Server %s)"
    --#ARGUMENTS       { 2, 0 }
    --#SEVERITY        INFORMATIONAL
    --#TIMEINDEX       1
    --#HELP            ""
    --#STATE           OPERATIONAL
    ::= 10335

-- EVT_PD_TOO_SMALL_FOR_AUTO_REBUILD

svrTrapPDTooSmallForAutoRebuild TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk too small to be used for auto-rebuild."
    --#TYPE            "Disk too small to be used for auto-rebuild"
    --#SUMMARY         "Adapter %s: Disk (%s) too small to be used for auto rebuild (Server %s)"
    --#ARGUMENTS       { 2, 3, 0 }
    --#SEVERITY        MINOR
    --#TIMEINDEX       1
    --#HELP            "Check your disk configuration."
    --#STATE           OPERATIONAL
    ::= 10336

-- EVT_BBU_GOOD

svrTrapBBUGood TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU enabled; changing Write-through virtual disks to Write-back."
    --#TYPE            "BBU enabled; changing Write-through virtual disks to Write-back"
    --#SUMMARY         "Adapter %s: BBU enabled; changing Write-through logical drives to Write-back (Server %s)"
    --#ARGUMENTS       { 2, 0 }
    --#SEVERITY        INFORMATIONAL
    --#TIMEINDEX       1
    --#HELP            ""
    --#STATE           OPERATIONAL
    ::= 10337

-- EVT_BBU_BAD

svrTrapBBUBad TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU disabled; changing Write-back virtual disks to Write-through."
    --#TYPE            "BBU disabled; changing Write-back virtual disks to Write-through"
    --#SUMMARY         "Adapter %s: BBU disabled; changing Write-back logical drives to Write-through (Server %s)"
    --#ARGUMENTS       { 2, 0 }
    --#SEVERITY        MINOR
    --#TIMEINDEX       1
    --#HELP            "Note: Only informational during recalibration process. 1) Check connection between BBU data/power cable and RAID controller. 2) Check version of RAID controller/iRMC firmware, and BIOS. 3) If problem persists replace BBU."
    --#STATE           OPERATIONAL
    ::= 10338

-- EVT_PD_BBM_LOG_80_PERCENT_FULL

svrTrapPDBBMLog80PercentFull TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table 80 percent full."
    --#TYPE            "Bad block table 80 percent full"
    --#SUMMARY         "Adapter %s: Bad block table on disk (%s) is 80 percent full (Server %s)"
    --#ARGUMENTS       { 2, 3, 0 }
    --#SEVERITY        INFORMATIONAL
    --#TIMEINDEX       1
    --#HELP            ""
    --#STATE           OPERATIONAL
    ::= 10339

-- EVT_PD_BBM_LOG_FULL

svrTrapPDBBMLogFull TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table full"
    --#TYPE            "Bad block table full"
    --#SUMMARY         "Adapter %s: Bad block table on disk (%s) is full; unable to log Block %s (Server %s)"
    --#ARGUMENTS       { 2, 3, 4, 0 }
    --#SEVERITY        MAJOR
    --#TIMEINDEX       1
    --#HELP            "Replace affected disk."
    --#STATE           OPERATIONAL
    ::= 10340

-- EVT_LD_MDC_OWNERSHIP_LOSS_ABORT

svrTrapLDMDCOwnershipLossAbort TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC aborted due to ownership loss."
    --#TYPE            "MDC aborted due to ownership loss"
    --#SUMMARY         "Adapter %s: MDC aborted due to ownership loss on logical drive %s (Server %s)"
    --#ARGUMENTS       { 2, 3, 0 }
    --#SEVERITY        MINOR
    --#TIMEINDEX       1
    --#HELP            "1) Restart consistency check (MDC)."
    --#STATE           OPERATIONAL
    ::= 10341

-- EVT_LD_BGI_OWNERSHIP_LOSS_ABORT

svrTrapLDBGIOwnershipLossAbort TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI aborted."
    --#TYPE            "BGI aborted"
    --#SUMMARY         "Adapter %s: BGI aborted due to ownership loss on logical drive %s (Server %s)"
    --#ARGUMENTS       { 2, 3, 0 }
    --#SEVERITY        MINOR
    --#TIMEINDEX       1
    --#HELP            "1) Restart Background initialization (BGI)."
    --#STATE           OPERATIONAL
    ::= 10342

-- EVT_BBU_BATTERY_SOH_INVALID

svrTrapBBUBatterySOHInvalid TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU/charger problems detected."
    --#TYPE            "BBU/charger problems detected"
    --#SUMMARY         "Adapter %s: BBU/charger problems detected; SOH bad (Server %s)"
    --#ARGUMENTS       { 2, 0 }
    --#SEVERITY        MAJOR
    --#TIMEINDEX       1
    --#HELP            "Replace the BBU."
    --#STATE           OPERATIONAL
    ::= 10343

-- EVT_CTRL_MEM_ECC_SINGLE_BIT_WARNING

svrTrapCtrlMemECCSingleBitWarning TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Single-bit ECC error; warning threshold exceeded."
    --#TYPE            "Single-bit ECC error; warning threshold exceeded"
    --#SUMMARY         "Adapter %s: Single-bit ECC error: ECAR=%s, ELOG=%s, (%s); warning threshold exceeded (Server %s)"
    --#ARGUMENTS       { 2, 3, 4, 5, 0 }
    --#SEVERITY        MINOR
    --#TIMEINDEX       1
    --#HELP            "If the problem occurs repeatedly replace the RAID controller DIMM module (cache)."
    --#STATE           OPERATIONAL
    ::= 10344

-- EVT_CTRL_MEM_ECC_SINGLE_BIT_CRITICAL

svrTrapCtrlMemECCSingleBitCritical TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Single-bit ECC error; critical threshold exceeded."
    --#TYPE            "Single-bit ECC error; critical threshold exceeded"
    --#SUMMARY         "Adapter %s: Single-bit ECC error: ECAR=%s, ELOG=%s, (%s); critical threshold exceeded (Server %s)"
    --#ARGUMENTS       { 2, 3, 4, 5, 0 }
    --#SEVERITY        MAJOR
    --#TIMEINDEX       1
    --#HELP            "1) Replace the RAID controller DIMM module (cache). 2) If problem persists replace RAID controller."
    --#STATE           OPERATIONAL
    ::= 10345

-- EVT_CTRL_MEM_ECC_SINGLE_BIT_DISABLED

svrTrapCtrlMemECCSingleBitDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Single-bit ECC error: further reporting disabled."
    --#TYPE            "Single-bit ECC error: further reporting disabled"
    --#SUMMARY         "Adapter %s: Single-bit ECC error: ECAR=%s, ELOG=%s, (%s); further reporting disabled (Server %s)"
    --#ARGUMENTS       { 2, 3, 4, 5, 0 }
    --#SEVERITY        MAJOR
    --#TIMEINDEX       1
    --#HELP            ""
    --#STATE           OPERATIONAL
    ::= 10346

-- EVT_ENCL_POWER_SUPPLY_CABLE_REMOVED

svrTrapEnclPowerSupplyCableRemoved TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure power supply cable removed."
    --#TYPE            "Enclosure power supply cable removed"
    --#SUMMARY         "Adapter %s: Enclosure %s power supply %s cable removed (Server %s)"
    --#ARGUMENTS       { 2, 3, 4, 0 }
    --#SEVERITY        MINOR
    --#TIMEINDEX       1
    --#HELP            "Check the enclosure power cable(s)."
    --#STATE           OPERATIONAL
    ::= 10347

-- EVT_ENCL_POWER_SUPPLY_CABLE_INSERTED

svrTrapEnclPowerSupplyCableInserted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure power supply cable inserted."
    --#TYPE            "Enclosure power supply cable inserted"
    --#SUMMARY         "Adapter %s: Enclosure %s power supply %s cable inserted (Server %s)"
    --#ARGUMENTS       { 2, 3, 4, 0 }
    --#SEVERITY        INFORMATIONAL
    --#TIMEINDEX       1
    --#HELP            ""
    --#STATE           OPERATIONAL
    ::= 10348

-- EVT_ENCL_FAN_RETURNED_TO_NORMAL

svrTrapEnclFanReturnedToNormal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure fan returned to normal."
    --#TYPE            "Enclosure fan returned to normal"
    --#SUMMARY         "Adapter %s: Enclosure %s fan %s returned to normal (Server %s)"
    --#ARGUMENTS       { 2, 3, 4, 0 }
    --#SEVERITY        INFORMATIONAL
    --#TIMEINDEX       1
    --#HELP            ""
    --#STATE           OPERATIONAL
    ::= 10349

-- EVT_DIAG_BBU_RETENTION_TEST_STARTED_ON_PREV_BOOT

svrTrapDiagBBURetentionTestStartedOnPrevReboot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU retention started on previous Boot."
    --#TYPE            "BBU retention started on previous Boot"
    --#SUMMARY         "Adapter %s: BBU retention started on previous boot (Server %s)"
    --#ARGUMENTS       { 2, 0 }
    --#SEVERITY        INFORMATIONAL
    --#TIMEINDEX       1
    --#HELP            ""
    --#STATE           OPERATIONAL
    ::= 10350

-- EVT_DIAG_BBU_RETENTION_PASSED

svrTrapDiagBBURetentionPassed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU retention test passed."
    --#TYPE            "BBU retention test passed"
    --#SUMMARY         "Adapter %s: BBU retention test passed (Server %s)"
    --#ARGUMENTS       { 2, 0 }
    --#SEVERITY        INFORMATIONAL
    --#TIMEINDEX       1
    --#HELP            ""
    --#STATE           OPERATIONAL
    ::= 10351

-- EVT_DIAG_BAT_RETENTION_TEST_FAILED

svrTrapDiagBatRetentionTestFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU retention test failed."
    --#TYPE            "BBU retention test failed"
    --#SUMMARY         "Adapter %s: BBU retention test failed (Server %s)"
    --#ARGUMENTS       { 2, 0 }
    --#SEVERITY        MAJOR
    --#TIMEINDEX       1
    --#HELP            "Note: In general additional error messages should occur. If there are no other actions defined call your local Fujitsu Helpdesk."
    --#STATE           OPERATIONAL
    ::= 10352

-- EVT_DIAG_NVRAM_RET_TEST_STARTED_ON_PREV_BOOT

svrTrapDiagNVRAMRetTestStartedOnPrevReboot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Retention test started on previous reboot."
    --#TYPE            "Retention test started on previous reboot"
    --#SUMMARY         "Adapter %s: Retention test started on previous reboot (Server %s)"
    --#ARGUMENTS       { 2, 0 }
    --#SEVERITY        INFORMATIONAL
    --#TIMEINDEX       1
    --#HELP            ""
    --#STATE           OPERATIONAL
    ::= 10353

-- EVT_DIAG_NVRAM_RENTION_TEST_SUCCESS

svrTrapDiagRetentionTestSuccess TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "NVRAM retention test passed."
    --#TYPE            "NVRAM retention test passed"
    --#SUMMARY         "Adapter %s: NVRAM retention test passed (Server %s)"
    --#ARGUMENTS       { 2, 0 }
    --#SEVERITY        INFORMATIONAL
    --#TIMEINDEX       1
    --#HELP            ""
    --#STATE           OPERATIONAL
    ::= 10354

-- EVT_DIAG_NVRAM_RENTION_TEST_FAILED

svrTrapDiagNVRAMRentionTestFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "NVRAM retention test failed."
    --#TYPE            "NVRAM retention test failed"
    --#SUMMARY         "Adapter %s: NVRAM retention test failed (Server %s)"
    --#ARGUMENTS       { 2, 0 }
    --#SEVERITY        MAJOR
    --#TIMEINDEX       1
    --#HELP            "Note: In general additional error messages should occur. If there are no other actions defined call your local Fujitsu Helpdesk."
    --#STATE           OPERATIONAL
    ::= 10355

-- EVT_DIAG_SELF_CHECK_TEST_PASS

svrTrapDiagSelfCheckTestPass TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Self check test finished successfully."
    --#TYPE            "Self check test finished successfully"
    --#SUMMARY         "Adapter %s: %s test finished %s passes successfully (Server %s)"
    --#ARGUMENTS       { 2, 3, 4, 0 }
    --#SEVERITY        INFORMATIONAL
    --#TIMEINDEX       1
    --#HELP            ""
    --#STATE           OPERATIONAL
    ::= 10356

-- EVT_DIAG_SELF_CHECK_TEST_FAIL

svrTrapDiagSelfCheckTestFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Self check test failed."
    --#TYPE            "Self check test failed"
    --#SUMMARY         "Adapter %s: %s test failed on %s pass. fail data: errorOffset=%s goodData=%s badData=%s (Server %s)"
    --#ARGUMENTS       { 2, 3, 4, 5, 6, 7, 0 }
    --#SEVERITY        MAJOR
    --#TIMEINDEX       1
    --#HELP            "Note: In general additional error messages should occur. If there are no other actions defined call your local Fujitsu Helpdesk."
    --#STATE           OPERATIONAL
    ::= 10357

-- EVT_DIAG_SELF_CHECK_DONE

svrTrapDiagSelfCheckDone TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Self check diagnostics finished."
    --#TYPE            "Self check diagnostics finished"
    --#SUMMARY         "Adapter %s: Self-check diagnostics finished (Server %s)"
    --#ARGUMENTS       { 2, 0 }
    --#SEVERITY        INFORMATIONAL
    --#TIMEINDEX       1
    --#HELP            ""
    --#STATE           OPERATIONAL
    ::= 10358

-- EVT_FOREIGN_CFG_DETECTED

svrTrapForeignCfgDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Foreign configuration detected."
    --#TYPE            "Foreign configuration detected"
    --#SUMMARY         "Adapter %s: Foreign configuration detected (Server %s)"
    --#ARGUMENTS       { 2, 0 }
    --#SEVERITY        INFORMATIONAL
    --#TIMEINDEX       1
    --#HELP            ""
    --#STATE           OPERATIONAL
    ::= 10359

-- EVT_FOREIGN_CFG_IMPORTED

svrTrapForeignCfgImported TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Foreign configuration imported."
    --#TYPE            "Foreign configuration imported"
    --#SUMMARY         "Adapter %s: Foreign configuration imported (Server %s)"
    --#ARGUMENTS       { 2, 0 }
    --#SEVERITY        INFORMATIONAL
    --#TIMEINDEX       1
    --#HELP            ""
    --#STATE           OPERATIONAL
    ::= 10360

-- EVT_FOREIGN_CFG_CLEARED

svrTrapForeignCfgCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Foreign configuration cleared."
    --#TYPE            "Foreign configuration cleared"
    --#SUMMARY         "Adapter %s: Foreign configuration cleared (Server %s)"
    --#ARGUMENTS       { 2, 0 }
    --#SEVERITY        INFORMATIONAL
    --#TIMEINDEX       1
    --#HELP            ""
    --#STATE           OPERATIONAL
    ::= 10361

-- EVT_NVRAM_CORRUPT

svrTrapNVRAMCorrupt TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "NVRAM is corrupt; reinitializing."
    --#TYPE            "NVRAM is corrupt; reinitializing"
    --#SUMMARY         "Adapter %s: NVRAM is corrupt; reinitializing (Server %s)"
    --#ARGUMENTS       { 2, 0 }
    --#SEVERITY        MINOR
    --#TIMEINDEX       1
    --#HELP            "If the problem occurs repeatedly replace the RAID controller."
    --#STATE           OPERATIONAL
    ::= 10362

-- EVT_NVRAM_MISMATCH

svrTrapNVRAMMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "NVRAM mismatch occurred."
    --#TYPE            "NVRAM mismatch occurred"
    --#SUMMARY         "Adapter %s: NVRAM mismatch occurred (Server %s)"
    --#ARGUMENTS       { 2, 0 }
    --#SEVERITY        MINOR
    --#TIMEINDEX       1
    --#HELP            "If the problem occurs repeatedly replace the RAID controller."
    --#STATE           OPERATIONAL
    ::= 10363

-- EVT_SAS_WIDE_PORT_LINK_LOST

svrTrapSASWidePortLinkLost TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS wide port lost link on PHY."
    --#TYPE            "SAS wide port lost link on PHY"
    --#SUMMARY         "Adapter %s: SAS wide port %s lost link on PHY %s (Server %s)"
    --#ARGUMENTS       { 2, 3, 4, 0 }
    --#SEVERITY        MINOR
    --#TIMEINDEX       1
    --#HELP            "1) Unplug affected disk, wait 30 seconds, reinsert it. 2) Check/replace cable between controller and affected disk. 3) Check version of RAID controller/iRMC firmware, and BIOS. 4) Replace affected disk."
    --#STATE           OPERATIONAL
    ::= 10364

-- EVT_SAS_WIDE_PORT_LINK_RESTORED

svrTrapSASWidePortLinkRestored TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS wide port restored link on PHY."
    --#TYPE            "SAS wide port restored link on PHY"
    --#SUMMARY         "Adapter %s: SAS wide port %s restored link on PHY %s (Server %s)"
    --#ARGUMENTS       { 2, 3, 4, 0 }
    --#SEVERITY        INFORMATIONAL
    --#TIMEINDEX       1
    --#HELP            ""
    --#STATE           OPERATIONAL
    ::= 10365

-- EVT_SAS_PHY_ERROR_RATE_EXCEEDED

svrTrapSASPhyErrorRateExceeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS port has exceeded the allowed error rate."
    --#TYPE            "SAS port has exceeded the allowed error rate"
    --#SUMMARY         "Adapter %s: SAS port %s, PHY %s has exceeded the allowed error rate (Server %s)"
    --#ARGUMENTS       { 2, 3, 4, 0 }
    --#SEVERITY        MINOR
    --#TIMEINDEX       1
    --#HELP            "Note: Disk reports errors. The affected disk might fail soon. 1) Replace the disk as soon as possible."
    --#STATE           OPERATIONAL
    ::= 10366

-- EVT_SATA_BAD_BLOCK_REMAPED

svrTrapSATABadBlockRemaped TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block reassigned."
    --#TYPE            "Bad block reassigned"
    --#SUMMARY         "Adapter %s: Bad block reassigned on disk (%s) from LBA %s to LBA %s (Server %s)"
    --#ARGUMENTS       { 2, 3, 4, 5, 0 }
    --#SEVERITY        MINOR
    --#TIMEINDEX       1
    --#HELP            "If the problem occurs repeatedly replace the disk during next maintenance."
    --#STATE           OPERATIONAL
    ::= 10367

-- EVT_CTRL_HOTPLUG_DETECTED

svrTrapCtrlHotplugDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Controller hot plug detected."
    --#TYPE            "Controller hot plug detected"
    --#SUMMARY         "Adapter %s: Adapter hot plug detected (Server %s)"
    --#ARGUMENTS       { 2, 0 }
    --#SEVERITY        INFORMATIONAL
    --#TIMEINDEX       1
    --#HELP            ""
    --#STATE           OPERATIONAL
    ::= 10368

-- EVT_ENCL_TEMPERATURE_DIFFERENTIAL

svrTrapEnclTemperatureDifferential TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure temperature sensor differential detected."
    --#TYPE            "Enclosure temperature sensor differential detected"
    --#SUMMARY         "Adapter %s: Enclosure %s temperature sensor %s differential detected (Server %s)"
    --#ARGUMENTS       { 2, 3, 4, 0 }
    --#SEVERITY        INFORMATIONAL
    --#TIMEINDEX       1
    --#HELP            "For information only."
    --#STATE           OPERATIONAL
    ::= 10369

-- EVT_DIAG_DISK_TEST_CANNOT_START

svrTrapDiagDiskTestCannotStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk test cannot start. No qualifying disks found."
    --#TYPE            "Disk test cannot start. No qualifying disks found"
    --#SUMMARY         "Adapter %s: Disk test cannot start. No qualifying disks found (Server %s)"
    --#ARGUMENTS       { 2, 0 }
    --#SEVERITY        INFORMATIONAL
    --#TIMEINDEX       1
    --#HELP            ""
    --#STATE           OPERATIONAL
    ::= 10370

-- EVT_DIAG_TIME_NOT_SUFFICIENT

svrTrapDiagTimeNotSufficient TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Time duration provided by host is not sufficient for self-checking."
    --#TYPE            "Time duration provided by host is not sufficient for self-checking"
    --#SUMMARY         "Adapter %s: Time duration provided by host is not sufficient for self-checking (Server %s)"
    --#ARGUMENTS       { 2, 0 }
    --#SEVERITY        INFORMATIONAL
    --#TIMEINDEX       1
    --#HELP            ""
    --#STATE           OPERATIONAL
    ::= 10371

-- EVT_PD_MARK_MISSING

svrTrapPDTMarkMissing TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Marked as missing."
    --#TYPE            "Marked as missing"
    --#SUMMARY         "Adapter %s: Disk (%s) on array %s row %s marked as missing (Server %s)"
    --#ARGUMENTS       { 2, 3, 4, 5, 0 }
    --#SEVERITY        INFORMATIONAL
    --#TIMEINDEX       1
    --#HELP            ""
    --#STATE           OPERATIONAL
    ::= 10372

-- EVT_PD_REPLACE_MISSING

svrTrapPDReplaceMissing TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Replaced missing."
    --#TYPE            "Replaced missing"
    --#SUMMARY         "Adapter %s: Disk (%s) replaced missing on array %s row %s (Server %s)"
    --#ARGUMENTS       { 2, 3, 4, 5, 0 }
    --#SEVERITY        INFORMATIONAL
    --#TIMEINDEX       1
    --#HELP            ""
    --#STATE           DEGRADED
    ::= 10373

-- EVT_ENCL_TEMPERATURE_RETURNED_TO_NORMAL

svrTrapEnclTemperatureReturnedToNormal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure temperature sensor returned to normal."
    --#TYPE            "Enclosure temperature sensor returned to normal"
    --#SUMMARY         "Adapter %s: Enclosure %s temperature sensor %s returned to normal (Server %s)"
    --#ARGUMENTS       { 2, 3, 4, 0 }
    --#SEVERITY        INFORMATIONAL
    --#TIMEINDEX       1
    --#HELP            ""
    --#STATE           OPERATIONAL
    ::= 10374

-- EVT_ENCL_FIRMWARE_FLASH_IN_PROGRESS

svrTrapEnclFirmwareFlashInProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure firmware download in progress."
    --#TYPE            "Enclosure firmware download in progress"
    --#SUMMARY         "Adapter %s: Enclosure %s firmware download in progress (Server %s)"
    --#ARGUMENTS       { 2, 3, 0 }
    --#SEVERITY        INFORMATIONAL
    --#TIMEINDEX       1
    --#HELP            ""
    --#STATE           OPERATIONAL
    ::= 10375

-- EVT_ENCL_FIRMWARE_DOWNLOAD_FAILED

svrTrapEnclFirmwareDownloadFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure firmware download failed."
    --#TYPE            "Enclosure firmware download failed"
    --#SUMMARY         "Adapter %s: Enclosure %s firmware download failed (Server %s)"
    --#ARGUMENTS       { 2, 3, 0 }
    --#SEVERITY        MAJOR
    --#TIMEINDEX       1
    --#HELP            "Call your local Fujitsu Helpdesk."
    --#STATE           OPERATIONAL
    ::= 10376

-- EVT_PD_NOT_CERTIFIED

svrTrapPDNotCertified TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk is not certified."
    --#TYPE            "Disk is not certified"
    --#SUMMARY         "Adapter %s: Disk (%s) is not certified (Server %s)"
    --#ARGUMENTS       { 2, 3, 0 }
    --#SEVERITY        MINOR
    --#TIMEINDEX       1
    --#HELP            "Check the type of your disk."
    --#STATE           OPERATIONAL
    ::= 10377

-- EVT_CTRL_CACHE_DISCARD_BY_USER

svrTrapCtrlCacheDiscardByUser TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Dirty cache data discarded by user."
    --#TYPE            "Dirty cache data discarded by user"
    --#SUMMARY         "Adapter %s: Dirty cache data discarded by user (Server %s)"
    --#ARGUMENTS       { 2, 0 }
    --#SEVERITY        MINOR
    --#TIMEINDEX       1
    --#HELP            "For information only."
    --#STATE           OPERATIONAL
    ::= 10378

-- EVT_CTRL_BOOT_MISSING_PDS

svrTrapCtrlBootMissingPDs TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "PDs missing from configuration at boot."
    --#TYPE            "PDs missing from configuration at boot"
    --#SUMMARY         "Adapter %s: Disks missing from configuration at boot (Server %s)"
    --#ARGUMENTS       { 2, 0 }
    --#SEVERITY        MINOR
    --#TIMEINDEX       1
    --#HELP            "Check your RAID configuration."
    --#STATE           OPERATIONAL
    ::= 10379

-- EVT_CTRL_BOOT_LDS_WILL_GO_OFFLINE

svrTrapCtrlBootLDsWillGoOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "VDs missing drives and will go offline at boot."
    --#TYPE            "VDs missing drives and will go offline at boot"
    --#SUMMARY         "Adapter %s: Logical drives missing drives and will go offline at boot: %s (Server %s)"
    --#ARGUMENTS       { 2, 3, 0 }
    --#SEVERITY        MINOR
    --#TIMEINDEX       1
    --#HELP            "Check your RAID configuration."
    --#STATE           OPERATIONAL
    ::= 10380

-- EVT_CTRL_BOOT_LDS_MISSING

svrTrapCtrlBootLDsMissing TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "VDs missing at boot."
    --#TYPE            "VDs missing at boot"
    --#SUMMARY         "Adapter %s: Logical drives missing at boot: %s (Server %s)"
    --#ARGUMENTS       { 2, 3, 0 }
    --#SEVERITY        MINOR
    --#TIMEINDEX       1
    --#HELP            "Check your RAID configuration."
    --#STATE           OPERATIONAL
    ::= 10381

-- EVT_CTRL_BOOT_CONFIG_MISSING

svrTrapCtrlBootConfigMissing TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Previous configuration completely missing at boot."
    --#TYPE            "Previous configuration completely missing at boot"
    --#SUMMARY         "Adapter %s: Previous configuration completely missing at boot (Server %s)"
    --#ARGUMENTS       { 2, 0 }
    --#SEVERITY        MINOR
    --#TIMEINDEX       1
    --#HELP            "Check your RAID configuration."
    --#STATE           OPERATIONAL
    ::= 10382

-- EVT_BBU_CHARGE_COMPLETE

svrTrapBBUChargeComplete TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU charging complete."
    --#TYPE            "BBU charging complete"
    --#SUMMARY         "Adapter %s: BBU charging complete (Server %s)"
    --#ARGUMENTS       { 2, 0 }
    --#SEVERITY        INFORMATIONAL
    --#TIMEINDEX       1
    --#HELP            ""
    --#STATE           OPERATIONAL
    ::= 10383

-- EVT_ENCL_FAN_SPEED_CHANGED

svrTrapEnclFanSpeedChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure fan speed changed."
    --#TYPE            "Enclosure fan speed changed"
    --#SUMMARY         "Adapter %s: Enclosure %s fan %s speed changed (Server %s)"
    --#ARGUMENTS       { 2, 3, 4, 0 }
    --#SEVERITY        INFORMATIONAL
    --#TIMEINDEX       1
    --#HELP            ""
    --#STATE           OPERATIONAL
    ::= 10384

-- EVT_PD_SPARE_DEDICATED_IMPORTED_AS_GLOBAL

svrTrapPDSpareDedicatedImportedAsGlobal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Dedicated spare imported as global due to missing arrays."
    --#TYPE            "Dedicated spare imported as global due to missing arrays"
    --#SUMMARY         "Adapter %s: Dedicated hot spare (%s) imported as global due to missing arrays (Server %s)"
    --#ARGUMENTS       { 2, 3, 0 }
    --#SEVERITY        INFORMATIONAL
    --#TIMEINDEX       1
    --#HELP            ""
    --#STATE           OPERATIONAL
    ::= 10385

-- EVT_PD_NO_REBUILD_SAS_SATA_MIX_NOT_ALLOWED_IN_LD

svrTrapPDNoRebuildSASSATAMixNotAllowedInLD TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk rebuild not possible as SAS/SATA mixing is not supported in an array."
    --#TYPE            "Disk rebuild not possible as SAS/SATA mixing is not supported in an array"
    --#SUMMARY         "Adapter %s: Disk (%s) rebuild not possible as SAS/SATA mixing is not supported in an array (Server %s)"
    --#ARGUMENTS       { 2, 3, 0 }
    --#SEVERITY        INFORMATIONAL
    --#TIMEINDEX       1
    --#HELP            ""
    --#STATE           OPERATIONAL
    ::= 10386

-- EVT_SEP_IS_BEING_REBOOTED

svrTrapSEPIsBeingRebooted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "I/O module has been rebooted as part of enclosure firmware download."
    --#TYPE            "I/O module has been rebooted as part of enclosure firmware download"
    --#SUMMARY         "Adapter %s: I/O module %s has been rebooted as part of enclosure firmware download. It will be unavailable until reboot completes (Server %s)"
    --#ARGUMENTS       { 2, 3, 0 }
    --#SEVERITY        INFORMATIONAL
    --#TIMEINDEX       1
    --#HELP            ""
    --#STATE           OPERATIONAL
    ::= 10387

-- EVT_LD_PARTIALLY_DEGRADED

svrTrapLDPartiallyDegraded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is partially degraded."
    --#TYPE            "Logical drive is partially degraded"
    --#SUMMARY         "Adapter %s: Logical drive %s partially degraded (Server %s)"
    --#ARGUMENTS       { 2, 3, 0 }
    --#SEVERITY        MINOR
    --#TIMEINDEX       1
    --#HELP            "Replace affected disk."
    --#STATE           DEGRADED
    ::= 10388

-- EVT_BBU_RELEARN_REQUESTED

svrTrapBBURelearnRequested TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU requires reconditioning."
    --#TYPE            "BBU requires reconditioning"
    --#SUMMARY         "Adapter %s: BBU requires reconditioning; please initiate a LEARN cycle (Server %s)"
    --#ARGUMENTS       { 2, 0 }
    --#SEVERITY        MINOR
    --#TIMEINDEX       1
    --#HELP            ""
    --#STATE           OPERATIONAL
    ::= 10389

-- EVT_COERCION_MODE_CHANGED

svrTrapCoercionModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Coercion mode changed."
    --#TYPE            "Coercion mode changed"
    --#SUMMARY         "Adapter %s: Coercion mode changed (Server %s)"
    --#ARGUMENTS       { 2, 0 }
    --#SEVERITY        INFORMATIONAL
    --#TIMEINDEX       1
    --#HELP            ""
    --#STATE           OPERATIONAL
    ::= 10390

-- EVT_BBU_AUTO_LEARN_MODE_CHANGED

svrTrapBBUAutoLearnModeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU automatic Learn mode changed."
    --#TYPE            "BBU automatic Learn mode changed"
    --#SUMMARY         "Adapter %s: BBU automatic learn mode changed (Server %s)"
    --#ARGUMENTS       { 2, 0 }
    --#SEVERITY        INFORMATIONAL
    --#TIMEINDEX       1
    --#HELP            ""
    --#STATE           OPERATIONAL
    ::= 10391

-- EVT_BBU_AUTO_LEARN_PERIOD_CHANGED

svrTrapBBUAutoModeLearnPeriodChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU automatic learn period changed."
    --#TYPE            "BBU automatic learn period changed"
    --#SUMMARY         "Adapter %s: BBU automatic learn period changed (Server %s)"
    --#ARGUMENTS       { 2, 0 }
    --#SEVERITY        INFORMATIONAL
    --#TIMEINDEX       1
    --#HELP            ""
    --#STATE           OPERATIONAL
    ::= 10392

-- EVT_BBU_LEARN_DELAY_INTERVAL_CHANGED

svrTrapBBULearnDelayIntervalChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU learn delay interval changed."
    --#TYPE            "BBU learn delay interval changed"
    --#SUMMARY         "Adapter %s: BBU learn delay interval changed (Server %s)"
    --#ARGUMENTS       { 2, 0 }
    --#SEVERITY        INFORMATIONAL
    --#TIMEINDEX       1
    --#HELP            ""
    --#STATE           OPERATIONAL
    ::= 10393

-- EVT_BBU_NEXT_LEARN_TIME_CHANGED

svrTrapBBUNextLearnTimeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU next learn time changed."
    --#TYPE            "BBU next learn time changed"
    --#SUMMARY         "Adapter %s: BBU next learn time changed (Server %s)"
    --#ARGUMENTS       { 2, 0 }
    --#SEVERITY        INFORMATIONAL
    --#TIMEINDEX       1
    --#HELP            ""
    --#STATE           OPERATIONAL
    ::= 10394

-- EVT_PATROLREAD_MAXPD_CHANGED

svrTrapPatrolreadMaxPDChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Max. disk count for Patrol Read changed."
    --#TYPE            "Max. disk count for Patrol Read changed"
    --#SUMMARY         "Adapter %s: Max. disk count for Patrol Read changed to %s (Server %s)"
    --#ARGUMENTS       { 2, 3, 0 }
    --#SEVERITY        INFORMATIONAL
    --#TIMEINDEX       1
    --#HELP            ""
    --#STATE           OPERATIONAL
    ::= 10395

-- EVT_PATROLREAD_CONTINUOUS_PATROLLING_ENABLED

svrTrapPatrolreadContinuousPatrollingEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Continuous patrolling enabled."
    --#TYPE            "Continuous patrolling enabled"
    --#SUMMARY         "Adapter %s: Continuous patrolling enabled (Server %s)"
    --#ARGUMENTS       { 2, 0 }
    --#SEVERITY        INFORMATIONAL
    --#TIMEINDEX       1
    --#HELP            ""
    --#STATE           OPERATIONAL
    ::= 10396

-- EVT_PATROLREAD_CONTINUOUS_PATROLLING_DISABLED

svrTrapPatrolreadContinousPatrollingDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Continuous patrolling disabled."
    --#TYPE            "Continuous patrolling disabled"
    --#SUMMARY         "Adapter %s: Continuous patrolling disabled (Server %s)"
    --#ARGUMENTS       { 2, 0 }
    --#SEVERITY        INFORMATIONAL
    --#TIMEINDEX       1
    --#HELP            ""
    --#STATE           OPERATIONAL
    ::= 10397

-- EVT_MDC_ERROR

svrTrapLDMDCFinishedWithErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC finished with errors on logical drive."
    --#TYPE            "MDC finished with errors on logical drive"
    --#SUMMARY         "Adapter %s: MDC finished with errors on logical drive %s (Server %s)"
    --#ARGUMENTS       { 2, 3, 0 }
    --#SEVERITY        MAJOR
    --#TIMEINDEX       1
    --#HELP            "1) Manually initiate second consistency check (MDC). 2) If problem persists replace affected disk."
    --#STATE           OPERATIONAL
    ::= 10398

-- EVT_LD_DISABLED_NO_SUPPORT_FOR_RAID5

svrTrapLDDisabledNoSupportForRAID5 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive disabled because RAID-5 not supported."
    --#TYPE            "Logical drive disabled because RAID-5 not supported"
    --#SUMMARY         "Adapter %s: Logical drive %s disabled because RAID-5 is not supported by this RAID key (Server %s)"
    --#ARGUMENTS       { 2, 3, 0 }
    --#SEVERITY        INFORMATIONAL
    --#TIMEINDEX       1
    --#HELP            ""
    --#STATE           OPERATIONAL
    ::= 10399

-- EVT_LD_DISABLED_NO_SUPPORT_FOR_RAID6

svrTrapLDDisabledNoSupportForRAID6 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive disabled because RAID-6 not supported."
    --#TYPE            "Logical drive disabled because RAID-6 not supported"
    --#SUMMARY         "Adapter %s: Logical drive %s disabled because RAID-6 is not supported by this RAID key (Server %s)"
    --#ARGUMENTS       { 2, 3, 0 }
    --#SEVERITY        INFORMATIONAL
    --#TIMEINDEX       1
    --#HELP            ""
    --#STATE           OPERATIONAL
    ::= 10400

-- EVT_LD_DISABLED_NO_SUPPORT_FOR_SAS

svrTrapLDDisabledNoSupportForSAS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive disabled because SAS drives not supported."
    --#TYPE            "Logical drive disabled because SAS drives not supported"
    --#SUMMARY         "Adapter %s: Logical drive %s disabled because SAS drives are not supported by this RAID key (Server %s)"
    --#ARGUMENTS       { 2, 3, 0 }
    --#SEVERITY        MINOR
    --#TIMEINDEX       1
    --#HELP            "Check the disks."
    --#STATE           OPERATIONAL
    ::= 10401

-- EVT_CTRL_BOOT_MISSING_PDS_EXT

svrTrapCtrlBootMissingPDsExt TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disks missing."
    --#TYPE            "Disks missing"
    --#SUMMARY         "Adapter %s: Disks missing (Server %s)"
    --#ARGUMENTS       { 2, 0 }
    --#SEVERITY        MINOR
    --#TIMEINDEX       1
    --#HELP            "Check your RAID configuration."
    --#STATE           OPERATIONAL
    ::= 10402

-- EVT_REBUILD_RATE_CHANGED_EX

svrTrapAdapterRebuildRateChangedEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild rate changed."
    --#TYPE            "Rebuild rate changed"
    --#SUMMARY         "Adapter %s: Rebuild rate changed to %s percent (Server %s)"
    --#ARGUMENTS       { 2, 3, 0 }
    --#SEVERITY        INFORMATIONAL
    --#TIMEINDEX       1
    --#HELP            ""
    --#STATE           OPERATIONAL
    ::= 10403

-- EVT_CHECK_RATE_CHANGED_EX

svrTrapAdapterConCheckRateChangedEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check rate changed."
    --#TYPE            "Consistency check rate changed"
    --#SUMMARY         "Adapter %s: Consistency check rate changed to %s percent (Server %s)"
    --#ARGUMENTS       { 2, 3, 0 }
    --#SEVERITY        INFORMATIONAL
    --#TIMEINDEX       1
    --#HELP            ""
    --#STATE           OPERATIONAL
    ::= 10404

-- EVT_SMART_POLL_INTERVAL_CHANGED_EX

svrTrapAdapterSMARTPollIntervalChangedEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SMART poll interval changed."
    --#TYPE            "SMART poll interval changed"
    --#SUMMARY         "Adapter %s: SMART poll interval changed to %s s (Server %s)"
    --#ARGUMENTS       { 2, 3, 0 }
    --#SEVERITY        INFORMATIONAL
    --#TIMEINDEX       1
    --#HELP            ""
    --#STATE           OPERATIONAL
    ::= 10405

-- EVT_MDC_STARTED

svrTrapLDMDCStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC started on logical drive."
    --#TYPE            "MDC started on logical drive"
    --#SUMMARY         "Adapter %s: MDC started on logical drive %s (Server %s)"
    --#ARGUMENTS       { 2, 3, 0 }
    --#SEVERITY        INFORMATIONAL
    --#TIMEINDEX       1
    --#HELP            ""
    --#STATE           OPERATIONAL
    ::= 10406

-- EVT_MDC_FINISHED

svrTrapLDMDCFinished TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC finished on logical drive."
    --#TYPE            "MDC finished on logical drive"
    --#SUMMARY         "Adapter %s: MDC finished on logical drive %s (Server %s)"
    --#ARGUMENTS       { 2, 3, 0 }
    --#SEVERITY        INFORMATIONAL
    --#TIMEINDEX       1
    --#HELP            ""
    --#STATE           OPERATIONAL
    ::= 10407

-- EVT_MDC_FAILED

svrTrapLDMDCFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC failed on logical drive."
    --#TYPE            "MDC failed on logical drive"
    --#SUMMARY         "Adapter %s: MDC failed on logical drive %s (Server %s)"
    --#ARGUMENTS       { 2, 3, 0 }
    --#SEVERITY        MAJOR
    --#TIMEINDEX       1
    --#HELP            "1) Manually initiate second consistency check (MDC). 2) If problem persists replace affected disk."
    --#STATE           OPERATIONAL
    ::= 10408

-- EVT_MDC_CANCELED

svrTrapLDMDCAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC aborted on logical drive."
    --#TYPE            "MDC aborted on logical drive"
    --#SUMMARY         "Adapter %s: MDC aborted on logical drive %s (Server %s)"
    --#ARGUMENTS       { 2, 3, 0 }
    --#SEVERITY        MINOR
    --#TIMEINDEX       1
    --#HELP            "For information only."
    --#STATE           OPERATIONAL
    ::= 10409

-- EVT_MDC_PAUSED

svrTrapLDMDCPaused TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC suspended on logical drive."
    --#TYPE            "MDC suspended on logical drive"
    --#SUMMARY         "Adapter %s: MDC suspended on logical drive %s (Server %s)"
    --#ARGUMENTS       { 2, 3, 0 }
    --#SEVERITY        INFORMATIONAL
    --#TIMEINDEX       1
    --#HELP            ""
    --#STATE           OPERATIONAL
    ::= 10410

-- EVT_MDC_STARTED_UNINITIALIZED

svrTrapLDUninitialisedMDCStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC started on uninitialized logical drive."
    --#TYPE            "MDC started on uninitialized logical drive"
    --#SUMMARY         "Adapter %s: MDC started on uninitialized logical drive %s (Server %s)"
    --#ARGUMENTS       { 2, 3, 0 }
    --#SEVERITY        INFORMATIONAL
    --#TIMEINDEX       1
    --#HELP            ""
    --#STATE           OPERATIONAL
    ::= 10411

-- EVT_LD_STATE_CHANGE_OP_TO_DEG

svrTrapLDStateChangedOpToDeg TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to degraded."
    --#TYPE            "State change from operational to degraded"
    --#SUMMARY         "Adapter %s: State change on logical drive %s from operational to degraded (Server %s)"
    --#ARGUMENTS       { 2, 3, 0 }
    --#SEVERITY        MAJOR
    --#TIMEINDEX       1
    --#HELP            "Replace affected disk."
    --#STATE           DEGRADED
    ::= 10412

-- EVT_LD_STATE_CHANGE_OP_TO_PAR_DEG

svrTrapLDStateChangedOpToParDeg TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to partially degraded."
    --#TYPE            "State change from operational to partially degraded"
    --#SUMMARY         "Adapter %s: State change on logical drive %s from operational to partially degraded (Server %s)"
    --#ARGUMENTS       { 2, 3, 0 }
    --#SEVERITY        MINOR
    --#TIMEINDEX       1
    --#HELP            "Replace affected disk."
    --#STATE           DEGRADED
    ::= 10413

-- EVT_LD_STATE_CHANGE_OP_TO_FAIL

svrTrapLDStateChangedOpToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to failed."
    --#TYPE            "State change from operational to failed"
    --#SUMMARY         "Adapter %s: State change on logical drive %s from operational to failed (Server %s)"
    --#ARGUMENTS       { 2, 3, 0 }
    --#SEVERITY        CRITICAL
    --#TIMEINDEX       1
    --#HELP            "1) Check version of RAID controller/iRMC firmware, and BIOS."
    --#STATE           NONOPERATIONAL
    ::= 10414

-- EVT_LD_STATE_CHANGE_DEG_TO_OP

svrTrapLDStateChangedDegToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from degraded to operational."
    --#TYPE            "State change from degraded to operational"
    --#SUMMARY         "Adapter %s: State change on logical drive %s from degraded to operational (Server %s)"
    --#ARGUMENTS       { 2, 3, 0 }
    --#SEVERITY        INFORMATIONAL
    --#TIMEINDEX       1
    --#HELP            ""
    --#STATE           OPERATIONAL
    ::= 10415

-- EVT_LD_STATE_CHANGE_DEG_TO_DEG

svrTrapLDStateChangedDegToDeg TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from degraded to degraded."
    --#TYPE            "State change from degraded to degraded"
    --#SUMMARY         "Adapter %s: State change on logical drive %s from degraded to degraded (Server %s)"
    --#ARGUMENTS       { 2, 3, 0 }
    --#SEVERITY        MINOR
    --#TIMEINDEX       1
    --#HELP            "Call your local Fujitsu Helpdesk."
    --#STATE           DEGRADED
    ::= 10416

-- EVT_LD_STATE_CHANGE_DEG_TO_PAR_DEG

svrTrapLDStateChangedDegToParDeg TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from degraded to partially degraded."
    --#TYPE            "State change from degraded to partially degraded"
    --#SUMMARY         "Adapter %s: State change on logical drive %s from degraded to partially degraded (Server %s)"
    --#ARGUMENTS       { 2, 3, 0 }
    --#SEVERITY        MINOR
    --#TIMEINDEX       1
    --#HELP            "For information only."
    --#STATE           DEGRADED
    ::= 10417

-- EVT_LD_STATE_CHANGE_DEG_TO_FAIL

svrTrapLDStateChangedDegToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from degraded to failed."
    --#TYPE            "State change from degraded to failed"
    --#SUMMARY         "Adapter %s: State change on logical drive %s from degraded to failed (Server %s)"
    --#ARGUMENTS       { 2, 3, 0 }
    --#SEVERITY        CRITICAL
    --#TIMEINDEX       1
    --#HELP            "1) Replace affected disks. 2) The array has to be recreated. Note: Data loss is probable."
    --#STATE           NONOPERATIONAL
    ::= 10418

-- EVT_LD_STATE_CHANGE_PAR_DEG_TO_OP

svrTrapLDStateChangedParDegToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from partially degraded to operational."
    --#TYPE            "State change from partially degraded to operational"
    --#SUMMARY         "Adapter %s: State change on logical drive %s from partially degraded to operational (Server %s)"
    --#ARGUMENTS       { 2, 3, 0 }
    --#SEVERITY        INFORMATIONAL
    --#TIMEINDEX       1
    --#HELP            ""
    --#STATE           OPERATIONAL
    ::= 10419

-- EVT_LD_STATE_CHANGE_PAR_DEG_TO_DEG

svrTrapLDStateChangedParDegToDeg TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from partially degraded to degraded."
    --#TYPE            "State change from partially degraded to degraded"
    --#SUMMARY         "Adapter %s: State change on logical drive %s from partially degraded to degraded (Server %s)"
    --#ARGUMENTS       { 2, 3, 0 }
    --#SEVERITY        MINOR
    --#TIMEINDEX       1
    --#HELP            "Replace affected disk."
    --#STATE           DEGRADED
    ::= 10420

-- EVT_LD_STATE_CHANGE_PAR_DEG_TO_PAR_DEG

svrTrapLDStateChangedParDegToParDeg TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from partially degraded to partially degraded."
    --#TYPE            "State change from partially degraded to partially degraded"
    --#SUMMARY         "Adapter %s: State change on logical drive %s from partially degraded to partially degraded (Server %s)"
    --#ARGUMENTS       { 2, 3, 0 }
    --#SEVERITY        MINOR
    --#TIMEINDEX       1
    --#HELP            "Call your local Fujitsu Helpdesk."
    --#STATE           DEGRADED
    ::= 10421

-- EVT_LD_STATE_CHANGE_PAR_DEG_TO_FAIL

svrTrapLDStateChangedParDegToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from partially degraded to failed."
    --#TYPE            "State change from partially degraded to failed"
    --#SUMMARY         "Adapter %s: State change on logical drive %s from partially degraded to failed (Server %s)"
    --#ARGUMENTS       { 2, 3, 0 }
    --#SEVERITY        CRITICAL
    --#TIMEINDEX       1
    --#HELP            "1) Replace affected disks. 2) The array has to be recreated. Note: Data loss is probable."
    --#STATE           NONOPERATIONAL
    ::= 10422

-- EVT_LD_STATE_CHANGE_FAIL_TO_OP

svrTrapLDStateChangedFailToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to operational."
    --#TYPE            "State change from failed to operational"
    --#SUMMARY         "Adapter %s: State change on logical drive %s from failed to operational (Server %s)"
    --#ARGUMENTS       { 2, 3, 0 }
    --#SEVERITY        INFORMATIONAL
    --#TIMEINDEX       1
    --#HELP            ""
    --#STATE           OPERATIONAL
    ::= 10423

-- EVT_LD_STATE_CHANGE_FAIL_TO_DEG

svrTrapLDStateChangedFailToDeg TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to degraded."
    --#TYPE            "State change from failed to degraded"
    --#SUMMARY         "Adapter %s: State change on logical drive %s from failed to degraded (Server %s)"
    --#ARGUMENTS       { 2, 3, 0 }
    --#SEVERITY        MINOR
    --#TIMEINDEX       1
    --#HELP            "For information only."
    --#STATE           DEGRADED
    ::= 10424

-- EVT_LD_STATE_CHANGE_FAIL_TO_PAR_DEG

svrTrapLDStateChangedFailToParDeg TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to partially degraded."
    --#TYPE            "State change from failed to partially degraded"
    --#SUMMARY         "Adapter %s: State change on logical drive %s from failed to partially degraded (Server %s)"
    --#ARGUMENTS       { 2, 3, 0 }
    --#SEVERITY        MINOR
    --#TIMEINDEX       1
    --#HELP            "For information only."
    --#STATE           DEGRADED
    ::= 10425

-- EVT_LD_STATE_CHANGE_FAIL_TO_FAIL

svrTrapLDStateChangedFailToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to failed."
    --#TYPE            "State change from failed to failed"
    --#SUMMARY         "Adapter %s: State change on logical drive %s from failed to failed (Server %s)"
    --#ARGUMENTS       { 2, 3, 0 }
    --#SEVERITY        CRITICAL
    --#TIMEINDEX       1
    --#HELP            "Call your local Fujitsu Helpdesk."
    --#STATE           NONOPERATIONAL
    ::= 10426

-- EVT_PD_STATE_CHANGE_BY_USER_AVAIL_TO_FAIL

svrTrapPDStateChangeByUserAvailToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to failed."
    --#TYPE            "State change by user from available to failed"
    --#SUMMARY         "Adapter %s: State change by user on disk (%s) from available to failed (Server %s)"
    --#ARGUMENTS       { 2, 3, 0 }
    --#SEVERITY        CRITICAL
    --#TIMEINDEX       1
    --#HELP            "For information only."
    --#STATE           NONOPERATIONAL
    ::= 10427

-- EVT_PD_STATE_CHANGE_BY_USER_AVAIL_TO_HS

svrTrapPDStateChangeByUserAvailToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to hot spare."
    --#TYPE            "State change by user from available to hot spare"
    --#SUMMARY         "Adapter %s: State change by user on disk (%s) from available to hot spare (Server %s)"
    --#ARGUMENTS       { 2, 3, 0 }
    --#SEVERITY        INFORMATIONAL
    --#TIMEINDEX       1
    --#HELP            ""
    --#STATE           OPERATIONAL
    ::= 10428

-- EVT_PD_STATE_CHANGE_BY_USER_AVAIL_TO_RBLD

svrTrapPDStateChangeByUserAvailToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to rebuilding."
    --#TYPE            "State change by user from available to rebuilding"
    --#SUMMARY         "Adapter %s: State change by user on disk (%s) from available to rebuilding (Server %s)"
    --#ARGUMENTS       { 2, 3, 0 }
    --#SEVERITY        INFORMATIONAL
    --#TIMEINDEX       1
    --#HELP            ""
    --#STATE           OPERATIONAL
    ::= 10429

-- EVT_PD_STATE_CHANGE_BY_USER_AVAIL_TO_OP

svrTrapPDStateChangeByUserAvailToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to operational."
    --#TYPE            "State change by user from available to operational"
    --#SUMMARY         "Adapter %s: State change by user on disk (%s) from available to operational (Server %s)"
    --#ARGUMENTS       { 2, 3, 0 }
    --#SEVERITY        INFORMATIONAL
    --#TIMEINDEX       1
    --#HELP            ""
    --#STATE           OPERATIONAL
    ::= 10430

-- EVT_PD_STATE_CHANGE_BY_USER_FAIL_TO_AVAIL

svrTrapPDStateChangeByUserFailToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to available."
    --#TYPE            "State change by user from failed to available"
    --#SUMMARY         "Adapter %s: State change by user on disk (%s) from failed to available (Server %s)"
    --#ARGUMENTS       { 2, 3, 0 }
    --#SEVERITY        INFORMATIONAL
    --#TIMEINDEX       1
    --#HELP            ""
    --#STATE           OPERATIONAL
    ::= 10431

-- EVT_PD_STATE_CHANGE_BY_USER_FAIL_TO_FAIL

svrTrapPDStateChangeByUserFailToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to failed."
    --#TYPE            "State change by user from failed to failed"
    --#SUMMARY         "Adapter %s: State change by user on disk (%s) from failed to failed (Server %s)"
    --#ARGUMENTS       { 2, 3, 0 }
    --#SEVERITY        CRITICAL
    --#TIMEINDEX       1
    --#HELP            "For information only."
    --#STATE           NONOPERATIONAL
    ::= 10432

-- EVT_PD_STATE_CHANGE_BY_USER_FAIL_TO_HS

svrTrapPDStateChangeByUserFailToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to hot spare."
    --#TYPE            "State change by user from failed to hot spare"
    --#SUMMARY         "Adapter %s: State change by user on disk (%s) from failed to hot spare (Server %s)"
    --#ARGUMENTS       { 2, 3, 0 }
    --#SEVERITY        INFORMATIONAL
    --#TIMEINDEX       1
    --#HELP            ""
    --#STATE           OPERATIONAL
    ::= 10433

-- EVT_PD_STATE_CHANGE_BY_USER_FAIL_TO_RBLD

svrTrapPDStateChangeByUserFailToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to rebuilding."
    --#TYPE            "State change by user from failed to rebuilding"
    --#SUMMARY         "Adapter %s: State change by user on disk (%s) from failed to rebuilding (Server %s)"
    --#ARGUMENTS       { 2, 3, 0 }
    --#SEVERITY        INFORMATIONAL
    --#TIMEINDEX       1
    --#HELP            ""
    --#STATE           OPERATIONAL
    ::= 10434

-- EVT_PD_STATE_CHANGE_BY_USER_FAIL_TO_OP

svrTrapPDStateChangeByUserFailToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to operational."
    --#TYPE            "State change by user from failed to operational"
    --#SUMMARY         "Adapter %s: State change by user on disk (%s) from failed to operational (Server %s)"
    --#ARGUMENTS       { 2, 3, 0 }
    --#SEVERITY        INFORMATIONAL
    --#TIMEINDEX       1
    --#HELP            ""
    --#STATE           OPERATIONAL
    ::= 10435

-- EVT_PD_STATE_CHANGE_BY_USER_HS_TO_AVAIL

svrTrapPDStateChangeByUserHSToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to available."
    --#TYPE            "State change by user from hot spare to available"
    --#SUMMARY         "Adapter %s: State change by user on disk (%s) from hot spare to available (Server %s)"
    --#ARGUMENTS       { 2, 3, 0 }
    --#SEVERITY        INFORMATIONAL
    --#TIMEINDEX       1
    --#HELP            ""
    --#STATE           OPERATIONAL
    ::= 10436

-- EVT_PD_STATE_CHANGE_BY_USER_HS_TO_FAIL

svrTrapPDStateChangeByUserHSToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to failed."
    --#TYPE            "State change by user from hot spare to failed"
    --#SUMMARY         "Adapter %s: State change by user on disk (%s) from hot spare to failed (Server %s)"
    --#ARGUMENTS       { 2, 3, 0 }
    --#SEVERITY        CRITICAL
    --#TIMEINDEX       1
    --#HELP            "For information only."
    --#STATE           NONOPERATIONAL
    ::= 10437

-- EVT_PD_STATE_CHANGE_BY_USER_HS_TO_HS

svrTrapPDStateChangeByUserHSToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to hot spare."
    --#TYPE            "State change by user from hot spare to hot spare"
    --#SUMMARY         "Adapter %s: State change by user on disk (%s) from hot spare to hot spare (Server %s)"
    --#ARGUMENTS       { 2, 3, 0 }
    --#SEVERITY        INFORMATIONAL
    --#TIMEINDEX       1
    --#HELP            ""
    --#STATE           OPERATIONAL
    ::= 10438

-- EVT_PD_STATE_CHANGE_BY_USER_HS_TO_RBLD

svrTrapPDStateChangeByUserHSToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to rebuilding."
    --#TYPE            "State change by user from hot spare to rebuilding"
    --#SUMMARY         "Adapter %s: State change by user on disk (%s) from hot spare to rebuilding (Server %s)"
    --#ARGUMENTS       { 2, 3, 0 }
    --#SEVERITY        INFORMATIONAL
    --#TIMEINDEX       1
    --#HELP            ""
    --#STATE           OPERATIONAL
    ::= 10439

-- EVT_PD_STATE_CHANGE_BY_USER_HS_TO_OP

svrTrapPDStateChangeByUserHSToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to operational."
    --#TYPE            "State change by user from hot spare to operational"
    --#SUMMARY         "Adapter %s: State change by user on disk (%s) from hot spare to operational (Server %s)"
    --#ARGUMENTS       { 2, 3, 0 }
    --#SEVERITY        INFORMATIONAL
    --#TIMEINDEX       1
    --#HELP            ""
    --#STATE           OPERATIONAL
    ::= 10440

-- EVT_PD_STATE_CHANGE_BY_USER_RBLD_TO_AVAIL

svrTrapPDStateChangeByUserRbldToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to available."
    --#TYPE            "State change by user from rebuilding to available"
    --#SUMMARY         "Adapter %s: State change by user on disk (%s) from rebuilding to available (Server %s)"
    --#ARGUMENTS       { 2, 3, 0 }
    --#SEVERITY        INFORMATIONAL
    --#TIMEINDEX       1
    --#HELP            ""
    --#STATE           OPERATIONAL
    ::= 10441

-- EVT_PD_STATE_CHANGE_BY_USER_RBLD_TO_FAIL

svrTrapPDStateChangeByUserRbldToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to failed."
    --#TYPE            "State change by user from rebuilding to failed"
    --#SUMMARY         "Adapter %s: State change by user on disk (%s) from rebuilding to failed (Server %s)"
    --#ARGUMENTS       { 2, 3, 0 }
    --#SEVERITY        CRITICAL
    --#TIMEINDEX       1
    --#HELP            "For information only."
    --#STATE           NONOPERATIONAL
    ::= 10442

-- EVT_PD_STATE_CHANGE_BY_USER_RBLD_TO_HS

svrTrapPDStateChangeByUserRbldToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to hot spare."
    --#TYPE            "State change by user from rebuilding to hot spare"
    --#SUMMARY         "Adapter %s: State change by user on disk (%s) from rebuilding to hot spare (Server %s)"
    --#ARGUMENTS       { 2, 3, 0 }
    --#SEVERITY        INFORMATIONAL
    --#TIMEINDEX       1
    --#HELP            ""
    --#STATE           OPERATIONAL
    ::= 10443

-- EVT_PD_STATE_CHANGE_BY_USER_RBLD_TO_RBLD

svrTrapPDStateChangeByUserRbldToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to rebuilding."
    --#TYPE            "State change by user from rebuilding to rebuilding"
    --#SUMMARY         "Adapter %s: State change by user on disk (%s) from rebuilding to rebuilding (Server %s)"
    --#ARGUMENTS       { 2, 3, 0 }
    --#SEVERITY        INFORMATIONAL
    --#TIMEINDEX       1
    --#HELP            ""
    --#STATE           OPERATIONAL
    ::= 10444

-- EVT_PD_STATE_CHANGE_BY_USER_RBLD_TO_OP

svrTrapPDStateChangeByUserRbldToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to operational."
    --#TYPE            "State change by user from rebuilding to operational"
    --#SUMMARY         "Adapter %s: State change by user on disk (%s) from rebuilding to operational (Server %s)"
    --#ARGUMENTS       { 2, 3, 0 }
    --#SEVERITY        INFORMATIONAL
    --#TIMEINDEX       1
    --#HELP            ""
    --#STATE           OPERATIONAL
    ::= 10445

-- EVT_PD_STATE_CHANGE_BY_USER_OP_TO_AVAIL

svrTrapPDStateChangeByUserOpToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to available."
    --#TYPE            "State change by user from operational to available"
    --#SUMMARY         "Adapter %s: State change by user on disk (%s) from operational to available (Server %s)"
    --#ARGUMENTS       { 2, 3, 0 }
    --#SEVERITY        INFORMATIONAL
    --#TIMEINDEX       1
    --#HELP            ""
    --#STATE           OPERATIONAL
    ::= 10446

-- EVT_PD_STATE_CHANGE_BY_USER_OP_TO_FAIL

svrTrapPDStateChangeByUserOpToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to failed."
    --#TYPE            "State change by user from operational to failed"
    --#SUMMARY         "Adapter %s: State change by user on disk (%s) from operational to failed (Server %s)"
    --#ARGUMENTS       { 2, 3, 0 }
    --#SEVERITY        CRITICAL
    --#TIMEINDEX       1
    --#HELP            "For information only."
    --#STATE           NONOPERATIONAL
    ::= 10447

-- EVT_PD_STATE_CHANGE_BY_USER_OP_TO_HS

svrTrapPDStateChangeByUserOpToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to hot spare."
    --#TYPE            "State change by user from operational to hot spare"
    --#SUMMARY         "Adapter %s: State change by user on disk (%s) from operational to hot spare (Server %s)"
    --#ARGUMENTS       { 2, 3, 0 }
    --#SEVERITY        INFORMATIONAL
    --#TIMEINDEX       1
    --#HELP            ""
    --#STATE           OPERATIONAL
    ::= 10448

-- EVT_PD_STATE_CHANGE_BY_USER_OP_TO_RBLD

svrTrapPDStateChangeByUserOpToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to rebuilding."
    --#TYPE            "State change by user from operational to rebuilding"
    --#SUMMARY         "Adapter %s: State change by user on disk (%s) from operational to rebuilding (Server %s)"
    --#ARGUMENTS       { 2, 3, 0 }
    --#SEVERITY        INFORMATIONAL
    --#TIMEINDEX       1
    --#HELP            ""
    --#STATE           OPERATIONAL
    ::= 10449

-- EVT_PD_STATE_CHANGE_BY_USER_OP_TO_OP

svrTrapPDStateChangeByUserOpToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to operational."
    --#TYPE            "State change by user from operational to operational"
    --#SUMMARY         "Adapter %s: State change by user on disk (%s) from operational to operational (Server %s)"
    --#ARGUMENTS       { 2, 3, 0 }
    --#SEVERITY        INFORMATIONAL
    --#TIMEINDEX       1
    --#HELP            ""
    --#STATE           OPERATIONAL
    ::= 10450

-- EVT_PD_STATE_CHANGE_AVAIL_TO_FAIL

svrTrapPDStateChangeAvailToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to failed."
    --#TYPE            "State change from available to failed"
    --#SUMMARY         "Adapter %s: State change on disk (%s) from available to failed (Server %s)"
    --#ARGUMENTS       { 2, 3, 0 }
    --#SEVERITY        CRITICAL
    --#TIMEINDEX       1
    --#HELP            "Replace affected disk."
    --#STATE           NONOPERATIONAL
    ::= 10451

-- EVT_PD_STATE_CHANGE_AVAIL_TO_HS

svrTrapPDStateChangeAvailToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to hot spare."
    --#TYPE            "State change from available to hot spare"
    --#SUMMARY         "Adapter %s: State change on disk (%s) from available to hot spare (Server %s)"
    --#ARGUMENTS       { 2, 3, 0 }
    --#SEVERITY        INFORMATIONAL
    --#TIMEINDEX       1
    --#HELP            ""
    --#STATE           OPERATIONAL
    ::= 10452

-- EVT_PD_STATE_CHANGE_AVAIL_TO_RBLD

svrTrapPDStateChangeAvailToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to rebuilding."
    --#TYPE            "State change from available to rebuilding"
    --#SUMMARY         "Adapter %s: State change on disk (%s) from available to rebuilding (Server %s)"
    --#ARGUMENTS       { 2, 3, 0 }
    --#SEVERITY        INFORMATIONAL
    --#TIMEINDEX       1
    --#HELP            ""
    --#STATE           OPERATIONAL
    ::= 10453

-- EVT_PD_STATE_CHANGE_AVAIL_TO_OP

svrTrapPDStateChangeAvailToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to operational."
    --#TYPE            "State change from available to operational"
    --#SUMMARY         "Adapter %s: State change on disk (%s) from available to operational (Server %s)"
    --#ARGUMENTS       { 2, 3, 0 }
    --#SEVERITY        INFORMATIONAL
    --#TIMEINDEX       1
    --#HELP            ""
    --#STATE           OPERATIONAL
    ::= 10454

-- EVT_PD_STATE_CHANGE_FAIL_TO_AVAIL

svrTrapPDStateChangeFailToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to available."
    --#TYPE            "State change from failed to available"
    --#SUMMARY         "Adapter %s: State change on disk (%s) from failed to available (Server %s)"
    --#ARGUMENTS       { 2, 3, 0 }
    --#SEVERITY        INFORMATIONAL
    --#TIMEINDEX       1
    --#HELP            ""
    --#STATE           OPERATIONAL
    ::= 10455

-- EVT_PD_STATE_CHANGE_FAIL_TO_FAIL

svrTrapPDStateChangeFailToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to failed."
    --#TYPE            "State change from failed to failed"
    --#SUMMARY         "Adapter %s: State change on disk (%s) from failed to failed (Server %s)"
    --#ARGUMENTS       { 2, 3, 0 }
    --#SEVERITY        CRITICAL
    --#TIMEINDEX       1
    --#HELP            "Call your local Fujitsu Helpdesk."
    --#STATE           NONOPERATIONAL
    ::= 10456

-- EVT_PD_STATE_CHANGE_FAIL_TO_HS

svrTrapPDStateChangeFailToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to hot spare."
    --#TYPE            "State change from failed to hot spare"
    --#SUMMARY         "Adapter %s: State change on disk (%s) from failed to hot spare (Server %s)"
    --#ARGUMENTS       { 2, 3, 0 }
    --#SEVERITY        INFORMATIONAL
    --#TIMEINDEX       1
    --#HELP            ""
    --#STATE           OPERATIONAL
    ::= 10457

-- EVT_PD_STATE_CHANGE_FAIL_TO_RBLD

svrTrapPDStateChangeFailToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to rebuilding."
    --#TYPE            "State change from failed to rebuilding"
    --#SUMMARY         "Adapter %s: State change on disk (%s) from failed to rebuilding (Server %s)"
    --#ARGUMENTS       { 2, 3, 0 }
    --#SEVERITY        INFORMATIONAL
    --#TIMEINDEX       1
    --#HELP            ""
    --#STATE           OPERATIONAL
    ::= 10458

-- EVT_PD_STATE_CHANGE_FAIL_TO_OP

svrTrapPDStateChangeFailToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to operational."
    --#TYPE            "State change from failed to operational"
    --#SUMMARY         "Adapter %s: State change on disk (%s) from failed to operational (Server %s)"
    --#ARGUMENTS       { 2, 3, 0 }
    --#SEVERITY        INFORMATIONAL
    --#TIMEINDEX       1
    --#HELP            ""
    --#STATE           OPERATIONAL
    ::= 10459

-- EVT_PD_STATE_CHANGE_HS_TO_AVAIL

svrTrapPDStateChangeHSToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to available."
    --#TYPE            "State change from hot spare to available"
    --#SUMMARY         "Adapter %s: State change on disk (%s) from hot spare to available (Server %s)"
    --#ARGUMENTS       { 2, 3, 0 }
    --#SEVERITY        INFORMATIONAL
    --#TIMEINDEX       1
    --#HELP            ""
    --#STATE           OPERATIONAL
    ::= 10460

-- EVT_PD_STATE_CHANGE_HS_TO_FAIL

svrTrapPDStateChangeHSToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to failed."
    --#TYPE            "State change from hot spare to failed"
    --#SUMMARY         "Adapter %s: State change on disk (%s) from hot spare to failed (Server %s)"
    --#ARGUMENTS       { 2, 3, 0 }
    --#SEVERITY        CRITICAL
    --#TIMEINDEX       1
    --#HELP            "Replace affected disk."
    --#STATE           NONOPERATIONAL
    ::= 10461

-- EVT_PD_STATE_CHANGE_HS_TO_HS

svrTrapPDStateChangeHSToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to hot spare."
    --#TYPE            "State change from hot spare to hot spare"
    --#SUMMARY         "Adapter %s: State change on disk (%s) from hot spare to hot spare (Server %s)"
    --#ARGUMENTS       { 2, 3, 0 }
    --#SEVERITY        INFORMATIONAL
    --#TIMEINDEX       1
    --#HELP            ""
    --#STATE           OPERATIONAL
    ::= 10462

-- EVT_PD_STATE_CHANGE_HS_TO_RBLD

svrTrapPDStateChangeHSToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to rebuilding."
    --#TYPE            "State change from hot spare to rebuilding"
    --#SUMMARY         "Adapter %s: State change on disk (%s) from hot spare to rebuilding (Server %s)"
    --#ARGUMENTS       { 2, 3, 0 }
    --#SEVERITY        INFORMATIONAL
    --#TIMEINDEX       1
    --#HELP            ""
    --#STATE           OPERATIONAL
    ::= 10463

-- EVT_PD_STATE_CHANGE_HS_TO_OP

svrTrapPDStateChangeHSToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to operational."
    --#TYPE            "State change from hot spare to operational"
    --#SUMMARY         "Adapter %s: State change on disk (%s) from hot spare to operational (Server %s)"
    --#ARGUMENTS       { 2, 3, 0 }
    --#SEVERITY        INFORMATIONAL
    --#TIMEINDEX       1
    --#HELP            ""
    --#STATE           OPERATIONAL
    ::= 10464

-- EVT_PD_STATE_CHANGE_RBLD_TO_AVAIL

svrTrapPDStateChangeRbldToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to available."
    --#TYPE            "State change from rebuilding to available"
    --#SUMMARY         "Adapter %s: State change on disk (%s) from rebuilding to available (Server %s)"
    --#ARGUMENTS       { 2, 3, 0 }
    --#SEVERITY        INFORMATIONAL
    --#TIMEINDEX       1
    --#HELP            ""
    --#STATE           OPERATIONAL
    ::= 10465

-- EVT_PD_STATE_CHANGE_RBLD_TO_FAIL

svrTrapPDStateChangeRbldToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to failed."
    --#TYPE            "State change from rebuilding to failed"
    --#SUMMARY         "Adapter %s: State change on disk (%s) from rebuilding to failed (Server %s)"
    --#ARGUMENTS       { 2, 3, 0 }
    --#SEVERITY        CRITICAL
    --#TIMEINDEX       1
    --#HELP            "1) Manually initiate a second rebuild (e.g. via ServerView RAID Manager). 2) If problem persists replace affected disk."
    --#STATE           NONOPERATIONAL
    ::= 10466

-- EVT_PD_STATE_CHANGE_RBLD_TO_HS

svrTrapPDStateChangeRbldToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to hot spare."
    --#TYPE            "State change from rebuilding to hot spare"
    --#SUMMARY         "Adapter %s: State change on disk (%s) from rebuilding to hot spare (Server %s)"
    --#ARGUMENTS       { 2, 3, 0 }
    --#SEVERITY        INFORMATIONAL
    --#TIMEINDEX       1
    --#HELP            ""
    --#STATE           OPERATIONAL
    ::= 10467

-- EVT_PD_STATE_CHANGE_RBLD_TO_RBLD

svrTrapPDStateChangeRbldToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to rebuilding."
    --#TYPE            "State change from rebuilding to rebuilding"
    --#SUMMARY         "Adapter %s: State change on disk (%s) from rebuilding to rebuilding (Server %s)"
    --#ARGUMENTS       { 2, 3, 0 }
    --#SEVERITY        INFORMATIONAL
    --#TIMEINDEX       1
    --#HELP            ""
    --#STATE           OPERATIONAL
    ::= 10468

-- EVT_PD_STATE_CHANGE_RBLD_TO_OP

svrTrapPDStateChangeRbldToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to operational."
    --#TYPE            "State change from rebuilding to operational"
    --#SUMMARY         "Adapter %s: State change on disk (%s) from rebuilding to operational (Server %s)"
    --#ARGUMENTS       { 2, 3, 0 }
    --#SEVERITY        INFORMATIONAL
    --#TIMEINDEX       1
    --#HELP            ""
    --#STATE           OPERATIONAL
    ::= 10469

-- EVT_PD_STATE_CHANGE_OP_TO_AVAIL

svrTrapPDStateChangeOpToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to available."
    --#TYPE            "State change from operational to available"
    --#SUMMARY         "Adapter %s: State change on disk (%s) from operational to available (Server %s)"
    --#ARGUMENTS       { 2, 3, 0 }
    --#SEVERITY        INFORMATIONAL
    --#TIMEINDEX       1
    --#HELP            ""
    --#STATE           OPERATIONAL
    ::= 10470

-- EVT_PD_STATE_CHANGE_OP_TO_FAIL

svrTrapPDStateChangeOpToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to failed."
    --#TYPE            "State change from operational to failed"
    --#SUMMARY         "Adapter %s: State change on disk (%s) from operational to failed (Server %s)"
    --#ARGUMENTS       { 2, 3, 0 }
    --#SEVERITY        CRITICAL
    --#TIMEINDEX       1
    --#HELP            "Replace affected disk."
    --#STATE           NONOPERATIONAL
    ::= 10471

-- EVT_PD_STATE_CHANGE_OP_TO_HS

svrTrapPDStateChangeOpToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to hot spare."
    --#TYPE            "State change from operational to hot spare"
    --#SUMMARY         "Adapter %s: State change on disk (%s) from operational to hot spare (Server %s)"
    --#ARGUMENTS       { 2, 3, 0 }
    --#SEVERITY        INFORMATIONAL
    --#TIMEINDEX       1
    --#HELP            ""
    --#STATE           OPERATIONAL
    ::= 10472

-- EVT_PD_STATE_CHANGE_OP_TO_RBLD

svrTrapPDStateChangeOpToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to rebuilding."
    --#TYPE            "State change from operational to rebuilding"
    --#SUMMARY         "Adapter %s: State change on disk (%s) from operational to rebuilding (Server %s)"
    --#ARGUMENTS       { 2, 3, 0 }
    --#SEVERITY        INFORMATIONAL
    --#TIMEINDEX       1
    --#HELP            ""
    --#STATE           OPERATIONAL
    ::= 10473

-- EVT_PD_STATE_CHANGE_OP_TO_OP

svrTrapPDStateChangeOpToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to operational."
    --#TYPE            "State change from operational to operational"
    --#SUMMARY         "Adapter %s: State change on disk (%s) from operational to operational (Server %s)"
    --#ARGUMENTS       { 2, 3, 0 }
    --#SEVERITY        INFORMATIONAL
    --#TIMEINDEX       1
    --#HELP            ""
    --#STATE           OPERATIONAL
    ::= 10474

-- EVT_MDC_DOUBLE_MEDIUM_ERRORS_DETECTED

svrTrapLDMDCDoubleMediumErrorsDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC detected uncorrectable multiple medium errors on logical drive."
    --#TYPE            "MDC detected uncorrectable multiple medium errors on logical drive"
    --#SUMMARY         "Adapter %s: MDC detected uncorrectable multiple medium errors (disk (%s) at LBA %s on logical drive %s) (Server %s)"
    --#ARGUMENTS       { 2, 3, 4, 5, 0 }
    --#SEVERITY        MAJOR
    --#TIMEINDEX       1
    --#HELP            "Replace affected disk."
    --#STATE           OPERATIONAL
    ::= 10475

-- EVT_PD_MISSING_AFTER_REBOOT

svrTrapPDMissingAfterReboot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk missing after reboot."
    --#TYPE            "Disk missing after reboot"
    --#SUMMARY         "Adapter %s: Disk (%s) missing after reboot (Server %s)"
    --#ARGUMENTS       { 2, 3, 0 }
    --#SEVERITY        MAJOR
    --#TIMEINDEX       1
    --#HELP            "Check your RAID configuration."
    --#STATE           OPERATIONAL
    ::= 10476

-- EVT_LD_MISSING_AFTER_REBOOT

svrTrapLDMissingAfterReboot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive missing after reboot."
    --#TYPE            "Logical drive missing after reboot"
    --#SUMMARY         "Adapter %s: Logical drive %s missing after reboot (Server %s)"
    --#ARGUMENTS       { 2, 3, 0 }
    --#SEVERITY        MAJOR
    --#TIMEINDEX       1
    --#HELP            "Check your RAID configuration."
    --#STATE           OPERATIONAL
    ::= 10477

-- EVT_PD_APPEARED_AFTER_REBOOT

svrTrapPDAppearedAfterReboot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk appeared new after reboot."
    --#TYPE            "Disk appeared new after reboot"
    --#SUMMARY         "Adapter %s: Disk (%s) appeared new after reboot (Server %s)"
    --#ARGUMENTS       { 2, 3, 0 }
    --#SEVERITY        INFORMATIONAL
    --#TIMEINDEX       1
    --#HELP            ""
    --#STATE           OPERATIONAL
    ::= 10478

-- EVT_LD_APPEARED_AFTER_REBOOT

svrTrapLDAppearedAfterReboot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive appeared new after reboot."
    --#TYPE            "Logical drive appeared new after reboot"
    --#SUMMARY         "Adapter %s: Logical drive %s appeared new after reboot (Server %s)"
    --#ARGUMENTS       { 2, 3, 0 }
    --#SEVERITY        INFORMATIONAL
    --#TIMEINDEX       1
    --#HELP            ""
    --#STATE           OPERATIONAL
    ::= 10479

-- EVT_CTRL_PUNCTURE_ENABLED

svrTrapCtrlPunctureEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Puncture enabled."
    --#TYPE            "Puncture enabled"
    --#SUMMARY         "Adapter %s: Puncturing of LBAs enabled (Server %s)"
    --#ARGUMENTS       { 2, 0 }
    --#SEVERITY        MAJOR
    --#TIMEINDEX       1
    --#HELP            "Call your local Fujitsu Helpdesk."
    --#STATE           OPERATIONAL
    ::= 10480

-- EVT_CTRL_PUNCTURE_DISABLED

svrTrapCtrlPunctureDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Puncture disabled."
    --#TYPE            "Puncture disabled"
    --#SUMMARY         "Adapter %s: Puncturing of LBAs disabled (Server %s)"
    --#ARGUMENTS       { 2, 0 }
    --#SEVERITY        MAJOR
    --#TIMEINDEX       1
    --#HELP            "Call your local Fujitsu Helpdesk."
    --#STATE           OPERATIONAL
    ::= 10481

-- EVT_ENCL_SIM_NOT_INSTALLED

svrTrapEnclSimNotInstalled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure I/O module not installed."
    --#TYPE            "Enclosure I/O module not installed"
    --#SUMMARY         "Adapter %s: Enclosure %s I/O module %s not installed (Server %s)"
    --#ARGUMENTS       { 2, 3, 4, 0 }
    --#SEVERITY        CRITICAL
    --#TIMEINDEX       1
    --#HELP            "Call your local Fujitsu Helpdesk."
    --#STATE           OPERATIONAL
    ::= 10482

-- EVT_PACKAGE_VERSION

svrTrapPackageVersion TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Package version."
    --#TYPE            "Package version"
    --#SUMMARY         "Adapter %s: Package version %s (Server %s)"
    --#ARGUMENTS       { 2, 3, 0 }
    --#SEVERITY        INFORMATIONAL
    --#TIMEINDEX       1
    --#HELP            ""
    --#STATE           OPERATIONAL
    ::= 10483

-- EVT_LD_MV_CORRECTED_MEDIUM_ERROR

svrTrapLDMVCorrectedMediumError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Media verification corrected error."
    --#TYPE            "Media verification corrected error"
    --#SUMMARY         "Adapter %s: Media verification corrected error (logical drive %s at LBA %s on disk (%s) at LBA %s) (Server %s)"
    --#ARGUMENTS       { 2, 3, 4, 5, 6, 0 }
    --#SEVERITY        INFORMATIONAL
    --#TIMEINDEX       1
    --#HELP            ""
    --#STATE           OPERATIONAL
    ::= 10484

-- EVT_PD_STATE_CHANGE_AVAIL_TO_OFFL

svrTrapPDStateChangeAvailToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to offline."
    --#TYPE            "State change from available to offline"
    --#SUMMARY         "Adapter %s: State change on disk (%s) from available to offline (Server %s)"
    --#ARGUMENTS       { 2, 3, 0 }
    --#SEVERITY        MINOR
    --#TIMEINDEX       1
    --#HELP            "For information only."
    --#STATE           DEGRADED
    ::= 10485

-- EVT_PD_STATE_CHANGE_BY_USER_AVAIL_TO_OFFL

svrTrapPDStateChangeByUserAvailToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to offline."
    --#TYPE            "State change by user from available to offline"
    --#SUMMARY         "Adapter %s: State change by user on disk (%s) from available to offline (Server %s)"
    --#ARGUMENTS       { 2, 3, 0 }
    --#SEVERITY        MINOR
    --#TIMEINDEX       1
    --#HELP            "For information only."
    --#STATE           DEGRADED
    ::= 10486

-- EVT_PD_STATE_CHANGE_BY_USER_FAIL_TO_OFFL

svrTrapPDStateChangeByUserFailToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to offline."
    --#TYPE            "State change by user from failed to offline"
    --#SUMMARY         "Adapter %s: State change by user on disk (%s) from failed to offline (Server %s)"
    --#ARGUMENTS       { 2, 3, 0 }
    --#SEVERITY        MINOR
    --#TIMEINDEX       1
    --#HELP            "For information only."
    --#STATE           DEGRADED
    ::= 10487

-- EVT_PD_STATE_CHANGE_BY_USER_HS_TO_OFFL

svrTrapPDStateChangeByUserHotspareToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to offline."
    --#TYPE            "State change by user from hot spare to offline"
    --#SUMMARY         "Adapter %s: State change by user on disk (%s) from hot spare to offline (Server %s)"
    --#ARGUMENTS       { 2, 3, 0 }
    --#SEVERITY        MINOR
    --#TIMEINDEX       1
    --#HELP            "For information only."
    --#STATE           DEGRADED
    ::= 10488

-- EVT_PD_STATE_CHANGE_BY_USER_OFFL_TO_AVAIL

svrTrapPDStateChangeByUserOfflineToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to available."
    --#TYPE            "State change by user from offline to available"
    --#SUMMARY         "Adapter %s: State change by user on disk (%s) from offline to available (Server %s)"
    --#ARGUMENTS       { 2, 3, 0 }
    --#SEVERITY        INFORMATIONAL
    --#TIMEINDEX       1
    --#HELP            ""
    --#STATE           OPERATIONAL
    ::= 10489

-- EVT_PD_STATE_CHANGE_BY_USER_OFFL_TO_FAIL

svrTrapPDStateChangeByUserOfflineToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to failed."
    --#TYPE            "State change by user from offline to failed"
    --#SUMMARY         "Adapter %s: State change by user on disk (%s) from offline to failed (Server %s)"
    --#ARGUMENTS       { 2, 3, 0 }
    --#SEVERITY        CRITICAL
    --#TIMEINDEX       1
    --#HELP            "For information only."
    --#STATE           NONOPERATIONAL
    ::= 10490

-- EVT_PD_STATE_CHANGE_BY_USER_OFFL_TO_HS

svrTrapPDStateChangeByUserOfflineToHotspare TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to hot spare."
    --#TYPE            "State change by user from offline to hot spare"
    --#SUMMARY         "Adapter %s: State change by user on disk (%s) from offline to hot spare (Server %s)"
    --#ARGUMENTS       { 2, 3, 0 }
    --#SEVERITY        INFORMATIONAL
    --#TIMEINDEX       1
    --#HELP            ""
    --#STATE           OPERATIONAL
    ::= 10491

-- EVT_PD_STATE_CHANGE_BY_USER_OFFL_TO_OFFL

svrTrapPDStateChangeByUserOfflineToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to offline."
    --#TYPE            "State change by user from offline to offline"
    --#SUMMARY         "Adapter %s: State change by user on disk (%s) from offline to offline (Server %s)"
    --#ARGUMENTS       { 2, 3, 0 }
    --#SEVERITY        MINOR
    --#TIMEINDEX       1
    --#HELP            "For information only."
    --#STATE           DEGRADED
    ::= 10492

-- EVT_PD_STATE_CHANGE_BY_USER_OFFL_TO_OP

svrTrapPDStateChangeByUserOfflineToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to operational."
    --#TYPE            "State change by user from offline to operational"
    --#SUMMARY         "Adapter %s: State change by user on disk (%s) from offline to operational (Server %s)"
    --#ARGUMENTS       { 2, 3, 0 }
    --#SEVERITY        INFORMATIONAL
    --#TIMEINDEX       1
    --#HELP            ""
    --#STATE           OPERATIONAL
    ::= 10493

-- EVT_PD_STATE_CHANGE_BY_USER_OFFL_TO_RBLD

svrTrapPDStateChangeByUserOfflineToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to rebuilding."
    --#TYPE            "State change by user from offline to rebuilding"
    --#SUMMARY         "Adapter %s: State change by user on disk (%s) from offline to rebuilding (Server %s)"
    --#ARGUMENTS       { 2, 3, 0 }
    --#SEVERITY        INFORMATIONAL
    --#TIMEINDEX       1
    --#HELP            ""
    --#STATE           DEGRADED
    ::= 10494

-- EVT_PD_STATE_CHANGE_BY_USER_OP_TO_OFFL

svrTrapPDStateChangeByUserOpToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to offline."
    --#TYPE            "State change by user from operational to offline"
    --#SUMMARY         "Adapter %s: State change by user on disk (%s) from operational to offline (Server %s)"
    --#ARGUMENTS       { 2, 3, 0 }
    --#SEVERITY        MINOR
    --#TIMEINDEX       1
    --#HELP            "For information only."
    --#STATE           DEGRADED
    ::= 10495

-- EVT_PD_STATE_CHANGE_BY_USER_RBLD_TO_OFFL

svrTrapPDStateChangeByUserRbldToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to offline."
    --#TYPE            "State change by user from rebuilding to offline"
    --#SUMMARY         "Adapter %s: State change by user on disk (%s) from rebuilding to offline (Server %s)"
    --#ARGUMENTS       { 2, 3, 0 }
    --#SEVERITY        MINOR
    --#TIMEINDEX       1
    --#HELP            "For information only."
    --#STATE           DEGRADED
    ::= 10496

-- EVT_PD_STATE_CHANGE_FAIL_TO_OFFL

svrTrapPDStateChangeFailToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to offline."
    --#TYPE            "State change from failed to offline"
    --#SUMMARY         "Adapter %s: State change on disk (%s) from failed to offline (Server %s)"
    --#ARGUMENTS       { 2, 3, 0 }
    --#SEVERITY        MINOR
    --#TIMEINDEX       1
    --#HELP            "For information only."
    --#STATE           DEGRADED
    ::= 10497

-- EVT_PD_STATE_CHANGE_HS_TO_OFFL

svrTrapPDStateChangeHSToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to offline."
    --#TYPE            "State change from hot spare to offline"
    --#SUMMARY         "Adapter %s: State change on disk (%s) from hot spare to offline (Server %s)"
    --#ARGUMENTS       { 2, 3, 0 }
    --#SEVERITY        MINOR
    --#TIMEINDEX       1
    --#HELP            "1) Manually set the disk to hot spare again (e.g. via ServerView RAID Manager). 2) If problem persists replace affected disk."
    --#STATE           NONOPERATIONAL
    ::= 10498

-- EVT_PD_STATE_CHANGE_OFFL_TO_AVAIL

svrTrapPDStateChangeOfflineToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to available."
    --#TYPE            "State change from offline to available"
    --#SUMMARY         "Adapter %s: State change on disk (%s) from offline to available (Server %s)"
    --#ARGUMENTS       { 2, 3, 0 }
    --#SEVERITY        INFORMATIONAL
    --#TIMEINDEX       1
    --#HELP            ""
    --#STATE           OPERATIONAL
    ::= 10499

-- EVT_PD_STATE_CHANGE_OFFL_TO_FAIL

svrTrapPDStateChangeOfflineToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to failed."
    --#TYPE            "State change from offline to failed"
    --#SUMMARY         "Adapter %s: State change on disk (%s) from offline to failed (Server %s)"
    --#ARGUMENTS       { 2, 3, 0 }
    --#SEVERITY        CRITICAL
    --#TIMEINDEX       1
    --#HELP            "Replace affected disk."
    --#STATE           NONOPERATIONAL
    ::= 10500

-- EVT_PD_STATE_CHANGE_OFFL_TO_HS

svrTrapPDStateChangeOfflineToHS TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to hot spare."
    --#TYPE            "State change from offline to hot spare"
    --#SUMMARY         "Adapter %s: State change on disk (%s) from offline to hot spare (Server %s)"
    --#ARGUMENTS       { 2, 3, 0 }
    --#SEVERITY        INFORMATIONAL
    --#TIMEINDEX       1
    --#HELP            ""
    --#STATE           OPERATIONAL
    ::= 10501

-- EVT_PD_STATE_CHANGE_OFFL_TO_OFFL

svrTrapPDStateChangeOfflineToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to offline."
    --#TYPE            "State change from offline to offline"
    --#SUMMARY         "Adapter %s: State change on disk (%s) from offline to offline (Server %s)"
    --#ARGUMENTS       { 2, 3, 0 }
    --#SEVERITY        MINOR
    --#TIMEINDEX       1
    --#HELP            "For information only."
    --#STATE           DEGRADED
    ::= 10502

-- EVT_PD_STATE_CHANGE_OFFL_TO_OP

svrTrapPDStateChangeOfflineToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to operational."
    --#TYPE            "State change from offline to operational"
    --#SUMMARY         "Adapter %s: State change on disk (%s) from offline to operational (Server %s)"
    --#ARGUMENTS       { 2, 3, 0 }
    --#SEVERITY        INFORMATIONAL
    --#TIMEINDEX       1
    --#HELP            ""
    --#STATE           OPERATIONAL
    ::= 10503

-- EVT_PD_STATE_CHANGE_OFFL_TO_RBLD

svrTrapPDStateChangeOfflineToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to rebuilding."
    --#TYPE            "State change from offline to rebuilding"
    --#SUMMARY         "Adapter %s: State change on disk (%s) from offline to rebuilding (Server %s)"
    --#ARGUMENTS       { 2, 3, 0 }
    --#SEVERITY        INFORMATIONAL
    --#TIMEINDEX       1
    --#HELP            ""
    --#STATE           DEGRADED
    ::= 10504

-- EVT_PD_STATE_CHANGE_OP_TO_OFFL

svrTrapPDStateChangeOpToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to offline."
    --#TYPE            "State change from operational to offline"
    --#SUMMARY         "Adapter %s: State change on disk (%s) from operational to offline (Server %s)"
    --#ARGUMENTS       { 2, 3, 0 }
    --#SEVERITY        MINOR
    --#TIMEINDEX       1
    --#HELP            "Note: Only informational if status change was forced by user otherwise: 1) Replace affected disk."
    --#STATE           DEGRADED
    ::= 10505

-- EVT_PD_STATE_CHANGE_RBLD_TO_OFFL

svrTrapPDStateChangeRbldToOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to offline."
    --#TYPE            "State change from rebuilding to offline"
    --#SUMMARY         "Adapter %s: State change on disk (%s) from rebuilding to offline (Server %s)"
    --#ARGUMENTS       { 2, 3, 0 }
    --#SEVERITY        MINOR
    --#TIMEINDEX       1
    --#HELP            "Note: Only informational if status change was forced by user otherwise: 1) Replace affected disk."
    --#STATE           DEGRADED
    ::= 10506

-- EVT_CACHE_FLUSHED

svrTrapCacheFlushed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Data in cache flushed during power up."
    --#TYPE            "Data in cache flushed during power up"
    --#SUMMARY         "Adapter %s: Data in cache flushed during power up (Server %s)"
    --#ARGUMENTS       { 2, 0 }
    --#SEVERITY        INFORMATIONAL
    --#TIMEINDEX       1
    --#HELP            ""
    --#STATE           OPERATIONAL
    ::= 10507

-- EVT_CACHE_NOT_FLUSHED

svrTrapCacheNotFlushed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Data in cache not flushed during power up."
    --#TYPE            "Data in cache not flushed during power up"
    --#SUMMARY         "Adapter %s: Data in cache not flushed during power up (Server %s)"
    --#ARGUMENTS       { 2, 0 }
    --#SEVERITY        MAJOR
    --#TIMEINDEX       1
    --#HELP            "If the problem occurs repeatedly call your local Fujitsu Helpdesk."
    --#STATE           OPERATIONAL
    ::= 10508

-- EVT_REBUILD_RESUMED

svrTrapRebuildResumed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild resumed on disk."
    --#TYPE            "Rebuild resumed on disk"
    --#SUMMARY         "Adapter %s: Rebuild resumed on disk (%s) (Server %s)"
    --#ARGUMENTS       { 2, 3, 0 }
    --#SEVERITY        INFORMATIONAL
    --#TIMEINDEX       1
    --#HELP            ""
    --#STATE           OPERATIONAL
    ::= 10509

-- EVT_AUTO_REBUILD_STARTED

svrTrapAutoRebuildStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic rebuild started on logical drive."
    --#TYPE            "Automatic rebuild started on logical drive"
    --#SUMMARY         "Adapter %s: Automatic rebuild started on logical drive %s (Server %s)"
    --#ARGUMENTS       { 2, 3, 0 }
    --#SEVERITY        INFORMATIONAL
    --#TIMEINDEX       1
    --#HELP            ""
    --#STATE           OPERATIONAL
    ::= 10510

-- EVT_BGI_RESTARTED

svrTrapBGIRestarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI restarted on logical drive."
    --#TYPE            "BGI restarted on logical drive"
    --#SUMMARY         "Adapter %s: BGI restarted on logical drive %s (Server %s)"
    --#ARGUMENTS       { 2, 3, 0 }
    --#SEVERITY        INFORMATIONAL
    --#TIMEINDEX       1
    --#HELP            ""
    --#STATE           OPERATIONAL
    ::= 10511

-- EVT_LOGICALDRIVE_DISK_MEDIA_ERROR

svrTrapLDPDMediaError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive error on disk media."
    --#TYPE            "Logical drive error on disk media"
    --#SUMMARY         "Adapter %s: Logical drive %s: Error on disk %s %s (Server %s)"
    --#ARGUMENTS       { 2, 3, 4, 5, 0 }
    --#SEVERITY        MAJOR
    --#TIMEINDEX       1
    --#HELP            "Replace affected disk."
    --#STATE           OPERATIONAL
    ::= 10512

-- EVT_LD_REBUILD_RESUMED

svrTrapLDRebuildResumed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild on logical drive resumed."
    --#TYPE            "Rebuild on logical drive resumed"
    --#SUMMARY         "Adapter %s: Rebuild on logical drive %s resumed (Server %s)"
    --#ARGUMENTS       { 2, 3, 0 }
    --#SEVERITY        INFORMATIONAL
    --#TIMEINDEX       1
    --#HELP            ""
    --#STATE           OPERATIONAL
    ::= 10513

-- EVT_CHECK_ERROR_LBA

svrTrapLDConCheckFinishedWithLBAErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check finished with errors on logical drive."
    --#TYPE            "Consistency check finished with errors on logical drive"
    --#SUMMARY         "Adapter %s: Consistency check finished with errors on logical drive %s: %s (Server %s)"
    --#ARGUMENTS       { 2, 3, 4, 0 }
    --#SEVERITY        MAJOR
    --#TIMEINDEX       1
    --#HELP            "1) Manually initiate second consistency check (MDC). 2) If problem persists backup data from affected logical drive. 3) Delete and recreate affected logical drive. 4) Restore data."
    --#STATE           OPERATIONAL
    ::= 10514

-- EVT_CHECK_ERROR_LOG

svrTrapLDConCheckErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Error on logical drive detected."
    --#TYPE            "Error on logical drive detected"
    --#SUMMARY         "Adapter %s: Error on logical drive %s detected (Server %s)"
    --#ARGUMENTS       { 2, 3, 0 }
    --#SEVERITY        MAJOR
    --#TIMEINDEX       1
    --#HELP            "1) Check/replace cable between controller and affected disk. 2) If problem persists replace disk."
    --#STATE           OPERATIONAL
    ::= 10515

-- EVT_DISK_TEMPORARY_OFFLINE

svrTrapPDForcedFromFailedToOnline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk forced from failed to online."
    --#TYPE            "Disk forced from failed to online"
    --#SUMMARY         "Adapter %s: Disk (%s) forced from failed to online (Server %s)"
    --#ARGUMENTS       { 2, 3, 0 }
    --#SEVERITY        MAJOR
    --#TIMEINDEX       1
    --#HELP            "For information only."
    --#STATE           OPERATIONAL
    ::= 10516

-- EVT_TRANSFER_SPEED_CHANGED

svrTrapPDTransferSpeedValueChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Transfer speed of disk changed."
    --#TYPE            "Transfer speed of disk changed"
    --#SUMMARY         "Adapter %s: Transfer speed of disk (%s) changed (Server %s)"
    --#ARGUMENTS       { 2, 3, 0 }
    --#SEVERITY        MINOR
    --#TIMEINDEX       1
    --#HELP            "1) Check/replace cable between controller and affected disk. 2) If problem persists replace disk."
    --#STATE           OPERATIONAL
    ::= 10517

-- EVT_SAS_PORT_LINK_LOST

svrTrapSASPortLinkLost TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS port lost link."
    --#TYPE            "SAS port lost link"
    --#SUMMARY         "Adapter %s: SAS port %s lost link (Server %s)"
    --#ARGUMENTS       { 2, 3, 0 }
    --#SEVERITY        MAJOR
    --#TIMEINDEX       1
    --#HELP            "1) Unplug affected disk, wait 30 seconds, reinsert it. 2) Check/replace cable between controller and affected disk. 3) Check version of RAID controller/iRMC firmware, and BIOS. 4) Replace affected disk."
    --#STATE           OPERATIONAL
    ::= 10518

-- EVT_SAS_PORT_LINK_RESTORED

svrTrapSASPortLinkRestored TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS port restored link."
    --#TYPE            "SAS port restored link"
    --#SUMMARY         "Adapter %s: SAS port %s restored link (Server %s)"
    --#ARGUMENTS       { 2, 3, 0 }
    --#SEVERITY        INFORMATIONAL
    --#TIMEINDEX       1
    --#HELP            ""
    --#STATE           OPERATIONAL
    ::= 10519

-- EVT_CTRL_CACHE_MODE_BACK

svrTrapCacheModeChangedToWriteBack TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cache mode changed to Write-back."
    --#TYPE            "Cache mode changed to Write-back"
    --#SUMMARY         "Adapter %s: Cache mode changed to Write-back (Server %s)"
    --#ARGUMENTS       { 2, 0 }
    --#SEVERITY        INFORMATIONAL
    --#TIMEINDEX       1
    --#HELP            ""
    --#STATE           OPERATIONAL
    ::= 10520

-- EVT_CTRL_CACHE_MODE_WRITETHROUGH

svrTrapCacheModeChangedToWriteThrough TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cache mode changed to Write-through."
    --#TYPE            "Cache mode changed to Write-through"
    --#SUMMARY         "Adapter %s: Cache mode changed to Write-through (Server %s)"
    --#ARGUMENTS       { 2, 0 }
    --#SEVERITY        INFORMATIONAL
    --#TIMEINDEX       1
    --#HELP            ""
    --#STATE           OPERATIONAL
    ::= 10521

-- EVT_PD_SPARE_AFFINITY_IGNORED

svrTrapPDSpareAffinityIgnored TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Global affinity hot spare commissioned in a different enclosure."
    --#TYPE            "Global affinity hot spare commissioned in a different enclosure"
    --#SUMMARY         "Adapter %s: Global affinity hot spare (%s) commissioned in a different enclosure (Server %s)"
    --#ARGUMENTS       { 2, 3, 0 }
    --#SEVERITY        MINOR
    --#TIMEINDEX       1
    --#HELP            "Check your RAID configuration."
    --#STATE           OPERATIONAL
    ::= 10522

-- EVT_FOREIGN_CFG_TABLE_OVERFLOW

svrTrapForeignConfigTableOverflow TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Foreign configuration table overflow."
    --#TYPE            "Foreign configuration table overflow"
    --#SUMMARY         "Adapter %s: Foreign configuration table overflow (Server %s)"
    --#ARGUMENTS       { 2, 0 }
    --#SEVERITY        MINOR
    --#TIMEINDEX       1
    --#HELP            "Call your local Fujitsu Helpdesk."
    --#STATE           OPERATIONAL
    ::= 10523

-- EVT_FOREIGN_CFG_PARTIAL_IMPORT

svrTrapForeignConfigPartialImport TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Partial foreign configuration imported."
    --#TYPE            "Partial foreign configuration imported"
    --#SUMMARY         "Adapter %s: Partial foreign configuration imported, disks not imported (device numbers): %s (Server %s)"
    --#ARGUMENTS       { 2, 3, 0 }
    --#SEVERITY        MINOR
    --#TIMEINDEX       1
    --#HELP            "Note: Only parts of your config were imported. 1) Call your local Fujitsu Helpdesk."
    --#STATE           OPERATIONAL
    ::= 10524

-- EVT_SAS_MUX_ACTIVATED_CONNECTOR

svrTrapSASMuxActivatedConnector TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Connector is active."
    --#TYPE            "Connector is active"
    --#SUMMARY         "Adapter %s: Connector %s is active (Server %s)"
    --#ARGUMENTS       { 2, 3, 0 }
    --#SEVERITY        INFORMATIONAL
    --#TIMEINDEX       1
    --#HELP            ""
    --#STATE           OPERATIONAL
    ::= 10525

-- EVT_CTRL_MISSING_AFTER_REBOOT

svrTrapctrlmissingafterreboot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter missing after reboot."
    --#TYPE            "Adapter missing after reboot"
    --#SUMMARY         "Adapter %s: Adapter missing after reboot (Server %s)"
    --#ARGUMENTS       { 2, 0 }
    --#SEVERITY        CRITICAL
    --#TIMEINDEX       1
    --#HELP            "Note: Only informational if controller was removed by user otherwise: 1) Unplug affected controller, wait 30 seconds, reinsert it. 2) If problem persists replace affected controller. 3) If problem persists replace mainboard."
    --#STATE           OPERATIONAL
    ::= 10526

-- EVT_CTRL_APPEARED_AFTER_REBOOT

svrTrapctrlappearedafterreboot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter appeared new after reboot."
    --#TYPE            "Adapter appeared new after reboot"
    --#SUMMARY         "Adapter %s: Adapter appeared new after reboot (Server %s)"
    --#ARGUMENTS       { 2, 0 }
    --#SEVERITY        INFORMATIONAL
    --#TIMEINDEX       1
    --#HELP            ""
    --#STATE           OPERATIONAL
    ::= 10527

-- EVT_DISK_REBUILD_CANCELED

svrTrapPDRebuildAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild aborted on disk."
    --#TYPE            "Rebuild aborted on disk"
    --#SUMMARY         "Adapter %s: Rebuild aborted on disk (%s) (Server %s)"
    --#ARGUMENTS       { 2, 3, 0 }
    --#SEVERITY        MINOR
    --#TIMEINDEX       1
    --#HELP            "Note: Only informational if rebuild was aborted by user otherwise: 1) Initiate a rebuild again (e.g. via ServerView RAID Manager)."
    --#STATE           DEGRADED
    ::= 10528

-- EVT_CHECK_ERROR_CORRECTABLE

svrTrapCheckErrorCorrectable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check finished with correctable errors on logical drive."
    --#TYPE            "Consistency check finished with correctable errors on logical drive"
    --#SUMMARY         "Adapter %s: Consistency check finished with %s correctable errors on logical drive %s (Server %s)"
    --#ARGUMENTS       { 2, 4, 3, 0 }
    --#SEVERITY        MAJOR
    --#TIMEINDEX       1
    --#HELP            "1) Manually initiate second consistency check (MDC). 2) If problem persists backup data from affected logical drive. 3) Delete and recreate affected logical drive. 4) Restore data."
    --#STATE           OPERATIONAL
    ::= 10529

-- EVT_CHECK_ERROR_UNCORRECTABLE

svrTrapCheckErrorUnCorrectable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check finished with uncorrectable errors on logical drive."
    --#TYPE            "Consistency check finished with uncorrectable errors on logical drive"
    --#SUMMARY         "Adapter %s: Consistency check finished with %s uncorrectable errors on logical drive %s (Server %s)"
    --#ARGUMENTS       { 2, 4, 3, 0 }
    --#SEVERITY        MAJOR
    --#TIMEINDEX       1
    --#HELP            "1) Backup data from affected logical drive. 2) Delete and recreate affected logical drive. 3) Restore data."
    --#STATE           OPERATIONAL
    ::= 10530

-- EVT_MDC_ERROR_CORRECTABLE

svrTrapMDCErrorCorrectable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC finished with correctable errors on logical drive."
    --#TYPE            "MDC finished with correctable errors on logical drive"
    --#SUMMARY         "Adapter %s: MDC finished with %s correctable errors on logical drive %s (Server %s)"
    --#ARGUMENTS       { 2, 4, 3, 0 }
    --#SEVERITY        INFORMATIONAL
    --#TIMEINDEX       1
    --#HELP            ""
    --#STATE           OPERATIONAL
    ::= 10531

-- EVT_MDC_ERROR_UNCORRECTABLE

svrTrapMDCErrorUnCorrectable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC finished with uncorrectable errors on logical drive."
    --#TYPE            "MDC finished with uncorrectable errors on logical drive"
    --#SUMMARY         "Adapter %s: MDC finished with %s uncorrectable errors on logical drive %s (Server %s)"
    --#ARGUMENTS       { 2, 4, 3, 0 }
    --#SEVERITY        MAJOR
    --#TIMEINDEX       1
    --#HELP            "1) Backup data from affected logical drive. 2) Delete and recreate affected logical drive. 3) Restore data."
    --#STATE           OPERATIONAL
    ::= 10532

-- EVT_RESET_ERROR_COUNTERS

svrTrapResetErrorCounters TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Error counters reset on disk."
    --#TYPE            "Error counters reset on disk"
    --#SUMMARY         "Adapter %s: Error counters reset on disk (%s) (Server %s)"
    --#ARGUMENTS       { 2, 3, 0 }
    --#SEVERITY        INFORMATIONAL
    --#TIMEINDEX       1
    --#HELP            ""
    --#STATE           OPERATIONAL
    ::= 10533

-- EVT_ADAPTER_PROPERTY_CHANGED

svrTrapAdapterPropertyChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Changed adapter property detected after reboot."
    --#TYPE            "Changed adapter property detected after reboot"
    --#SUMMARY         "Adapter %s: Changed adapter property detected after reboot (Server %s)"
    --#ARGUMENTS       { 2, 0 }
    --#SEVERITY        MINOR
    --#TIMEINDEX       1
    --#HELP            "Check your adapter properties (e.g. via ServerView RAID Manager)."
    --#STATE           OPERATIONAL
    ::= 10534

-- EVT_CTRL_FRU

svrTrapAdapterFRU TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Board revision."
    --#TYPE            "Board revision"
    --#SUMMARY         "Adapter %s: Board revision %s (Server %s)"
    --#ARGUMENTS       { 2, 3, 0 }
    --#SEVERITY        INFORMATIONAL
    --#TIMEINDEX       1
    --#HELP            ""
    --#STATE           OPERATIONAL
    ::= 10535

-- EVT_PD_COMMAND_TIMEOUT

svrTrapPDCommandTimeout TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Command timeout on disk."
    --#TYPE            "Command timeout on disk"
    --#SUMMARY         "Adapter %s: Command timeout on disk (%s), CDB:%s (Server %s)"
    --#ARGUMENTS       { 2, 3, 4, 0 }
    --#SEVERITY        MINOR
    --#TIMEINDEX       1
    --#HELP            "Note: Only if problem occurs repeatedly: 1) Check/replace cable between controller and affected disk. 2) If problem persists replace affected disk and/or backplane."
    --#STATE           OPERATIONAL
    ::= 10536

-- EVT_PD_RESET

svrTrapPDReset TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk reset."
    --#TYPE            "Disk reset"
    --#SUMMARY         "Adapter %s: Disk (%s) reset (type %s) (Server %s)"
    --#ARGUMENTS       { 2, 3, 4, 0 }
    --#SEVERITY        MINOR
    --#TIMEINDEX       1
    --#HELP            "Note: Only if problem occurs repeatedly: 1) Check/replace cable between controller and affected disk. 2) If problem persists replace affected disk."
    --#STATE           OPERATIONAL
    ::= 10537

-- EVT_LD_BBM_LOG_80_PERCENT_FULL

svrTrapLDLog80Full TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table on logical drive is 80 percent full."
    --#TYPE            "Bad block table on logical drive is 80 percent full"
    --#SUMMARY         "Adapter %s: Bad block table on logical drive %s is 80 percent full (Server %s)"
    --#ARGUMENTS       { 2, 3, 0 }
    --#SEVERITY        MINOR
    --#TIMEINDEX       1
    --#HELP            "Check for additional error messages for affected disk."
    --#STATE           OPERATIONAL
    ::= 10538

-- EVT_LD_BBM_LOG_FULL

svrTrapLDLogFull TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table on logical drive is full."
    --#TYPE            "Bad block table on logical drive is full"
    --#SUMMARY         "Adapter %s: Bad block table on logical drive %s is full; unable to log LBA %s (on disk (%s) at LBA %s) (Server %s)"
    --#ARGUMENTS       { 2, 3, 4, 5, 6, 0 }
    --#SEVERITY        MAJOR
    --#TIMEINDEX       1
    --#HELP            "Check for additional error messages for affected disk."
    --#STATE           OPERATIONAL
    ::= 10539

-- EVT_LD_LOG_MEDIUM_ERROR

svrTrapLDLogUncorrMediumError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Uncorrectable medium error logged for logical drive."
    --#TYPE            "Uncorrectable medium error logged for logical drive"
    --#SUMMARY         "Adapter %s: Uncorrectable medium error logged for logical drive %s at LBA %s (on disk (%s) at LBA %s) (Server %s)"
    --#ARGUMENTS       { 2, 3, 4, 5, 6, 0 }
    --#SEVERITY        MAJOR
    --#TIMEINDEX       1
    --#HELP            "Check for additional error messages for affected disk."
    --#STATE           OPERATIONAL
    ::= 10540

-- EVT_LD_CORRECTED_MEDIUM_ERROR

svrTrapLDMediumErrorCorr TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Medium error corrected on logical drive."
    --#TYPE            "Medium error corrected on logical drive"
    --#SUMMARY         "Adapter %s: Medium error corrected on logical drive %s at LBA %s (Server %s)"
    --#ARGUMENTS       { 2, 3, 4, 0 }
    --#SEVERITY        INFORMATIONAL
    --#TIMEINDEX       1
    --#HELP            "Check for additional error messages for affected disk."
    --#STATE           OPERATIONAL
    ::= 10541

-- EVT_PD_BBM_LOG_100_PERCENT_FULL

svrTrapPDBadBlockLog100Full TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table on disk is 100 percent full."
    --#TYPE            "Bad block table on disk is 100 percent full"
    --#SUMMARY         "Adapter %s: Bad block table on disk (%s) is 100 percent full (Server %s)"
    --#ARGUMENTS       { 2, 3, 0 }
    --#SEVERITY        MINOR
    --#TIMEINDEX       1
    --#HELP            "Replace affected disk."
    --#STATE           OPERATIONAL
    ::= 10542

-- EVT_LD_BBM_LOG_100_PERCENT_FULL

svrTrapLDBadBlockLog100Full TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table on logical drive is 100 percent full."
    --#TYPE            "Bad block table on logical drive is 100 percent full"
    --#SUMMARY         "Adapter %s: Bad block table on logical drive %s is 100 percent full (Server %s)"
    --#ARGUMENTS       { 2, 3, 0 }
    --#SEVERITY        MINOR
    --#TIMEINDEX       1
    --#HELP            "Check for additional error messages for affected disk."
    --#STATE           OPERATIONAL
    ::= 10543

-- EVT_DIAG_FAULTY_IOP_DETECTED

svrTrapDiagFaultyIOPDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter needs replacement, faulty IOP detected."
    --#TYPE            "Adapter needs replacement, faulty IOP detected"
    --#SUMMARY         "Adapter %s: Adapter needs replacement, faulty IOP detected (Server %s)"
    --#ARGUMENTS       { 2, 0 }
    --#SEVERITY        CRITICAL
    --#TIMEINDEX       1
    --#HELP            "1) Replace affected RAID controller."
    --#STATE           NONOPERATIONAL
    ::= 10544

-- EVT_PD_COPYBACK_START

svrTrapPDCopyBackStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback started on disk from disk."
    --#TYPE            "Copyback started on disk from disk"
    --#SUMMARY         "Adapter %s: Copyback started on disk (%s) from disk (%s) (Server %s)"
    --#ARGUMENTS       { 2, 3, 4, 0 }
    --#SEVERITY        INFORMATIONAL
    --#TIMEINDEX       1
    --#HELP            ""
    --#STATE           OPERATIONAL
    ::= 10545

-- EVT_PD_COPYBACK_ABORT

svrTrapPDCopyBackAbort TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback aborted on disk from disk."
    --#TYPE            "Copyback aborted on disk from disk"
    --#SUMMARY         "Adapter %s: Copyback aborted on disk (%s) from disk (%s) (Server %s)"
    --#ARGUMENTS       { 2, 3, 4, 0 }
    --#SEVERITY        INFORMATIONAL
    --#TIMEINDEX       1
    --#HELP            ""
    --#STATE           OPERATIONAL
    ::= 10546

-- EVT_PD_COPYBACK_DONE

svrTrapPDCopyBackDone TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback complete on disk from disk."
    --#TYPE            "Copyback complete on disk from disk"
    --#SUMMARY         "Adapter %s: Copyback complete on disk (%s) from disk (%s) (Server %s)"
    --#ARGUMENTS       { 2, 3, 4, 0 }
    --#SEVERITY        INFORMATIONAL
    --#TIMEINDEX       1
    --#HELP            ""
    --#STATE           OPERATIONAL
    ::= 10547

-- EVT_PD_COPYBACK_PROGRESS

svrTrapPDCopyBackProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback progress."
    --#TYPE            "Copyback progress"
    --#SUMMARY         "Adapter %s: Copyback progress on disk (%s) is %s (Server %s)"
    --#ARGUMENTS       { 2, 3, 4, 0 }
    --#SEVERITY        INFORMATIONAL
    --#TIMEINDEX       1
    --#HELP            ""
    --#STATE           OPERATIONAL
    ::= 10548

-- EVT_PD_COPYBACK_RESUME

svrTrapPDCopyBackResume TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback resumed on disk."
    --#TYPE            "Copyback resumed on disk"
    --#SUMMARY         "Adapter %s: Copyback resumed on disk (%s) (Server %s)"
    --#ARGUMENTS       { 2, 3, 0 }
    --#SEVERITY        INFORMATIONAL
    --#TIMEINDEX       1
    --#HELP            ""
    --#STATE           OPERATIONAL
    ::= 10549

-- EVT_PD_COPYBACK_AUTO

svrTrapPDCopyBackAuto TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback automatically started on disk."
    --#TYPE            "Copyback automatically started on disk"
    --#SUMMARY         "Adapter %s: Copyback automatically started on disk (%s) (Server %s)"
    --#ARGUMENTS       { 2, 3, 0 }
    --#SEVERITY        INFORMATIONAL
    --#TIMEINDEX       1
    --#HELP            ""
    --#STATE           OPERATIONAL
    ::= 10550

-- EVT_PD_COPYBACK_FAILED

svrTrapPDCopyBackFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback failed on disk."
    --#TYPE            "Copyback failed on disk"
    --#SUMMARY         "Adapter %s: Copyback failed on disk (%s) (Server %s)"
    --#ARGUMENTS       { 2, 3, 0 }
    --#SEVERITY        MAJOR
    --#TIMEINDEX       1
    --#HELP            "Check for additional error messages for affected disk."
    --#STATE           OPERATIONAL
    ::= 10551

-- EVT_CTRL_EPOW_UNSUCCESSFUL

svrTrapCtrlEpowUnsuccessful TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Early power off warning was unsuccessful."
    --#TYPE            "Early power off warning was unsuccessful"
    --#SUMMARY         "Adapter %s: Early power off warning was unsuccessful (Server %s)"
    --#ARGUMENTS       { 2, 0 }
    --#SEVERITY        MINOR
    --#TIMEINDEX       1
    --#HELP            "Call your local Fujitsu Helpdesk."
    --#STATE           OPERATIONAL
    ::= 10552

-- EVT_BBU_FRU

svrTrapBBUFRU TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU FRU."
    --#TYPE            "BBU FRU"
    --#SUMMARY         "Adapter %s: BBU FRU is %s (Server %s)"
    --#ARGUMENTS       { 2, 3, 0 }
    --#SEVERITY        INFORMATIONAL
    --#TIMEINDEX       1
    --#HELP            ""
    --#STATE           OPERATIONAL
    ::= 10553

-- EVT_PD_FRU

svrTrapPDFRU TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk FRU."
    --#TYPE            "Disk FRU"
    --#SUMMARY         "Adapter %s: Disk (%s) FRU is %s (Server %s)"
    --#ARGUMENTS       { 2, 3, 4, 0 }
    --#SEVERITY        INFORMATIONAL
    --#TIMEINDEX       1
    --#HELP            ""
    --#STATE           OPERATIONAL
    ::= 10554

-- EVT_CTRL_HW_REVISION

svrTrapCtrlHWRevision TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter hardware revision ID."
    --#TYPE            "Adapter hardware revision ID"
    --#SUMMARY         "Adapter %s: Adapter hardware revision ID %s (Server %s)"
    --#ARGUMENTS       { 2, 3, 0 }
    --#SEVERITY        INFORMATIONAL
    --#TIMEINDEX       1
    --#HELP            ""
    --#STATE           OPERATIONAL
    ::= 10555

-- EVT_FOREIGN_CFG_UPGRADE_REQUIRED

svrTrapForeignCfgUpgradeRequired TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Foreign configuration metadata needs to be upgraded."
    --#TYPE            "Foreign configuration metadata needs to be upgraded"
    --#SUMMARY         "Adapter %s: Foreign configuration metadata needs to be upgraded, may become incompatible (Server %s)"
    --#ARGUMENTS       { 2, 0 }
    --#SEVERITY        MINOR
    --#TIMEINDEX       1
    --#HELP            "For information only."
    --#STATE           OPERATIONAL
    ::= 10556

-- EVT_CONT_ON_ERROR_ENABLED

svrTrapAdapterContOnErrorEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BIOS continue on error enabled."
    --#TYPE            "BIOS continue on error enabled"
    --#SUMMARY         "Adapter %s: BIOS continue on error enabled (Server %s)"
    --#ARGUMENTS       { 2, 0 }
    --#SEVERITY        INFORMATIONAL
    --#TIMEINDEX       1
    --#HELP            ""
    --#STATE           OPERATIONAL
    ::= 10557

-- EVT_CONT_ON_ERROR_DISABLED

svrTrapAdapterContOnErrorDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BIOS continue on error disabled."
    --#TYPE            "BIOS continue on error disabled"
    --#SUMMARY         "Adapter %s: BIOS continue on error disabled (Server %s)"
    --#ARGUMENTS       { 2, 0 }
    --#SEVERITY        INFORMATIONAL
    --#TIMEINDEX       1
    --#HELP            ""
    --#STATE           OPERATIONAL
    ::= 10558

-- EVT_PD_FAIL_EX

svrTrapPDFailEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Additional information for failed disk."
    --#TYPE            "Additional information for failed disk"
    --#SUMMARY         "Adapter %s: Additional information for failed disk (%s) - firmware version: %s, serial number %s, first use: %s, total running time: %s days (Server %s)"
    --#ARGUMENTS       { 2, 3, 4, 5, 6, 7, 0 }
    --#SEVERITY        INFORMATIONAL
    --#TIMEINDEX       1
    --#HELP            ""
    --#STATE           NONOPERATIONAL
    ::= 10559

-- EVT_MIGRATION_FINISHED_EX

svrTrapMigrationFinishedEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reread disk information."
    --#TYPE            "Reread disk information"
    --#SUMMARY         "Adapter %s: If the logical size of logical drive %s has changed use appropriate operating system tool to reread disk information (Server %s)"
    --#ARGUMENTS       { 2, 3, 0 }
    --#SEVERITY        INFORMATIONAL
    --#TIMEINDEX       1
    --#HELP            ""
    --#STATE           OPERATIONAL
    ::= 10560

-- EVT_ENCL_DEVICES_EXPOSURE_CHANGED

svrTrapEnclDevicesExposureChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure device exposure changed."
    --#TYPE            "Enclosure device exposure changed"
    --#SUMMARY         "Adapter %s: Enclosure device exposure changed (Server %s)"
    --#ARGUMENTS       { 2, 0 }
    --#SEVERITY        INFORMATIONAL
    --#TIMEINDEX       1
    --#HELP            ""
    --#STATE           OPERATIONAL
    ::= 10561

-- EVT_CC_ABORT_ON_ERROR_CHANGED

svrTrapCCAbortOnErrorChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Abort consistency check on error changed."
    --#TYPE            "Abort consistency check on error changed"
    --#SUMMARY         "Adapter %s: Abort consistency check on error changed (Server %s)"
    --#ARGUMENTS       { 2, 0 }
    --#SEVERITY        INFORMATIONAL
    --#TIMEINDEX       1
    --#HELP            ""
    --#STATE           OPERATIONAL
    ::= 10562

-- EVT_MDC_ABORT_ON_ERROR_CHANGED

svrTrapMDCAbortOnErrorChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Abort MDC on error changed."
    --#TYPE            "Abort MDC on error changed"
    --#SUMMARY         "Adapter %s: Abort MDC on error changed (Server %s)"
    --#ARGUMENTS       { 2, 0 }
    --#SEVERITY        INFORMATIONAL
    --#TIMEINDEX       1
    --#HELP            ""
    --#STATE           OPERATIONAL
    ::= 10563

-- EVT_PD_SAS_REDUNDANT_PATH_RESTORED

svrTrapPDSASRedundantPathRestored TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundant path restored."
    --#TYPE            "Redundant path restored"
    --#SUMMARY         "Adapter %s: Redundant path restored for disk (%s) (Server %s)"
    --#ARGUMENTS       { 2, 3, 0 }
    --#SEVERITY        INFORMATIONAL
    --#TIMEINDEX       1
    --#HELP            ""
    --#STATE           OPERATIONAL
    ::= 10564

-- EVT_PD_SAS_REDUNDANT_PATH_BROKEN

svrTrapPDSASRedundantPathBroken TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundant path broken."
    --#TYPE            "Redundant path broken"
    --#SUMMARY         "Adapter %s: Redundant path broken for disk (%s) (Server %s)"
    --#ARGUMENTS       { 2, 3, 0 }
    --#SEVERITY        MINOR
    --#TIMEINDEX       1
    --#HELP            "Call your local Fujitsu Helpdesk."
    --#STATE           OPERATIONAL
    ::= 10565

-- EVT_ENCL_REDUNDANT_ENCL_MODULE_INSERTED

svrTrapEnclRedundantEnclModuleInserted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundant enclosure inserted."
    --#TYPE            "Redundant enclosure inserted"
    --#SUMMARY         "Adapter %s: Redundant enclosure I/O module %s inserted for I/O module %s (Server %s)"
    --#ARGUMENTS       { 2, 3, 4, 0 }
    --#SEVERITY        INFORMATIONAL
    --#TIMEINDEX       1
    --#HELP            ""
    --#STATE           OPERATIONAL
    ::= 10566

-- EVT_ENCL_REDUNDANT_ENCL_MODULE_REMOVED

svrTrapEnclRedundantEnclModuleRemoved TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundant enclosure removed."
    --#TYPE            "Redundant enclosure removed"
    --#SUMMARY         "Adapter %s: Redundant enclosure I/O module %s removed for I/O module %s (Server %s)"
    --#ARGUMENTS       { 2, 3, 4, 0 }
    --#SEVERITY        MINOR
    --#TIMEINDEX       1
    --#HELP            "Call your local Fujitsu Helpdesk."
    --#STATE           OPERATIONAL
    ::= 10567

-- EVT_CTRL_PR_CANT_START

svrTrapCtrlPRCantStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read can't be started."
    --#TYPE            "Patrol Read can't be started"
    --#SUMMARY         "Adapter %s: Patrol Read can't be started, all disks are either not online, or are in a logical drive with an active process, or are in an excluded logical drive (Server %s)"
    --#ARGUMENTS       { 2, 0 }
    --#SEVERITY        MINOR
    --#TIMEINDEX       1
    --#HELP            "For information only."
    --#STATE           OPERATIONAL
    ::= 10568

-- EVT_PD_COPYBACK_ABORT_BY_USER

svrTrapPDCopyBackAbortByUser TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback aborted by user."
    --#TYPE            "Copyback aborted by user"
    --#SUMMARY         "Adapter %s: Copyback aborted by user on disk (%s) from disk (%s) (Server %s)"
    --#ARGUMENTS       { 2, 3, 4, 0 }
    --#SEVERITY        INFORMATIONAL
    --#TIMEINDEX       1
    --#HELP            ""
    --#STATE           OPERATIONAL
    ::= 10569

-- EVT_PD_COPYBACK_ABORT_FOR_SPARE

svrTrapPDCopyBackAbortForSpare TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback aborted on hot spare."
    --#TYPE            "Copyback aborted on hot spare"
    --#SUMMARY         "Adapter %s: Copyback aborted on hot spare (%s) from disk (%s) as hot spare needed for rebuild (Server %s)"
    --#ARGUMENTS       { 2, 3, 4, 0 }
    --#SEVERITY        MAJOR
    --#TIMEINDEX       1
    --#HELP            "Call your local Fujitsu Helpdesk."
    --#STATE           OPERATIONAL
    ::= 10570

-- EVT_PD_COPYBACK_ABORT_FOR_REBUILD

svrTrapPDCopyBackAbortForRebuild TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback aborted for rebuild."
    --#TYPE            "Copyback aborted for rebuild"
    --#SUMMARY         "Adapter %s: Copyback aborted on disk (%s) from disk (%s) as rebuild required in the array (Server %s)"
    --#ARGUMENTS       { 2, 3, 4, 0 }
    --#SEVERITY        MINOR
    --#TIMEINDEX       1
    --#HELP            "Call your local Fujitsu Helpdesk."
    --#STATE           OPERATIONAL
    ::= 10571

-- EVT_LD_CACHE_DISCARDED

svrTrapCDCacheDiscarded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cache discarded for logical drive (missing or offline)."
    --#TYPE            "Cache discarded for logical drive (missing or offline)"
    --#SUMMARY         "Adapter %s: Cache discarded for logical drive (missing or offline) %s (Server %s)"
    --#ARGUMENTS       { 2, 3, 0 }
    --#SEVERITY        MAJOR
    --#TIMEINDEX       1
    --#HELP            "For information only."
    --#STATE           OPERATIONAL
    ::= 10572

-- EVT_REDUNDANT_COPY_STARTED

svrTrapRedundantCopyStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundancy building started on disk."
    --#TYPE            "Redundancy building started on disk"
    --#SUMMARY         "Adapter %s: Redundancy building started on disk (%s) (Server %s)"
    --#ARGUMENTS       { 2, 3, 0 }
    --#SEVERITY        INFORMATIONAL
    --#TIMEINDEX       1
    --#HELP            ""
    --#STATE           OPERATIONAL
    ::= 10573

-- EVT_REDUNDANT_COPY_FINISHED

svrTrapRedundantCopyFinished TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundancy building finished on disk."
    --#TYPE            "Redundancy building finished on disk"
    --#SUMMARY         "Adapter %s: Redundancy building finished on disk (%s) (Server %s)"
    --#ARGUMENTS       { 2, 3, 0 }
    --#SEVERITY        INFORMATIONAL
    --#TIMEINDEX       1
    --#HELP            ""
    --#STATE           OPERATIONAL
    ::= 10574

-- EVT_REDUNDANT_COPY_FAILED

svrTrapRedundantCopyFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundancy building failed on disk."
    --#TYPE            "Redundancy building failed on disk"
    --#SUMMARY         "Adapter %s: Redundancy building failed on disk (%s) (Server %s)"
    --#ARGUMENTS       { 2, 3, 0 }
    --#SEVERITY        MAJOR
    --#TIMEINDEX       1
    --#HELP            "Call your local Fujitsu Helpdesk."
    --#STATE           OPERATIONAL
    ::= 10575

-- EVT_REDUNDANT_COPY_CANCELED

svrTrapRedundantCopyAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundancy building aborted on disk."
    --#TYPE            "Redundancy building aborted on disk"
    --#SUMMARY         "Adapter %s: Redundancy building aborted on disk (%s) (Server %s)"
    --#ARGUMENTS       { 2, 3, 0 }
    --#SEVERITY        MINOR
    --#TIMEINDEX       1
    --#HELP            "Call your local Fujitsu Helpdesk."
    --#STATE           OPERATIONAL
    ::= 10576

-- EVT_REDUNDANT_COPY_PAUSED

svrTrapRedundantCopyPaused TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundancy building suspended on disk."
    --#TYPE            "Redundancy building suspended on disk"
    --#SUMMARY         "Adapter %s: Redundancy building suspended on disk (%s) (Server %s)"
    --#ARGUMENTS       { 2, 3, 0 }
    --#SEVERITY        INFORMATIONAL
    --#TIMEINDEX       1
    --#HELP            ""
    --#STATE           OPERATIONAL
    ::= 10577

-- EVT_IDLE_MODE_ENABLED

svrTrapIdleModeEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk power management idle mode enabled."
    --#TYPE            "Disk power management idle mode enabled"
    --#SUMMARY         "Adapter %s: Disk (%s) power management idle mode enabled (Server %s)"
    --#ARGUMENTS       { 2, 3, 0 }
    --#SEVERITY        INFORMATIONAL
    --#TIMEINDEX       1
    --#HELP            ""
    --#STATE           OPERATIONAL
    ::= 10578

-- EVT_IDLE_MODE_DISABLED

svrTrapIdleModeDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk power management idle mode disabled."
    --#TYPE            "Disk power management idle mode disabled"
    --#SUMMARY         "Adapter %s: Disk (%s) power management idle mode disabled (Server %s)"
    --#ARGUMENTS       { 2, 3, 0 }
    --#SEVERITY        INFORMATIONAL
    --#TIMEINDEX       1
    --#HELP            ""
    --#STATE           OPERATIONAL
    ::= 10579

-- EVT_IDLE_TIMER_CHANGED

svrTrapIdleConditionTimerChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk power management idle condition timer changed."
    --#TYPE            "Disk power management idle condition timer changed"
    --#SUMMARY         "Adapter %s: Disk (%s) power management idle condition timer changed (Server %s)"
    --#ARGUMENTS       { 2, 3, 0 }
    --#SEVERITY        INFORMATIONAL
    --#TIMEINDEX       1
    --#HELP            ""
    --#STATE           OPERATIONAL
    ::= 10580

-- EVT_STANDBY_MODE_ENABLED

svrTrapStandbyModeEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk power management standby mode enabled."
    --#TYPE            "Disk power management standby mode enabled"
    --#SUMMARY         "Adapter %s: Disk (%s) power management standby mode enabled (Server %s)"
    --#ARGUMENTS       { 2, 3, 0 }
    --#SEVERITY        INFORMATIONAL
    --#TIMEINDEX       1
    --#HELP            ""
    --#STATE           OPERATIONAL
    ::= 10581

-- EVT_STANDBY_MODE_DISABLED

svrTrapStandbyModeDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk power management standby mode disabled."
    --#TYPE            "Disk power management standby mode disabled"
    --#SUMMARY         "Adapter %s: Disk (%s) power management standby mode disabled (Server %s)"
    --#ARGUMENTS       { 2, 3, 0 }
    --#SEVERITY        INFORMATIONAL
    --#TIMEINDEX       1
    --#HELP            ""
    --#STATE           OPERATIONAL
    ::= 10582

-- EVT_STANDBY_TIMER_CHANGED

svrTrapStandbyTimerChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk power management standby condition timer changed."
    --#TYPE            "Disk power management standby condition timer changed"
    --#SUMMARY         "Adapter %s: Disk (%s) power management standby condition timer changed (Server %s)"
    --#ARGUMENTS       { 2, 3, 0 }
    --#SEVERITY        INFORMATIONAL
    --#TIMEINDEX       1
    --#HELP            ""
    --#STATE           OPERATIONAL
    ::= 10583

-- EVT_PD_TOO_SMALL_FOR_COPYBACK

svrTrapPDTooSmallForCopyBack TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback cannot be started as disk is too small for disk."
    --#TYPE            "Copyback cannot be started as disk is too small for disk"
    --#SUMMARY         "Adapter %s: Copyback cannot be started as disk (%s) is too small for disk (%s) (Server %s)"
    --#ARGUMENTS       { 2, 3, 4, 0 }
    --#SEVERITY        INFORMATIONAL
    --#TIMEINDEX       1
    --#HELP            ""
    --#STATE           OPERATIONAL
    ::= 10584

-- EVT_PD_NO_COPYBACK_SAS_SATA_MIX_NOT_ALLOWED_IN_LD

svrTrapPDNoCopyBackSASSATAMixNotAllowedInLD TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback cannot be started on disk from disk as SAS/SATA mixing is not supported in an array."
    --#TYPE            "Copyback cannot be started on disk from disk as SAS/SATA mixing is not supported in an array"
    --#SUMMARY         "Adapter %s: Copyback cannot be started on disk (%s) from disk (%s) as SAS/SATA mixing is not supported in an array (Server %s)"
    --#ARGUMENTS       { 2, 3, 4, 0 }
    --#SEVERITY        INFORMATIONAL
    --#TIMEINDEX       1
    --#HELP            ""
    --#STATE           OPERATIONAL
    ::= 10585

-- EVT_PD_FW_DOWNLOAD_START

svrTrapPDFWDownloadStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware update started on disk."
    --#TYPE            "Firmware update started on disk"
    --#SUMMARY         "Adapter %s: Firmware update started on disk (%s) (Server %s)"
    --#ARGUMENTS       { 2, 3, 0 }
    --#SEVERITY        INFORMATIONAL
    --#TIMEINDEX       1
    --#HELP            ""
    --#STATE           OPERATIONAL
    ::= 10586

-- EVT_PD_FW_DOWNLOAD_COMPLETE

svrTrapPDFWDownloadComplete TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware update completed on disk."
    --#TYPE            "Firmware update completed on disk"
    --#SUMMARY         "Adapter %s: Firmware update completed on disk (%s) (Server %s)"
    --#ARGUMENTS       { 2, 3, 0 }
    --#SEVERITY        INFORMATIONAL
    --#TIMEINDEX       1
    --#HELP            ""
    --#STATE           OPERATIONAL
    ::= 10587

-- EVT_PD_FW_DOWNLOAD_TIMEOUT

svrTrapPDFWDownloadTimeout TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware update timeout on disk."
    --#TYPE            "Firmware update timeout on disk"
    --#SUMMARY         "Adapter %s: Firmware update timeout on disk (%s) (Server %s)"
    --#ARGUMENTS       { 2, 3, 0 }
    --#SEVERITY        MINOR
    --#TIMEINDEX       1
    --#HELP            "Call your local Fujitsu Helpdesk."
    --#STATE           OPERATIONAL
    ::= 10588

-- EVT_PD_FW_DOWNLOAD_FAILED

svrTrapPDFWDownloadFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware update failed on disk."
    --#TYPE            "Firmware update failed on disk"
    --#SUMMARY         "Adapter %s: Firmware update failed on disk (%s) (Server %s)"
    --#ARGUMENTS       { 2, 3, 0 }
    --#SEVERITY        MINOR
    --#TIMEINDEX       1
    --#HELP            "Call your local Fujitsu Helpdesk."
    --#STATE           OPERATIONAL
    ::= 10589

-- EVT_CTRL_PROP_CHANGED

svrTrapCtrlPropChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter properties changed."
    --#TYPE            "Adapter properties changed"
    --#SUMMARY         "Adapter %s: Adapter properties changed (Server %s)"
    --#ARGUMENTS       { 2, 0 }
    --#SEVERITY        INFORMATIONAL
    --#TIMEINDEX       1
    --#HELP            ""
    --#STATE           OPERATIONAL
    ::= 10590

-- EVT_CTRL_PR_PROP_CHANGED

svrTrapCtrlPRPropChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read properties changed."
    --#TYPE            "Patrol Read properties changed"
    --#SUMMARY         "Adapter %s: Patrol Read properties changed (Server %s)"
    --#ARGUMENTS       { 2, 0 }
    --#SEVERITY        INFORMATIONAL
    --#TIMEINDEX       1
    --#HELP            ""
    --#STATE           OPERATIONAL
    ::= 10591

-- EVT_CTRL_CC_SCHEDULE_PROP_CHANGED

svrTrapCtrlCCSchedulePropChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC schedule properties changed."
    --#TYPE            "MDC schedule properties changed"
    --#SUMMARY         "Adapter %s: MDC schedule properties changed (Server %s)"
    --#ARGUMENTS       { 2, 0 }
    --#SEVERITY        INFORMATIONAL
    --#TIMEINDEX       1
    --#HELP            ""
    --#STATE           OPERATIONAL
    ::= 10592

-- EVT_BBU_PROP_CHANGED

svrTrapCtrlBBUPropChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU properties changed."
    --#TYPE            "BBU properties changed"
    --#SUMMARY         "Adapter %s: BBU properties changed (Server %s)"
    --#ARGUMENTS       { 2, 0 }
    --#SEVERITY        INFORMATIONAL
    --#TIMEINDEX       1
    --#HELP            ""
    --#STATE           OPERATIONAL
    ::= 10593

-- EVT_MDC_RESUMED

svrTrapMDCContinuedOnLogicalDrive TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC resumed on logical drive."
    --#TYPE            "MDC resumed on logical drive"
    --#SUMMARY         "Adapter %s: MDC resumed on logical drive %s (Server %s)"
    --#ARGUMENTS       { 2, 3, 0 }
    --#SEVERITY        INFORMATIONAL
    --#TIMEINDEX       1
    --#HELP            ""
    --#STATE           OPERATIONAL
    ::= 10594

-- EVT_CTRL_SPINDOWN_MODE_ENABLED

svrTrapCtrlSpindownModeEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Spindown mode enabled."
    --#TYPE            "Spindown mode enabled"
    --#SUMMARY         "Adapter %s: Spindown mode enabled (Server %s)"
    --#ARGUMENTS       { 2, 0 }
    --#SEVERITY        INFORMATIONAL
    --#TIMEINDEX       1
    --#HELP            ""
    --#STATE           OPERATIONAL
    ::= 10595

-- EVT_CTRL_SPINDOWN_MODE_DISABLED

svrTrapCtrlSpindownModeDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Spindown mode disabled."
    --#TYPE            "Spindown mode disabled"
    --#SUMMARY         "Adapter %s: Spindown mode disabled (Server %s)"
    --#ARGUMENTS       { 2, 0 }
    --#SEVERITY        INFORMATIONAL
    --#TIMEINDEX       1
    --#HELP            ""
    --#STATE           OPERATIONAL
    ::= 10596

-- EVT_CTRL_SPINDOWN_DELAY_CHANGED

svrTrapCtrlSpindownDelayChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Spindown delay changed."
    --#TYPE            "Spindown delay changed"
    --#SUMMARY         "Adapter %s: Spindown delay changed to %s seconds (Server %s)"
    --#ARGUMENTS       { 2, 3, 0 }
    --#SEVERITY        INFORMATIONAL
    --#TIMEINDEX       1
    --#HELP            ""
    --#STATE           OPERATIONAL
    ::= 10597

-- EVT_CTRL_SPINUP_DELAY_CHANGED

svrTrapCtrlSpinupDelayChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Spinup delay changed."
    --#TYPE            "Spinup delay changed"
    --#SUMMARY         "Adapter %s: Spinup delay changed to %s seconds (Server %s)"
    --#ARGUMENTS       { 2, 3, 0 }
    --#SEVERITY        INFORMATIONAL
    --#TIMEINDEX       1
    --#HELP            ""
    --#STATE           OPERATIONAL
    ::= 10598

-- EVT_REDUNDANT_COPY_RATE_CHANGED_EX

svrTrapAdapterRedundantCopyRateChangedEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundancy build rate changed."
    --#TYPE            "Redundancy build rate changed"
    --#SUMMARY         "Adapter %s: Redundancy build rate changed to %s percent (Server %s)"
    --#ARGUMENTS       { 2, 3, 0 }
    --#SEVERITY        INFORMATIONAL
    --#TIMEINDEX       1
    --#HELP            ""
    --#STATE           OPERATIONAL
    ::= 10599

-- EVT_COPY_BACK_RATE_CHANGED_EX

svrTrapAdapterCopybackRateChangedEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback rate changed."
    --#TYPE            "Copyback rate changed"
    --#SUMMARY         "Adapter %s: Copyback rate changed to %s percent (Server %s)"
    --#ARGUMENTS       { 2, 3, 0 }
    --#SEVERITY        INFORMATIONAL
    --#TIMEINDEX       1
    --#HELP            ""
    --#STATE           OPERATIONAL
    ::= 10600

-- EVT_BBU_PERIODIC_RELEARN_PENDING

svrTrapBBUPeriodicRelearnPending TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Periodic BBU relearn is pending."
    --#TYPE            "Periodic BBU relearn is pending"
    --#SUMMARY         "Adapter %s: Periodic BBU relearn is pending. Please initiate manual learn cycle as automatic learn is not enabled (Server %s)"
    --#ARGUMENTS       { 2, 0 }
    --#SEVERITY        MINOR
    --#TIMEINDEX       1
    --#HELP            "Initiate manual learn cycle as automatic learn is not enabled."
    --#STATE           OPERATIONAL
    ::= 10601

-- EVT_CTRL_LOCK_KEY_CREATED

svrTrapCtrlLockKeyCreated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key created."
    --#TYPE            "Disk security key created"
    --#SUMMARY         "Adapter %s: Disk security key created (Server %s)"
    --#ARGUMENTS       { 2, 0 }
    --#SEVERITY        INFORMATIONAL
    --#TIMEINDEX       1
    --#HELP            ""
    --#STATE           OPERATIONAL
    ::= 10602

-- EVT_CTRL_LOCK_KEY_BACKEDUP

svrTrapCtrlLockKeyBackedup TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key backed up."
    --#TYPE            "Disk security key backed up"
    --#SUMMARY         "Adapter %s: Disk security key backed up (Server %s)"
    --#ARGUMENTS       { 2, 0 }
    --#SEVERITY        INFORMATIONAL
    --#TIMEINDEX       1
    --#HELP            ""
    --#STATE           OPERATIONAL
    ::= 10603

-- EVT_CTRL_LOCK_KEY_VERIFIED_ESCROW

svrTrapCtrlLockKeyVerifiedEscrow TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key from escrow, verified."
    --#TYPE            "Disk security key from escrow, verified"
    --#SUMMARY         "Adapter %s: Disk security key from escrow, verified (Server %s)"
    --#ARGUMENTS       { 2, 0 }
    --#SEVERITY        INFORMATIONAL
    --#TIMEINDEX       1
    --#HELP            ""
    --#STATE           OPERATIONAL
    ::= 10604

-- EVT_CTRL_LOCK_KEY_REKEYED

svrTrapCtrlLockKeyRekeyed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key changed."
    --#TYPE            "Disk security key changed"
    --#SUMMARY         "Adapter %s: Disk security key changed (Server %s)"
    --#ARGUMENTS       { 2, 0 }
    --#SEVERITY        INFORMATIONAL
    --#TIMEINDEX       1
    --#HELP            ""
    --#STATE           OPERATIONAL
    ::= 10605

-- EVT_CTRL_LOCK_KEY_REKEY_FAILED

svrTrapCtrlLockKeyRekeyFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key, re-key operation failed."
    --#TYPE            "Disk security key, re-key operation failed"
    --#SUMMARY         "Adapter %s: Disk security key, re-key operation failed (Server %s)"
    --#ARGUMENTS       { 2, 0 }
    --#SEVERITY        MINOR
    --#TIMEINDEX       1
    --#HELP            "Call your local Fujitsu Helpdesk."
    --#STATE           OPERATIONAL
    ::= 10606

-- EVT_CTRL_LOCK_KEY_INVALID

svrTrapCtrlLockKeyInvalid TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key is invalid."
    --#TYPE            "Disk security key is invalid"
    --#SUMMARY         "Adapter %s: Disk security key is invalid (Server %s)"
    --#ARGUMENTS       { 2, 0 }
    --#SEVERITY        MINOR
    --#TIMEINDEX       1
    --#HELP            "Call your local Fujitsu Helpdesk."
    --#STATE           OPERATIONAL
    ::= 10607

-- EVT_CTRL_LOCK_KEY_DESTROYED

svrTrapCtrlLockKeyDestroyed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key destroyed."
    --#TYPE            "Disk security key destroyed"
    --#SUMMARY         "Adapter %s: Disk security key destroyed (Server %s)"
    --#ARGUMENTS       { 2, 0 }
    --#SEVERITY        INFORMATIONAL
    --#TIMEINDEX       1
    --#HELP            ""
    --#STATE           OPERATIONAL
    ::= 10608

-- EVT_CTRL_ESCROW_KEY_INVALID

svrTrapCtrlEscrowKeyInvalid TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key from escrow is invalid."
    --#TYPE            "Disk security key from escrow is invalid"
    --#SUMMARY         "Adapter %s: Disk security key from escrow is invalid (Server %s)"
    --#ARGUMENTS       { 2, 0 }
    --#SEVERITY        MINOR
    --#TIMEINDEX       1
    --#HELP            "Call your local Fujitsu Helpdesk."
    --#STATE           OPERATIONAL
    ::= 10609

-- EVT_LD_SECURED

svrTrapLDSecured TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is now secured."
    --#TYPE            "Logical drive is now secured"
    --#SUMMARY         "Adapter %s: Logical drive %s is now secured (Server %s)"
    --#ARGUMENTS       { 2, 3, 0 }
    --#SEVERITY        INFORMATIONAL
    --#TIMEINDEX       1
    --#HELP            ""
    --#STATE           OPERATIONAL
    ::= 10610

-- EVT_LD_PARTIALLY_SECURED

svrTrapLDPartiallySecured TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is partially secured."
    --#TYPE            "Logical drive is partially secured"
    --#SUMMARY         "Adapter %s: Logical drive %s is partially secured (Server %s)"
    --#ARGUMENTS       { 2, 3, 0 }
    --#SEVERITY        MINOR
    --#TIMEINDEX       1
    --#HELP            "For information only."
    --#STATE           OPERATIONAL
    ::= 10611

-- EVT_PD_SECURED

svrTrapPDSecured TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security activated."
    --#TYPE            "Disk security activated"
    --#SUMMARY         "Adapter %s: Disk (%s) security activated (Server %s)"
    --#ARGUMENTS       { 2, 3, 0 }
    --#SEVERITY        INFORMATIONAL
    --#TIMEINDEX       1
    --#HELP            ""
    --#STATE           OPERATIONAL
    ::= 10612

-- EVT_PD_UNSECURED

svrTrapPDUnsecured TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security disabled."
    --#TYPE            "Disk security disabled"
    --#SUMMARY         "Adapter %s: Disk (%s) security disabled (Server %s)"
    --#ARGUMENTS       { 2, 3, 0 }
    --#SEVERITY        INFORMATIONAL
    --#TIMEINDEX       1
    --#HELP            ""
    --#STATE           OPERATIONAL
    ::= 10613

-- EVT_PD_REPROVISIONED

svrTrapPDReprovisioned TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk is reprovisioned."
    --#TYPE            "Disk is reprovisioned"
    --#SUMMARY         "Adapter %s: Disk (%s) is reprovisioned (Server %s)"
    --#ARGUMENTS       { 2, 3, 0 }
    --#SEVERITY        INFORMATIONAL
    --#TIMEINDEX       1
    --#HELP            ""
    --#STATE           OPERATIONAL
    ::= 10614

-- EVT_PD_LOCK_KEY_REKEYED

svrTrapPDLockKeyRekeyed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key changed."
    --#TYPE            "Disk security key changed"
    --#SUMMARY         "Adapter %s: Disk (%s) security key changed (Server %s)"
    --#ARGUMENTS       { 2, 3, 0 }
    --#SEVERITY        INFORMATIONAL
    --#TIMEINDEX       1
    --#HELP            ""
    --#STATE           OPERATIONAL
    ::= 10615

-- EVT_PD_SECURITY_FAILURE

svrTrapPDSecurityFailure TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Security subsystem problems detected for disk."
    --#TYPE            "Security subsystem problems detected for disk"
    --#SUMMARY         "Adapter %s: Security subsystem problems detected for disk (%s) (Server %s)"
    --#ARGUMENTS       { 2, 3, 0 }
    --#SEVERITY        MAJOR
    --#TIMEINDEX       1
    --#HELP            "Call your local Fujitsu Helpdesk."
    --#STATE           OPERATIONAL
    ::= 10616

-- EVT_LD_CACHE_PINNED

svrTrapLDCachePinned TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter cache preserved for missing or offline logical drive."
    --#TYPE            "Adapter cache preserved for missing or offline logical drive"
    --#SUMMARY         "Adapter %s: Adapter cache preserved for missing or offline logical drive %s (Server %s)"
    --#ARGUMENTS       { 2, 3, 0 }
    --#SEVERITY        MAJOR
    --#TIMEINDEX       1
    --#HELP            "Check error messages for related logical drive and resolve problems."
    --#STATE           OPERATIONAL
    ::= 10617

-- EVT_CTRL_BOOT_LDS_CACHE_PINNED

svrTrapBootLDsCachePinned TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter cache preserved for missing or offline logical drives."
    --#TYPE            "Adapter cache preserved for missing or offline logical drives"
    --#SUMMARY         "Adapter %s: Adapter cache preserved for missing or offline logical drives (Server %s)"
    --#ARGUMENTS       { 2, 0 }
    --#SEVERITY        MAJOR
    --#TIMEINDEX       1
    --#HELP            "Check error messages for related logical drives and resolve problems."
    --#STATE           OPERATIONAL
    ::= 10618

-- EVT_CTRL_LDS_CACHE_DISCARDED_BY_USER

svrTrapLDsCacheDiscardedByUser TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter cache discarded by user for logical drives."
    --#TYPE            "Adapter cache discarded by user for logical drives"
    --#SUMMARY         "Adapter %s: Adapter cache discarded by user for logical drives (Server %s)"
    --#ARGUMENTS       { 2, 0 }
    --#SEVERITY        INFORMATIONAL
    --#TIMEINDEX       1
    --#HELP            ""
    --#STATE           OPERATIONAL
    ::= 10619

-- EVT_LD_CACHE_DESTAGED

svrTrapLDCacheDestaged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter cache destaged for logical drive."
    --#TYPE            "Adapter cache destaged for logical drive"
    --#SUMMARY         "Adapter %s: Adapter cache destaged for logical drive %s (Server %s)"
    --#ARGUMENTS       { 2, 3, 0 }
    --#SEVERITY        INFORMATIONAL
    --#TIMEINDEX       1
    --#HELP            ""
    --#STATE           OPERATIONAL
    ::= 10620

-- EVT_LD_CC_STARTED_ON_INCONSISTENT_LD

svrTrapLDCCStartedOnInconsistentLD TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC started on an inconsistent logical drive."
    --#TYPE            "MDC started on an inconsistent logical drive"
    --#SUMMARY         "Adapter %s: MDC started on an inconsistent logical drive %s (Server %s)"
    --#ARGUMENTS       { 2, 3, 0 }
    --#SEVERITY        MINOR
    --#TIMEINDEX       1
    --#HELP            "For information only."
    --#STATE           OPERATIONAL
    ::= 10621

-- EVT_CTRL_LOCK_KEY_FAILED

svrTrapCtrlLockKeyFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key failure, cannot access secured configuration."
    --#TYPE            "Disk security key failure, cannot access secured configuration"
    --#SUMMARY         "Adapter %s: Disk security key failure, cannot access secured configuration (Server %s)"
    --#ARGUMENTS       { 2, 0 }
    --#SEVERITY        MINOR
    --#TIMEINDEX       1
    --#HELP            "Call your local Fujitsu Helpdesk."
    --#STATE           OPERATIONAL
    ::= 10622

-- EVT_CTRL_SECRET_KEY_INVALID

svrTrapCtrlSecretKeyInvalid TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security pass phrase from user is invalid."
    --#TYPE            "Disk security pass phrase from user is invalid"
    --#SUMMARY         "Adapter %s: Disk security pass phrase from user is invalid (Server %s)"
    --#ARGUMENTS       { 2, 0 }
    --#SEVERITY        MINOR
    --#TIMEINDEX       1
    --#HELP            "Call your local Fujitsu Helpdesk."
    --#STATE           OPERATIONAL
    ::= 10623

-- EVT_CONFIGURATION_WRITTEN_TO_FILE

svrTrapConfigurationWrittenToFile TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Complete RAID configuration written to file on the server."
    --#TYPE            "Complete RAID configuration written to file on the server"
    --#SUMMARY         "Complete RAID configuration written to file '%s' on the server (Server %s)"
    --#ARGUMENTS       { 2, 0 }
    --#SEVERITY        INFORMATIONAL
    --#TIMEINDEX       1
    --#HELP            ""
    --#STATE           OPERATIONAL
    ::= 10624

-- EVT_ABNORMAL_SHUTDOWN

svrTrapAbnormalShutdown TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Abnormal shutdown sequence detected."
    --#TYPE            "Abnormal shutdown sequence detected"
    --#SUMMARY         "Adapter %s: Abnormal shutdown sequence detected (Server %s)"
    --#ARGUMENTS       { 2, 0 }
    --#SEVERITY        MINOR
    --#TIMEINDEX       1
    --#HELP            ""
    --#STATE           OPERATIONAL
    ::= 10625

-- EVT_CTLR_INTERNAL_HARD_ERROR

svrTrapCtlrInternalHardError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal hardware error."
    --#TYPE            "Internal hardware error"
    --#SUMMARY         "Adapter %s: Internal hardware error (Server %s)"
    --#ARGUMENTS       { 2, 0 }
    --#SEVERITY        MAJOR
    --#TIMEINDEX       1
    --#HELP            "Call your local Fujitsu Helpdesk."
    --#STATE           OPERATIONAL
    ::= 10626

-- EVT_CTLR_INTERNAL_HARD_ERROR_POST

svrTrapCtlrInternalHardErrorPOST TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal hardware error during POST."
    --#TYPE            "Internal hardware error during POST"
    --#SUMMARY         "Adapter %s: Internal hardware error during POST (Server %s)"
    --#ARGUMENTS       { 2, 0 }
    --#SEVERITY        MAJOR
    --#TIMEINDEX       1
    --#HELP            "Call your local Fujitsu Helpdesk."
    --#STATE           OPERATIONAL
    ::= 10627

-- EVT_PD_BBT_THRESHOLD_EXCEEDED

svrTrapPDBBTThresholdExceeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table threshold exceeded."
    --#TYPE            "Bad block table threshold exceeded"
    --#SUMMARY         "Adapter %s: Bad block table of disk (%s) threshold exceeded; table is about to overflow (Server %s)"
    --#ARGUMENTS       { 2, 3, 0 }
    --#SEVERITY        INFORMATIONAL
    --#TIMEINDEX       1
    --#HELP            ""
    --#STATE           OPERATIONAL
    ::= 10628

-- EVT_PD_BBT_CLEARED

svrTrapPDBBTCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table cleared."
    --#TYPE            "Bad block table cleared"
    --#SUMMARY         "Adapter %s: Bad block table of disk (%s) cleared (Server %s)"
    --#ARGUMENTS       { 2, 3, 0 }
    --#SEVERITY        INFORMATIONAL
    --#TIMEINDEX       1
    --#HELP            ""
    --#STATE           OPERATIONAL
    ::= 10629

-- EVT_PD_FAIL_BBT

svrTrapPDFailBBT TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failed due to bad block table overflow."
    --#TYPE            "Disk failed due to bad block table overflow"
    --#SUMMARY         "Adapter %s: Disk (%s) failed due to bad block table overflow (Server %s)"
    --#ARGUMENTS       { 2, 3, 0 }
    --#SEVERITY        CRITICAL
    --#TIMEINDEX       1
    --#HELP            "Replace affected disk."
    --#STATE           NONOPERATIONAL
    ::= 10630

-- EVT_PD_FAIL_BOOT

svrTrapPDFailBoot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failure detected during POST."
    --#TYPE            "Disk failure detected during POST"
    --#SUMMARY         "Adapter %s: Disk (%s) failure detected during POST (Server %s)"
    --#ARGUMENTS       { 2, 3, 0 }
    --#SEVERITY        CRITICAL
    --#TIMEINDEX       1
    --#HELP            "Replace affected disk."
    --#STATE           NONOPERATIONAL
    ::= 10631

-- EVT_CTLR_FAIL_BOOT

svrTrapCtlrFailBoot TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Failure detected during POST."
    --#TYPE            "Failure detected during POST"
    --#SUMMARY         "Adapter %s: Failure detected during POST (Server %s)"
    --#ARGUMENTS       { 2, 0 }
    --#SEVERITY        CRITICAL
    --#TIMEINDEX       1
    --#HELP            "Call your local Fujitsu Helpdesk."
    --#STATE           NONOPERATIONAL
    ::= 10632

-- EVT_PD_MULTI_FAIL

svrTrapPDMultiFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Multiple failure on disk detected."
    --#TYPE            "Multiple failure on disk detected"
    --#SUMMARY         "Adapter %s: Multiple failure on disk (%s) detected, internal info %s (Server %s)"
    --#ARGUMENTS       { 2, 3, 4, 0 }
    --#SEVERITY        CRITICAL
    --#TIMEINDEX       1
    --#HELP            "Replace affected disk."
    --#STATE           NONOPERATIONAL
    ::= 10633

-- EVT_BGI_STARTED_CTLR_CHANGE

svrTrapBGIStartedCtlrChange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI started due to adapter exchange."
    --#TYPE            "BGI started due to adapter exchange"
    --#SUMMARY         "Adapter %s: BGI started due to adapter exchange (Server %s)"
    --#ARGUMENTS       { 2, 0 }
    --#SEVERITY        INFORMATIONAL
    --#TIMEINDEX       1
    --#HELP            ""
    --#STATE           OPERATIONAL
    ::= 10634

-- EVT_PD_FAIL_PR

svrTrapPDFailPR TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failure detected by Patrol Read."
    --#TYPE            "Disk failure detected by Patrol Read"
    --#SUMMARY         "Adapter %s: Disk (%s) failure detected by Patrol Read (Server %s)"
    --#ARGUMENTS       { 2, 3, 0 }
    --#SEVERITY        CRITICAL
    --#TIMEINDEX       1
    --#HELP            "Replace affected disk."
    --#STATE           NONOPERATIONAL
    ::= 10635

-- EVT_PD_FAIL_REDUNDANT_COPY_NO_ERROR

svrTrapPDFailRedundantCopyNoError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failure detected after successfully building redundancy."
    --#TYPE            "Disk failure detected after successfully building redundancy"
    --#SUMMARY         "Adapter %s: Disk (%s) failure detected after successfully building redundancy (Server %s)"
    --#ARGUMENTS       { 2, 3, 0 }
    --#SEVERITY        CRITICAL
    --#TIMEINDEX       1
    --#HELP            "Replace affected disk."
    --#STATE           NONOPERATIONAL
    ::= 10636

-- EVT_PD_FAIL_REDUNDANT_COPY_ERROR

svrTrapPDFailRedundantCopyError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failure detected after aborting building redundancy."
    --#TYPE            "Disk failure detected after aborting building redundancy"
    --#SUMMARY         "Adapter %s: Disk (%s) failure detected after aborting building redundancy (Server %s)"
    --#ARGUMENTS       { 2, 3, 0 }
    --#SEVERITY        CRITICAL
    --#TIMEINDEX       1
    --#HELP            "Replace affected disk."
    --#STATE           NONOPERATIONAL
    ::= 10637

-- EVT_PD_FAIL

svrTrapPDFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failed."
    --#TYPE            "Disk failed"
    --#SUMMARY         "Adapter %s: Disk (%s) failed (Server %s)"
    --#ARGUMENTS       { 2, 3, 0 }
    --#SEVERITY        CRITICAL
    --#TIMEINDEX       1
    --#HELP            "Replace affected disk."
    --#STATE           NONOPERATIONAL
    ::= 10638

-- EVT_PD_FAIL_EX2

svrTrapPDFailEx2 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failed."
    --#TYPE            "Disk failed"
    --#SUMMARY         "Adapter %s: Disk (%s) failed, internal info %s (Server %s)"
    --#ARGUMENTS       { 2, 3, 4, 0 }
    --#SEVERITY        CRITICAL
    --#TIMEINDEX       1
    --#HELP            "Replace affected disk."
    --#STATE           NONOPERATIONAL
    ::= 10639

-- EVT_CTLR_CHANGED

svrTrapCtlrChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter was exchanged."
    --#TYPE            "Adapter was exchanged"
    --#SUMMARY         "Adapter %s was exchanged (Server %s)"
    --#ARGUMENTS       { 2, 0 }
    --#SEVERITY        INFORMATIONAL
    --#TIMEINDEX       1
    --#HELP            ""
    --#STATE           OPERATIONAL
    ::= 10640

-- EVT_CTLR_FLASH_UPLOAD_STARTED

svrTrapCtlrFlashUploadStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware upload started."
    --#TYPE            "Firmware upload started"
    --#SUMMARY         "Adapter %s: Firmware upload started (Server %s)"
    --#ARGUMENTS       { 2, 0 }
    --#SEVERITY        INFORMATIONAL
    --#TIMEINDEX       1
    --#HELP            ""
    --#STATE           OPERATIONAL
    ::= 10641

-- EVT_CTLR_FLASH_UPLOAD_RUNNING

svrTrapCtlrFlashUploadDone TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware upload is executing."
    --#TYPE            "Firmware upload is executing"
    --#SUMMARY         "Adapter %s: Firmware upload is executing (Server %s)"
    --#ARGUMENTS       { 2, 0 }
    --#SEVERITY        INFORMATIONAL
    --#TIMEINDEX       1
    --#HELP            ""
    --#STATE           OPERATIONAL
    ::= 10642

-- EVT_CTLR_WRITE_CONFIG_DONE

svrTrapCtlrWriteConfigDone TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Save configuration."
    --#TYPE            "Save configuration"
    --#SUMMARY         "Adapter %s: Save configuration (Server %s)"
    --#ARGUMENTS       { 2, 0 }
    --#SEVERITY        INFORMATIONAL
    --#TIMEINDEX       1
    --#HELP            ""
    --#STATE           OPERATIONAL
    ::= 10643

-- EVT_ARRAYS_CREATED

svrTrapArraysCreated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Arrays created."
    --#TYPE            "Arrays created"
    --#SUMMARY         "Adapter %s: Arrays %s created (Server %s)"
    --#ARGUMENTS       { 2, 3, 0 }
    --#SEVERITY        INFORMATIONAL
    --#TIMEINDEX       1
    --#HELP            ""
    --#STATE           OPERATIONAL
    ::= 10644

-- EVT_ARRAYS_DELETED

svrTrapArraysDeleted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Arrays deleted."
    --#TYPE            "Arrays deleted"
    --#SUMMARY         "Adapter %s: Arrays %s deleted (Server %s)"
    --#ARGUMENTS       { 2, 3, 0 }
    --#SEVERITY        INFORMATIONAL
    --#TIMEINDEX       1
    --#HELP            ""
    --#STATE           OPERATIONAL
    ::= 10645

-- EVT_CTLR_SET_TRACE_MODE

svrTrapCtlrSetTraceMode TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Trace mode changed."
    --#TYPE            "Trace mode changed"
    --#SUMMARY         "Adapter %s: Trace mode changed (Server %s)"
    --#ARGUMENTS       { 2, 0 }
    --#SEVERITY        INFORMATIONAL
    --#TIMEINDEX       1
    --#HELP            ""
    --#STATE           OPERATIONAL
    ::= 10646

-- EVT_CTLR_CLEAR_PANIC_DUMP_DATA

svrTrapCtlrClearPanicDumpData TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Panic dump data deleted."
    --#TYPE            "Panic dump data deleted"
    --#SUMMARY         "Adapter %s: Panic dump data deleted (Server %s)"
    --#ARGUMENTS       { 2, 0 }
    --#SEVERITY        INFORMATIONAL
    --#TIMEINDEX       1
    --#HELP            ""
    --#STATE           OPERATIONAL
    ::= 10647

-- EVT_CTLR_FORCE_PANIC

svrTrapCtlrForcePanic TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Panic forced."
    --#TYPE            "Panic forced"
    --#SUMMARY         "Adapter %s: Panic forced (Server %s)"
    --#ARGUMENTS       { 2, 0 }
    --#SEVERITY        INFORMATIONAL
    --#TIMEINDEX       1
    --#HELP            ""
    --#STATE           OPERATIONAL
    ::= 10648

-- EVT_CTLR_SET_SCRIPT

svrTrapCtlrSetScript TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Startup script set."
    --#TYPE            "Startup script set"
    --#SUMMARY         "Adapter %s: Startup script set (Server %s)"
    --#ARGUMENTS       { 2, 0 }
    --#SEVERITY        INFORMATIONAL
    --#TIMEINDEX       1
    --#HELP            ""
    --#STATE           OPERATIONAL
    ::= 10649

-- EVT_CTLR_EXBIOS_PARAM_CHANGED

svrTrapCtlrEXBIOSParamChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "EXBIOS parameter changed."
    --#TYPE            "EXBIOS parameter changed"
    --#SUMMARY         "Adapter %s: EXBIOS parameter changed (Server %s)"
    --#ARGUMENTS       { 2, 0 }
    --#SEVERITY        INFORMATIONAL
    --#TIMEINDEX       1
    --#HELP            ""
    --#STATE           OPERATIONAL
    ::= 10650

-- EVT_CTLR_SET_AUTO_OFFLINE

svrTrapCtlrSetAutoOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Auto offline recovery mode changed."
    --#TYPE            "Auto offline recovery mode changed"
    --#SUMMARY         "Adapter %s: Auto offline recovery mode changed (Server %s)"
    --#ARGUMENTS       { 2, 0 }
    --#SEVERITY        INFORMATIONAL
    --#TIMEINDEX       1
    --#HELP            ""
    --#STATE           OPERATIONAL
    ::= 10651

-- EVT_CTLR_SET_CLOCK

svrTrapCtlrSetClock TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Clock time changed."
    --#TYPE            "Clock time changed"
    --#SUMMARY         "Adapter %s: Clock time changed (Server %s)"
    --#ARGUMENTS       { 2, 0 }
    --#SEVERITY        INFORMATIONAL
    --#TIMEINDEX       1
    --#HELP            ""
    --#STATE           OPERATIONAL
    ::= 10652

-- EVT_CTLR_SET_FACTORY_SETTINGS

svrTrapCtlrSetFactorySettings TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Factory shipment settings restored."
    --#TYPE            "Factory shipment settings restored"
    --#SUMMARY         "Adapter %s: Factory shipment settings restored (Server %s)"
    --#ARGUMENTS       { 2, 0 }
    --#SEVERITY        INFORMATIONAL
    --#TIMEINDEX       1
    --#HELP            ""
    --#STATE           OPERATIONAL
    ::= 10653

-- EVT_CTLR_DISK_LOG_CLEARED

svrTrapCtlrDiskLogCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal log cleared."
    --#TYPE            "Internal log cleared"
    --#SUMMARY         "Adapter %s: Internal log cleared (Server %s)"
    --#ARGUMENTS       { 2, 0 }
    --#SEVERITY        INFORMATIONAL
    --#TIMEINDEX       1
    --#HELP            ""
    --#STATE           OPERATIONAL
    ::= 10654

-- EVT_CTLR_NVRAM_LOG_CLEARED

svrTrapCtlrNVRAMLogCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "NVRAM log cleared."
    --#TYPE            "NVRAM log cleared"
    --#SUMMARY         "Adapter %s: NVRAM log cleared (Server %s)"
    --#ARGUMENTS       { 2, 0 }
    --#SEVERITY        INFORMATIONAL
    --#TIMEINDEX       1
    --#HELP            ""
    --#STATE           OPERATIONAL
    ::= 10655

-- EVT_CTLR_REFRESH_UNIQUE_KEY

svrTrapCtlrRefreshUniqueKey TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unique key refreshed."
    --#TYPE            "Unique key refreshed"
    --#SUMMARY         "Adapter %s: Unique key refreshed (Server %s)"
    --#ARGUMENTS       { 2, 0 }
    --#SEVERITY        INFORMATIONAL
    --#TIMEINDEX       1
    --#HELP            ""
    --#STATE           OPERATIONAL
    ::= 10656

-- EVT_CTLR_SET_WRITE_CHECK_PARAM

svrTrapCtlrSetWriteCheckParam TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write check parameter changed."
    --#TYPE            "Write check parameter changed"
    --#SUMMARY         "Adapter %s: Write check parameter changed (Server %s)"
    --#ARGUMENTS       { 2, 0 }
    --#SEVERITY        INFORMATIONAL
    --#TIMEINDEX       1
    --#HELP            ""
    --#STATE           OPERATIONAL
    ::= 10657

-- EVT_CTLR_OP_FAILED

svrTrapCtlrOpFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Operation failed."
    --#TYPE            "Operation failed"
    --#SUMMARY         "Adapter %s: Operation failed (Server %s)"
    --#ARGUMENTS       { 2, 0 }
    --#SEVERITY        MINOR
    --#TIMEINDEX       1
    --#HELP            "1) Replace affected RAID controller."
    --#STATE           OPERATIONAL
    ::= 10658

-- EVT_CTLR_NEW_FIRMWARE_VERSION

svrTrapCtlrNewFirmwareVersion TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "New firmware version detected."
    --#TYPE            "New firmware version detected"
    --#SUMMARY         "Adapter %s: New firmware version %s detected (Server %s)"
    --#ARGUMENTS       { 2, 3, 0 }
    --#SEVERITY        INFORMATIONAL
    --#TIMEINDEX       1
    --#HELP            ""
    --#STATE           OPERATIONAL
    ::= 10659

-- EVT_CTLR_DG_WITHOUT_LD

svrTrapCtlrDGWithoutLD TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Array without logical drive left."
    --#TYPE            "Array without logical drive left"
    --#SUMMARY         "Adapter %s: Array %s without logical drive left (Server %s)"
    --#ARGUMENTS       { 2, 3, 0 }
    --#SEVERITY        MINOR
    --#TIMEINDEX       1
    --#HELP            "There is an array which has no logical drive. Create a logical drive to use the array."
    --#STATE           OPERATIONAL
    ::= 10660

-- EVT_CTLR_INCORRECT_CALENDAR

svrTrapCtlrIncorrectCalendar TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Incorrect calendar parameter detected."
    --#TYPE            "Incorrect calendar parameter detected"
    --#SUMMARY         "Adapter %s: Incorrect calendar parameter detected (Server %s)"
    --#ARGUMENTS       { 2, 0 }
    --#SEVERITY        MINOR
    --#TIMEINDEX       1
    --#HELP            "Check the scheduler settings."
    --#STATE           OPERATIONAL
    ::= 10661

-- EVT_LD_COPY_BACK_ABORTED_BBT_OVER

svrTrapCtlrSIUBBT TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback on logical drive aborted due to bad block table overflow."
    --#TYPE            "Copyback on logical drive aborted due to bad block table overflow"
    --#SUMMARY         "Adapter %s: Copyback on logical drive %s aborted due to bad block table overflow (Server %s)"
    --#ARGUMENTS       { 2, 3, 0 }
    --#SEVERITY        MAJOR
    --#TIMEINDEX       1
    --#HELP            "A large number of uncorrectable bad blocks were detected on logical drive. 1) Restore last good data."
    --#STATE           OPERATIONAL
    ::= 10662

-- EVT_LD_REDUNDANT_COPY_ABORTED_BBT_OVER

svrTrapCtlrSIUBBTEnd TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Redundant copy on logical drive aborted due to bad block table overflow."
    --#TYPE            "Redundant copy on logical drive aborted due to bad block table overflow"
    --#SUMMARY         "Adapter %s: Redundant copy on logical drive %s aborted due to bad block table overflow (Server %s)"
    --#ARGUMENTS       { 2, 3, 0 }
    --#SEVERITY        MAJOR
    --#TIMEINDEX       1
    --#HELP            "A large number of uncorrectable bad blocks were detected on logical drive. 1) Restore last good data."
    --#STATE           OPERATIONAL
    ::= 10663

-- EVT_CTLR_BBT_INIT

svrTrapCtlrBBTInit TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table expansion area initialized."
    --#TYPE            "Bad block table expansion area initialized"
    --#SUMMARY         "Adapter %s: Bad block table expansion area initialized (Server %s)"
    --#ARGUMENTS       { 2, 0 }
    --#SEVERITY        INFORMATIONAL
    --#TIMEINDEX       1
    --#HELP            ""
    --#STATE           OPERATIONAL
    ::= 10664

-- EVT_CTLR_BBT_INIT_FAILED

svrTrapCtlrBBTInitFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table expansion area initialization failed."
    --#TYPE            "Bad block table expansion area initialization failed"
    --#SUMMARY         "Adapter %s: Bad block table expansion area initialization failed (Server %s)"
    --#ARGUMENTS       { 2, 0 }
    --#SEVERITY        INFORMATIONAL
    --#TIMEINDEX       1
    --#HELP            ""
    --#STATE           OPERATIONAL
    ::= 10665

-- EVT_LD_DISK_ERROR_ON_WRITE

svrTrapLDDiskErrorOnWrite TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk error detected by write data on logical drive during redundant copy."
    --#TYPE            "Disk error detected by write data on logical drive during redundant copy"
    --#SUMMARY         "Adapter %s: Disk error detected by write data on logical drive %s during redundant copy (Server %s)"
    --#ARGUMENTS       { 2, 3, 0 }
    --#SEVERITY        INFORMATIONAL
    --#TIMEINDEX       1
    --#HELP            ""
    --#STATE           OPERATIONAL
    ::= 10666

-- EVT_PD_BAD_BLOCK

svrTrapPDBadBlock TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block detected on disk."
    --#TYPE            "Bad block detected on disk"
    --#SUMMARY         "Adapter %s: Bad block detected on disk (%s), %s (Server %s)"
    --#ARGUMENTS       { 2, 3, 4, 0 }
    --#SEVERITY        MINOR
    --#TIMEINDEX       1
    --#HELP            "For information only."
    --#STATE           OPERATIONAL
    ::= 10667

-- EVT_PD_MULTIDEAD_RECOVERY

svrTrapPDMultideadRecovery TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Multiple failure recovery on disk successful."
    --#TYPE            "Multiple failure recovery on disk successful"
    --#SUMMARY         "Adapter %s: Multiple failure recovery on disk (%s) successful (Server %s)"
    --#ARGUMENTS       { 2, 3, 0 }
    --#SEVERITY        INFORMATIONAL
    --#TIMEINDEX       1
    --#HELP            ""
    --#STATE           OPERATIONAL
    ::= 10668

-- EVT_PD_HS_AVAILABLE

svrTrapPDHSAvailable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Hot spare available."
    --#TYPE            "Hot spare available"
    --#SUMMARY         "Adapter %s: Hot spare available (Server %s)"
    --#ARGUMENTS       { 2, 0 }
    --#SEVERITY        INFORMATIONAL
    --#TIMEINDEX       1
    --#HELP            ""
    --#STATE           OPERATIONAL
    ::= 10669

-- EVT_PD_PR_START

svrTrapPDPRStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read (one cycle) started on disk."
    --#TYPE            "Patrol Read (one cycle) started on disk"
    --#SUMMARY         "Adapter %s: Patrol Read (one cycle) started on disk (%s) (Server %s)"
    --#ARGUMENTS       { 2, 3, 0 }
    --#SEVERITY        INFORMATIONAL
    --#TIMEINDEX       1
    --#HELP            ""
    --#STATE           OPERATIONAL
    ::= 10670

-- EVT_PD_PR_END

svrTrapPDPREnd TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read (one cycle) finished on disk."
    --#TYPE            "Patrol Read (one cycle) finished on disk"
    --#SUMMARY         "Adapter %s: Patrol Read (one cycle) finished on disk (%s) (Server %s)"
    --#ARGUMENTS       { 2, 3, 0 }
    --#SEVERITY        INFORMATIONAL
    --#TIMEINDEX       1
    --#HELP            ""
    --#STATE           OPERATIONAL
    ::= 10671

-- EVT_PD_SAS_ERROR

svrTrapPDSASError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Error detected on disk."
    --#TYPE            "Error detected on disk"
    --#SUMMARY         "Adapter %s: Error detected on disk (%s), %s (Server %s)"
    --#ARGUMENTS       { 2, 3, 4, 0 }
    --#SEVERITY        MINOR
    --#TIMEINDEX       1
    --#HELP            "For information only."
    --#STATE           OPERATIONAL
    ::= 10672

-- EVT_PD_SAS_RECOVERED

svrTrapPDSASRecovered TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Error recovered on disk."
    --#TYPE            "Error recovered on disk"
    --#SUMMARY         "Adapter %s: Error recovered on disk (%s), %s (Server %s)"
    --#ARGUMENTS       { 2, 3, 4, 0 }
    --#SEVERITY        INFORMATIONAL
    --#TIMEINDEX       1
    --#HELP            ""
    --#STATE           OPERATIONAL
    ::= 10673

-- EVT_PD_MEDIA_RECOVERED

svrTrapPDMediaRecovered TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Media error recovered on disk by reassigning new block."
    --#TYPE            "Media error recovered on disk by reassigning new block"
    --#SUMMARY         "Adapter %s: Media error recovered on disk (%s) by reassigning new block (Server %s)"
    --#ARGUMENTS       { 2, 3, 0 }
    --#SEVERITY        INFORMATIONAL
    --#TIMEINDEX       1
    --#HELP            ""
    --#STATE           OPERATIONAL
    ::= 10674

-- EVT_CTLR_PD_MOVE_LD

svrTrapCTLRPDMoveLD TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk location in logical drive changed."
    --#TYPE            "Disk location in logical drive changed"
    --#SUMMARY         "Adapter %s: Disk location in logical drive changed from port %s to port %s (Server %s)"
    --#ARGUMENTS       { 2, 3, 4, 0 }
    --#SEVERITY        MINOR
    --#TIMEINDEX       1
    --#HELP            "For information only."
    --#STATE           OPERATIONAL
    ::= 10675

-- EVT_CTLR_PD_INCR_COLD

svrTrapCTLRPDIncrCold TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk increased by cold swap."
    --#TYPE            "Disk increased by cold swap"
    --#SUMMARY         "Adapter %s: Disk increased by cold swap on port %s (Server %s)"
    --#ARGUMENTS       { 2, 3, 0 }
    --#SEVERITY        INFORMATIONAL
    --#TIMEINDEX       1
    --#HELP            ""
    --#STATE           OPERATIONAL
    ::= 10676

-- EVT_CTLR_PD_DECR_COLD

svrTrapCTLRPDDecrCold TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk decreased by cold swap."
    --#TYPE            "Disk decreased by cold swap"
    --#SUMMARY         "Adapter %s: Disk decreased by cold swap on port %s (Server %s)"
    --#ARGUMENTS       { 2, 3, 0 }
    --#SEVERITY        INFORMATIONAL
    --#TIMEINDEX       1
    --#HELP            ""
    --#STATE           OPERATIONAL
    ::= 10677

-- EVT_CTLR_PD_EXCH_COLD

svrTrapCTLRPDExchCold TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk exchanged by cold swap."
    --#TYPE            "Disk exchanged by cold swap"
    --#SUMMARY         "Adapter %s: Disk exchanged by cold swap on port %s (Server %s)"
    --#ARGUMENTS       { 2, 3, 0 }
    --#SEVERITY        INFORMATIONAL
    --#TIMEINDEX       1
    --#HELP            ""
    --#STATE           OPERATIONAL
    ::= 10678

-- EVT_CTLR_SAS_IFRATE

svrTrapCTLRSASIFRate TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS interface rate changed."
    --#TYPE            "SAS interface rate changed"
    --#SUMMARY         "Adapter %s: SAS interface rate changed on port %s (Server %s)"
    --#ARGUMENTS       { 2, 3, 0 }
    --#SEVERITY        INFORMATIONAL
    --#TIMEINDEX       1
    --#HELP            ""
    --#STATE           OPERATIONAL
    ::= 10679

-- EVT_CTLR_DRIVER_ERROR

svrTrapCtlrDriverError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Driver error."
    --#TYPE            "Driver error"
    --#SUMMARY         "Adapter %s: Driver error (Server %s)"
    --#ARGUMENTS       { 2, 0 }
    --#SEVERITY        MINOR
    --#TIMEINDEX       1
    --#HELP            "Check the driver version."
    --#STATE           OPERATIONAL
    ::= 10680

-- EVT_PD_COPYBACK_START1

svrTrapPDCopybackStart1 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback started on disk."
    --#TYPE            "Copyback started on disk"
    --#SUMMARY         "Adapter %s: Copyback started on disk (%s) (Server %s)"
    --#ARGUMENTS       { 2, 3, 0 }
    --#SEVERITY        INFORMATIONAL
    --#TIMEINDEX       1
    --#HELP            ""
    --#STATE           OPERATIONAL
    ::= 10681

-- EVT_PD_COPYBACK_ABORT1

svrTrapPDCopybackAbort1 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback aborted on disk."
    --#TYPE            "Copyback aborted on disk"
    --#SUMMARY         "Adapter %s: Copyback aborted on disk (%s) (Server %s)"
    --#ARGUMENTS       { 2, 3, 0 }
    --#SEVERITY        MINOR
    --#TIMEINDEX       1
    --#HELP            "For information only."
    --#STATE           OPERATIONAL
    ::= 10682

-- EVT_PD_COPYBACK_DONE1

svrTrapPDCopybackDone1 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback complete on disk."
    --#TYPE            "Copyback complete on disk"
    --#SUMMARY         "Adapter %s: Copyback complete on disk (%s) (Server %s)"
    --#ARGUMENTS       { 2, 3, 0 }
    --#SEVERITY        INFORMATIONAL
    --#TIMEINDEX       1
    --#HELP            ""
    --#STATE           OPERATIONAL
    ::= 10683

-- EVT_CTLR_INTERNAL_HARD_ERROR1

svrTrapCtlrInternalHardError1 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal hardware error."
    --#TYPE            "Internal hardware error"
    --#SUMMARY         "Adapter %s: Internal hardware error (Server %s)"
    --#ARGUMENTS       { 2, 0 }
    --#SEVERITY        MINOR
    --#TIMEINDEX       1
    --#HELP            "1) Replace affected RAID controller."
    --#STATE           OPERATIONAL
    ::= 10684

-- EVT_CTLR_INTERNAL_HARD_ERROR2

svrTrapCtlrInternalHardError2 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal hardware error."
    --#TYPE            "Internal hardware error"
    --#SUMMARY         "Adapter %s: Internal hardware error (Server %s)"
    --#ARGUMENTS       { 2, 0 }
    --#SEVERITY        MAJOR
    --#TIMEINDEX       1
    --#HELP            "1) Replace affected RAID controller."
    --#STATE           OPERATIONAL
    ::= 10685

-- EVT_PD_BBT_OVERFLOW

svrTrapPDBBTOverflow TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk bad block table overflow error."
    --#TYPE            "Disk bad block table overflow error"
    --#SUMMARY         "Adapter %s: Disk (%s) bad block table overflow error (Server %s)"
    --#ARGUMENTS       { 2, 3, 0 }
    --#SEVERITY        MAJOR
    --#TIMEINDEX       1
    --#HELP            "A large number of uncorrectable bad blocks were detected on the disk. 1) Restore last good data."
    --#STATE           OPERATIONAL
    ::= 10686

-- EVT_BBU_REMOTE_CONNECTOR_ERROR

svrTrapBBURemoteConnectorError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Error with the remote BBU connector cable detected."
    --#TYPE            "Error with the remote BBU connector cable detected"
    --#SUMMARY         "Adapter %s: Error with the remote BBU connector cable detected (Server %s)"
    --#ARGUMENTS       { 2, 0 }
    --#SEVERITY        MINOR
    --#TIMEINDEX       1
    --#HELP            "Replace the BBU data/power cable."
    --#STATE           OPERATIONAL
    ::= 10687

-- EVT_PD_MULTI_FAIL_POST

svrTrapPDMultiFailPOST TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Multiple failure on disk detected during POST."
    --#TYPE            "Multiple failure on disk detected during POST"
    --#SUMMARY         "Adapter %s: Multiple failure on disk (%s) detected during POST, internal info %s (Server %s)"
    --#ARGUMENTS       { 2, 3, 4, 0 }
    --#SEVERITY        CRITICAL
    --#TIMEINDEX       1
    --#HELP            "1) Replace affected disk. 2) Replace affected backplane or the data cable."
    --#STATE           NONOPERATIONAL
    ::= 10688

-- EVT_PD_SAS_IFERR_RATE_HIGH

svrTrapPDSASIfrateHigh TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failed due to SAS/SATA interface error rate too high."
    --#TYPE            "Disk failed due to SAS/SATA interface error rate too high"
    --#SUMMARY         "Adapter %s: Disk (%s) failed due to SAS/SATA interface error rate too high (Server %s)"
    --#ARGUMENTS       { 2, 3, 0 }
    --#SEVERITY        CRITICAL
    --#TIMEINDEX       1
    --#HELP            "1) Replace affected disk. 2) Replace affected backplane or the data cable."
    --#STATE           NONOPERATIONAL
    ::= 10689

-- EVT_PD_OFFLINE_REDUNDANT_COPY_START

svrTrapPDMarkedOfflineRedundantCopy TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Operation to mark disk offline (redundant copy) started."
    --#TYPE            "Operation to mark disk offline (redundant copy) started"
    --#SUMMARY         "Adapter %s: Operation to mark disk (%s) offline (redundant copy) started (Server %s)"
    --#ARGUMENTS       { 2, 3, 0 }
    --#SEVERITY        INFORMATIONAL
    --#TIMEINDEX       1
    --#HELP            ""
    --#STATE           OPERATIONAL
    ::= 10690

-- EVT_LD_REGISTER_MIGRATION

svrTrapLDRegisterMigration TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "RAID migration registered for logical drive."
    --#TYPE            "RAID migration registered for logical drive"
    --#SUMMARY         "Adapter %s: RAID migration registered for logical drive %s (Server %s)"
    --#ARGUMENTS       { 2, 3, 0 }
    --#SEVERITY        INFORMATIONAL
    --#TIMEINDEX       1
    --#HELP            ""
    --#STATE           OPERATIONAL
    ::= 10691

-- EVT_LD_MDC_ABORT_BY_USER

svrTrapLDMDCAbortByUser TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MDC aborted by user on logical drive."
    --#TYPE            "MDC aborted by user on logical drive"
    --#SUMMARY         "Adapter %s: MDC aborted by user on logical drive %s (Server %s)"
    --#ARGUMENTS       { 2, 3, 0 }
    --#SEVERITY        INFORMATIONAL
    --#TIMEINDEX       1
    --#HELP            ""
    --#STATE           OPERATIONAL
    ::= 10692

-- EVT_ALARM_SET

svrTrapAlarmSet TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Alarm set."
    --#TYPE            "Alarm set"
    --#SUMMARY         "Adapter %s: Alarm set (Server %s)"
    --#ARGUMENTS       { 2, 0 }
    --#SEVERITY        INFORMATIONAL
    --#TIMEINDEX       1
    --#HELP            ""
    --#STATE           OPERATIONAL
    ::= 10693

-- EVT_LD_DEGRADED_BBT

svrTrapLDDegradedBBT TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive degraded due to bad block table overflow."
    --#TYPE            "Logical drive degraded due to bad block table overflow"
    --#SUMMARY         "Adapter %s: Logical drive %s degraded due to bad block table overflow (Server %s)"
    --#ARGUMENTS       { 2, 3, 0 }
    --#SEVERITY        MAJOR
    --#TIMEINDEX       1
    --#HELP            "A large number of uncorrectable bad blocks were detected on the disk. 1) Restore last good data."
    --#STATE           DEGRADED
    ::= 10694

-- EVT_PD_DRIVER_WRITE_ERROR

svrTrapPDDriverWriteError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failed due to write error detection by driver."
    --#TYPE            "Disk failed due to write error detection by driver"
    --#SUMMARY         "Adapter %s: Disk (%s) failed due to write error detection by driver (Server %s)"
    --#ARGUMENTS       { 2, 3, 0 }
    --#SEVERITY        CRITICAL
    --#TIMEINDEX       1
    --#HELP            "Replace affected disk."
    --#STATE           NONOPERATIONAL
    ::= 10695

-- EVT_PD_ABNORMAL_CAPACITY

svrTrapPDAbnormalCapacity TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Abnormal capacity of disk in logical drive detected."
    --#TYPE            "Abnormal capacity of disk in logical drive detected"
    --#SUMMARY         "Adapter %s: Abnormal capacity of disk (%s) in logical drive detected (Server %s)"
    --#ARGUMENTS       { 2, 3, 0 }
    --#SEVERITY        MINOR
    --#TIMEINDEX       1
    --#HELP            "Check the array configuration."
    --#STATE           OPERATIONAL
    ::= 10696

-- EVT_PD_ABNORMAL_TYPE

svrTrapPDAbnormalType TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Illegal type of disk in logical drive detected."
    --#TYPE            "Illegal type of disk in logical drive detected"
    --#SUMMARY         "Adapter %s: Illegal type of disk (%s) in logical drive detected (Server %s)"
    --#ARGUMENTS       { 2, 3, 0 }
    --#SEVERITY        MINOR
    --#TIMEINDEX       1
    --#HELP            "Check the array configuration."
    --#STATE           OPERATIONAL
    ::= 10697

-- EVT_LD_NO_BACK_RECOV_BBT_OVER

svrTrapLDNoBackRecovBBTOver TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Background recovery of logical drive could not be started due to bad block table overflow."
    --#TYPE            "Background recovery of logical drive could not be started due to bad block table overflow"
    --#SUMMARY         "Adapter %s: Background recovery of logical drive %s could not be started due to bad block table overflow (Server %s)"
    --#ARGUMENTS       { 2, 3, 0 }
    --#SEVERITY        INFORMATIONAL
    --#TIMEINDEX       1
    --#HELP            ""
    --#STATE           OPERATIONAL
    ::= 10698

-- EVT_HS_PNPADD

svrTrapHSDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "New hot spare detected."
    --#TYPE            "New hot spare detected"
    --#SUMMARY         "Adapter %s: New hot spare (%s) detected (Server %s)"
    --#ARGUMENTS       { 2, 3, 0 }
    --#SEVERITY        INFORMATIONAL
    --#TIMEINDEX       1
    --#HELP            ""
    --#STATE           OPERATIONAL
    ::= 10699

-- EVT_CTLR_INTERNAL_PCI_HARD_ERROR

svrTrapCtlrInternalPCIHardError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal PCI hardware error."
    --#TYPE            "Internal PCI hardware error"
    --#SUMMARY         "Adapter %s: Internal PCI hardware error (Server %s)"
    --#ARGUMENTS       { 2, 0 }
    --#SEVERITY        MAJOR
    --#TIMEINDEX       1
    --#HELP            "Replace affected RAID controller."
    --#STATE           OPERATIONAL
    ::= 10700

-- EVT_PD_BBT_UPDATE

svrTrapPDBBTUpdate TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table was updated by disk."
    --#TYPE            "Bad block table was updated by disk"
    --#SUMMARY         "Adapter %s: Bad block table was updated by disk (%s) (Server %s)"
    --#ARGUMENTS       { 2, 3, 0 }
    --#SEVERITY        MINOR
    --#TIMEINDEX       1
    --#HELP            "For information only."
    --#STATE           OPERATIONAL
    ::= 10701

-- EVT_CTLR_PD_INVALID_START

svrTrapPDInvalidStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Invalid disk on port during start up detected."
    --#TYPE            "Invalid disk on port during start up detected"
    --#SUMMARY         "Adapter %s: Invalid disk on port %s during start up detected (Server %s)"
    --#ARGUMENTS       { 2, 3, 0 }
    --#SEVERITY        MINOR
    --#TIMEINDEX       1
    --#HELP            "For information only."
    --#STATE           OPERATIONAL
    ::= 10702

-- EVT_CTLR_PD_INVALID_HOT_SWAP

svrTrapPDInvalidHotSwap TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Invalid disk on port during hot swap detected."
    --#TYPE            "Invalid disk on port during hot swap detected"
    --#SUMMARY         "Adapter %s: Invalid disk on port %s during hot swap detected (Server %s)"
    --#ARGUMENTS       { 2, 3, 0 }
    --#SEVERITY        MINOR
    --#TIMEINDEX       1
    --#HELP            "For information only."
    --#STATE           OPERATIONAL
    ::= 10703

-- EVT_PD_SMART_BY_ERROR_THRESHOLD

svrTrapPDSMARTByErrorThreshold TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SMART error on disk because internal error threshold on adapter is exceeded."
    --#TYPE            "SMART error on disk because internal error threshold on adapter is exceeded"
    --#SUMMARY         "Adapter %s: SMART error on disk (%s) because internal error threshold on adapter is exceeded (Server %s)"
    --#ARGUMENTS       { 2, 3, 0 }
    --#SEVERITY        MINOR
    --#TIMEINDEX       1
    --#HELP            "Note: Disk reports a prefailure. The affected disk might fail soon. 1) Replace the disk during next maintenance."
    --#STATE           OPERATIONAL
    ::= 10704

-- EVT_CTLR_FIRMWARE_DRIVER_MISMATCH

svrTrapCtlrFirmwareDriverMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware and driver version mismatch."
    --#TYPE            "Firmware and driver version mismatch"
    --#SUMMARY         "Adapter %s: Firmware and driver version mismatch (Server %s)"
    --#ARGUMENTS       { 2, 0 }
    --#SEVERITY        MINOR
    --#TIMEINDEX       1
    --#HELP            "Check the driver and firmware version."
    --#STATE           OPERATIONAL
    ::= 10705

-- EVT_CTLR_RESET_RECEIVED

svrTrapCtlrResetReceived TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reset received."
    --#TYPE            "Reset received"
    --#SUMMARY         "Adapter %s: Reset received (Server %s)"
    --#ARGUMENTS       { 2, 0 }
    --#SEVERITY        INFORMATIONAL
    --#TIMEINDEX       1
    --#HELP            ""
    --#STATE           OPERATIONAL
    ::= 10706

-- EVT_PD_OFFLINE_START

svrTrapPDOfflineStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Operation to mark disk offline started."
    --#TYPE            "Operation to mark disk offline started"
    --#SUMMARY         "Adapter %s: Operation to mark disk (%s) offline started (Server %s)"
    --#ARGUMENTS       { 2, 3, 0 }
    --#SEVERITY        INFORMATIONAL
    --#TIMEINDEX       1
    --#HELP            ""
    --#STATE           OPERATIONAL
    ::= 10707

-- EVT_ARRAYS_DELETE_START

svrTrapArraysDeleteStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Operation to delete arrays started."
    --#TYPE            "Operation to delete arrays started"
    --#SUMMARY         "Adapter %s: Operation to delete arrays %s started (Server %s)"
    --#ARGUMENTS       { 2, 3, 0 }
    --#SEVERITY        INFORMATIONAL
    --#TIMEINDEX       1
    --#HELP            ""
    --#STATE           OPERATIONAL
    ::= 10708

-- EVT_LOGICALDRIVE_DELETE_START

svrTrapLDDeleteStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Operation to delete logical drive started."
    --#TYPE            "Operation to delete logical drive started"
    --#SUMMARY         "Adapter %s: Operation to delete logical drive %s started (Server %s)"
    --#ARGUMENTS       { 2, 3, 0 }
    --#SEVERITY        INFORMATIONAL
    --#TIMEINDEX       1
    --#HELP            ""
    --#STATE           OPERATIONAL
    ::= 10709

-- EVT_GLOBAL_HOTSPARE_DELETE_START

svrTrapGlobalHotspareDeleteStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Operation to delete global hot spare on disk started."
    --#TYPE            "Operation to delete global hot spare on disk started"
    --#SUMMARY         "Adapter %s: Operation to delete global hot spare on disk (%s) started (Server %s)"
    --#ARGUMENTS       { 2, 3, 0 }
    --#SEVERITY        INFORMATIONAL
    --#TIMEINDEX       1
    --#HELP            ""
    --#STATE           OPERATIONAL
    ::= 10710

-- EVT_PD_NOT_READY

svrTrapPDNotReady TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failed since it never entered ready state."
    --#TYPE            "Disk failed since it never entered ready state"
    --#SUMMARY         "Adapter %s: Disk (%s) failed since it never entered ready state, %s (Server %s)"
    --#ARGUMENTS       { 2, 3, 4, 0 }
    --#SEVERITY        CRITICAL
    --#TIMEINDEX       1
    --#HELP            "Replace affected disk."
    --#STATE           NONOPERATIONAL
    ::= 10711

-- EVT_INTERNAL_SOFTWARE_IF_ERROR

svrTrapInternalSoftwareIFError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal software interface error."
    --#TYPE            "Internal software interface error"
    --#SUMMARY         "Adapter %s: Internal software interface error (function: %s) (Server %s)"
    --#ARGUMENTS       { 2, 3, 0 }
    --#SEVERITY        MINOR
    --#TIMEINDEX       1
    --#HELP            "Note: The driver encountered an error. 1) Check the status of the operating system. 2) Reboot your system."
    --#STATE           OPERATIONAL
    ::= 10712

-- EVT_DEVICE_OPEN_ERROR

svrTrapDeviceOpenError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Device open error."
    --#TYPE            "Device open error"
    --#SUMMARY         "Adapter %s: Device open error (device: %s) (Server %s)"
    --#ARGUMENTS       { 2, 3, 0 }
    --#SEVERITY        MINOR
    --#TIMEINDEX       1
    --#HELP            "Note: The driver encountered an error. 1) Check the status of the operating system. 2) Reboot your system."
    --#STATE           OPERATIONAL
    ::= 10713

-- EVT_IOCTL_SEND_ERROR

svrTrapIoctlSendError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Ioctl send error."
    --#TYPE            "Ioctl send error"
    --#SUMMARY         "Adapter %s: Ioctl send error (details: %s) (Server %s)"
    --#ARGUMENTS       { 2, 3, 0 }
    --#SEVERITY        MINOR
    --#TIMEINDEX       1
    --#HELP            "Note: The driver encountered an error. 1) Check the status of the operating system. 2) Reboot your system."
    --#STATE           OPERATIONAL
    ::= 10714

-- EVT_INSUFFICIENT_MEMORY

svrTrapInsufficientMemory TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Insufficient application memory."
    --#TYPE            "Insufficient application memory"
    --#SUMMARY         "Adapter %s: Insufficient application memory (function: %s) (Server %s)"
    --#ARGUMENTS       { 2, 3, 0 }
    --#SEVERITY        MINOR
    --#TIMEINDEX       1
    --#HELP            "Note: The driver encountered an error. 1) Check the status of the operating system. 2) Reboot your system."
    --#STATE           OPERATIONAL
    ::= 10715

-- EVT_SYS_API_ERROR

svrTrapSysAPIError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "System API error."
    --#TYPE            "System API error"
    --#SUMMARY         "Adapter %s: System API error (code: %s, function/item: %s) (Server %s)"
    --#ARGUMENTS       { 2, 3, 4, 0 }
    --#SEVERITY        MINOR
    --#TIMEINDEX       1
    --#HELP            "Note: The driver encountered an error. 1) Check the status of the operating system. 2) Reboot your system."
    --#STATE           OPERATIONAL
    ::= 10716

-- EVT_FW_INIT_FAILED

svrTrapFWInitFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware initialization failed."
    --#TYPE            "Firmware initialization failed"
    --#SUMMARY         "Adapter %s: Firmware initialization failed (Server %s)"
    --#ARGUMENTS       { 2, 0 }
    --#SEVERITY        CRITICAL
    --#TIMEINDEX       1
    --#HELP            "1) Replace affected RAID controller."
    --#STATE           NONOPERATIONAL
    ::= 10717

-- EVT_FW_RECOVERY_FAILED

svrTrapFWRecoveryFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware recovery failed."
    --#TYPE            "Firmware recovery failed"
    --#SUMMARY         "Adapter %s: Firmware recovery failed (Server %s)"
    --#ARGUMENTS       { 2, 0 }
    --#SEVERITY        CRITICAL
    --#TIMEINDEX       1
    --#HELP            "1) Replace affected RAID controller."
    --#STATE           NONOPERATIONAL
    ::= 10718

-- EVT_IOCTL_BUSY

svrTrapIoctlBusy TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Ioctl busy."
    --#TYPE            "Ioctl busy"
    --#SUMMARY         "Adapter %s: Ioctl busy (Server %s)"
    --#ARGUMENTS       { 2, 0 }
    --#SEVERITY        INFORMATIONAL
    --#TIMEINDEX       1
    --#HELP            ""
    --#STATE           OPERATIONAL
    ::= 10719

-- EVT_BOOT_LOGICALDRIVE_NUMBER_CHANGED

svrTrapBootLogicalDriveNumberChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive number for boot changed."
    --#TYPE            "Logical drive number for boot changed"
    --#SUMMARY         "Adapter %s: Logical drive number for boot changed to %s (Server %s)"
    --#ARGUMENTS       { 2, 3, 0 }
    --#SEVERITY        INFORMATIONAL
    --#TIMEINDEX       1
    --#HELP            ""
    --#STATE           OPERATIONAL
    ::= 10720

-- EVT_PD_POWER_STATE_CHANGE_ACTIVE_TO_STOP

svrTrapPDPowerStateChangeActiveToStop TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change on disk from active to stopped."
    --#TYPE            "Power state change on disk from active to stopped"
    --#SUMMARY         "Adapter %s: Power state change on disk (%s) from active to stopped (Server %s)"
    --#ARGUMENTS       { 2, 3, 0 }
    --#SEVERITY        INFORMATIONAL
    --#TIMEINDEX       1
    --#HELP            ""
    --#STATE           OPERATIONAL
    ::= 10721

-- EVT_PD_POWER_STATE_CHANGE_STOP_TO_ACTIVE

svrTrapPDPowerStateChangeStopToActive TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change on disk from stopped to active."
    --#TYPE            "Power state change on disk from stopped to active"
    --#SUMMARY         "Adapter %s: Power state change on disk (%s) from stopped to active (Server %s)"
    --#ARGUMENTS       { 2, 3, 0 }
    --#SEVERITY        INFORMATIONAL
    --#TIMEINDEX       1
    --#HELP            ""
    --#STATE           OPERATIONAL
    ::= 10722

-- EVT_ENCL_ELEMENT_STATUS_CHANGED

svrTrapEnclElementStatusChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure element status changed."
    --#TYPE            "Enclosure element status changed"
    --#SUMMARY         "Adapter %s: Enclosure %s element (SES code %s) status changed (Server %s)"
    --#ARGUMENTS       { 2, 3, 4, 0 }
    --#SEVERITY        INFORMATIONAL
    --#TIMEINDEX       1
    --#HELP            ""
    --#STATE           OPERATIONAL
    ::= 10723

-- EVT_CTLR_FIRMWARE_UPDATED

svrTrapCtlrFirmwareUpdated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware upload process finished."
    --#TYPE            "Firmware upload process finished"
    --#SUMMARY         "Adapter %s: Firmware upload process finished (Server %s)"
    --#ARGUMENTS       { 2, 0 }
    --#SEVERITY        INFORMATIONAL
    --#TIMEINDEX       1
    --#HELP            ""
    --#STATE           OPERATIONAL
    ::= 10724

-- EVT_CTLR_PD_FW_UPLOAD_START

svrTrapCtlrPDFWUploadStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk firmware update process started."
    --#TYPE            "Disk firmware update process started"
    --#SUMMARY         "Adapter %s: Disk firmware update process started (Server %s)"
    --#ARGUMENTS       { 2, 0 }
    --#SEVERITY        INFORMATIONAL
    --#TIMEINDEX       1
    --#HELP            ""
    --#STATE           OPERATIONAL
    ::= 10725

-- EVT_CTLR_PD_FW_UPLOAD_END

svrTrapCtlrPDFWUploadEnd TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk firmware update process finished."
    --#TYPE            "Disk firmware update process finished"
    --#SUMMARY         "Adapter %s: Disk firmware update process finished (Server %s)"
    --#ARGUMENTS       { 2, 0 }
    --#SEVERITY        INFORMATIONAL
    --#TIMEINDEX       1
    --#HELP            ""
    --#STATE           OPERATIONAL
    ::= 10726

-- EVT_CTLR_TOD_CHANGED

svrTrapCtlrTODChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Difference in time information changed."
    --#TYPE            "Difference in time information changed"
    --#SUMMARY         "Adapter %s: Difference in time information changed (Server %s)"
    --#ARGUMENTS       { 2, 0 }
    --#SEVERITY        INFORMATIONAL
    --#TIMEINDEX       1
    --#HELP            ""
    --#STATE           OPERATIONAL
    ::= 10727

-- EVT_CTLR_INIT_FACTORY_SETTINGS

svrTrapCtlrInitFactorySettings TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Factory shipment settings initialized."
    --#TYPE            "Factory shipment settings initialized"
    --#SUMMARY         "Adapter %s: Factory shipment settings initialized (Server %s)"
    --#ARGUMENTS       { 2, 0 }
    --#SEVERITY        INFORMATIONAL
    --#TIMEINDEX       1
    --#HELP            ""
    --#STATE           OPERATIONAL
    ::= 10728

-- EVT_BBU_RECALIBRATION_NEEDED

svrTrapBBURecalibrationNeeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU requires recalibration."
    --#TYPE            "BBU requires recalibration"
    --#SUMMARY         "Adapter %s: BBU requires reconditioning; please initiate recalibration (Server %s)"
    --#ARGUMENTS       { 2, 0 }
    --#SEVERITY        MINOR
    --#TIMEINDEX       1
    --#HELP            "1) Initiate manual recalibration process (e.g. via ServerView RAID Manager). Note: Do not interrupt the charging process by reboots or shutdowns. 2) If problem persists replace BBU."
    --#STATE           OPERATIONAL
    ::= 10729

-- EVT_PD_NO_REBUILD_HDD_SSD_MIX_NOT_ALLOWED_IN_LD

svrTrapNoRebuildHDDSDDMix TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk rebuild not possible as HDD/SSD mix is not supported in an array."
    --#TYPE            "Disk rebuild not possible as HDD/SSD mix is not supported in an array"
    --#SUMMARY         "Adapter %s: Disk (%s) rebuild not possible as HDD/SSD mix is not supported in an array (Server %s)"
    --#ARGUMENTS       { 2, 3, 0 }
    --#SEVERITY        INFORMATIONAL
    --#TIMEINDEX       1
    --#HELP            ""
    --#STATE           OPERATIONAL
    ::= 10730

-- EVT_PD_NO_COPYBACK_HDD_SSD_MIX_NOT_ALLOWED_IN_LD

svrTrapPDNoCopybackHDDSDDMix TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback cannot be started on disk from disk as HDD/SSD mix is not supported in an array."
    --#TYPE            "Copyback cannot be started on disk from disk, as HDD/SSD mix is not supported in an array"
    --#SUMMARY         "Adapter %s: Copyback cannot be started on disk (%s) from disk (%s), as HDD/SSD mix is not supported in an array (Server %s)"
    --#ARGUMENTS       { 2, 3, 4, 0 }
    --#SEVERITY        INFORMATIONAL
    --#TIMEINDEX       1
    --#HELP            ""
    --#STATE           OPERATIONAL
    ::= 10731

-- EVT_TASK_PROBLEM

svrTrapTaskProblem TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Task for object cannot be started. The scheduler will try to start the task again later."
    --#TYPE            "Task for object cannot be started. The scheduler will try to start the task again later"
    --#SUMMARY         "Task %s for object %s cannot be started (error %s). The scheduler will try to start the task again later (Server %s)"
    --#ARGUMENTS       { 2, 3, 4, 0 }
    --#SEVERITY        MINOR
    --#TIMEINDEX       1
    --#HELP            "Check the error code. Then check the controller settings, scheduler settings and disk/logical drive/BBU status."
    --#STATE           OPERATIONAL
    ::= 10732

-- EVT_TASK_START

svrTrapTaskStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Task was started."
    --#TYPE            "Task was started"
    --#SUMMARY         "Task %s for object %s was started by scheduler (Server %s)"
    --#ARGUMENTS       { 2, 3, 0 }
    --#SEVERITY        INFORMATIONAL
    --#TIMEINDEX       1
    --#HELP            ""
    --#STATE           OPERATIONAL
    ::= 10733

-- EVT_TASK_STOP

svrTrapTaskStop TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Task for object cannot be started. The scheduler has disabled the task."
    --#TYPE            "Task for object cannot be started. The scheduler has disabled the task"
    --#SUMMARY         "Task %s for object %s cannot be started (error %s). The scheduler has disabled the task (Server %s)"
    --#ARGUMENTS       { 2, 3, 4, 0 }
    --#SEVERITY        MAJOR
    --#TIMEINDEX       1
    --#HELP            "Check the error code. Then check the controller settings, scheduler settings and disk/logical drive/BBU status."
    --#STATE           NONOPERATIONAL
    ::= 10734

-- EVT_LD_BBM_LOG_CLEARED

svrTrapLDBBMLogCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Bad block table of logical drive cleared."
    --#TYPE            "Bad block table of logical drive cleared"
    --#SUMMARY         "Adapter %s: Bad block table of logical drive %s cleared (Server %s)"
    --#ARGUMENTS       { 2, 3, 0 }
    --#SEVERITY        INFORMATIONAL
    --#TIMEINDEX       1
    --#HELP            ""
    --#STATE           OPERATIONAL
    ::= 10735

-- EVT_SAS_TOPOLOGY_ERROR

svrTrapSASTopologyError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "SAS topology error."
    --#TYPE            "SAS topology error"
    --#SUMMARY         "Adapter %s: SAS topology error: %s (Server %s)"
    --#ARGUMENTS       { 2, 3, 0 }
    --#SEVERITY        MAJOR
    --#TIMEINDEX       1
    --#HELP            "1) Unplug affected disk, wait 30 seconds, reinsert it. 2) Replace affected disk. 3) Replace affected backplane or the data cable."
    --#STATE           NONOPERATIONAL
    ::= 10736

-- EVT_BBU_AUTOMATIC_RECALIBRATION

svrTrapBBUAutomaticRecalibration TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU requires recalibration automatically initiated."
    --#TYPE            "BBU requires recalibration automatically initiated"
    --#SUMMARY         "Adapter %s: BBU required reconditioning; recalibration initiated (Server %s)"
    --#ARGUMENTS       { 2, 0 }
    --#SEVERITY        MINOR
    --#TIMEINDEX       1
    --#HELP            "For information only."
    --#STATE           OPERATIONAL
    ::= 10737

-- EVT_TASK_POWER

svrTrapTaskPower TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Task for object could not be started at the normal execution time because the service or system was down."
    --#TYPE            "Task for object could not be started at the normal execution time because the service or system was down"
    --#SUMMARY         "Task %s for object %s could not be started at the normal execution time because the service or system was down (Server %s)"
    --#ARGUMENTS       { 2, 3, 0 }
    --#SEVERITY        MINOR
    --#TIMEINDEX       1
    --#HELP            "Check the scheduler settings."
    --#STATE           OPERATIONAL
    ::= 10738

-- EVT_TASK_SKIP

svrTrapTaskSkip TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Task for object cannot be started. The task will be set to the next regular execution time."
    --#TYPE            "Task for object cannot be started. The scheduler will try to start the task again later"
    --#SUMMARY         "Task %s for object %s cannot be started (error %s). The task will be set to the next regular execution time (Server %s)"
    --#ARGUMENTS       { 2, 3, 4, 0 }
    --#SEVERITY        MINOR
    --#TIMEINDEX       1
    --#HELP            "Check the error code. Then check the controller settings, scheduler settings and disk/logical drive/BBU status."
    --#STATE           OPERATIONAL
    ::= 10739

-- EVT_LD_CORRECTED_CLUSTER_OF_MEDIUM_ERRORS

svrTrapLDCorrectedClusterOfMediumErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cluster of medium errors corrected for logical drive."
    --#TYPE            "Cluster of medium errors corrected for logical drive"
    --#SUMMARY         "Adapter %s: Cluster of medium errors corrected for logical drive %s at %s (on disk %s at %s) (Server %s)"
    --#ARGUMENTS       { 2, 3, 4, 5, 6, 0 }
    --#SEVERITY        INFORMATIONAL
    --#TIMEINDEX       1
    --#HELP            ""
    --#STATE           OPERATIONAL
    ::= 10740

-- EVT_CTRL_HOST_BUS_SCAN_REQUESTED

svrTrapCtrlHostBusScanRequested TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Host bus rescan requested."
    --#TYPE            "Host bus rescan requested"
    --#SUMMARY         "Adapter %s: Host bus rescan requested (Server %s)"
    --#ARGUMENTS       { 2, 0 }
    --#SEVERITY        INFORMATIONAL
    --#TIMEINDEX       1
    --#HELP            ""
    --#STATE           OPERATIONAL
    ::= 10741

-- EVT_CTRL_FACTORY_REPURPOSED

svrTrapCtrlFactoryRepurposed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter repurposed and factory defaults restored."
    --#TYPE            "Adapter repurposed and factory defaults restored"
    --#SUMMARY         "Adapter %s: Adapter repurposed and factory defaults restored (Server %s)"
    --#ARGUMENTS       { 2, 0 }
    --#SEVERITY        INFORMATIONAL
    --#TIMEINDEX       1
    --#HELP            ""
    --#STATE           OPERATIONAL
    ::= 10742

-- EVT_CTRL_LOCK_KEY_BINDING_UPDATED

svrTrapCtrlLockKeyBindingUpdated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security key binding updated."
    --#TYPE            "Disk security key binding updated"
    --#SUMMARY         "Adapter %s: Disk security key binding updated (Server %s)"
    --#ARGUMENTS       { 2, 0 }
    --#SEVERITY        INFORMATIONAL
    --#TIMEINDEX       1
    --#HELP            ""
    --#STATE           OPERATIONAL
    ::= 10743

-- EVT_PD_STATE_CHANGE_AVAIL_TO_CB

svrTrapPDStateChangeAvailToCB TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to copyback."
    --#TYPE            "State change from available to copyback"
    --#SUMMARY         "Adapter %s: State change on disk (%s) from available to copyback (Server %s)"
    --#ARGUMENTS       { 2, 3, 0 }
    --#SEVERITY        INFORMATIONAL
    --#TIMEINDEX       1
    --#HELP            ""
    --#STATE           OPERATIONAL
    ::= 10744

-- EVT_PD_STATE_CHANGE_AVAIL_TO_SYS

svrTrapPDStateChangeAvailToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to JBOD."
    --#TYPE            "State change from available to JBOD"
    --#SUMMARY         "Adapter %s: State change on disk (%s) from available to JBOD (Server %s)"
    --#ARGUMENTS       { 2, 3, 0 }
    --#SEVERITY        INFORMATIONAL
    --#TIMEINDEX       1
    --#HELP            ""
    --#STATE           OPERATIONAL
    ::= 10745

-- EVT_PD_STATE_CHANGE_FAIL_TO_CB

svrTrapPDStateChangeFailToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to copyback."
    --#TYPE            "State change from failed to copyback"
    --#SUMMARY         "Adapter %s: State change on disk (%s) from failed to copyback (Server %s)"
    --#ARGUMENTS       { 2, 3, 0 }
    --#SEVERITY        INFORMATIONAL
    --#TIMEINDEX       1
    --#HELP            ""
    --#STATE           OPERATIONAL
    ::= 10746

-- EVT_PD_STATE_CHANGE_FAIL_TO_SYS

svrTrapPDStateChangeFailToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to JBOD."
    --#TYPE            "State change from failed to JBOD"
    --#SUMMARY         "Adapter %s: State change on disk (%s) from failed to JBOD (Server %s)"
    --#ARGUMENTS       { 2, 3, 0 }
    --#SEVERITY        INFORMATIONAL
    --#TIMEINDEX       1
    --#HELP            ""
    --#STATE           OPERATIONAL
    ::= 10747

-- EVT_PD_STATE_CHANGE_HS_TO_CB

svrTrapPDStateChangeHsToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to copyback."
    --#TYPE            "State change from hot spare to copyback"
    --#SUMMARY         "Adapter %s: State change on disk (%s) from hot spare to copyback (Server %s)"
    --#ARGUMENTS       { 2, 3, 0 }
    --#SEVERITY        INFORMATIONAL
    --#TIMEINDEX       1
    --#HELP            ""
    --#STATE           OPERATIONAL
    ::= 10748

-- EVT_PD_STATE_CHANGE_HS_TO_SYS

svrTrapPDStateChangeHsToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to JBOD."
    --#TYPE            "State change from hot spare to JBOD"
    --#SUMMARY         "Adapter %s: State change on disk (%s) from hot spare to JBOD (Server %s)"
    --#ARGUMENTS       { 2, 3, 0 }
    --#SEVERITY        INFORMATIONAL
    --#TIMEINDEX       1
    --#HELP            ""
    --#STATE           OPERATIONAL
    ::= 10749

-- EVT_PD_STATE_CHANGE_RBLD_TO_CB

svrTrapPDStateChangeRbldToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to copyback."
    --#TYPE            "State change from rebuilding to copyback"
    --#SUMMARY         "Adapter %s: State change on disk (%s) from rebuilding to copyback (Server %s)"
    --#ARGUMENTS       { 2, 3, 0 }
    --#SEVERITY        INFORMATIONAL
    --#TIMEINDEX       1
    --#HELP            ""
    --#STATE           OPERATIONAL
    ::= 10750

-- EVT_PD_STATE_CHANGE_RBLD_TO_SYS

svrTrapPDStateChangeRbldToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to JBOD."
    --#TYPE            "State change from rebuilding to JBOD"
    --#SUMMARY         "Adapter %s: State change on disk (%s) from rebuilding to JBOD (Server %s)"
    --#ARGUMENTS       { 2, 3, 0 }
    --#SEVERITY        INFORMATIONAL
    --#TIMEINDEX       1
    --#HELP            ""
    --#STATE           OPERATIONAL
    ::= 10751

-- EVT_PD_STATE_CHANGE_OP_TO_CB

svrTrapPDStateChangeOpToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to copyback."
    --#TYPE            "State change from operational to copyback"
    --#SUMMARY         "Adapter %s: State change on disk (%s) from operational to copyback (Server %s)"
    --#ARGUMENTS       { 2, 3, 0 }
    --#SEVERITY        INFORMATIONAL
    --#TIMEINDEX       1
    --#HELP            ""
    --#STATE           OPERATIONAL
    ::= 10752

-- EVT_PD_STATE_CHANGE_OP_TO_SYS

svrTrapPDStateChangeOpToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to JBOD."
    --#TYPE            "State change from operational to JBOD"
    --#SUMMARY         "Adapter %s: State change on disk (%s) from operational to JBOD (Server %s)"
    --#ARGUMENTS       { 2, 3, 0 }
    --#SEVERITY        INFORMATIONAL
    --#TIMEINDEX       1
    --#HELP            ""
    --#STATE           OPERATIONAL
    ::= 10753

-- EVT_PD_STATE_CHANGE_CB_TO_AVAIL

svrTrapPDStateChangeCbToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to available."
    --#TYPE            "State change from copyback to available"
    --#SUMMARY         "Adapter %s: State change on disk (%s) from copyback to available (Server %s)"
    --#ARGUMENTS       { 2, 3, 0 }
    --#SEVERITY        INFORMATIONAL
    --#TIMEINDEX       1
    --#HELP            ""
    --#STATE           OPERATIONAL
    ::= 10754

-- EVT_PD_STATE_CHANGE_CB_TO_FAIL

svrTrapPDStateChangeCbToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to failed."
    --#TYPE            "State change from copyback to failed"
    --#SUMMARY         "Adapter %s: State change on disk (%s) from copyback to failed (Server %s)"
    --#ARGUMENTS       { 2, 3, 0 }
    --#SEVERITY        CRITICAL
    --#TIMEINDEX       1
    --#HELP            "Replace affected disk."
    --#STATE           NONOPERATIONAL
    ::= 10755

-- EVT_PD_STATE_CHANGE_CB_TO_HS

svrTrapPDStateChangeCbToHs TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to hot spare."
    --#TYPE            "State change from copyback to hot spare"
    --#SUMMARY         "Adapter %s: State change on disk (%s) from copyback to hot spare (Server %s)"
    --#ARGUMENTS       { 2, 3, 0 }
    --#SEVERITY        INFORMATIONAL
    --#TIMEINDEX       1
    --#HELP            ""
    --#STATE           OPERATIONAL
    ::= 10756

-- EVT_PD_STATE_CHANGE_CB_TO_OFFL

svrTrapPDStateChangeCbToOffl TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to offline."
    --#TYPE            "State change from copyback to offline"
    --#SUMMARY         "Adapter %s: State change on disk (%s) from copyback to offline (Server %s)"
    --#ARGUMENTS       { 2, 3, 0 }
    --#SEVERITY        MINOR
    --#TIMEINDEX       1
    --#HELP            "For information only."
    --#STATE           DEGRADED
    ::= 10757

-- EVT_PD_STATE_CHANGE_CB_TO_OP

svrTrapPDStateChangeCbToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to operational."
    --#TYPE            "State change from copyback to operational"
    --#SUMMARY         "Adapter %s: State change on disk (%s) from copyback to operational (Server %s)"
    --#ARGUMENTS       { 2, 3, 0 }
    --#SEVERITY        INFORMATIONAL
    --#TIMEINDEX       1
    --#HELP            ""
    --#STATE           OPERATIONAL
    ::= 10758

-- EVT_PD_STATE_CHANGE_CB_TO_RBLD

svrTrapPDStateChangeCbToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to rebuilding."
    --#TYPE            "State change from copyback to rebuilding"
    --#SUMMARY         "Adapter %s: State change on disk (%s) from copyback to rebuilding (Server %s)"
    --#ARGUMENTS       { 2, 3, 0 }
    --#SEVERITY        INFORMATIONAL
    --#TIMEINDEX       1
    --#HELP            ""
    --#STATE           OPERATIONAL
    ::= 10759

-- EVT_PD_STATE_CHANGE_CB_TO_CB

svrTrapPDStateChangeCbToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to copyback."
    --#TYPE            "State change from copyback to copyback"
    --#SUMMARY         "Adapter %s: State change on disk (%s) from copyback to copyback (Server %s)"
    --#ARGUMENTS       { 2, 3, 0 }
    --#SEVERITY        INFORMATIONAL
    --#TIMEINDEX       1
    --#HELP            ""
    --#STATE           OPERATIONAL
    ::= 10760

-- EVT_PD_STATE_CHANGE_CB_TO_SYS

svrTrapPDStateChangeCbToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to JBOD."
    --#TYPE            "State change from copyback to JBOD"
    --#SUMMARY         "Adapter %s: State change on disk (%s) from copyback to JBOD (Server %s)"
    --#ARGUMENTS       { 2, 3, 0 }
    --#SEVERITY        INFORMATIONAL
    --#TIMEINDEX       1
    --#HELP            ""
    --#STATE           OPERATIONAL
    ::= 10761

-- EVT_PD_STATE_CHANGE_SYS_TO_AVAIL

svrTrapPDStateChangeSysToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to available."
    --#TYPE            "State change from JBOD to available"
    --#SUMMARY         "Adapter %s: State change on disk (%s) from JBOD to available (Server %s)"
    --#ARGUMENTS       { 2, 3, 0 }
    --#SEVERITY        INFORMATIONAL
    --#TIMEINDEX       1
    --#HELP            ""
    --#STATE           OPERATIONAL
    ::= 10762

-- EVT_PD_STATE_CHANGE_SYS_TO_FAIL

svrTrapPDStateChangeSysToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to failed."
    --#TYPE            "State change from JBOD to failed"
    --#SUMMARY         "Adapter %s: State change on disk (%s) from JBOD to failed (Server %s)"
    --#ARGUMENTS       { 2, 3, 0 }
    --#SEVERITY        CRITICAL
    --#TIMEINDEX       1
    --#HELP            "Replace affected disk."
    --#STATE           NONOPERATIONAL
    ::= 10763

-- EVT_PD_STATE_CHANGE_SYS_TO_HS

svrTrapPDStateChangeSysToHs TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to hot spare."
    --#TYPE            "State change from JBOD to hot spare"
    --#SUMMARY         "Adapter %s: State change on disk (%s) from JBOD to hot spare (Server %s)"
    --#ARGUMENTS       { 2, 3, 0 }
    --#SEVERITY        INFORMATIONAL
    --#TIMEINDEX       1
    --#HELP            ""
    --#STATE           OPERATIONAL
    ::= 10764

-- EVT_PD_STATE_CHANGE_SYS_TO_OFFL

svrTrapPDStateChangeSysToOffl TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to offline."
    --#TYPE            "State change from JBOD to offline"
    --#SUMMARY         "Adapter %s: State change on disk (%s) from JBOD to offline (Server %s)"
    --#ARGUMENTS       { 2, 3, 0 }
    --#SEVERITY        MINOR
    --#TIMEINDEX       1
    --#HELP            "For information only."
    --#STATE           NONOPERATIONAL
    ::= 10765

-- EVT_PD_STATE_CHANGE_SYS_TO_OP

svrTrapPDStateChangeSysToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to operational."
    --#TYPE            "State change from JBOD to operational"
    --#SUMMARY         "Adapter %s: State change on disk (%s) from JBOD to operational (Server %s)"
    --#ARGUMENTS       { 2, 3, 0 }
    --#SEVERITY        INFORMATIONAL
    --#TIMEINDEX       1
    --#HELP            ""
    --#STATE           OPERATIONAL
    ::= 10766

-- EVT_PD_STATE_CHANGE_SYS_TO_RBLD

svrTrapPDStateChangeSysToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to rebuilding."
    --#TYPE            "State change from JBOD to rebuilding"
    --#SUMMARY         "Adapter %s: State change on disk (%s) from JBOD to rebuilding (Server %s)"
    --#ARGUMENTS       { 2, 3, 0 }
    --#SEVERITY        INFORMATIONAL
    --#TIMEINDEX       1
    --#HELP            ""
    --#STATE           OPERATIONAL
    ::= 10767

-- EVT_PD_STATE_CHANGE_SYS_TO_CB

svrTrapPDStateChangeSysToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to copyback."
    --#TYPE            "State change from JBOD to copyback"
    --#SUMMARY         "Adapter %s: State change on disk (%s) from JBOD to copyback (Server %s)"
    --#ARGUMENTS       { 2, 3, 0 }
    --#SEVERITY        INFORMATIONAL
    --#TIMEINDEX       1
    --#HELP            ""
    --#STATE           OPERATIONAL
    ::= 10768

-- EVT_PD_STATE_CHANGE_SYS_TO_SYS

svrTrapPDStateChangeSysToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to JBOD."
    --#TYPE            "State change from JBOD to JBOD"
    --#SUMMARY         "Adapter %s: State change on disk (%s) from JBOD to JBOD (Server %s)"
    --#ARGUMENTS       { 2, 3, 0 }
    --#SEVERITY        INFORMATIONAL
    --#TIMEINDEX       1
    --#HELP            ""
    --#STATE           OPERATIONAL
    ::= 10769

-- EVT_PD_STATE_CHANGE_BY_USER_AVAIL_TO_CB

svrTrapPDStateChangeByUserAvailToCB TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to copyback."
    --#TYPE            "State change by user from available to copyback"
    --#SUMMARY         "Adapter %s: State change by user on disk (%s) from available to copyback (Server %s)"
    --#ARGUMENTS       { 2, 3, 0 }
    --#SEVERITY        INFORMATIONAL
    --#TIMEINDEX       1
    --#HELP            ""
    --#STATE           OPERATIONAL
    ::= 10770

-- EVT_PD_STATE_CHANGE_BY_USER_AVAIL_TO_SYS

svrTrapPDStateChangeByUserAvailToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to JBOD."
    --#TYPE            "State change by user from available to JBOD"
    --#SUMMARY         "Adapter %s: State change by user on disk (%s) from available to JBOD (Server %s)"
    --#ARGUMENTS       { 2, 3, 0 }
    --#SEVERITY        INFORMATIONAL
    --#TIMEINDEX       1
    --#HELP            ""
    --#STATE           OPERATIONAL
    ::= 10771

-- EVT_PD_STATE_CHANGE_BY_USER_FAIL_TO_CB

svrTrapPDStateChangeByUserFailToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to copyback."
    --#TYPE            "State change by user from failed to copyback"
    --#SUMMARY         "Adapter %s: State change by user on disk (%s) from failed to copyback (Server %s)"
    --#ARGUMENTS       { 2, 3, 0 }
    --#SEVERITY        INFORMATIONAL
    --#TIMEINDEX       1
    --#HELP            ""
    --#STATE           OPERATIONAL
    ::= 10772

-- EVT_PD_STATE_CHANGE_BY_USER_FAIL_TO_SYS

svrTrapPDStateChangeByUserFailToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to JBOD."
    --#TYPE            "State change by user from failed to JBOD"
    --#SUMMARY         "Adapter %s: State change by user on disk (%s) from failed to JBOD (Server %s)"
    --#ARGUMENTS       { 2, 3, 0 }
    --#SEVERITY        INFORMATIONAL
    --#TIMEINDEX       1
    --#HELP            ""
    --#STATE           OPERATIONAL
    ::= 10773

-- EVT_PD_STATE_CHANGE_BY_USER_HS_TO_CB

svrTrapPDStateChangeByUserHsToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to copyback."
    --#TYPE            "State change by user from hot spare to copyback"
    --#SUMMARY         "Adapter %s: State change by user on disk (%s) from hot spare to copyback (Server %s)"
    --#ARGUMENTS       { 2, 3, 0 }
    --#SEVERITY        INFORMATIONAL
    --#TIMEINDEX       1
    --#HELP            ""
    --#STATE           OPERATIONAL
    ::= 10774

-- EVT_PD_STATE_CHANGE_BY_USER_HS_TO_SYS

svrTrapPDStateChangeByUserHsToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to JBOD."
    --#TYPE            "State change by user from hot spare to JBOD"
    --#SUMMARY         "Adapter %s: State change by user on disk (%s) from hot spare to JBOD (Server %s)"
    --#ARGUMENTS       { 2, 3, 0 }
    --#SEVERITY        INFORMATIONAL
    --#TIMEINDEX       1
    --#HELP            ""
    --#STATE           OPERATIONAL
    ::= 10775

-- EVT_PD_STATE_CHANGE_BY_USER_RBLD_TO_CB

svrTrapPDStateChangeByUserRbldToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to copyback."
    --#TYPE            "State change by user from rebuilding to copyback"
    --#SUMMARY         "Adapter %s: State change by user on disk (%s) from rebuilding to copyback (Server %s)"
    --#ARGUMENTS       { 2, 3, 0 }
    --#SEVERITY        INFORMATIONAL
    --#TIMEINDEX       1
    --#HELP            ""
    --#STATE           OPERATIONAL
    ::= 10776

-- EVT_PD_STATE_CHANGE_BY_USER_RBLD_TO_SYS

svrTrapPDStateChangeByUserRbldToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to JBOD."
    --#TYPE            "State change by user from rebuilding to JBOD"
    --#SUMMARY         "Adapter %s: State change by user on disk (%s) from rebuilding to JBOD (Server %s)"
    --#ARGUMENTS       { 2, 3, 0 }
    --#SEVERITY        INFORMATIONAL
    --#TIMEINDEX       1
    --#HELP            ""
    --#STATE           OPERATIONAL
    ::= 10777

-- EVT_PD_STATE_CHANGE_BY_USER_OP_TO_CB

svrTrapPDStateChangeByUserOpToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to copyback."
    --#TYPE            "State change by user from operational to copyback"
    --#SUMMARY         "Adapter %s: State change by user on disk (%s) from operational to copyback (Server %s)"
    --#ARGUMENTS       { 2, 3, 0 }
    --#SEVERITY        INFORMATIONAL
    --#TIMEINDEX       1
    --#HELP            ""
    --#STATE           OPERATIONAL
    ::= 10778

-- EVT_PD_STATE_CHANGE_BY_USER_OP_TO_SYS

svrTrapPDStateChangeByUserOpToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to JBOD."
    --#TYPE            "State change by user from operational to JBOD"
    --#SUMMARY         "Adapter %s: State change by user on disk (%s) from operational to JBOD (Server %s)"
    --#ARGUMENTS       { 2, 3, 0 }
    --#SEVERITY        INFORMATIONAL
    --#TIMEINDEX       1
    --#HELP            ""
    --#STATE           OPERATIONAL
    ::= 10779

-- EVT_PD_STATE_CHANGE_BY_USER_CB_TO_AVAIL

svrTrapPDStateChangeByUserCbToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to available."
    --#TYPE            "State change by user from copyback to available"
    --#SUMMARY         "Adapter %s: State change by user on disk (%s) from copyback to available (Server %s)"
    --#ARGUMENTS       { 2, 3, 0 }
    --#SEVERITY        INFORMATIONAL
    --#TIMEINDEX       1
    --#HELP            ""
    --#STATE           OPERATIONAL
    ::= 10780

-- EVT_PD_STATE_CHANGE_BY_USER_CB_TO_FAIL

svrTrapPDStateChangeByUserCbToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to failed."
    --#TYPE            "State change by user from copyback to failed"
    --#SUMMARY         "Adapter %s: State change by user on disk (%s) from copyback to failed (Server %s)"
    --#ARGUMENTS       { 2, 3, 0 }
    --#SEVERITY        CRITICAL
    --#TIMEINDEX       1
    --#HELP            "Replace affected disk."
    --#STATE           NONOPERATIONAL
    ::= 10781

-- EVT_PD_STATE_CHANGE_BY_USER_CB_TO_HS

svrTrapPDStateChangeByUserCbToHs TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to hot spare."
    --#TYPE            "State change by user from copyback to hot spare"
    --#SUMMARY         "Adapter %s: State change by user on disk (%s) from copyback to hot spare (Server %s)"
    --#ARGUMENTS       { 2, 3, 0 }
    --#SEVERITY        INFORMATIONAL
    --#TIMEINDEX       1
    --#HELP            ""
    --#STATE           OPERATIONAL
    ::= 10782

-- EVT_PD_STATE_CHANGE_BY_USER_CB_TO_OFFL

svrTrapPDStateChangeByUserCbToOffl TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to offline."
    --#TYPE            "State change by user from copyback to offline"
    --#SUMMARY         "Adapter %s: State change by user on disk (%s) from copyback to offline (Server %s)"
    --#ARGUMENTS       { 2, 3, 0 }
    --#SEVERITY        MINOR
    --#TIMEINDEX       1
    --#HELP            "For information only."
    --#STATE           DEGRADED
    ::= 10783

-- EVT_PD_STATE_CHANGE_BY_USER_CB_TO_OP

svrTrapPDStateChangeByUserCbToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to operational."
    --#TYPE            "State change by user from copyback to operational"
    --#SUMMARY         "Adapter %s: State change by user on disk (%s) from copyback to operational (Server %s)"
    --#ARGUMENTS       { 2, 3, 0 }
    --#SEVERITY        INFORMATIONAL
    --#TIMEINDEX       1
    --#HELP            ""
    --#STATE           OPERATIONAL
    ::= 10784

-- EVT_PD_STATE_CHANGE_BY_USER_CB_TO_RBLD

svrTrapPDStateChangeByUserCbToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to rebuilding."
    --#TYPE            "State change by user from copyback to rebuilding"
    --#SUMMARY         "Adapter %s: State change by user on disk (%s) from copyback to rebuilding (Server %s)"
    --#ARGUMENTS       { 2, 3, 0 }
    --#SEVERITY        INFORMATIONAL
    --#TIMEINDEX       1
    --#HELP            ""
    --#STATE           OPERATIONAL
    ::= 10785

-- EVT_PD_STATE_CHANGE_BY_USER_CB_TO_CB

svrTrapPDStateChangeByUserCbToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to copyback."
    --#TYPE            "State change by user from copyback to copyback"
    --#SUMMARY         "Adapter %s: State change by user on disk (%s) from copyback to copyback (Server %s)"
    --#ARGUMENTS       { 2, 3, 0 }
    --#SEVERITY        INFORMATIONAL
    --#TIMEINDEX       1
    --#HELP            ""
    --#STATE           OPERATIONAL
    ::= 10786

-- EVT_PD_STATE_CHANGE_BY_USER_CB_TO_SYS

svrTrapPDStateChangeByUserCbToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to JBOD."
    --#TYPE            "State change by user from copyback to JBOD"
    --#SUMMARY         "Adapter %s: State change by user on disk (%s) from copyback to JBOD (Server %s)"
    --#ARGUMENTS       { 2, 3, 0 }
    --#SEVERITY        INFORMATIONAL
    --#TIMEINDEX       1
    --#HELP            ""
    --#STATE           OPERATIONAL
    ::= 10787

-- EVT_PD_STATE_CHANGE_BY_USER_SYS_TO_AVAIL

svrTrapPDStateChangeByUserSysToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to available."
    --#TYPE            "State change by user from JBOD to available"
    --#SUMMARY         "Adapter %s: State change by user on disk (%s) from JBOD to available (Server %s)"
    --#ARGUMENTS       { 2, 3, 0 }
    --#SEVERITY        INFORMATIONAL
    --#TIMEINDEX       1
    --#HELP            ""
    --#STATE           OPERATIONAL
    ::= 10788

-- EVT_PD_STATE_CHANGE_BY_USER_SYS_TO_FAIL

svrTrapPDStateChangeByUserSysToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to failed."
    --#TYPE            "State change by user from JBOD to failed"
    --#SUMMARY         "Adapter %s: State change by user on disk (%s) from JBOD to failed (Server %s)"
    --#ARGUMENTS       { 2, 3, 0 }
    --#SEVERITY        CRITICAL
    --#TIMEINDEX       1
    --#HELP            "For information only."
    --#STATE           NONOPERATIONAL
    ::= 10789

-- EVT_PD_STATE_CHANGE_BY_USER_SYS_TO_HS

svrTrapPDStateChangeByUserSysToHs TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to hot spare."
    --#TYPE            "State change by user from JBOD to hot spare"
    --#SUMMARY         "Adapter %s: State change by user on disk (%s) from JBOD to hot spare (Server %s)"
    --#ARGUMENTS       { 2, 3, 0 }
    --#SEVERITY        INFORMATIONAL
    --#TIMEINDEX       1
    --#HELP            ""
    --#STATE           OPERATIONAL
    ::= 10790

-- EVT_PD_STATE_CHANGE_BY_USER_SYS_TO_OFFL

svrTrapPDStateChangeByUserSysToOffl TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to offline."
    --#TYPE            "State change by user from JBOD to offline"
    --#SUMMARY         "Adapter %s: State change by user on disk (%s) from JBOD to offline (Server %s)"
    --#ARGUMENTS       { 2, 3, 0 }
    --#SEVERITY        MINOR
    --#TIMEINDEX       1
    --#HELP            "For information only."
    --#STATE           DEGRADED
    ::= 10791

-- EVT_PD_STATE_CHANGE_BY_USER_SYS_TO_OP

svrTrapPDStateChangeByUserSysToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to operational."
    --#TYPE            "State change by user from JBOD to operational"
    --#SUMMARY         "Adapter %s: State change by user on disk (%s) from JBOD to operational (Server %s)"
    --#ARGUMENTS       { 2, 3, 0 }
    --#SEVERITY        INFORMATIONAL
    --#TIMEINDEX       1
    --#HELP            ""
    --#STATE           OPERATIONAL
    ::= 10792

-- EVT_PD_STATE_CHANGE_BY_USER_SYS_TO_RBLD

svrTrapPDStateChangeByUserSysToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to rebuilding."
    --#TYPE            "State change by user from JBOD to rebuilding"
    --#SUMMARY         "Adapter %s: State change by user on disk (%s) from JBOD to rebuilding (Server %s)"
    --#ARGUMENTS       { 2, 3, 0 }
    --#SEVERITY        INFORMATIONAL
    --#TIMEINDEX       1
    --#HELP            ""
    --#STATE           OPERATIONAL
    ::= 10793

-- EVT_PD_STATE_CHANGE_BY_USER_SYS_TO_CB

svrTrapPDStateChangeByUserSysToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to copyback."
    --#TYPE            "State change by user from JBOD to copyback"
    --#SUMMARY         "Adapter %s: State change by user on disk (%s) from JBOD to copyback (Server %s)"
    --#ARGUMENTS       { 2, 3, 0 }
    --#SEVERITY        INFORMATIONAL
    --#TIMEINDEX       1
    --#HELP            ""
    --#STATE           OPERATIONAL
    ::= 10794

-- EVT_PD_STATE_CHANGE_BY_USER_SYS_TO_SYS

svrTrapPDStateChangeByUserSysToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to JBOD."
    --#TYPE            "State change by user from JBOD to JBOD"
    --#SUMMARY         "Adapter %s: State change by user on disk (%s) from JBOD to JBOD (Server %s)"
    --#ARGUMENTS       { 2, 3, 0 }
    --#SEVERITY        INFORMATIONAL
    --#TIMEINDEX       1
    --#HELP            ""
    --#STATE           OPERATIONAL
    ::= 10795

-- EVT_PD_STATE_CHANGE_OFFL_TO_CB

svrTrapPDStateChangeOfflToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to copyback."
    --#TYPE            "State change from offline to copyback"
    --#SUMMARY         "Adapter %s: State change on disk (%s) from offline to copyback (Server %s)"
    --#ARGUMENTS       { 2, 3, 0 }
    --#SEVERITY        INFORMATIONAL
    --#TIMEINDEX       1
    --#HELP            ""
    --#STATE           OPERATIONAL
    ::= 10796

-- EVT_PD_STATE_CHANGE_BY_USER_OFFL_TO_CB

svrTrapPDStateChangeByUserOfflToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to copyback."
    --#TYPE            "State change by user from offline to copyback"
    --#SUMMARY         "Adapter %s: State change by user on disk (%s) from offline to copyback (Server %s)"
    --#ARGUMENTS       { 2, 3, 0 }
    --#SEVERITY        INFORMATIONAL
    --#TIMEINDEX       1
    --#HELP            ""
    --#STATE           OPERATIONAL
    ::= 10797

-- EVT_PD_STATE_CHANGE_OFFL_TO_SYS

svrTrapPDStateChangeOfflToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to JBOD."
    --#TYPE            "State change from offline to JBOD"
    --#SUMMARY         "Adapter %s: State change on disk (%s) from offline to JBOD (Server %s)"
    --#ARGUMENTS       { 2, 3, 0 }
    --#SEVERITY        INFORMATIONAL
    --#TIMEINDEX       1
    --#HELP            ""
    --#STATE           OPERATIONAL
    ::= 10798

-- EVT_PD_STATE_CHANGE_BY_USER_OFFL_TO_SYS

svrTrapPDStateChangeByUserOfflToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to JBOD."
    --#TYPE            "State change by user from offline to JBOD"
    --#SUMMARY         "Adapter %s: State change by user on disk (%s) from offline to JBOD (Server %s)"
    --#ARGUMENTS       { 2, 3, 0 }
    --#SEVERITY        INFORMATIONAL
    --#TIMEINDEX       1
    --#HELP            ""
    --#STATE           OPERATIONAL
    ::= 10799

-- EVT_CTRL_LOCK_KEY_EKM_MODE

svrTrapCtrlLockKeyEKMMode TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security is in external key management mode."
    --#TYPE            "Disk security is in external key management mode"
    --#SUMMARY         "Adapter %s: Disk security is in external key management mode (Server %s)"
    --#ARGUMENTS       { 2, 0 }
    --#SEVERITY        INFORMATIONAL
    --#TIMEINDEX       1
    --#HELP            ""
    --#STATE           OPERATIONAL
    ::= 10800

-- EVT_CTRL_LOCK_KEY_EKM_FAILURE

svrTrapCtrlLockKeyEKMFailure TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk security failed to communicate with external key management system."
    --#TYPE            "Disk security failed to communicate with external key management system"
    --#SUMMARY         "Adapter %s: Disk security failed to communicate with external key management system (Server %s)"
    --#ARGUMENTS       { 2, 0 }
    --#SEVERITY        MINOR
    --#TIMEINDEX       1
    --#HELP            "Call your local Fujitsu Helpdesk."
    --#STATE           OPERATIONAL
    ::= 10801

-- EVT_PD_LOCK_KEY_REQUIRED

svrTrapPDLockKeyRequired TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk needs key."
    --#TYPE            "Disk needs key"
    --#SUMMARY         "Adapter %s: Disk (%s) needs key to be %s %s (Server %s)"
    --#ARGUMENTS       { 2, 3, 4, 5, 0 }
    --#SEVERITY        INFORMATIONAL
    --#TIMEINDEX       1
    --#HELP            ""
    --#STATE           OPERATIONAL
    ::= 10802

-- EVT_LD_SECURE_FAILED

svrTrapLDSecureFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive secure failed."
    --#TYPE            "Logical drive secure failed"
    --#SUMMARY         "Adapter %s: Logical drive %s secure failed (Server %s)"
    --#ARGUMENTS       { 2, 3, 0 }
    --#SEVERITY        MINOR
    --#TIMEINDEX       1
    --#HELP            "For information only."
    --#STATE           OPERATIONAL
    ::= 10803

-- EVT_CTRL_ONLINE_RESET

svrTrapCtrlOnlineReset TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Controller encountered a fatal error and was reset."
    --#TYPE            "Controller encountered a fatal error and was reset"
    --#SUMMARY         "Adapter %s: Controller encountered a fatal error and was reset (Server %s)"
    --#ARGUMENTS       { 2, 0 }
    --#SEVERITY        MAJOR
    --#TIMEINDEX       1
    --#HELP            "1) Replace affected RAID controller."
    --#STATE           OPERATIONAL
    ::= 10804

-- EVT_CFG_CMD_LOST

svrTrapCfgCmdLost TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Configuration command could not be committed to disk."
    --#TYPE            "Configuration command could not be committed to disk"
    --#SUMMARY         "Adapter %s: Configuration command could not be committed to disk, please retry (Server %s)"
    --#ARGUMENTS       { 2, 0 }
    --#SEVERITY        MAJOR
    --#TIMEINDEX       1
    --#HELP            "Call your local Fujitsu Helpdesk."
    --#STATE           OPERATIONAL
    ::= 10805

-- EVT_PD_COD_STALE

svrTrapPDCODStale TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "COD on disk updated as it was stale."
    --#TYPE            "COD on disk updated as it was stale"
    --#SUMMARY         "Adapter %s: COD on disk (%s) updated as it was stale (Server %s)"
    --#ARGUMENTS       { 2, 3, 0 }
    --#SEVERITY        INFORMATIONAL
    --#TIMEINDEX       1
    --#HELP            ""
    --#STATE           OPERATIONAL
    ::= 10806

-- EVT_PD_POWER_STATE_CHANGE_ACTIVE_TO_STOP_FAILED

svrTrapPDPowerStateChangeActiveToStopFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change failed on disk (from active to stopped)."
    --#TYPE            "Power state change failed on disk (from active to stopped)"
    --#SUMMARY         "Adapter %s: Power state change failed on disk (%s) (from active to stopped) (Server %s)"
    --#ARGUMENTS       { 2, 3, 0 }
    --#SEVERITY        MINOR
    --#TIMEINDEX       1
    --#HELP            "Replace affected disk."
    --#STATE           OPERATIONAL
    ::= 10807

-- EVT_PD_POWER_STATE_CHANGE_STOP_TO_ACTIVE_FAILED

svrTrapPDPowerStateChangeStopToActiveFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change failed on disk (from stopped to active)."
    --#TYPE            "Power state change failed on disk (from stopped to active)"
    --#SUMMARY         "Adapter %s: Power state change failed on disk (%s) (from stopped to active) (Server %s)"
    --#ARGUMENTS       { 2, 3, 0 }
    --#SEVERITY        MINOR
    --#TIMEINDEX       1
    --#HELP            "Replace affected disk."
    --#STATE           OPERATIONAL
    ::= 10808

-- EVT_LD_NOT_READY

svrTrapLDNotReady TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is not ready."
    --#TYPE            "Logical drive is not ready"
    --#SUMMARY         "Adapter %s: Logical drive %s is not ready (Server %s)"
    --#ARGUMENTS       { 2, 3, 0 }
    --#SEVERITY        MINOR
    --#TIMEINDEX       1
    --#HELP            "For information only."
    --#STATE           OPERATIONAL
    ::= 10809

-- EVT_LD_IS_READY

svrTrapLDIsReady TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is ready."
    --#TYPE            "Logical drive is ready"
    --#SUMMARY         "Adapter %s: Logical drive %s is ready (Server %s)"
    --#ARGUMENTS       { 2, 3, 0 }
    --#SEVERITY        INFORMATIONAL
    --#TIMEINDEX       1
    --#HELP            ""
    --#STATE           OPERATIONAL
    ::= 10810

-- EVT_MAIL_SUCCESSFULLY_SENT

svrTrapMailSuccessfullySent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Test E-mail was sent successfully."
    --#TYPE            "Test E-mail was sent successfully"
    --#SUMMARY         "Test E-mail was sent successfully (Server %s)"
    --#ARGUMENTS       { 0 }
    --#SEVERITY        INFORMATIONAL
    --#TIMEINDEX       1
    --#HELP            ""
    --#STATE           OPERATIONAL
    ::= 10811

-- EVT_ADAPTER_REPLACED

svrTrapAdapterReplaced TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter has been replaced during reboot."
    --#TYPE            "Adapter has been replaced during reboot"
    --#SUMMARY         "Adapter %s: Adapter has been replaced during reboot (Server %s)"
    --#ARGUMENTS       { 2, 0 }
    --#SEVERITY        MINOR
    --#TIMEINDEX       1
    --#HELP            "For information only."
    --#STATE           OPERATIONAL
    ::= 10812

-- EVT_ENCL_POWER_REMOVED

svrTrapEnclPowerRemoved TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure power supply removed."
    --#TYPE            "Enclosure power supply removed"
    --#SUMMARY         "Adapter %s: Enclosure %s power supply %s removed (Server %s)"
    --#ARGUMENTS       { 2, 3, 4, 0 }
    --#SEVERITY        MINOR
    --#TIMEINDEX       1
    --#HELP            "For information only."
    --#STATE           OPERATIONAL
    ::= 10813

-- EVT_ENCL_POWER_SUPPLY_OFF

svrTrapEnclPowerSupplyOff TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure power supply turned off."
    --#TYPE            "Enclosure power supply turned off"
    --#SUMMARY         "Adapter %s: Enclosure %s power supply %s turned off (Server %s)"
    --#ARGUMENTS       { 2, 3, 4, 0 }
    --#SEVERITY        MINOR
    --#TIMEINDEX       1
    --#HELP            "For information only."
    --#STATE           OPERATIONAL
    ::= 10814

-- EVT_ENCL_POWER_INSERTED

svrTrapEnclPowerInserted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure power supply inserted."
    --#TYPE            "Enclosure power supply inserted"
    --#SUMMARY         "Adapter %s: Enclosure %s power supply %s inserted (Server %s)"
    --#ARGUMENTS       { 2, 3, 4, 0 }
    --#SEVERITY        INFORMATIONAL
    --#TIMEINDEX       1
    --#HELP            ""
    --#STATE           OPERATIONAL
    ::= 10815

-- EVT_ENCL_POWER_SUPPLY_ON

svrTrapEnclPowerSupplyOn TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure power supply turned on."
    --#TYPE            "Enclosure power supply turned on"
    --#SUMMARY         "Adapter %s: Enclosure %s power supply %s turned on (Server %s)"
    --#ARGUMENTS       { 2, 3, 4, 0 }
    --#SEVERITY        INFORMATIONAL
    --#TIMEINDEX       1
    --#HELP            ""
    --#STATE           OPERATIONAL
    ::= 10816

-- EVT_ENCL_TEMPERATURE_BELOW_WARNING

svrTrapEnclTemperatureBelowWarning TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure temperature sensor below warning threshold."
    --#TYPE            "Enclosure temperature sensor below warning threshold"
    --#SUMMARY         "Adapter %s: Enclosure %s temperature sensor %s below warning threshold (Server %s)"
    --#ARGUMENTS       { 2, 3, 4, 0 }
    --#SEVERITY        MINOR
    --#TIMEINDEX       1
    --#HELP            "1) Check environmental temperature."
    --#STATE           OPERATIONAL
    ::= 10817

-- EVT_ENCL_TEMPERATURE_BELOW_ERROR

svrTrapEnclTemperatureBelowError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure temperature sensor below error threshold."
    --#TYPE            "Enclosure temperature sensor below error threshold"
    --#SUMMARY         "Adapter %s: Enclosure %s temperature sensor %s below error threshold (Server %s)"
    --#ARGUMENTS       { 2, 3, 4, 0 }
    --#SEVERITY        MAJOR
    --#TIMEINDEX       1
    --#HELP            "1) Check environmental temperature."
    --#STATE           OPERATIONAL
    ::= 10818

-- EVT_ENCL_TEMPERATURE_ABOVE_WARNING

svrTrapEnclTemperatureAboveWarning TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure temperature sensor above warning threshold."
    --#TYPE            "Enclosure temperature sensor above warning threshold"
    --#SUMMARY         "Adapter %s: Enclosure %s temperature sensor %s above warning threshold (Server %s)"
    --#ARGUMENTS       { 2, 3, 4, 0 }
    --#SEVERITY        MINOR
    --#TIMEINDEX       1
    --#HELP            "1) Check installation of all air flow channels, closed housing, and unblocked louvers. 2) Check environmental temperature."
    --#STATE           OPERATIONAL
    ::= 10819

-- EVT_ENCL_TEMPERATURE_ABOVE_ERROR

svrTrapEnclTemperatureAboveError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure temperature sensor above error threshold."
    --#TYPE            "Enclosure temperature sensor above error threshold"
    --#SUMMARY         "Adapter %s: Enclosure %s temperature sensor %s above error threshold (Server %s)"
    --#ARGUMENTS       { 2, 3, 4, 0 }
    --#SEVERITY        MAJOR
    --#TIMEINDEX       1
    --#HELP            "1) Check installation of all air flow channels, closed housing, and unblocked louvers. 2) Check environmental temperature."
    --#STATE           OPERATIONAL
    ::= 10820

-- EVT_PD_POWER_STATE_CHANGE_ACTIVE_TO_TRANSITION

svrTrapPDPowerStateChangeActiveToTransition TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change on disk from active to transition."
    --#TYPE            "Power state change on disk from active to transition"
    --#SUMMARY         "Adapter %s: Power state change on disk (%s) from active to transition (Server %s)"
    --#ARGUMENTS       { 2, 3, 0 }
    --#SEVERITY        INFORMATIONAL
    --#TIMEINDEX       1
    --#HELP            ""
    --#STATE           OPERATIONAL
    ::= 10821

-- EVT_PD_POWER_STATE_CHANGE_ACTIVE_TO_TRANSITION_FAILED

svrTrapPDPowerStateChangeChangeActiveToTransitionFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change failed on disk (from active to transition)."
    --#TYPE            "Power state change failed on disk (from active to transition)"
    --#SUMMARY         "Adapter %s: Power state change failed on disk (%s) (from active to transition) (Server %s)"
    --#ARGUMENTS       { 2, 3, 0 }
    --#SEVERITY        MINOR
    --#TIMEINDEX       1
    --#HELP            "Replace affected disk."
    --#STATE           OPERATIONAL
    ::= 10822

-- EVT_PD_POWER_STATE_CHANGE_STOP_TO_TRANSITION

svrTrapPDPowerStateChangeStopToTransition TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change on disk from stopped to transition."
    --#TYPE            "Power state change on disk from stopped to transition"
    --#SUMMARY         "Adapter %s: Power state change on disk (%s) from stopped to transition (Server %s)"
    --#ARGUMENTS       { 2, 3, 0 }
    --#SEVERITY        INFORMATIONAL
    --#TIMEINDEX       1
    --#HELP            ""
    --#STATE           OPERATIONAL
    ::= 10823

-- EVT_PD_POWER_STATE_CHANGE_STOP_TO_TRANSITION_FAILED

svrTrapPDPowerStateChangeChangeStopToTransitionFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change failed on disk (from stopped to transition)."
    --#TYPE            "Power state change failed on disk (from stopped to transition)"
    --#SUMMARY         "Adapter %s: Power state change failed on disk (%s) (from stopped to transition) (Server %s)"
    --#ARGUMENTS       { 2, 3, 0 }
    --#SEVERITY        MINOR
    --#TIMEINDEX       1
    --#HELP            "Replace affected disk."
    --#STATE           OPERATIONAL
    ::= 10824

-- EVT_PD_POWER_STATE_CHANGE_TRANSITION_TO_ACTIVE

svrTrapPDPowerStateChangeTransitionToActive TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change on disk from transition to active."
    --#TYPE            "Power state change on disk from transition to active"
    --#SUMMARY         "Adapter %s: Power state change on disk (%s) from transition to active (Server %s)"
    --#ARGUMENTS       { 2, 3, 0 }
    --#SEVERITY        INFORMATIONAL
    --#TIMEINDEX       1
    --#HELP            ""
    --#STATE           OPERATIONAL
    ::= 10825

-- EVT_PD_POWER_STATE_CHANGE_TRANSITION_TO_ACTIVE_FAILED

svrTrapPDPowerStateChangeChangeTransitionToActiveFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change failed on disk (from transition to active)."
    --#TYPE            "Power state change failed on disk (from transition to active)"
    --#SUMMARY         "Adapter %s: Power state change failed on disk (%s) (from transition to active) (Server %s)"
    --#ARGUMENTS       { 2, 3, 0 }
    --#SEVERITY        MINOR
    --#TIMEINDEX       1
    --#HELP            "Replace affected disk."
    --#STATE           OPERATIONAL
    ::= 10826

-- EVT_PD_POWER_STATE_CHANGE_TRANSITION_TO_STOP

svrTrapPDPowerStateChangeTransitionToStop TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change on disk from transition to stopped."
    --#TYPE            "Power state change on disk from transition to stopped"
    --#SUMMARY         "Adapter %s: Power state change on disk (%s) from transition to stopped (Server %s)"
    --#ARGUMENTS       { 2, 3, 0 }
    --#SEVERITY        INFORMATIONAL
    --#TIMEINDEX       1
    --#HELP            ""
    --#STATE           OPERATIONAL
    ::= 10827

-- EVT_PD_POWER_STATE_CHANGE_TRANSITION_TO_STOP_FAILED

svrTrapPDPowerStateChangeChangeTransitionToStopFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power state change failed on disk (from transition to stopped)."
    --#TYPE            "Power state change failed on disk (from transition to stopped)"
    --#SUMMARY         "Adapter %s: Power state change failed on disk (%s) (from transition to stopped) (Server %s)"
    --#ARGUMENTS       { 2, 3, 0 }
    --#SEVERITY        MINOR
    --#TIMEINDEX       1
    --#HELP            "Replace affected disk."
    --#STATE           OPERATIONAL
    ::= 10828

-- EVT_CTRL_RESET_EXPANDER

svrTrapCtrlResetExpander TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reset on-board expander."
    --#TYPE            "Reset on-board expander"
    --#SUMMARY         "Adapter %s: Reset on-board expander (Server %s)"
    --#ARGUMENTS       { 2, 0 }
    --#SEVERITY        MINOR
    --#TIMEINDEX       1
    --#HELP            "For information only."
    --#STATE           OPERATIONAL
    ::= 10829

-- EVT_ENCL_TEMPERATURE_INCREASE

svrTrapEnclTemperatureIncrease TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure temperature sensor temperature increase detected."
    --#TYPE            "Enclosure temperature sensor temperature increase detected"
    --#SUMMARY         "Adapter %s: Enclosure %s temperature sensor %s temperature increase detected (Server %s)"
    --#ARGUMENTS       { 2, 3, 4, 0 }
    --#SEVERITY        INFORMATIONAL
    --#TIMEINDEX       1
    --#HELP            "For information only."
    --#STATE           OPERATIONAL
    ::= 10830

-- EVT_ENCL_TEMPERATURE_DROP

svrTrapEnclTemperatureDrop TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure temperature sensor temperature drop detected."
    --#TYPE            "Enclosure temperature sensor temperature drop detected"
    --#SUMMARY         "Adapter %s: Enclosure %s temperature sensor %s temperature drop detected (Server %s)"
    --#ARGUMENTS       { 2, 3, 4, 0 }
    --#SEVERITY        INFORMATIONAL
    --#TIMEINDEX       1
    --#HELP            "For information only."
    --#STATE           OPERATIONAL
    ::= 10831

-- EVT_ENCL_FAN_SPEED_LOW

svrTrapEnclFanSpeedLow TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure fan speed changed to low."
    --#TYPE            "Enclosure fan speed changed to low"
    --#SUMMARY         "Adapter %s: Enclosure %s fan %s speed changed to low (Server %s)"
    --#ARGUMENTS       { 2, 3, 4, 0 }
    --#SEVERITY        INFORMATIONAL
    --#TIMEINDEX       1
    --#HELP            ""
    --#STATE           OPERATIONAL
    ::= 10832

-- EVT_ENCL_FAN_SPEED_MEDIUM

svrTrapEnclFanSpeedMedium TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure fan speed changed to medium."
    --#TYPE            "Enclosure fan speed changed to medium"
    --#SUMMARY         "Adapter %s: Enclosure %s fan %s speed changed to medium (Server %s)"
    --#ARGUMENTS       { 2, 3, 4, 0 }
    --#SEVERITY        INFORMATIONAL
    --#TIMEINDEX       1
    --#HELP            ""
    --#STATE           OPERATIONAL
    ::= 10833

-- EVT_ENCL_FAN_SPEED_HIGH

svrTrapEnclFanSpeedHigh TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Enclosure fan speed changed to high."
    --#TYPE            "Enclosure fan speed changed to high"
    --#SUMMARY         "Adapter %s: Enclosure %s fan %s speed changed to high (Server %s)"
    --#ARGUMENTS       { 2, 3, 4, 0 }
    --#SEVERITY        INFORMATIONAL
    --#TIMEINDEX       1
    --#HELP            ""
    --#STATE           OPERATIONAL
    ::= 10834

-- EVT_PD_OFFLINE_EXCESSIVE_PHY_ERRORS

svrTrapPDOfflineExcessivePhyErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk will be set offline due to SAS/SATA interface error rate too high."
    --#TYPE            "Disk will be set offline due to SAS/SATA interface error rate too high"
    --#SUMMARY         "Adapter %s: Disk (%s) will be set offline due to SAS/SATA interface error rate too high (Server %s)"
    --#ARGUMENTS       { 2, 3, 0 }
    --#SEVERITY        INFORMATIONAL
    --#TIMEINDEX       1
    --#HELP            ""
    --#STATE           OPERATIONAL
    ::= 10835

-- EVT_PD_WRITE_CACHE_ENABLED

svrTrapPDWriteCacheEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write cache on disk enabled."
    --#TYPE            "Write cache on disk enabled"
    --#SUMMARY         "Adapter %s: Write cache on disk (%s) enabled (Server %s)"
    --#ARGUMENTS       { 2, 3, 0 }
    --#SEVERITY        INFORMATIONAL
    --#TIMEINDEX       1
    --#HELP            ""
    --#STATE           OPERATIONAL
    ::= 10836

-- EVT_PD_WRITE_CACHE_DISABLED

svrTrapPDWriteCacheDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write cache on disk disabled."
    --#TYPE            "Write cache on disk disabled"
    --#SUMMARY         "Adapter %s: Write cache on disk (%s) disabled (Server %s)"
    --#ARGUMENTS       { 2, 3, 0 }
    --#SEVERITY        INFORMATIONAL
    --#TIMEINDEX       1
    --#HELP            ""
    --#STATE           OPERATIONAL
    ::= 10837

-- EVT_PD_NCQ_ENABLED

svrTrapPDNCQEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Native Command Queuing on disk enabled."
    --#TYPE            "Native Command Queuing on disk enabled"
    --#SUMMARY         "Adapter %s: Native Command Queuing (NCQ) on disk (%s) enabled (Server %s)"
    --#ARGUMENTS       { 2, 3, 0 }
    --#SEVERITY        INFORMATIONAL
    --#TIMEINDEX       1
    --#HELP            ""
    --#STATE           OPERATIONAL
    ::= 10838

-- EVT_PD_NCQ_DISABLED

svrTrapPDNCQDisabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Native Command Queuing on disk disabled."
    --#TYPE            "Native Command Queuing on disk disabled"
    --#SUMMARY         "Adapter %s: Native Command Queuing (NCQ) on disk (%s) disabled (Server %s)"
    --#ARGUMENTS       { 2, 3, 0 }
    --#SEVERITY        INFORMATIONAL
    --#TIMEINDEX       1
    --#HELP            ""
    --#STATE           OPERATIONAL
    ::= 10839

-- EVT_AUTO_REBUILD_HOTSPARE

svrTrapAutoRebuildHotspare TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic rebuild will use hot spares."
    --#TYPE            "Automatic rebuild will use hot spares"
    --#SUMMARY         "Adapter %s: Automatic rebuild will use hot spares (Server %s)"
    --#ARGUMENTS       { 2, 0 }
    --#SEVERITY        INFORMATIONAL
    --#TIMEINDEX       1
    --#HELP            ""
    --#STATE           OPERATIONAL
    ::= 10840

-- EVT_AUTO_REBUILD_AVAILABLE_HOTSPARE

svrTrapAutoRebuildAvailableHotspare TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Automatic rebuild will use available disks and hot spares."
    --#TYPE            "Automatic rebuild will use available disks and hot spares"
    --#SUMMARY         "Adapter %s: Automatic rebuild will use available disks and hot spares (Server %s)"
    --#ARGUMENTS       { 2, 0 }
    --#SEVERITY        INFORMATIONAL
    --#TIMEINDEX       1
    --#HELP            ""
    --#STATE           OPERATIONAL
    ::= 10841

-- EVT_PATROL_READ_RATE_CHANGED

svrTrapPatrolReadRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read rate changed."
    --#TYPE            "Patrol Read rate changed"
    --#SUMMARY         "Adapter %s: Patrol Read rate changed (Server %s)"
    --#ARGUMENTS       { 2, 0 }
    --#SEVERITY        INFORMATIONAL
    --#TIMEINDEX       1
    --#HELP            ""
    --#STATE           OPERATIONAL
    ::= 10842

-- EVT_MIGRATION_RATE_CHANGED

svrTrapMigrationRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Migration rate changed."
    --#TYPE            "Migration rate changed"
    --#SUMMARY         "Adapter %s: Migration rate changed (Server %s)"
    --#ARGUMENTS       { 2, 0 }
    --#SEVERITY        INFORMATIONAL
    --#TIMEINDEX       1
    --#HELP            ""
    --#STATE           OPERATIONAL
    ::= 10843

-- EVT_INITIALIZATION_RATE_CHANGED

svrTrapInitializationRateChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization rate changed."
    --#TYPE            "Initialization rate changed"
    --#SUMMARY         "Adapter %s: Initialization rate changed (Server %s)"
    --#ARGUMENTS       { 2, 0 }
    --#SEVERITY        INFORMATIONAL
    --#TIMEINDEX       1
    --#HELP            ""
    --#STATE           OPERATIONAL
    ::= 10844

-- EVT_CHECK_RESUMED

svrTrapConsistencyCheckContinuedOnLogicalDrive TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check resumed on logical drive."
    --#TYPE            "Consistency check resumed on logical drive"
    --#SUMMARY         "Adapter %s: Consistency check resumed on logical drive %s (Server %s)"
    --#ARGUMENTS       { 2, 3, 0 }
    --#SEVERITY        INFORMATIONAL
    --#TIMEINDEX       1
    --#HELP            ""
    --#STATE           OPERATIONAL
    ::= 10845

-- EVT_CHECK_REJECTED

svrTrapConsistencyCheckRejectedOnLogicalDrive TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Consistency check rejected on uninitialized logical drive."
    --#TYPE            "Consistency check rejected on uninitialized logical drive"
    --#SUMMARY         "Adapter %s: Consistency check rejected on uninitialized logical drive %s (Server %s)"
    --#ARGUMENTS       { 2, 3, 0 }
    --#SEVERITY        MINOR
    --#TIMEINDEX       1
    --#HELP            "Initiate manual MDC to initialize the logical drive."
    --#STATE           OPERATIONAL
    ::= 10846

-- EVT_INITIALIZATION_PAUSED

svrTrapLDInitPaused TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization suspended on logical drive."
    --#TYPE            "Initialization suspended on logical drive"
    --#SUMMARY         "Adapter %s: Initialization suspended on logical drive %s (Server %s)"
    --#ARGUMENTS       { 2, 3, 0 }
    --#SEVERITY        INFORMATIONAL
    --#TIMEINDEX       1
    --#HELP            ""
    --#STATE           OPERATIONAL
    ::= 10847

-- EVT_INITIALIZATION_RESUMED

svrTrapLDInitResumed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Initialization resumed on logical drive."
    --#TYPE            "Initialization resumed on logical drive"
    --#SUMMARY         "Adapter %s: Initialization resumed on logical drive %s (Server %s)"
    --#ARGUMENTS       { 2, 3, 0 }
    --#SEVERITY        INFORMATIONAL
    --#TIMEINDEX       1
    --#HELP            ""
    --#STATE           OPERATIONAL
    ::= 10848

-- EVT_LD_IS_SSC

svrTrapLDIsSSC TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is used for CacheCade."
    --#TYPE            "Logical drive is used for CacheCade"
    --#SUMMARY         "Adapter %s: Logical drive %s is used for CacheCade with capacity %s MB (Server %s)"
    --#ARGUMENTS       { 2, 3, 4, 0 }
    --#SEVERITY        INFORMATIONAL
    --#TIMEINDEX       1
    --#HELP            ""
    --#STATE           OPERATIONAL
    ::= 10849

-- EVT_LD_IS_USING_SSC

svrTrapLDIsUsingSSC TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is using CacheCade."
    --#TYPE            "Logical drive is using CacheCade"
    --#SUMMARY         "Adapter %s: Logical drive %s is using CacheCade %s (Server %s)"
    --#ARGUMENTS       { 2, 3, 4, 0 }
    --#SEVERITY        INFORMATIONAL
    --#TIMEINDEX       1
    --#HELP            ""
    --#STATE           OPERATIONAL
    ::= 10850

-- EVT_LD_IS_NOT_USING_SSC

svrTrapLDIsNotUsingSSC TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is no longer using CacheCade."
    --#TYPE            "Logical drive is no longer using CacheCade"
    --#SUMMARY         "Adapter %s: Logical drive %s is no longer using CacheCade %s (Server %s)"
    --#ARGUMENTS       { 2, 3, 4, 0 }
    --#SEVERITY        INFORMATIONAL
    --#TIMEINDEX       1
    --#HELP            ""
    --#STATE           OPERATIONAL
    ::= 10851

-- EVT_LD_SSC_SIZE_CHANGED

svrTrapLDSSCSizeChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "CacheCade capacity changed."
    --#TYPE            "CacheCade capacity changed"
    --#SUMMARY         "Adapter %s: CacheCade %s capacity changed and is now %s MB (Server %s)"
    --#ARGUMENTS       { 2, 3, 4, 0 }
    --#SEVERITY        MINOR
    --#TIMEINDEX       1
    --#HELP            "For information only."
    --#STATE           OPERATIONAL
    ::= 10852

-- EVT_BBU_CANNOT_DO_TRANSPARENT_LEARN

svrTrapBBUCannotDoTransparentLearn TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU life has degraded and cannot initiate transparent learn cycles."
    --#TYPE            "BBU life has degraded and cannot initiate transparent learn cycles"
    --#SUMMARY         "Adapter %s: BBU life has degraded and cannot initiate transparent learn cycles (Server %s)"
    --#ARGUMENTS       { 2, 0 }
    --#SEVERITY        MINOR
    --#TIMEINDEX       1
    --#HELP            "1) Initiate manual relearn cycle. 2) If problem persists replace BBU."
    --#STATE           OPERATIONAL
    ::= 10853

-- EVT_CTRL_PFK_APPLIED

svrTrapCtrlPFKApplied TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MegaRAID Advanced Software Options key applied."
    --#TYPE            "MegaRAID Advanced Software Options key applied"
    --#SUMMARY         "Adapter %s: MegaRAID Advanced Software Options (%s) key applied (Server %s)"
    --#ARGUMENTS       { 2, 3, 0 }
    --#SEVERITY        INFORMATIONAL
    --#TIMEINDEX       1
    --#HELP            ""
    --#STATE           OPERATIONAL
    ::= 10854

-- EVT_CTRL_PFK_TRANSFERRED

svrTrapCtrlPFKTransferred TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MegaRAID Advanced Software Options key transferred."
    --#TYPE            "MegaRAID Advanced Software Options key transferred"
    --#SUMMARY         "Adapter %s: MegaRAID Advanced Software Options (%s) key transferred (Server %s)"
    --#ARGUMENTS       { 2, 3, 0 }
    --#SEVERITY        INFORMATIONAL
    --#TIMEINDEX       1
    --#HELP            ""
    --#STATE           OPERATIONAL
    ::= 10855

-- EVT_CTRL_PFK_SERIALNUM

svrTrapCtrlPFKSerialnum TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MegaRAID Advanced Software Options serial number."
    --#TYPE            "MegaRAID Advanced Software Options serial number"
    --#SUMMARY         "Adapter %s: MegaRAID Advanced Software Options serial number %s (Server %s)"
    --#ARGUMENTS       { 2, 3, 0 }
    --#SEVERITY        INFORMATIONAL
    --#TIMEINDEX       1
    --#HELP            ""
    --#STATE           OPERATIONAL
    ::= 10856

-- EVT_CTRL_PFK_SERIALNUM_MISMATCH

svrTrapCtrlPFKSerialnumMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MegaRAID Advanced Software Options serial number mismatch."
    --#TYPE            "MegaRAID Advanced Software Options serial number mismatch"
    --#SUMMARY         "Adapter %s: MegaRAID Advanced Software Options serial number mismatch. Key Vault serial number is %s (Server %s)"
    --#ARGUMENTS       { 2, 3, 0 }
    --#SEVERITY        MINOR
    --#TIMEINDEX       1
    --#HELP            "Controller serial number does not match with MegaRAID Advanced Software Options key. Apply key to appropriate controller."
    --#STATE           OPERATIONAL
    ::= 10857

-- EVT_BBU_REPLACEMENT_NEEDED_SOH_NOT_OPTIMAL

svrTrapBBUReplacementNeededSOHNotOptimal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU cannot support data retention."
    --#TYPE            "BBU cannot support data retention"
    --#SUMMARY         "Adapter %s: BBU cannot support data retention for more than %s hours (Server %s)"
    --#ARGUMENTS       { 2, 3, 0 }
    --#SEVERITY        MINOR
    --#TIMEINDEX       1
    --#HELP            "BBU capacity is decreased and buffering of data in controller cache is limited. To reach full data retention time replace BBU."
    --#STATE           OPERATIONAL
    ::= 10858

-- EVT_LD_POWER_STATE_CHANGE

svrTrapLDPowerStateChange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive power policy changed."
    --#TYPE            "Logical drive power policy changed"
    --#SUMMARY         "Adapter %s: Logical drive %s: %s changed (Server %s)"
    --#ARGUMENTS       { 2, 3, 4, 0 }
    --#SEVERITY        INFORMATIONAL
    --#TIMEINDEX       1
    --#HELP            ""
    --#STATE           OPERATIONAL
    ::= 10859

-- EVT_LD_POWER_STATE_MAX_UNAVAILABLE

svrTrapLDPowerStateMaxUnavailable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive cannot transition to maximum power savings."
    --#TYPE            "Logical drive cannot transition to maximum power savings"
    --#SUMMARY         "Adapter %s: Logical drive %s cannot transition to maximum power savings (Server %s)"
    --#ARGUMENTS       { 2, 3, 0 }
    --#SEVERITY        MINOR
    --#TIMEINDEX       1
    --#HELP            "For information only."
    --#STATE           OPERATIONAL
    ::= 10860

-- EVT_CTRL_HOST_DRIVER_LOADED

svrTrapCtrlHostDriverLoaded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Driver is loaded and operational."
    --#TYPE            "Driver is loaded and operational"
    --#SUMMARY         "Adapter %s: Driver is loaded and operational (Server %s)"
    --#ARGUMENTS       { 2, 0 }
    --#SEVERITY        INFORMATIONAL
    --#TIMEINDEX       1
    --#HELP            ""
    --#STATE           OPERATIONAL
    ::= 10861

-- EVT_LD_MIRROR_BROKEN

svrTrapLDMirrorBroken TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive mirror broken."
    --#TYPE            "Logical drive mirror broken"
    --#SUMMARY         "Adapter %s: Logical drive %s mirror broken (Server %s)"
    --#ARGUMENTS       { 2, 3, 0 }
    --#SEVERITY        INFORMATIONAL
    --#TIMEINDEX       1
    --#HELP            ""
    --#STATE           OPERATIONAL
    ::= 10862

-- EVT_LD_MIRROR_JOINED

svrTrapLDMirrorJoined TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive mirror joined."
    --#TYPE            "Logical drive mirror joined"
    --#SUMMARY         "Adapter %s: Logical drive %s mirror joined (Server %s)"
    --#ARGUMENTS       { 2, 3, 0 }
    --#SEVERITY        INFORMATIONAL
    --#TIMEINDEX       1
    --#HELP            ""
    --#STATE           OPERATIONAL
    ::= 10863

-- EVT_PD_SAS_WIDE_PORT_LINK_FAILURE

svrTrapPDSASWidePortLinkFailure TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk link failed in SAS wide port."
    --#TYPE            "Disk link failed in SAS wide port"
    --#SUMMARY         "Adapter %s: Disk (%s) link %s failed in SAS wide port (Server %s)"
    --#ARGUMENTS       { 2, 3, 4, 0 }
    --#SEVERITY        MINOR
    --#TIMEINDEX       1
    --#HELP            "1) Unplug affected disk, wait 30 seconds, reinsert it. 2) Check/replace cable between controller and affected disk. 3) Check version of RAID controller/iRMC firmware, and BIOS. 4) Replace affected disk."
    --#STATE           OPERATIONAL
    ::= 10864

-- EVT_PD_SAS_WIDE_PORT_LINK_RESTORED

svrTrapPDSASWidePortLinkRestored TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk link restored in SAS wide port."
    --#TYPE            "Disk link restored in SAS wide port"
    --#SUMMARY         "Adapter %s: Disk (%s) link %s restored in SAS wide port (Server %s)"
    --#ARGUMENTS       { 2, 3, 4, 0 }
    --#SEVERITY        INFORMATIONAL
    --#TIMEINDEX       1
    --#HELP            ""
    --#STATE           OPERATIONAL
    ::= 10865

-- EVT_TMM_FRU

svrTrapTMMFRU TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Memory module FRU."
    --#TYPE            "Memory module FRU"
    --#SUMMARY         "Adapter %s: Memory module FRU is %s (Server %s)"
    --#ARGUMENTS       { 2, 3, 0 }
    --#SEVERITY        INFORMATIONAL
    --#TIMEINDEX       1
    --#HELP            ""
    --#STATE           OPERATIONAL
    ::= 10866

-- EVT_BBU_REPLACEMENT_NEEDED

svrTrapBBUReplacementNeeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU power pack is sub-optimal."
    --#TYPE            "FBU power pack is sub-optimal"
    --#SUMMARY         "Adapter %s: FBU power pack is sub-optimal (Server %s)"
    --#ARGUMENTS       { 2, 0 }
    --#SEVERITY        MINOR
    --#TIMEINDEX       1
    --#HELP            "1) Replace FBU."
    --#STATE           OPERATIONAL
    ::= 10867

-- EVT_FOREIGN_CFG_AUTO_IMPORT_NONE

svrTrapForeignConfigAutoImportNone TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Foreign configuration auto-import did not import any drives."
    --#TYPE            "Foreign configuration auto-import did not import any drives"
    --#SUMMARY         "Adapter %s: Foreign configuration auto-import did not import any drives (Server %s)"
    --#ARGUMENTS       { 2, 0 }
    --#SEVERITY        MINOR
    --#TIMEINDEX       1
    --#HELP            "Attempt to import a foreign config failed. 1) Call your local Fujitsu Helpdesk."
    --#STATE           OPERATIONAL
    ::= 10868

-- EVT_BBU_MICROCODE_UPDATE_REQUIRED

svrTrapBBUMicrocodeUpdateRequired TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU firmware update required."
    --#TYPE            "FBU firmware update required"
    --#SUMMARY         "Adapter %s: FBU firmware update required (Server %s)"
    --#ARGUMENTS       { 2, 0 }
    --#SEVERITY        MINOR
    --#TIMEINDEX       1
    --#HELP            "1) Call your local Fujitsu Helpdesk."
    --#STATE           OPERATIONAL
    ::= 10869

-- EVT_LD_SSC_SIZE_EXCEEDED

svrTrapLDSSCSizeExceeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "CacheCade capacity exceeds maximum allowed size."
    --#TYPE            "CacheCade capacity exceeds maximum allowed size"
    --#SUMMARY         "Adapter %s: CacheCade %s capacity exceeds maximum allowed size of %s MB, extra capacity is not used (Server %s)"
    --#ARGUMENTS       { 2, 3, 4, 0 }
    --#SEVERITY        MINOR
    --#TIMEINDEX       1
    --#HELP            "Call your local Fujitsu Helpdesk."
    --#STATE           OPERATIONAL
    ::= 10870

-- EVT_LD_PI_LOST

svrTrapLDPILost TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive protection information lost."
    --#TYPE            "Logical drive protection information lost"
    --#SUMMARY         "Adapter %s: Logical drive %s protection information lost (Server %s)"
    --#ARGUMENTS       { 2, 3, 0 }
    --#SEVERITY        MINOR
    --#TIMEINDEX       1
    --#HELP            "1) Call your local Fujitsu Helpdesk."
    --#STATE           OPERATIONAL
    ::= 10871

-- EVT_PD_SHIELD_DIAG_PASS

svrTrapPDShieldDiagPass TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Diagnostics passed for disk."
    --#TYPE            "Diagnostics passed for disk"
    --#SUMMARY         "Adapter %s: Diagnostics passed for disk (%s) (Server %s)"
    --#ARGUMENTS       { 2, 3, 0 }
    --#SEVERITY        INFORMATIONAL
    --#TIMEINDEX       1
    --#HELP            ""
    --#STATE           OPERATIONAL
    ::= 10872

-- EVT_PD_SHIELD_DIAG_FAIL

svrTrapPDShieldDiagFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Diagnostics failed for disk."
    --#TYPE            "Diagnostics failed for disk"
    --#SUMMARY         "Adapter %s: Diagnostics failed for disk (%s) (Server %s)"
    --#ARGUMENTS       { 2, 3, 0 }
    --#SEVERITY        MAJOR
    --#TIMEINDEX       1
    --#HELP            "Replace affected disk."
    --#STATE           OPERATIONAL
    ::= 10873

-- EVT_CTRL_SERVER_POWER_DIAG_STARTED

svrTrapCtrlServerPowerDiagStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Server power capability diagnostic test started."
    --#TYPE            "Server power capability diagnostic test started"
    --#SUMMARY         "Adapter %s: Server power capability diagnostic test started (Server %s)"
    --#ARGUMENTS       { 2, 0 }
    --#SEVERITY        INFORMATIONAL
    --#TIMEINDEX       1
    --#HELP            ""
    --#STATE           OPERATIONAL
    ::= 10874

-- EVT_PD_RBLD_DRIVE_CACHE_ENABLED

svrTrapPDRbldDriveCacheEnabled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk cache settings enabled during rebuild for disk."
    --#TYPE            "Disk cache settings enabled during rebuild for disk"
    --#SUMMARY         "Adapter %s: Disk cache settings enabled during rebuild for disk (%s) (Server %s)"
    --#ARGUMENTS       { 2, 3, 0 }
    --#SEVERITY        INFORMATIONAL
    --#TIMEINDEX       1
    --#HELP            ""
    --#STATE           OPERATIONAL
    ::= 10875

-- EVT_PD_RBLD_DRIVE_CACHE_RESTORED

svrTrapPDRbldDriveCacheRestored TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk cache settings restored after rebuild for disk."
    --#TYPE            "Disk cache settings restored after rebuild for disk"
    --#SUMMARY         "Adapter %s: Disk cache settings restored after rebuild for disk (%s) (Server %s)"
    --#ARGUMENTS       { 2, 3, 0 }
    --#SEVERITY        INFORMATIONAL
    --#TIMEINDEX       1
    --#HELP            ""
    --#STATE           OPERATIONAL
    ::= 10876

-- EVT_PD_EMERGENCY_SPARE_COMMISSIONED

svrTrapPDEmergencySpareCommissioned TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk commissioned as emergency spare."
    --#TYPE            "Disk commissioned as emergency spare"
    --#SUMMARY         "Adapter %s: Disk (%s) commissioned as emergency spare (Server %s)"
    --#ARGUMENTS       { 2, 3, 0 }
    --#SEVERITY        INFORMATIONAL
    --#TIMEINDEX       1
    --#HELP            ""
    --#STATE           OPERATIONAL
    ::= 10877

-- EVT_PD_EMERGENCY_SPARE_COMMISSIONED_REMINDER

svrTrapPDEmergencySpareCommissionedReminder TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reminder: Potential non-optimal configuration because disk is commissioned as emergency spare."
    --#TYPE            "Reminder: Potential non-optimal configuration because disk is commissioned as emergency spare"
    --#SUMMARY         "Adapter %s: Reminder: Potential non-optimal configuration because disk (%s) is commissioned as emergency spare (Server %s)"
    --#ARGUMENTS       { 2, 3, 0 }
    --#SEVERITY        MINOR
    --#TIMEINDEX       1
    --#HELP            "For information only."
    --#STATE           OPERATIONAL
    ::= 10878

-- EVT_LD_BGI_SUSPENDED

svrTrapLDBGISuspended TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI suspended on logical drive."
    --#TYPE            "BGI suspended on logical drive"
    --#SUMMARY         "Adapter %s: BGI suspended on logical drive %s (Server %s)"
    --#ARGUMENTS       { 2, 3, 0 }
    --#SEVERITY        INFORMATIONAL
    --#TIMEINDEX       1
    --#HELP            ""
    --#STATE           OPERATIONAL
    ::= 10879

-- EVT_LD_BGI_RESUMED

svrTrapLDBGIResumed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BGI resumed on logical drive."
    --#TYPE            "BGI resumed on logical drive"
    --#SUMMARY         "Adapter %s: BGI resumed on logical drive %s (Server %s)"
    --#ARGUMENTS       { 2, 3, 0 }
    --#SEVERITY        INFORMATIONAL
    --#TIMEINDEX       1
    --#HELP            ""
    --#STATE           OPERATIONAL
    ::= 10880

-- EVT_LD_RECON_SUSPENDED

svrTrapLDReconSuspended TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Migration suspended on logical drive."
    --#TYPE            "Migration suspended on logical drive"
    --#SUMMARY         "Adapter %s: Migration suspended on logical drive %s (Server %s)"
    --#ARGUMENTS       { 2, 3, 0 }
    --#SEVERITY        INFORMATIONAL
    --#TIMEINDEX       1
    --#HELP            ""
    --#STATE           OPERATIONAL
    ::= 10881

-- EVT_PD_COPYBACK_SUSPENDED

svrTrapPDCopybackSuspended TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Copyback suspended on disk."
    --#TYPE            "Copyback suspended on disk"
    --#SUMMARY         "Adapter %s: Copyback suspended on disk (%s) (Server %s)"
    --#ARGUMENTS       { 2, 3, 0 }
    --#SEVERITY        INFORMATIONAL
    --#TIMEINDEX       1
    --#HELP            ""
    --#STATE           OPERATIONAL
    ::= 10882

-- EVT_LD_CC_SUSPENDED_REMINDER

svrTrapLDCCSuspendedReminder TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reminder: MDC suspended on logical drive."
    --#TYPE            "Reminder: MDC suspended on logical drive"
    --#SUMMARY         "Adapter %s: Reminder: MDC suspended on logical drive %s (Server %s)"
    --#ARGUMENTS       { 2, 3, 0 }
    --#SEVERITY        INFORMATIONAL
    --#TIMEINDEX       1
    --#HELP            ""
    --#STATE           OPERATIONAL
    ::= 10883

-- EVT_LD_BGI_SUSPENDED_REMINDER

svrTrapLDBGISuspendedReminder TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reminder: BGI suspended on logical drive."
    --#TYPE            "Reminder: BGI suspended on logical drive"
    --#SUMMARY         "Adapter %s: Reminder: BGI suspended on logical drive %s (Server %s)"
    --#ARGUMENTS       { 2, 3, 0 }
    --#SEVERITY        INFORMATIONAL
    --#TIMEINDEX       1
    --#HELP            ""
    --#STATE           OPERATIONAL
    ::= 10884

-- EVT_LD_RECON_SUSPENDED_REMINDER

svrTrapLDReconSuspendedReminder TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reminder: Migration suspended on logical drive."
    --#TYPE            "Reminder: Migration suspended on logical drive"
    --#SUMMARY         "Adapter %s: Reminder: Migration suspended on logical drive %s (Server %s)"
    --#ARGUMENTS       { 2, 3, 0 }
    --#SEVERITY        INFORMATIONAL
    --#TIMEINDEX       1
    --#HELP            ""
    --#STATE           OPERATIONAL
    ::= 10885

-- EVT_PD_RBLD_SUSPENDED_REMINDER

svrTrapPDRbldSuspendedReminder TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reminder: Rebuild suspended on disk."
    --#TYPE            "Reminder: Rebuild suspended on disk"
    --#SUMMARY         "Adapter %s: Reminder: Rebuild suspended on disk (%s) (Server %s)"
    --#ARGUMENTS       { 2, 3, 0 }
    --#SEVERITY        INFORMATIONAL
    --#TIMEINDEX       1
    --#HELP            ""
    --#STATE           OPERATIONAL
    ::= 10886

-- EVT_PD_COPYBACK_SUSPENDED_REMINDER

svrTrapPDCopybackSuspendedReminder TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reminder: Copyback suspended on disk."
    --#TYPE            "Reminder: Copyback suspended on disk"
    --#SUMMARY         "Adapter %s: Reminder: Copyback suspended on disk (%s) (Server %s)"
    --#ARGUMENTS       { 2, 3, 0 }
    --#SEVERITY        INFORMATIONAL
    --#TIMEINDEX       1
    --#HELP            ""
    --#STATE           OPERATIONAL
    ::= 10887

-- EVT_CTRL_PR_SUSPENDED_REMINDER

svrTrapCtrlPRSuspendedReminder TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reminder: Patrol Read suspended."
    --#TYPE            "Reminder: Patrol Read suspended"
    --#SUMMARY         "Adapter %s: Reminder: Patrol Read suspended (Server %s)"
    --#ARGUMENTS       { 2, 0 }
    --#SEVERITY        INFORMATIONAL
    --#TIMEINDEX       1
    --#HELP            ""
    --#STATE           OPERATIONAL
    ::= 10888

-- EVT_PD_ERASE_ABORTED

svrTrapPDEraseAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase aborted on disk."
    --#TYPE            "Erase aborted on disk"
    --#SUMMARY         "Adapter %s: Erase aborted on disk (%s) (Server %s)"
    --#ARGUMENTS       { 2, 3, 0 }
    --#SEVERITY        INFORMATIONAL
    --#TIMEINDEX       1
    --#HELP            ""
    --#STATE           OPERATIONAL
    ::= 10889

-- EVT_PD_ERASE_FAILED

svrTrapPDEraseFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase failed on disk."
    --#TYPE            "Erase failed on disk"
    --#SUMMARY         "Adapter %s: Erase failed on disk (%s) (error %s) (Server %s)"
    --#ARGUMENTS       { 2, 3, 4, 0 }
    --#SEVERITY        MAJOR
    --#TIMEINDEX       1
    --#HELP            "1) Call your local Fujitsu Helpdesk."
    --#STATE           OPERATIONAL
    ::= 10890

-- EVT_PD_ERASE_PROGRESS

svrTrapPDEraseProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase progress on disk."
    --#TYPE            "Erase progress on disk"
    --#SUMMARY         "Adapter %s: Erase progress on disk (%s) is %s (Server %s)"
    --#ARGUMENTS       { 2, 3, 4, 0 }
    --#SEVERITY        INFORMATIONAL
    --#TIMEINDEX       1
    --#HELP            ""
    --#STATE           OPERATIONAL
    ::= 10891

-- EVT_PD_ERASE_STARTED

svrTrapPDEraseStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase started on disk."
    --#TYPE            "Erase started on disk"
    --#SUMMARY         "Adapter %s: Erase started on disk (%s) (Server %s)"
    --#ARGUMENTS       { 2, 3, 0 }
    --#SEVERITY        INFORMATIONAL
    --#TIMEINDEX       1
    --#HELP            ""
    --#STATE           OPERATIONAL
    ::= 10892

-- EVT_PD_ERASE_SUCCESSFUL

svrTrapPDEraseSuccessful TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase finished on disk."
    --#TYPE            "Erase finished on disk"
    --#SUMMARY         "Adapter %s: Erase finished on disk (%s) (Server %s)"
    --#ARGUMENTS       { 2, 3, 0 }
    --#SEVERITY        INFORMATIONAL
    --#TIMEINDEX       1
    --#HELP            ""
    --#STATE           OPERATIONAL
    ::= 10893

-- EVT_LD_ERASE_ABORTED

svrTrapLDEraseAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase aborted on logical drive."
    --#TYPE            "Erase aborted on logical drive"
    --#SUMMARY         "Adapter %s: Erase aborted on logical drive %s (Server %s)"
    --#ARGUMENTS       { 2, 3, 0 }
    --#SEVERITY        INFORMATIONAL
    --#TIMEINDEX       1
    --#HELP            ""
    --#STATE           OPERATIONAL
    ::= 10894

-- EVT_LD_ERASE_FAILED

svrTrapLDEraseFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase failed on logical drive."
    --#TYPE            "Erase failed on logical drive"
    --#SUMMARY         "Adapter %s: Erase failed on logical drive %s (Server %s)"
    --#ARGUMENTS       { 2, 3, 0 }
    --#SEVERITY        MAJOR
    --#TIMEINDEX       1
    --#HELP            "1) Call your local Fujitsu Helpdesk."
    --#STATE           OPERATIONAL
    ::= 10895

-- EVT_LD_ERASE_PROGRESS

svrTrapLDEraseProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase progress on logical drive."
    --#TYPE            "Erase progress on logical drive"
    --#SUMMARY         "Adapter %s: Erase progress on logical drive %s is %s (Server %s)"
    --#ARGUMENTS       { 2, 3, 4, 0 }
    --#SEVERITY        INFORMATIONAL
    --#TIMEINDEX       1
    --#HELP            ""
    --#STATE           OPERATIONAL
    ::= 10896

-- EVT_LD_ERASE_START

svrTrapLDEraseStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase started on logical drive."
    --#TYPE            "Erase started on logical drive"
    --#SUMMARY         "Adapter %s: Erase started on logical drive %s (Server %s)"
    --#ARGUMENTS       { 2, 3, 0 }
    --#SEVERITY        INFORMATIONAL
    --#TIMEINDEX       1
    --#HELP            ""
    --#STATE           OPERATIONAL
    ::= 10897

-- EVT_LD_ERASE_SUCCESSFUL

svrTrapLDEraseSuccessful TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Erase finished on logical drive."
    --#TYPE            "Erase finished on logical drive"
    --#SUMMARY         "Adapter %s: Erase finished on logical drive %s (Server %s)"
    --#ARGUMENTS       { 2, 3, 0 }
    --#SEVERITY        INFORMATIONAL
    --#TIMEINDEX       1
    --#HELP            ""
    --#STATE           OPERATIONAL
    ::= 10898

-- EVT_LD_ERASE_POTENTIAL_LEAKAGE

svrTrapLDErasePotentialLeakage TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Potential leakage during erase on logical drive."
    --#TYPE            "Potential leakage during erase on logical drive"
    --#SUMMARY         "Adapter %s: Potential leakage during erase on logical drive %s (Server %s)"
    --#ARGUMENTS       { 2, 3, 0 }
    --#SEVERITY        MINOR
    --#TIMEINDEX       1
    --#HELP            "1) Call your local Fujitsu Helpdesk."
    --#STATE           OPERATIONAL
    ::= 10899

-- EVT_BBU_CHARGE_DISABLED_OTC

svrTrapBBUChargeDisabledOTC TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU charging was suspended due to high BBU temperature."
    --#TYPE            "BBU charging was suspended due to high BBU temperature"
    --#SUMMARY         "Adapter %s: BBU charging was suspended due to high BBU temperature (Server %s)"
    --#ARGUMENTS       { 2, 0 }
    --#SEVERITY        MINOR
    --#TIMEINDEX       1
    --#HELP            "Bring system back to normal operating temperature."
    --#STATE           OPERATIONAL
    ::= 10900

-- EVT_BBU_MICROCODE_UPDATED

svrTrapBBUMicrocodeUpdated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU firmware update finished."
    --#TYPE            "FBU firmware update finished"
    --#SUMMARY         "Adapter %s: FBU firmware update finished (Server %s)"
    --#ARGUMENTS       { 2, 0 }
    --#SEVERITY        INFORMATIONAL
    --#TIMEINDEX       1
    --#HELP            ""
    --#STATE           OPERATIONAL
    ::= 10901

-- EVT_BBU_MICROCODE_UPDATE_FAILED

svrTrapBBUMicrocodeUpdateFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU firmware update failed."
    --#TYPE            "FBU firmware update failed"
    --#SUMMARY         "Adapter %s: FBU firmware update failed (Server %s)"
    --#ARGUMENTS       { 2, 0 }
    --#SEVERITY        MINOR
    --#TIMEINDEX       1
    --#HELP            "1) Call your local Fujitsu Helpdesk."
    --#STATE           OPERATIONAL
    ::= 10902

-- EVT_LD_ACCESS_BLOCKED_SSC_OFFLINE

svrTrapLDAccessBlockedSSCOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive access blocked as cached data in CacheCade is unavailable."
    --#TYPE            "Logical drive access blocked as cached data in CacheCade is unavailable"
    --#SUMMARY         "Adapter %s: Logical drive %s access blocked as cached data in CacheCade is unavailable (Server %s)"
    --#ARGUMENTS       { 2, 3, 0 }
    --#SEVERITY        CRITICAL
    --#TIMEINDEX       1
    --#HELP            "Call your local Fujitsu Helpdesk."
    --#STATE           NONOPERATIONAL
    ::= 10903

-- EVT_LD_SSC_DISASSOCIATE_START

svrTrapLDSSCDisassociateStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "CacheCade disassociate started on logical drive."
    --#TYPE            "CacheCade disassociate started on logical drive"
    --#SUMMARY         "Adapter %s: CacheCade disassociate started on logical drive %s (Server %s)"
    --#ARGUMENTS       { 2, 3, 0 }
    --#SEVERITY        INFORMATIONAL
    --#TIMEINDEX       1
    --#HELP            ""
    --#STATE           OPERATIONAL
    ::= 10904

-- EVT_LD_SSC_DISASSOCIATE_DONE

svrTrapLDSSCDisassociateDone TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "CacheCade disassociate finished on logical drive."
    --#TYPE            "CacheCade disassociate finished on logical drive"
    --#SUMMARY         "Adapter %s: CacheCade disassociate finished on logical drive %s (Server %s)"
    --#ARGUMENTS       { 2, 3, 0 }
    --#SEVERITY        INFORMATIONAL
    --#TIMEINDEX       1
    --#HELP            ""
    --#STATE           OPERATIONAL
    ::= 10905

-- EVT_LD_SSC_DISASSOCIATE_FAILED

svrTrapLDSSCDisassociateFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "CacheCade disassociate failed on logical drive."
    --#TYPE            "CacheCade disassociate failed on logical drive"
    --#SUMMARY         "Adapter %s: CacheCade disassociate failed on logical drive %s (Server %s)"
    --#ARGUMENTS       { 2, 3, 0 }
    --#SEVERITY        MAJOR
    --#TIMEINDEX       1
    --#HELP            "Call your local Fujitsu Helpdesk."
    --#STATE           OPERATIONAL
    ::= 10906

-- EVT_LD_SSC_DISASSOCIATE_PROGRESS

svrTrapLDSSCDisassociateProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "CacheCade disassociate progress on logical drive."
    --#TYPE            "CacheCade disassociate progress on logical drive"
    --#SUMMARY         "Adapter %s: CacheCade disassociate progress on logical drive %s is %s (Server %s)"
    --#ARGUMENTS       { 2, 3, 4, 0 }
    --#SEVERITY        INFORMATIONAL
    --#TIMEINDEX       1
    --#HELP            ""
    --#STATE           OPERATIONAL
    ::= 10907

-- EVT_LD_SSC_DISASSOCIATE_ABORT_BY_USER

svrTrapLDSSCDisassociateAbortByUser TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "CacheCade disassociate aborted by user on logical drive."
    --#TYPE            "CacheCade disassociate aborted by user on logical drive"
    --#SUMMARY         "Adapter %s: CacheCade disassociate aborted by user on logical drive %s (Server %s)"
    --#ARGUMENTS       { 2, 3, 0 }
    --#SEVERITY        INFORMATIONAL
    --#TIMEINDEX       1
    --#HELP            ""
    --#STATE           OPERATIONAL
    ::= 10908

-- EVT_PD_SENSE_WARNING

svrTrapPDSenseWarning TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unexpected sense."
    --#TYPE            "Unexpected sense"
    --#SUMMARY         "Adapter %s: Unexpected sense: Disk (%s), Key/ASC/ASCQ: %s: %s (Server %s)"
    --#ARGUMENTS       { 2, 3, 4, 5, 0 }
    --#SEVERITY        MINOR
    --#TIMEINDEX       1
    --#HELP            "For information only."
    --#STATE           OPERATIONAL
    ::= 10909

-- EVT_PD_SENSE_ERROR

svrTrapPDSenseError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Unexpected sense."
    --#TYPE            "Unexpected sense"
    --#SUMMARY         "Adapter %s: Unexpected sense: Disk (%s), Key/ASC/ASCQ: %s: %s (Server %s)"
    --#ARGUMENTS       { 2, 3, 4, 5, 0 }
    --#SEVERITY        CRITICAL
    --#TIMEINDEX       1
    --#HELP            "For information only."
    --#STATE           OPERATIONAL
    ::= 10910

-- EVT_PD_REBUILD_PAUSED

svrTrapPDRebuildPaused TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild suspended on disk."
    --#TYPE            "Rebuild suspended on disk"
    --#SUMMARY         "Adapter %s: Rebuild suspended on disk (%s) (Server %s)"
    --#ARGUMENTS       { 2, 3, 0 }
    --#SEVERITY        INFORMATIONAL
    --#TIMEINDEX       1
    --#HELP            ""
    --#STATE           DEGRADED
    ::= 10911

-- EVT_PD_REBUILD_RESUMED

svrTrapPDRebuildResumed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Rebuild resumed on disk."
    --#TYPE            "Rebuild resumed on disk"
    --#SUMMARY         "Adapter %s: Rebuild resumed on disk (%s) (Server %s)"
    --#ARGUMENTS       { 2, 3, 0 }
    --#SEVERITY        INFORMATIONAL
    --#TIMEINDEX       1
    --#HELP            ""
    --#STATE           OPERATIONAL
    ::= 10912

-- EVT_SAS_PHY_LINK_SPEED_UPDATED

svrTrapSASPhyLinkSpeedUpdated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Link speed changed on SAS port and PHY."
    --#TYPE            "Link speed changed on SAS port and PHY"
    --#SUMMARY         "Adapter %s: Link speed changed on SAS port %s and PHY %s (Server %s)"
    --#ARGUMENTS       { 2, 3, 4, 0 }
    --#SEVERITY        INFORMATIONAL
    --#TIMEINDEX       1
    --#HELP            ""
    --#STATE           OPERATIONAL
    ::= 10913

-- EVT_CTRL_PFK_DEACTIVATED

svrTrapCtrlPFKDeactivated TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MegaRAID Advanced Software Options were deactivated for."
    --#TYPE            "MegaRAID Advanced Software Options were deactivated for"
    --#SUMMARY         "Adapter %s: MegaRAID Advanced Software Options were deactivated for - %s (Server %s)"
    --#ARGUMENTS       { 2, 3, 0 }
    --#SEVERITY        MINOR
    --#TIMEINDEX       1
    --#HELP            "Call your local Fujitsu Helpdesk."
    --#STATE           OPERATIONAL
    ::= 10914

-- EVT_LD_ACCESS_UNBLOCKED

svrTrapLDAccessUnblocked TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is now accessible."
    --#TYPE            "Logical drive is now accessible"
    --#SUMMARY         "Adapter %s: Logical drive %s is now accessible (Server %s)"
    --#ARGUMENTS       { 2, 3, 0 }
    --#SEVERITY        INFORMATIONAL
    --#TIMEINDEX       1
    --#HELP            ""
    --#STATE           OPERATIONAL
    ::= 10915

-- EVT_LD_IS_USING_SSC_2

svrTrapLDIsUsingSSC2 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is using CacheCade."
    --#TYPE            "Logical drive is using CacheCade"
    --#SUMMARY         "Adapter %s: Logical drive %s is using CacheCade (Server %s)"
    --#ARGUMENTS       { 2, 3, 0 }
    --#SEVERITY        INFORMATIONAL
    --#TIMEINDEX       1
    --#HELP            ""
    --#STATE           OPERATIONAL
    ::= 10916

-- EVT_LD_IS_NOT_USING_SSC_2

svrTrapLDIsNotUsingSSC2 TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is no longer using CacheCade."
    --#TYPE            "Logical drive is no longer using CacheCade"
    --#SUMMARY         "Adapter %s: Logical drive %s is no longer using CacheCade (Server %s)"
    --#ARGUMENTS       { 2, 3, 0 }
    --#SEVERITY        INFORMATIONAL
    --#TIMEINDEX       1
    --#HELP            ""
    --#STATE           OPERATIONAL
    ::= 10917

-- EVT_PD_PR_ABORTED

svrTrapPDPRAborted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Patrol Read aborted on disk."
    --#TYPE            "Patrol Read aborted on disk"
    --#SUMMARY         "Adapter %s: Patrol Read aborted on disk (%s) (Server %s)"
    --#ARGUMENTS       { 2, 3, 0 }
    --#SEVERITY        MINOR
    --#TIMEINDEX       1
    --#HELP            "Note: If there are errors directly before or after this event, perform the proper recovery action for that error. 1) For information only."
    --#STATE           OPERATIONAL
    ::= 10918

-- EVT_PD_TRANSIENT_ERROR_DETECTED

svrTrapPDTransientErrorDetected TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Transient error detected while communicating with disk."
    --#TYPE            "Transient error detected while communicating with disk"
    --#SUMMARY         "Adapter %s: Transient error detected while communicating with disk (%s) (Server %s)"
    --#ARGUMENTS       { 2, 3, 0 }
    --#SEVERITY        MINOR
    --#TIMEINDEX       1
    --#HELP            "Note: Doesn't affect the normal operation of the system, but can lead to degraded performance due to retries. 1) Replace affected disk/backplane/cable at next service."
    --#STATE           OPERATIONAL
    ::= 10919

-- EVT_PNPADD_EX

svrTrapPNPADDEx TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Additional information for detected disk."
    --#TYPE            "Additional information for detected disk"
    --#SUMMARY         "Adapter %s: Additional information for detected disk (%s) - firmware version: %s, serial number %s (Server %s)"
    --#ARGUMENTS       { 2, 3, 4, 5, 0 }
    --#SEVERITY        INFORMATIONAL
    --#TIMEINDEX       1
    --#HELP            ""
    --#STATE           OPERATIONAL
    ::= 10920

-- EVT_RAID_MANAGER_STARTED

svrTrapRAIDManagerStarted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "RAID Manager started."
    --#TYPE            "RAID Manager started"
    --#SUMMARY         "RAID Manager started (Server %s)"
    --#ARGUMENTS       { 0 }
    --#SEVERITY        INFORMATIONAL
    --#TIMEINDEX       1
    --#HELP            ""
    --#STATE           OPERATIONAL
    ::= 10921

-- EVT_RAID_MANAGER_STOPPED

svrTrapRAIDManagerStopped TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "RAID Manager stopped."
    --#TYPE            "RAID Manager stopped"
    --#SUMMARY         "RAID Manager stopped (Server %s)"
    --#ARGUMENTS       { 0 }
    --#SEVERITY        INFORMATIONAL
    --#TIMEINDEX       1
    --#HELP            ""
    --#STATE           OPERATIONAL
    ::= 10922

-- EVT_PD_STATE_CHANGE_SHIELD_TO_AVAIL

svrTrapPDStateChangeShieldToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to available."
    --#TYPE            "State change from shielded to available"
    --#SUMMARY         "Adapter %s: State change on disk (%s) from shielded to available (Server %s)"
    --#ARGUMENTS       { 2, 3, 0 }
    --#SEVERITY        INFORMATIONAL
    --#TIMEINDEX       1
    --#HELP            ""
    --#STATE           OPERATIONAL
    ::= 10923

-- EVT_PD_STATE_CHANGE_SHIELD_TO_OFFL

svrTrapPDStateChangeShieldToOffl TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to offline."
    --#TYPE            "State change from shielded to offline"
    --#SUMMARY         "Adapter %s: State change on disk (%s) from shielded to offline (Server %s)"
    --#ARGUMENTS       { 2, 3, 0 }
    --#SEVERITY        MINOR
    --#TIMEINDEX       1
    --#HELP            "Replace affected disk."
    --#STATE           DEGRADED
    ::= 10924

-- EVT_PD_STATE_CHANGE_SHIELD_TO_FAIL

svrTrapPDStateChangedShieldToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to failed."
    --#TYPE            "State change from shielded to failed"
    --#SUMMARY         "Adapter %s: State change on disk (%s) from shielded to failed (Server %s)"
    --#ARGUMENTS       { 2, 3, 0 }
    --#SEVERITY        CRITICAL
    --#TIMEINDEX       1
    --#HELP            "Replace affected disk."
    --#STATE           NONOPERATIONAL
    ::= 10925

-- EVT_PD_STATE_CHANGE_SHIELD_TO_HS

svrTrapPDStateChangeShieldToHs TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to hot spare."
    --#TYPE            "State change from shielded to hot spare"
    --#SUMMARY         "Adapter %s: State change on disk (%s) from shielded to hot spare (Server %s)"
    --#ARGUMENTS       { 2, 3, 0 }
    --#SEVERITY        INFORMATIONAL
    --#TIMEINDEX       1
    --#HELP            ""
    --#STATE           OPERATIONAL
    ::= 10926

-- EVT_PD_STATE_CHANGE_SHIELD_TO_RBLD

svrTrapPDStateChangeShieldToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to rebuilding."
    --#TYPE            "State change from shielded to rebuilding"
    --#SUMMARY         "Adapter %s: State change on disk (%s) from shielded to rebuilding (Server %s)"
    --#ARGUMENTS       { 2, 3, 0 }
    --#SEVERITY        INFORMATIONAL
    --#TIMEINDEX       1
    --#HELP            ""
    --#STATE           OPERATIONAL
    ::= 10927

-- EVT_PD_STATE_CHANGE_SHIELD_TO_OP

svrTrapPDStateChangeShieldToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to operational."
    --#TYPE            "State change from shielded to operational"
    --#SUMMARY         "Adapter %s: State change on disk (%s) from shielded to operational (Server %s)"
    --#ARGUMENTS       { 2, 3, 0 }
    --#SEVERITY        INFORMATIONAL
    --#TIMEINDEX       1
    --#HELP            ""
    --#STATE           OPERATIONAL
    ::= 10928

-- EVT_PD_STATE_CHANGE_SHIELD_TO_CB

svrTrapPDStateChangeShieldToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to copyback."
    --#TYPE            "State change from shielded to copyback"
    --#SUMMARY         "Adapter %s: State change on disk (%s) from shielded to copyback (Server %s)"
    --#ARGUMENTS       { 2, 3, 0 }
    --#SEVERITY        INFORMATIONAL
    --#TIMEINDEX       1
    --#HELP            ""
    --#STATE           OPERATIONAL
    ::= 10929

-- EVT_PD_STATE_CHANGE_SHIELD_TO_SYS

svrTrapPDStateChangeShieldToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to JBOD."
    --#TYPE            "State change from shielded to JBOD"
    --#SUMMARY         "Adapter %s: State change on disk (%s) from shielded to JBOD (Server %s)"
    --#ARGUMENTS       { 2, 3, 0 }
    --#SEVERITY        INFORMATIONAL
    --#TIMEINDEX       1
    --#HELP            ""
    --#STATE           OPERATIONAL
    ::= 10930

-- EVT_PD_STATE_CHANGE_SHIELD_TO_SHIELD

svrTrapPDStateChangedShieldToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from shielded to shielded."
    --#TYPE            "State change from shielded to shielded"
    --#SUMMARY         "Adapter %s: State change on disk (%s) from shielded to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10931

-- EVT_PD_STATE_CHANGE_AVAIL_TO_SHIELD

svrTrapPDStateChangedAvailToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from available to shielded."
    --#TYPE            "State change from available to shielded"
    --#SUMMARY         "Adapter %s: State change on disk (%s) from available to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10932

-- EVT_PD_STATE_CHANGE_OFFL_TO_SHIELD

svrTrapPDStateChangedOfflToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from offline to shielded."
    --#TYPE            "State change from offline to shielded"
    --#SUMMARY         "Adapter %s: State change on disk (%s) from offline to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10933

-- EVT_PD_STATE_CHANGE_FAIL_TO_SHIELD

svrTrapPDStateChangedFailToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from failed to shielded."
    --#TYPE            "State change from failed to shielded"
    --#SUMMARY         "Adapter %s: State change on disk (%s) from failed to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10934

-- EVT_PD_STATE_CHANGE_HS_TO_SHIELD

svrTrapPDStateChangedHsToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from hot spare to shielded."
    --#TYPE            "State change from hot spare to shielded"
    --#SUMMARY         "Adapter %s: State change on disk (%s) from hot spare to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10935

-- EVT_PD_STATE_CHANGE_RBLD_TO_SHIELD

svrTrapPDStateChangedRbldToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from rebuilding to shielded."
    --#TYPE            "State change from rebuilding to shielded"
    --#SUMMARY         "Adapter %s: State change on disk (%s) from rebuilding to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10936

-- EVT_PD_STATE_CHANGE_OP_TO_SHIELD

svrTrapPDStateChangedOpToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from operational to shielded."
    --#TYPE            "State change from operational to shielded"
    --#SUMMARY         "Adapter %s: State change on disk (%s) from operational to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10937

-- EVT_PD_STATE_CHANGE_CB_TO_SHIELD

svrTrapPDStateChangedCbToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from copyback to shielded."
    --#TYPE            "State change from copyback to shielded"
    --#SUMMARY         "Adapter %s: State change on disk (%s) from copyback to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10938

-- EVT_PD_STATE_CHANGE_SYS_TO_SHIELD

svrTrapPDStateChangedSysToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change from JBOD to shielded."
    --#TYPE            "State change from JBOD to shielded"
    --#SUMMARY         "Adapter %s: State change on disk (%s) from JBOD to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10939

-- EVT_PD_STATE_CHANGE_BY_USER_SHIELD_TO_AVAIL

svrTrapPDStateChangeByUserShieldToAvail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to available."
    --#TYPE            "State change by user from shielded to available"
    --#SUMMARY         "Adapter %s: State change by user on disk (%s) from shielded to available (Server %s)"
    --#ARGUMENTS       { 2, 3, 0 }
    --#SEVERITY        INFORMATIONAL
    --#TIMEINDEX       1
    --#HELP            ""
    --#STATE           OPERATIONAL
    ::= 10940

-- EVT_PD_STATE_CHANGE_BY_USER_SHIELD_TO_OFFL

svrTrapPDStateChangeByUserShieldToOffl TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to offline."
    --#TYPE            "State change by user from shielded to offline"
    --#SUMMARY         "Adapter %s: State change by user on disk (%s) from shielded to offline (Server %s)"
    --#ARGUMENTS       { 2, 3, 0 }
    --#SEVERITY        MINOR
    --#TIMEINDEX       1
    --#HELP            "Replace affected disk."
    --#STATE           DEGRADED
    ::= 10941

-- EVT_PD_STATE_CHANGE_BY_USER_SHIELD_TO_FAIL

svrTrapPDStateChangeByUserShieldToFail TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to failed."
    --#TYPE            "State change by user from shielded to failed"
    --#SUMMARY         "Adapter %s: State change by user on disk (%s) from shielded to failed (Server %s)"
    --#ARGUMENTS       { 2, 3, 0 }
    --#SEVERITY        CRITICAL
    --#TIMEINDEX       1
    --#HELP            "Replace affected disk."
    --#STATE           NONOPERATIONAL
    ::= 10942

-- EVT_PD_STATE_CHANGE_BY_USER_SHIELD_TO_HS

svrTrapPDStateChangeByUserShieldToHs TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to hot spare."
    --#TYPE            "State change by user from shielded to hot spare"
    --#SUMMARY         "Adapter %s: State change by user on disk (%s) from shielded to hot spare (Server %s)"
    --#ARGUMENTS       { 2, 3, 0 }
    --#SEVERITY        INFORMATIONAL
    --#TIMEINDEX       1
    --#HELP            ""
    --#STATE           OPERATIONAL
    ::= 10943

-- EVT_PD_STATE_CHANGE_BY_USER_SHIELD_TO_RBLD

svrTrapPDStateChangeByUserShieldToRbld TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to rebuilding."
    --#TYPE            "State change by user from shielded to rebuilding"
    --#SUMMARY         "Adapter %s: State change by user on disk (%s) from shielded to rebuilding (Server %s)"
    --#ARGUMENTS       { 2, 3, 0 }
    --#SEVERITY        INFORMATIONAL
    --#TIMEINDEX       1
    --#HELP            ""
    --#STATE           OPERATIONAL
    ::= 10944

-- EVT_PD_STATE_CHANGE_BY_USER_SHIELD_TO_OP

svrTrapPDStateChangeByUserShieldToOp TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to operational."
    --#TYPE            "State change by user from shielded to operational"
    --#SUMMARY         "Adapter %s: State change by user on disk (%s) from shielded to operational (Server %s)"
    --#ARGUMENTS       { 2, 3, 0 }
    --#SEVERITY        INFORMATIONAL
    --#TIMEINDEX       1
    --#HELP            ""
    --#STATE           OPERATIONAL
    ::= 10945

-- EVT_PD_STATE_CHANGE_BY_USER_SHIELD_TO_CB

svrTrapPDStateChangeByUserShieldToCb TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to copyback."
    --#TYPE            "State change by user from shielded to copyback"
    --#SUMMARY         "Adapter %s: State change by user on disk (%s) from shielded to copyback (Server %s)"
    --#ARGUMENTS       { 2, 3, 0 }
    --#SEVERITY        INFORMATIONAL
    --#TIMEINDEX       1
    --#HELP            ""
    --#STATE           OPERATIONAL
    ::= 10946

-- EVT_PD_STATE_CHANGE_BY_USER_SHIELD_TO_SYS

svrTrapPDStateChangeByUserShieldToSys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to JBOD."
    --#TYPE            "State change by user from shielded to JBOD"
    --#SUMMARY         "Adapter %s: State change by user on disk (%s) from shielded to JBOD (Server %s)"
    --#ARGUMENTS       { 2, 3, 0 }
    --#SEVERITY        INFORMATIONAL
    --#TIMEINDEX       1
    --#HELP            ""
    --#STATE           OPERATIONAL
    ::= 10947

-- EVT_PD_STATE_CHANGE_BY_USER_SHIELD_TO_SHIELD

svrTrapPDStateChangeByUserShieldToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from shielded to shielded."
    --#TYPE            "State change by user from shielded to shielded"
    --#SUMMARY         "Adapter %s: State change by user on disk (%s) from shielded to shielded (Server %s)"
    --#ARGUMENTS       { 2, 3, 0 }
    --#SEVERITY        CRITICAL
    --#TIMEINDEX       1
    --#HELP            "Replace affected disk."
    --#STATE           NONOPERATIONAL
    ::= 10948

-- EVT_PD_STATE_CHANGE_BY_USER_AVAIL_TO_SHIELD

svrTrapPDStateChangeByUserAvailToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from available to shielded."
    --#TYPE            "State change by user from available to shielded"
    --#SUMMARY         "Adapter %s: State change by user on disk (%s) from available to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10949

-- EVT_PD_STATE_CHANGE_BY_USER_OFFL_TO_SHIELD

svrTrapPDStateChangeByUserOfflToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from offline to shielded."
    --#TYPE            "State change by user from offline to shielded"
    --#SUMMARY         "Adapter %s: State change by user on disk (%s) from offline to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10950

-- EVT_PD_STATE_CHANGE_BY_USER_FAIL_TO_SHIELD

svrTrapPDStateChangeByUserFailToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from failed to shielded."
    --#TYPE            "State change by user from failed to shielded"
    --#SUMMARY         "Adapter %s: State change by user on disk (%s) from failed to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10951

-- EVT_PD_STATE_CHANGE_BY_USER_HS_TO_SHIELD

svrTrapPDStateChangeByUserHsToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from hot spare to shielded."
    --#TYPE            "State change by user from hot spare to shielded"
    --#SUMMARY         "Adapter %s: State change by user on disk (%s) from hot spare to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10952

-- EVT_PD_STATE_CHANGE_BY_USER_RBLD_TO_SHIELD

svrTrapPDStateChangeByUserRbldToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from rebuilding to shielded."
    --#TYPE            "State change by user from rebuilding to shielded"
    --#SUMMARY         "Adapter %s: State change by user on disk (%s) from rebuilding to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10953

-- EVT_PD_STATE_CHANGE_BY_USER_OP_TO_SHIELD

svrTrapPDStateChangeByUserOpToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from operational to shielded."
    --#TYPE            "State change by user from operational to shielded"
    --#SUMMARY         "Adapter %s: State change by user on disk (%s) from operational to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10954

-- EVT_PD_STATE_CHANGE_BY_USER_CB_TO_SHIELD

svrTrapPDStateChangeByUserCbToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from copyback to shielded."
    --#TYPE            "State change by user from copyback to shielded"
    --#SUMMARY         "Adapter %s: State change by user on disk (%s) from copyback to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10955

-- EVT_PD_STATE_CHANGE_BY_USER_SYS_TO_SHIELD

svrTrapPDStateChangeByUserSysToShield TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "State change by user from JBOD to shielded."
    --#TYPE            "State change by user from JBOD to shielded"
    --#SUMMARY         "Adapter %s: State change by user on disk (%s) from JBOD to shielded (Server %s)"
    --#ARGUMENTS       { 2, 3, 0 }
    --#SEVERITY        CRITICAL
    --#TIMEINDEX       1
    --#HELP            "1) Wait until checking in shielded state is completed. 2) Perform action according to upcoming status."
    --#STATE           NONOPERATIONAL
    ::= 10956

-- EVT_CTRL_INTERNAL_ERROR

svrTrapCtrlInternalError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal error."
    --#TYPE            "Internal error"
    --#SUMMARY         "Adapter %s: Internal error (Server %s)"
    --#ARGUMENTS       { 2, 0 }
    --#SEVERITY        CRITICAL
    --#TIMEINDEX       1
    --#HELP            "If problem persists after reboot, call your local Fujitsu Helpdesk."
    --#STATE           NONOPERATIONAL
    ::= 10957

-- EVT_CTRL_INCOMPATIBLE_PCI_BANDWIDTH

svrTrapCtrlIncompatiblePCIBandwidth TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Incompatible PCI slot bandwidth."
    --#TYPE            "Incompatible PCI slot bandwidth"
    --#SUMMARY         "Adapter %s: Incompatible PCI slot bandwidth (Server %s)"
    --#ARGUMENTS       { 2, 0 }
    --#SEVERITY        CRITICAL
    --#TIMEINDEX       1
    --#HELP            "Reinstall adapter in a compatible PCI slot."
    --#STATE           NONOPERATIONAL
    ::= 10958

-- EVT_CTRL_PARTIAL_WRITE_THROTTLING

svrTrapCtrlPartialWriteThrottling TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write performance reduced."
    --#TYPE            "Write performance reduced"
    --#SUMMARY         "Adapter %s: Write performance reduced (Server %s)"
    --#ARGUMENTS       { 2, 0 }
    --#SEVERITY        MAJOR
    --#TIMEINDEX       1
    --#HELP            "Check additional status property for more information."
    --#STATE           OPERATIONAL
    ::= 10959

-- EVT_CTRL_COMPLETE_WRITE_THROTTLING

svrTrapCtrlCompleteWriteThrottling TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write operations disabled."
    --#TYPE            "Write operations disabled"
    --#SUMMARY         "Adapter %s: Write operations disabled (Server %s)"
    --#ARGUMENTS       { 2, 0 }
    --#SEVERITY        MAJOR
    --#TIMEINDEX       1
    --#HELP            "Check additional status property for more information."
    --#STATE           OPERATIONAL
    ::= 10960

-- EVT_CTRL_TEMPERATURE_NEAR_ERROR

svrTrapCtrlTemperatureNearError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Temperature close to error threshold."
    --#TYPE            "Temperature close to error threshold"
    --#SUMMARY         "Adapter %s: Temperature close to error threshold (Server %s)"
    --#ARGUMENTS       { 2, 0 }
    --#SEVERITY        MAJOR
    --#TIMEINDEX       1
    --#HELP            "Increase cooling or reduce write load."
    --#STATE           OPERATIONAL
    ::= 10961

-- EVT_CTRL_TEMPERATURE_ABOVE_ERROR

svrTrapCtrlTemperatureAboveError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Temperature above error threshold."
    --#TYPE            "Temperature above error threshold"
    --#SUMMARY         "Adapter %s: Temperature above error threshold (Server %s)"
    --#ARGUMENTS       { 2, 0 }
    --#SEVERITY        CRITICAL
    --#TIMEINDEX       1
    --#HELP            "Increase cooling or reduce write load."
    --#STATE           NONOPERATIONAL
    ::= 10962

-- EVT_CTRL_INTERNAL_VOLTAGE_OUT_OF_RANGE

svrTrapCtrlInternalVoltageOutOfRange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Internal voltage out of range."
    --#TYPE            "Internal voltage out of range"
    --#SUMMARY         "Adapter %s: Internal voltage out of range (Server %s)"
    --#ARGUMENTS       { 2, 0 }
    --#SEVERITY        CRITICAL
    --#TIMEINDEX       1
    --#HELP            "If problem persists after reboot, call your local Fujitsu Helpdesk."
    --#STATE           NONOPERATIONAL
    ::= 10963

-- EVT_CTRL_AUXILIARY_VOLTAGE_OUT_OF_RANGE

svrTrapCtrlAuxiliaryVoltageOutOfRange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Auxiliary voltage out of range."
    --#TYPE            "Auxiliary voltage out of range"
    --#SUMMARY         "Adapter %s: Auxiliary voltage out of range (Server %s)"
    --#ARGUMENTS       { 2, 0 }
    --#SEVERITY        CRITICAL
    --#TIMEINDEX       1
    --#HELP            "If problem persists after reboot, call your local Fujitsu Helpdesk."
    --#STATE           NONOPERATIONAL
    ::= 10964

-- EVT_CTRL_FLASHBACK

svrTrapCtrlFlashback TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flashback error."
    --#TYPE            "Flashback error"
    --#SUMMARY         "Adapter %s: Flashback error (Server %s)"
    --#ARGUMENTS       { 2, 0 }
    --#SEVERITY        CRITICAL
    --#TIMEINDEX       1
    --#HELP            "1) Backup data from affected adapter. 2) Replace adapter as soon as possible. 3) Restore data."
    --#STATE           NONOPERATIONAL
    ::= 10965

-- EVT_CTRL_NONCORRECTABLE_PCI_ERRORS

svrTrapCtrlNonCorrectablePCIErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Non-correctable PCI errors detected."
    --#TYPE            "Non-correctable PCI errors detected"
    --#SUMMARY         "Adapter %s: Non-correctable PCI errors detected (Server %s)"
    --#ARGUMENTS       { 2, 0 }
    --#SEVERITY        CRITICAL
    --#TIMEINDEX       1
    --#HELP            "If problem persists after reboot, call your local Fujitsu Helpdesk."
    --#STATE           NONOPERATIONAL
    ::= 10966

-- EVT_CTRL_TEMPERATURE_ABOVE_WARN

svrTrapCtrlTemperatureAboveWarn TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Temperature above warning threshold."
    --#TYPE            "Temperature above warning threshold"
    --#SUMMARY         "Adapter %s: Temperature above warning threshold (Server %s)"
    --#ARGUMENTS       { 2, 0 }
    --#SEVERITY        MINOR
    --#TIMEINDEX       1
    --#HELP            "Increase cooling or reduce write load."
    --#STATE           OPERATIONAL
    ::= 10967

-- EVT_CTRL_NEAR_WEARING_OUT

svrTrapCtrlNearWearingOut TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Memory is close to wearing out."
    --#TYPE            "Memory is close to wearing out"
    --#SUMMARY         "Adapter %s: Memory is close to wearing out (Server %s)"
    --#ARGUMENTS       { 2, 0 }
    --#SEVERITY        MINOR
    --#TIMEINDEX       1
    --#HELP            "Formatting to a smaller size will free up reserve."
    --#STATE           OPERATIONAL
    ::= 10968

-- EVT_CTRL_NONOPTIMAL_PCI_BANDWIDTH

svrTrapCtrlNonOptimalPCISlotBandwidth TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Non-optimal PCI slot bandwidth."
    --#TYPE            "Non-optimal PCI slot bandwidth"
    --#SUMMARY         "Adapter %s: Non-optimal PCI slot bandwidth (Server %s)"
    --#ARGUMENTS       { 2, 0 }
    --#SEVERITY        MINOR
    --#TIMEINDEX       1
    --#HELP            "Reinstall adapter in an optimal PCI slot."
    --#STATE           OPERATIONAL
    ::= 10969

-- EVT_CTRL_CORRECTABLE_PCI_ERRORS

svrTrapCtrlCorrectablePCIErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Correctable PCI errors detected."
    --#TYPE            "Correctable PCI errors detected"
    --#SUMMARY         "Adapter %s: Correctable PCI errors detected (Server %s)"
    --#ARGUMENTS       { 2, 0 }
    --#SEVERITY        MINOR
    --#TIMEINDEX       1
    --#HELP            "For information only."
    --#STATE           OPERATIONAL
    ::= 10970

-- EVT_CTRL_NO_POWERLOSS_PROTECTION

svrTrapCtrlNoPowerlossProtection TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power loss protection disabled."
    --#TYPE            "Power loss protection disabled"
    --#SUMMARY         "Adapter %s: Power loss protection disabled (Server %s)"
    --#ARGUMENTS       { 2, 0 }
    --#SEVERITY        MINOR
    --#TIMEINDEX       1
    --#HELP            "Activate power loss protection."
    --#STATE           OPERATIONAL
    ::= 10971

-- EVT_CTRL_POWER_WRITE_REGULATION

svrTrapCtrlPowerWriteRegulation TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write regulation activated due to power constraints of PCI slot."
    --#TYPE            "Write regulation activated due to power constraints of PCI slot"
    --#SUMMARY         "Adapter %s: Write regulation activated due to power constraints of PCI slot (Server %s)"
    --#ARGUMENTS       { 2, 0 }
    --#SEVERITY        MINOR
    --#TIMEINDEX       1
    --#HELP            "If this condition persists, switch to a higher powered PCI slot or attach external power cable."
    --#STATE           OPERATIONAL
    ::= 10972

-- EVT_CTRL_TEMPERATURE_WRITE_REGULATION

svrTrapCtrlTemperatureWriteRegulation TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write regulation activated due to high temperature."
    --#TYPE            "Write regulation activated due to high temperature"
    --#SUMMARY         "Adapter %s: Write regulation activated due to high temperature (Server %s)"
    --#ARGUMENTS       { 2, 0 }
    --#SEVERITY        MINOR
    --#TIMEINDEX       1
    --#HELP            "If this condition persists, increase air flow, lower room temperature or reduce write load."
    --#STATE           OPERATIONAL
    ::= 10973

-- EVT_CTRL_LIFESPAN_WRITE_REGULATION

svrTrapCtrlLifespanWriteRegulation TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write regulation activated to ensure adapter lifespan."
    --#TYPE            "Write regulation activated to ensure adapter lifespan"
    --#SUMMARY         "Adapter %s: Write regulation activated to ensure adapter lifespan (Server %s)"
    --#ARGUMENTS       { 2, 0 }
    --#SEVERITY        MINOR
    --#TIMEINDEX       1
    --#HELP            "If this condition persists, reduce write load."
    --#STATE           OPERATIONAL
    ::= 10974

-- EVT_CTRL_MINIMAL

svrTrapCtrlMinimal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Running in minimal status."
    --#TYPE            "Running in minimal status"
    --#SUMMARY         "Adapter %s: Running in minimal status (Server %s)"
    --#ARGUMENTS       { 2, 0 }
    --#SEVERITY        MINOR
    --#TIMEINDEX       1
    --#HELP            "Check additional status property for more information."
    --#STATE           OPERATIONAL
    ::= 10975

-- EVT_CTRL_PCI_OVERPOWER

svrTrapCtrlPCIOverpower TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "PCI power budget alarm."
    --#TYPE            "PCI power budget alarm"
    --#SUMMARY         "Adapter %s: PCI power budget alarm (Server %s)"
    --#ARGUMENTS       { 2, 0 }
    --#SEVERITY        MINOR
    --#TIMEINDEX       1
    --#HELP            "Switch to a higher powered PCI slot or attach external power cable."
    --#STATE           OPERATIONAL
    ::= 10976

-- EVT_CTRL_LEB_MAP_MISSING

svrTrapCtrlLEBMapMissing TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "LEB map missing."
    --#TYPE            "LEB map missing"
    --#SUMMARY         "Adapter %s: LEB map missing (Server %s)"
    --#ARGUMENTS       { 2, 0 }
    --#SEVERITY        MINOR
    --#TIMEINDEX       1
    --#HELP            "If problem persists after reboot, call your local Fujitsu Helpdesk."
    --#STATE           OPERATIONAL
    ::= 10977

-- EVT_CTRL_UPDATE_IN_PROGRESS

svrTrapCtrlUpdateInProgress TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Update in progress."
    --#TYPE            "Update in progress"
    --#SUMMARY         "Adapter %s: Update in progress (Server %s)"
    --#ARGUMENTS       { 2, 0 }
    --#SEVERITY        MINOR
    --#TIMEINDEX       1
    --#HELP            "The adapter will not be usable until formatting is complete."
    --#STATE           OPERATIONAL
    ::= 10978

-- EVT_CTRL_RESERVES_DEPLETED

svrTrapCtrlReservesDepleted TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Reserves depleted."
    --#TYPE            "Reserves depleted"
    --#SUMMARY         "Adapter %s: Reserves depleted (Server %s)"
    --#ARGUMENTS       { 2, 0 }
    --#SEVERITY        MINOR
    --#TIMEINDEX       1
    --#HELP            "Formatting to a smaller size will free up reserve."
    --#STATE           OPERATIONAL
    ::= 10979

-- EVT_CTRL_NORMAL

svrTrapCtrlNormal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter normal."
    --#TYPE            "Adapter normal"
    --#SUMMARY         "Adapter %s: Adapter normal (Server %s)"
    --#ARGUMENTS       { 2, 0 }
    --#SEVERITY        INFORMATIONAL
    --#TIMEINDEX       1
    --#HELP            ""
    --#STATE           OPERATIONAL
    ::= 10980

-- EVT_CTRL_ATTACH_FAILED

svrTrapCtrlAttachFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Attach failed."
    --#TYPE            "Attach failed"
    --#SUMMARY         "Adapter %s: Attach failed (Server %s)"
    --#ARGUMENTS       { 2, 0 }
    --#SEVERITY        CRITICAL
    --#TIMEINDEX       1
    --#HELP            "If problem persists, call your local Fujitsu Helpdesk."
    --#STATE           NONOPERATIONAL
    ::= 10981

-- EVT_CTRL_DETACH_FAILED

svrTrapCtrlDetachFailed TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Detach failed."
    --#TYPE            "Detach failed"
    --#SUMMARY         "Adapter %s: Detach failed (Server %s)"
    --#ARGUMENTS       { 2, 0 }
    --#SEVERITY        MINOR
    --#TIMEINDEX       1
    --#HELP            "1) Force detach. 2) If problem persists, call your local Fujitsu Helpdesk."
    --#STATE           OPERATIONAL
    ::= 10982

-- EVT_CTRL_ATTACHED

svrTrapCtrlAttached TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Attached."
    --#TYPE            "Attached"
    --#SUMMARY         "Adapter %s: Attached (Server %s)"
    --#ARGUMENTS       { 2, 0 }
    --#SEVERITY        INFORMATIONAL
    --#TIMEINDEX       1
    --#HELP            ""
    --#STATE           OPERATIONAL
    ::= 10983

-- EVT_CTRL_DETACHED

svrTrapCtrlDetached TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Detached."
    --#TYPE            "Detached"
    --#SUMMARY         "Adapter %s: Detached (Server %s)"
    --#ARGUMENTS       { 2, 0 }
    --#SEVERITY        CRITICAL
    --#TIMEINDEX       1
    --#HELP            "For information only."
    --#STATE           NONOPERATIONAL
    ::= 10984

-- EVT_PD_FORMAT_CHANGED

svrTrapPDFormatChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Format of disk changed."
    --#TYPE            "Format of disk changed"
    --#SUMMARY         "Adapter %s: Format of disk (%s) changed (Server %s)"
    --#ARGUMENTS       { 2, 3, 0 }
    --#SEVERITY        INFORMATIONAL
    --#TIMEINDEX       1
    --#HELP            ""
    --#STATE           OPERATIONAL
    ::= 10985

-- EVT_LOG_CLEARED

svrTrapFileLogCleared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "File log cleared."
    --#TYPE            "File log cleared"
    --#SUMMARY         "File log cleared (Server %s)"
    --#ARGUMENTS       { 0 }
    --#SEVERITY        INFORMATIONAL
    --#TIMEINDEX       1
    --#HELP            ""
    --#STATE           OPERATIONAL
    ::= 10986

-- EVT_PD_OFFLINE_SMART

svrTrapPDOfflineSmart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk will be set offline due to SMART error."
    --#TYPE            "Disk will be set offline due to SMART error"
    --#SUMMARY         "Adapter %s: Disk (%s) will be set offline due to SMART error (Server %s)"
    --#ARGUMENTS       { 2, 3, 0 }
    --#SEVERITY        INFORMATIONAL
    --#TIMEINDEX       1
    --#HELP            ""
    --#STATE           OPERATIONAL
    ::= 10987

-- EVT_PD_OFFLINE_SENSE_KEYS

svrTrapPDOfflineSenseKeys TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk will be set offline due to too many unexpected sense events."
    --#TYPE            "Disk will be set offline due to too many unexpected sense events"
    --#SUMMARY         "Adapter %s: Disk (%s) will be set offline due to too many unexpected sense events (Server %s)"
    --#ARGUMENTS       { 2, 3, 0 }
    --#SEVERITY        INFORMATIONAL
    --#TIMEINDEX       1
    --#HELP            ""
    --#STATE           OPERATIONAL
    ::= 10988

-- EVT_LD_PI_ERR_IN_CACHE

svrTrapLDPIErrInCache TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Protection information error in cache for logical drive."
    --#TYPE            "Protection information error in cache for logical drive"
    --#SUMMARY         "Adapter %s: Protection information error in cache for logical drive %s at LBA %s (Server %s)"
    --#ARGUMENTS       { 2, 3, 4, 0 }
    --#SEVERITY        MINOR
    --#TIMEINDEX       1
    --#HELP            ""
    --#STATE           OPERATIONAL
    ::= 10989

-- EVT_CTRL_FLASH_IMAGE_UNSUPPORTED

svrTrapCtrlFlashImageUnsupported TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Flash downloaded image is not supported."
    --#TYPE            "Flash downloaded image is not supported"
    --#SUMMARY         "Adapter %s: Flash downloaded image is not supported (Server %s)"
    --#ARGUMENTS       { 2, 0 }
    --#SEVERITY        MINOR
    --#TIMEINDEX       1
    --#HELP            ""
    --#STATE           OPERATIONAL
    ::= 10990

-- EVT_BBU_MODE_SET

svrTrapBBUModeSet TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "BBU mode selected."
    --#TYPE            "BBU mode selected"
    --#SUMMARY         "Adapter %s: BBU mode selected - %s (Server %s)"
    --#ARGUMENTS       { 2, 3, 0 }
    --#SEVERITY        INFORMATIONAL
    --#TIMEINDEX       1
    --#HELP            ""
    --#STATE           OPERATIONAL
    ::= 10991

-- EVT_BBU_PERIODIC_RELEARN_RESCHEDULED

svrTrapBBUPeriodicRelearnRescheduled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Periodic BBU relearn was missed and rescheduled."
    --#TYPE            "Periodic BBU relearn was missed and rescheduled"
    --#SUMMARY         "Adapter %s: Periodic BBU relearn was missed, and rescheduled to %s (Server %s)"
    --#ARGUMENTS       { 2, 3, 0 }
    --#SEVERITY        INFORMATIONAL
    --#TIMEINDEX       1
    --#HELP            ""
    --#STATE           OPERATIONAL
    ::= 10992

-- EVT_CTRL_RESETNOW_START

svrTrapCtrlResetnowStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter reset requested by host."
    --#TYPE            "Adapter reset requested by host"
    --#SUMMARY         "Adapter %s: Adapter reset requested by host (Server %s)"
    --#ARGUMENTS       { 2, 0 }
    --#SEVERITY        INFORMATIONAL
    --#TIMEINDEX       1
    --#HELP            ""
    --#STATE           OPERATIONAL
    ::= 10993

-- EVT_CTRL_RESETNOW_DONE

svrTrapCtrlResetnowDone TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter reset requested by host completed."
    --#TYPE            "Adapter reset requested by host completed"
    --#SUMMARY         "Adapter %s: Adapter reset requested by host, completed (Server %s)"
    --#ARGUMENTS       { 2, 0 }
    --#SEVERITY        INFORMATIONAL
    --#TIMEINDEX       1
    --#HELP            ""
    --#STATE           OPERATIONAL
    ::= 10994

-- EVT_L3_CACHE_ERROR

svrTrapL3CacheError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "L3 cache error has been detected."
    --#TYPE            "L3 cache error has been detected"
    --#SUMMARY         "Adapter %s: L3 cache error has been detected (Server %s)"
    --#ARGUMENTS       { 2, 0 }
    --#SEVERITY        MAJOR
    --#TIMEINDEX       1
    --#HELP            ""
    --#STATE           OPERATIONAL
    ::= 10995

-- EVT_L2_CACHE_ERROR

svrTrapL2CacheError TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "L2 cache error has been detected."
    --#TYPE            "L2 cache error has been detected"
    --#SUMMARY         "Adapter %s: L2 cache error has been detected (Server %s)"
    --#ARGUMENTS       { 2, 0 }
    --#SEVERITY        MAJOR
    --#TIMEINDEX       1
    --#HELP            ""
    --#STATE           OPERATIONAL
    ::= 10996

-- EVT_CTRL_BOOT_HEADLESS_MODE_HAD_ERRORS

svrTrapCtrlBootHeadlessModeHadErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter booted in headless mode with errors."
    --#TYPE            "Adapter booted in headless mode with errors"
    --#SUMMARY         "Adapter %s: Adapter booted in headless mode with errors (Server %s)"
    --#ARGUMENTS       { 2, 0 }
    --#SEVERITY        MINOR
    --#TIMEINDEX       1
    --#HELP            ""
    --#STATE           OPERATIONAL
    ::= 10997

-- EVT_CTRL_BOOT_SAFE_MODE_FOR_ERRORS

svrTrapCtrlBootSafeModeForErrors TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter booted to safe mode due to critical errors."
    --#TYPE            "Adapter booted to safe mode due to critical errors"
    --#SUMMARY         "Adapter %s: Adapter booted to safe mode due to critical errors (Server %s)"
    --#ARGUMENTS       { 2, 0 }
    --#SEVERITY        MAJOR
    --#TIMEINDEX       1
    --#HELP            ""
    --#STATE           OPERATIONAL
    ::= 10998

-- EVT_CTRL_BOOT_ERROR_WARNING

svrTrapCtrlBootErrorWarning TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Warning during boot."
    --#TYPE            "Warning during boot"
    --#SUMMARY         "Adapter %s: Warning during boot - %s (Server %s)"
    --#ARGUMENTS       { 2, 3, 0 }
    --#SEVERITY        MINOR
    --#TIMEINDEX       1
    --#HELP            ""
    --#STATE           OPERATIONAL
    ::= 10999

-- EVT_CTRL_BOOT_ERROR_CRITICAL

svrTrapCtrlBootErrorCritical TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Critical error during boot."
    --#TYPE            "Critical error during boot"
    --#SUMMARY         "Adapter %s: Critical error during boot - %s (Server %s)"
    --#ARGUMENTS       { 2, 3, 0 }
    --#SEVERITY        MAJOR
    --#TIMEINDEX       1
    --#HELP            ""
    --#STATE           OPERATIONAL
    ::= 11000

-- EVT_CTRL_BOOT_ERROR_FATAL

svrTrapCtrlBootErrorFatal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Fatal error during boot."
    --#TYPE            "Fatal error during boot"
    --#SUMMARY         "Adapter %s: Fatal error during boot - %s (Server %s)"
    --#ARGUMENTS       { 2, 3, 0 }
    --#SEVERITY        CRITICAL
    --#TIMEINDEX       1
    --#HELP            ""
    --#STATE           NONOPERATIONAL
    ::= 11001

-- EVT_HA_NODE_JOIN

svrTrapHANodeJoin TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Peer adapter has joined high availability domain."
    --#TYPE            "Peer adapter has joined high availability domain"
    --#SUMMARY         "Adapter %s: Peer adapter has joined high availability domain (ID: %s) (Server %s)"
    --#ARGUMENTS       { 2, 3, 0 }
    --#SEVERITY        INFORMATIONAL
    --#TIMEINDEX       1
    --#HELP            ""
    --#STATE           OPERATIONAL
    ::= 11002

-- EVT_HA_NODE_BREAK

svrTrapHANodeBreak TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Peer adapter has left high availability domain."
    --#TYPE            "Peer adapter has left high availability domain"
    --#SUMMARY         "Adapter %s: Peer adapter has left high availability domain (ID: %s) (Server %s)"
    --#ARGUMENTS       { 2, 3, 0 }
    --#SEVERITY        MAJOR
    --#TIMEINDEX       1
    --#HELP            ""
    --#STATE           OPERATIONAL
    ::= 11003

-- EVT_HA_PD_IS_REMOTE

svrTrapHAPDIsRemote TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk is managed by peer adapter."
    --#TYPE            "Disk is managed by peer adapter"
    --#SUMMARY         "Adapter %s: Disk (%s) is managed by peer adapter (Server %s)"
    --#ARGUMENTS       { 2, 3, 0 }
    --#SEVERITY        INFORMATIONAL
    --#TIMEINDEX       1
    --#HELP            ""
    --#STATE           OPERATIONAL
    ::= 11004

-- EVT_HA_PD_IS_LOCAL

svrTrapHAPDIsLocal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk is managed by local adapter."
    --#TYPE            "Disk is managed by local adapter"
    --#SUMMARY         "Adapter %s: Disk (%s) is managed by local adapter (Server %s)"
    --#ARGUMENTS       { 2, 3, 0 }
    --#SEVERITY        INFORMATIONAL
    --#TIMEINDEX       1
    --#HELP            ""
    --#STATE           OPERATIONAL
    ::= 11005

-- EVT_HA_LD_IS_REMOTE

svrTrapHALDIsRemote TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is managed by peer adapter."
    --#TYPE            "Logical drive is managed by peer adapter"
    --#SUMMARY         "Adapter %s: Logical drive %s is managed by peer adapter (Server %s)"
    --#ARGUMENTS       { 2, 3, 0 }
    --#SEVERITY        INFORMATIONAL
    --#TIMEINDEX       1
    --#HELP            ""
    --#STATE           OPERATIONAL
    ::= 11006

-- EVT_HA_LD_IS_LOCAL

svrTrapHALDIsLocal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is managed by local adapter."
    --#TYPE            "Logical drive is managed by local adapter"
    --#SUMMARY         "Adapter %s: Logical drive %s is managed by local adapter (Server %s)"
    --#ARGUMENTS       { 2, 3, 0 }
    --#SEVERITY        INFORMATIONAL
    --#TIMEINDEX       1
    --#HELP            ""
    --#STATE           OPERATIONAL
    ::= 11007

-- EVT_HA_LD_TARGET_ID_CONFLICT

svrTrapHALDTargetIDConflict TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive has a conflict in high availability domain."
    --#TYPE            "Logical drive has a conflict in high availability domain"
    --#SUMMARY         "Adapter %s: Logical drive %s has a conflict in high availability domain (Server %s)"
    --#ARGUMENTS       { 2, 3, 0 }
    --#SEVERITY        MINOR
    --#TIMEINDEX       1
    --#HELP            ""
    --#STATE           OPERATIONAL
    ::= 11008

-- EVT_HA_LD_ACCESS_IS_SHARED

svrTrapHALDAccessIsShared TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive access is shared."
    --#TYPE            "Logical drive access is shared"
    --#SUMMARY         "Adapter %s: Logical drive %s access is shared (Server %s)"
    --#ARGUMENTS       { 2, 3, 0 }
    --#SEVERITY        INFORMATIONAL
    --#TIMEINDEX       1
    --#HELP            ""
    --#STATE           OPERATIONAL
    ::= 11009

-- EVT_HA_LD_ACCESS_IS_EXCLUSIVE

svrTrapHALDAccessIsExclusive TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive access is exclusive."
    --#TYPE            "Logical drive access is exclusive"
    --#SUMMARY         "Adapter %s: Logical drive %s access is exclusive (Server %s)"
    --#ARGUMENTS       { 2, 3, 0 }
    --#SEVERITY        INFORMATIONAL
    --#TIMEINDEX       1
    --#HELP            ""
    --#STATE           OPERATIONAL
    ::= 11010

-- EVT_HA_LD_INCOMPATIBLE

svrTrapHALDIncompatible TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is incompatible in the high availability domain."
    --#TYPE            "Logical drive is incompatible in the high availability domain"
    --#SUMMARY         "Adapter %s: Logical drive %s is incompatible in the high availability domain (Server %s)"
    --#ARGUMENTS       { 2, 3, 0 }
    --#SEVERITY        MINOR
    --#TIMEINDEX       1
    --#HELP            ""
    --#STATE           OPERATIONAL
    ::= 11011

-- EVT_HA_PEER_INCOMPATIBLE

svrTrapHAPeerIncompatible TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Peer adapter is incompatible."
    --#TYPE            "Peer adapter is incompatible"
    --#SUMMARY         "Adapter %s: Peer adapter is incompatible (Server %s)"
    --#ARGUMENTS       { 2, 0 }
    --#SEVERITY        MAJOR
    --#TIMEINDEX       1
    --#HELP            ""
    --#STATE           OPERATIONAL
    ::= 11012

-- EVT_HA_HW_INCOMPATIBLE

svrTrapHAHWIncompatible TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapters in the high availability domain are incompatible."
    --#TYPE            "Adapters in the high availability domain are incompatible"
    --#SUMMARY         "Adapter %s: Adapters in the high availability domain are incompatible (Server %s)"
    --#ARGUMENTS       { 2, 0 }
    --#SEVERITY        MAJOR
    --#TIMEINDEX       1
    --#HELP            ""
    --#STATE           OPERATIONAL
    ::= 11013

-- EVT_HA_CTRLPROP_INCOMPATIBLE

svrTrapHACtrlpropIncompatible TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter properties are incompatible between local and peer adapters."
    --#TYPE            "Adapter properties are incompatible between local and peer adapters"
    --#SUMMARY         "Adapter %s: Adapter properties are incompatible between local and peer adapters (Server %s)"
    --#ARGUMENTS       { 2, 0 }
    --#SEVERITY        MAJOR
    --#TIMEINDEX       1
    --#HELP            ""
    --#STATE           OPERATIONAL
    ::= 11014

-- EVT_HA_FW_VERSION_MISMATCH

svrTrapHAFWVersionMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware versions do not match in the high availability domain."
    --#TYPE            "Firmware versions do not match in the high availability domain"
    --#SUMMARY         "Adapter %s: Firmware versions do not match in the high availability domain (Server %s)"
    --#ARGUMENTS       { 2, 0 }
    --#SEVERITY        MINOR
    --#TIMEINDEX       1
    --#HELP            ""
    --#STATE           OPERATIONAL
    ::= 11015

-- EVT_HA_FEATURES_MISMATCH

svrTrapHAFeaturesMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "MegaRAID Advanced Software Options do not match in the high availability domain."
    --#TYPE            "MegaRAID Advanced Software Options do not match in the high availability domain"
    --#SUMMARY         "Adapter %s: MegaRAID Advanced Software Options %s do not match in the high availability domain (Server %s)"
    --#ARGUMENTS       { 2, 3, 0 }
    --#SEVERITY        MINOR
    --#TIMEINDEX       1
    --#HELP            ""
    --#STATE           OPERATIONAL
    ::= 11016

-- EVT_HA_CACHE_MIRROR_ONLINE

svrTrapHACacheMirrorOnline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "High availability cache mirror is online."
    --#TYPE            "High availability cache mirror is online"
    --#SUMMARY         "Adapter %s: High availability cache mirror is online (Server %s)"
    --#ARGUMENTS       { 2, 0 }
    --#SEVERITY        INFORMATIONAL
    --#TIMEINDEX       1
    --#HELP            ""
    --#STATE           OPERATIONAL
    ::= 11017

-- EVT_HA_CACHE_MIRROR_OFFLINE

svrTrapHACacheMirrorOffline TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "High availability cache mirror is offline."
    --#TYPE            "High availability cache mirror is offline"
    --#SUMMARY         "Adapter %s: High availability cache mirror is offline (Server %s)"
    --#ARGUMENTS       { 2, 0 }
    --#SEVERITY        MAJOR
    --#TIMEINDEX       1
    --#HELP            ""
    --#STATE           OPERATIONAL
    ::= 11018

-- EVT_LD_ACCESS_BLOCKED_PEER_UNAVAILABLE

svrTrapLDAccessBlockedPeerUnavailable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive access blocked as cached data from peer adapter is unavailable."
    --#TYPE            "Logical drive access blocked as cached data from peer adapter is unavailable"
    --#SUMMARY         "Adapter %s: Logical drive %s access blocked as cached data from peer adapter is unavailable (Server %s)"
    --#ARGUMENTS       { 2, 3, 0 }
    --#SEVERITY        CRITICAL
    --#TIMEINDEX       1
    --#HELP            ""
    --#STATE           NONOPERATIONAL
    ::= 11019

-- EVT_BBU_UNSUPPORTED

svrTrapBBUUnsupported TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU power pack is not supported."
    --#TYPE            "FBU power pack is not supported"
    --#SUMMARY         "Adapter %s: FBU power pack is not supported. Please replace the pack (Server %s)"
    --#ARGUMENTS       { 2, 0 }
    --#SEVERITY        MINOR
    --#TIMEINDEX       1
    --#HELP            ""
    --#STATE           OPERATIONAL
    ::= 11020

-- EVT_PD_TEMP_HIGH

svrTrapPDTempHigh TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk temperature is above warning threshold."
    --#TYPE            "Disk temperature is above warning threshold"
    --#SUMMARY         "Adapter %s: Disk (%s) temperature (%s C) is above warning threshold (Server %s)"
    --#ARGUMENTS       { 2, 3, 4, 0 }
    --#SEVERITY        MINOR
    --#TIMEINDEX       1
    --#HELP            ""
    --#STATE           OPERATIONAL
    ::= 11021

-- EVT_PD_TEMP_CRITICAL

svrTrapPDTempCritical TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk temperature is above critical threshold."
    --#TYPE            "Disk temperature is above critical threshold"
    --#SUMMARY         "Adapter %s: Disk (%s) temperature (%s C) is above critical threshold (Server %s)"
    --#ARGUMENTS       { 2, 3, 4, 0 }
    --#SEVERITY        MAJOR
    --#TIMEINDEX       1
    --#HELP            ""
    --#STATE           OPERATIONAL
    ::= 11022

-- EVT_PD_TEMP_NORMAL

svrTrapPDTempNormal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk temperature is normal."
    --#TYPE            "Disk temperature is normal"
    --#SUMMARY         "Adapter %s: Disk (%s) temperature (%s C) is normal (Server %s)"
    --#ARGUMENTS       { 2, 3, 4, 0 }
    --#SEVERITY        INFORMATIONAL
    --#TIMEINDEX       1
    --#HELP            ""
    --#STATE           OPERATIONAL
    ::= 11023

-- EVT_PD_IO_THROTTLED

svrTrapPDIOThrottled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk IOs are being throttled."
    --#TYPE            "Disk IOs are being throttled"
    --#SUMMARY         "Adapter %s: Disk (%s) IOs are being throttled (Server %s)"
    --#ARGUMENTS       { 2, 3, 0 }
    --#SEVERITY        MINOR
    --#TIMEINDEX       1
    --#HELP            ""
    --#STATE           OPERATIONAL
    ::= 11024

-- EVT_PD_IO_NOT_THROTTLED

svrTrapPDIONotThrottled TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk IOs are normal (no throttling)."
    --#TYPE            "Disk IOs are normal (no throttling)"
    --#SUMMARY         "Adapter %s: Disk (%s) IOs are normal (no throttling) (Server %s)"
    --#ARGUMENTS       { 2, 3, 0 }
    --#SEVERITY        INFORMATIONAL
    --#TIMEINDEX       1
    --#HELP            ""
    --#STATE           OPERATIONAL
    ::= 11025

-- EVT_PD_LIFE

svrTrapPDLife TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk has life left."
    --#TYPE            "Disk has life left"
    --#SUMMARY         "Adapter %s: Disk (%s) has %s percent life left. Life left thresholds - warning: %s percent, critical: %s percent (Server %s)"
    --#ARGUMENTS       { 2, 3, 4, 5, 6, 0 }
    --#SEVERITY        INFORMATIONAL
    --#TIMEINDEX       1
    --#HELP            ""
    --#STATE           OPERATIONAL
    ::= 11026

-- EVT_PD_LIFE_NOT_OPTIMAL

svrTrapPDLifeNotOptimal TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk life left is below optimal."
    --#TYPE            "Disk life left is below optimal"
    --#SUMMARY         "Adapter %s: Disk (%s) life left (%s percent) is below optimal. Life left thresholds - warning: %s percent, critical: %s percent (Server %s)"
    --#ARGUMENTS       { 2, 3, 4, 5, 6, 0 }
    --#SEVERITY        MINOR
    --#TIMEINDEX       1
    --#HELP            ""
    --#STATE           OPERATIONAL
    ::= 11027

-- EVT_PD_LIFE_CRITICAL

svrTrapPDLifeCritical TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk life left is critical."
    --#TYPE            "Disk life left is critical"
    --#SUMMARY         "Adapter %s: Disk (%s) life left (%s percent) is critical. Life left thresholds - warning: %s percent, critical: %s percent (Server %s)"
    --#ARGUMENTS       { 2, 3, 4, 5, 6, 0 }
    --#SEVERITY        MAJOR
    --#TIMEINDEX       1
    --#HELP            ""
    --#STATE           OPERATIONAL
    ::= 11028

-- EVT_PD_FAILURE_LOCKEDUP

svrTrapPDFailureLockedup TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Disk failure device locked-up."
    --#TYPE            "Disk failure device locked-up"
    --#SUMMARY         "Adapter %s: Disk (%s) failure, device locked-up (Server %s)"
    --#ARGUMENTS       { 2, 3, 0 }
    --#SEVERITY        MAJOR
    --#TIMEINDEX       1
    --#HELP            ""
    --#STATE           OPERATIONAL
    ::= 11029

-- EVT_CTRL_HOST_DRIVER_UPDATE_NEEDED

svrTrapCtrlHostDriverUpdateNeeded TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Driver needs to be upgraded."
    --#TYPE            "Driver needs to be upgraded"
    --#SUMMARY         "Adapter %s: Driver needs to be upgraded %s (Server %s)"
    --#ARGUMENTS       { 2, 3, 0 }
    --#SEVERITY        MINOR
    --#TIMEINDEX       1
    --#HELP            ""
    --#STATE           OPERATIONAL
    ::= 11030

-- EVT_HA_POSSIBLE_PEER_COMM_LOSS

svrTrapHAPossiblePeerCommLoss TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Direct communication with peer adapters was not established."
    --#TYPE            "Direct communication with peer adapters was not established"
    --#SUMMARY         "Adapter %s: Direct communication with peer adapter(s) was not established. Please check proper cable connections (Server %s)"
    --#ARGUMENTS       { 2, 0 }
    --#SEVERITY        MINOR
    --#TIMEINDEX       1
    --#HELP            ""
    --#STATE           OPERATIONAL
    ::= 11031

-- EVT_CTRL_FLASH_SIGNED_COMPONENT_NOT_PRESENT

svrTrapCtrlFlashSignedComponentNotPresent TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Firmware image does not contain signed component."
    --#TYPE            "Firmware image does not contain signed component"
    --#SUMMARY         "Adapter %s: Firmware image does not contain signed component (Server %s)"
    --#ARGUMENTS       { 2, 0 }
    --#SEVERITY        MINOR
    --#TIMEINDEX       1
    --#HELP            ""
    --#STATE           OPERATIONAL
    ::= 11032

-- EVT_CTRL_FLASH_AUTHENTICATION_FAILURE

svrTrapCtrlFlashAuthenticationFailure TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Authentication failure of the signed firmware image."
    --#TYPE            "Authentication failure of the signed firmware image"
    --#SUMMARY         "Adapter %s: Authentication failure of the signed firmware image (Server %s)"
    --#ARGUMENTS       { 2, 0 }
    --#SEVERITY        MINOR
    --#TIMEINDEX       1
    --#HELP            ""
    --#STATE           OPERATIONAL
    ::= 11033

-- EVT_LD_SET_BOOT_DEVICE

svrTrapLDSetBootDevice TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Setting logical drive as boot device."
    --#TYPE            "Setting logical drive as boot device"
    --#SUMMARY         "Adapter %s: Setting logical drive %s as boot device (Server %s)"
    --#ARGUMENTS       { 2, 3, 0 }
    --#SEVERITY        INFORMATIONAL
    --#TIMEINDEX       1
    --#HELP            ""
    --#STATE           OPERATIONAL
    ::= 11034

-- EVT_PD_SET_BOOT_DEVICE

svrTrapPDSetBootDevice TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Setting disk as boot device."
    --#TYPE            "Setting disk as boot device"
    --#SUMMARY         "Adapter %s: Setting disk (%s) as boot device (Server %s)"
    --#ARGUMENTS       { 2, 3, 0 }
    --#SEVERITY        INFORMATIONAL
    --#TIMEINDEX       1
    --#HELP            ""
    --#STATE           OPERATIONAL
    ::= 11035

-- EVT_BBU_TEMPERATURE_CHANGED

svrTrapBBUTemperatureChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "The BBU temperature is changed."
    --#TYPE            "The BBU temperature is changed"
    --#SUMMARY         "Adapter %s: The BBU temperature is changed to %s C (Server %s)"
    --#ARGUMENTS       { 2, 3, 0 }
    --#SEVERITY        INFORMATIONAL
    --#TIMEINDEX       1
    --#HELP            ""
    --#STATE           OPERATIONAL
    ::= 11036

-- EVT_CTRL_TEMPERATURE_CHANGED

svrTrapCtrlTemperatureChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "The adapter temperature is changed."
    --#TYPE            "The adapter temperature is changed"
    --#SUMMARY         "Adapter %s: The adapter temperature is changed to %s C (Server %s)"
    --#ARGUMENTS       { 2, 3, 0 }
    --#SEVERITY        INFORMATIONAL
    --#TIMEINDEX       1
    --#HELP            ""
    --#STATE           OPERATIONAL
    ::= 11037

-- EVT_NVCACHE_BACKUP_UNAVAILABLE

svrTrapNVCacheBackupUnavailable TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU capacity is too less to support data backup."
    --#TYPE            "FBU capacity is too less to support data backup"
    --#SUMMARY         "Adapter %s: FBU capacity is too less to support data backup. Write-back logical drives will be converted to Write-through (Server %s)"
    --#ARGUMENTS       { 2, 0 }
    --#SEVERITY        MAJOR
    --#TIMEINDEX       1
    --#HELP            ""
    --#STATE           OPERATIONAL
    ::= 11038

-- EVT_NVCACHE_CONSIDER_REPLACEMENT

svrTrapNVCacheConsiderReplacement TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU data backup capacity has decreased consider replacement."
    --#TYPE            "FBU data backup capacity has decreased consider replacement"
    --#SUMMARY         "Adapter %s: FBU data backup capacity has decreased, consider replacement (Server %s)"
    --#ARGUMENTS       { 2, 0 }
    --#SEVERITY        MINOR
    --#TIMEINDEX       1
    --#HELP            ""
    --#STATE           OPERATIONAL
    ::= 11039

-- EVT_NVCACHE_INVALID

svrTrapNVCacheInvalid TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU device failed."
    --#TYPE            "FBU device failed"
    --#SUMMARY         "Adapter %s: FBU device failed, cannot support data retention (Server %s)"
    --#ARGUMENTS       { 2, 0 }
    --#SEVERITY        MAJOR
    --#TIMEINDEX       1
    --#HELP            ""
    --#STATE           OPERATIONAL
    ::= 11040

-- EVT_BOOT_DEVICE_INVALID

svrTrapBootDeviceInvalid TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Boot device reset."
    --#TYPE            "Boot device reset"
    --#SUMMARY         "Adapter %s: Boot device reset, setting target ID as invalid (Server %s)"
    --#ARGUMENTS       { 2, 0 }
    --#SEVERITY        INFORMATIONAL
    --#TIMEINDEX       1
    --#HELP            ""
    --#STATE           OPERATIONAL
    ::= 11041

-- EVT_HA_SSC_WB_POOL_SIZE_MISMATCH

svrTrapHASSCWBPoolSizeMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Write-back Nytro cache size mismatch between the servers."
    --#TYPE            "Write-back Nytro cache size mismatch between the servers"
    --#SUMMARY         "Adapter %s: Write-back Nytro cache size mismatch between the servers. The Nytro cache size was adjusted to %s GB (Server %s)"
    --#ARGUMENTS       { 2, 3, 0 }
    --#SEVERITY        MINOR
    --#TIMEINDEX       1
    --#HELP            ""
    --#STATE           OPERATIONAL
    ::= 11042

-- EVT_HA_SSC_NONSHARED_VD_WB_ASSOCIATION

svrTrapHASSCNonsharedVDWBAssociation TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Logical drive is not shared between servers but assigned for caching."
    --#TYPE            "Logical drive is not shared between servers but assigned for caching"
    --#SUMMARY         "Adapter %s: Logical drive %s is not shared between servers but assigned for caching. Write-back Nytro cache content of the logical drive will be mirrored (Server %s)"
    --#ARGUMENTS       { 2, 3, 0 }
    --#SEVERITY        MINOR
    --#TIMEINDEX       1
    --#HELP            ""
    --#STATE           OPERATIONAL
    ::= 11043

-- EVT_CTRL_POWER_IO_THROTTLE_START

svrTrapCtrlPowerIOThrottleStart TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power watts usage base IOs throttle started."
    --#TYPE            "Power watts usage base IOs throttle started"
    --#SUMMARY         "Adapter %s: Power %s watts usage base IOs throttle started (Server %s)"
    --#ARGUMENTS       { 2, 3, 0 }
    --#SEVERITY        INFORMATIONAL
    --#TIMEINDEX       1
    --#HELP            ""
    --#STATE           OPERATIONAL
    ::= 11044

-- EVT_CTRL_POWER_IO_THROTTLE_STOP

svrTrapCtrlPowerIOThrottleStop TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Power base IOs throttle stopped."
    --#TYPE            "Power base IOs throttle stopped"
    --#SUMMARY         "Adapter %s: Power base IOs throttle stopped (Server %s)"
    --#ARGUMENTS       { 2, 0 }
    --#SEVERITY        INFORMATIONAL
    --#TIMEINDEX       1
    --#HELP            ""
    --#STATE           OPERATIONAL
    ::= 11045

-- EVT_CTRL_TUNABLE_PARAMETERS_CHANGED

svrTrapCtrlTunableParametersChanged TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter tunable parameters changed."
    --#TYPE            "Adapter tunable parameters changed"
    --#SUMMARY         "Adapter %s: Adapter tunable parameter(s) changed (Server %s)"
    --#ARGUMENTS       { 2, 0 }
    --#SEVERITY        INFORMATIONAL
    --#TIMEINDEX       1
    --#HELP            ""
    --#STATE           OPERATIONAL
    ::= 11046

-- EVT_CTRL_TEMP_WITHIN_OPTIMAL_RANGE

svrTrapCtrlTempWithinOptimalRange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter operating temperature within normal range."
    --#TYPE            "Adapter operating temperature within normal range"
    --#SUMMARY         "Adapter %s: Adapter operating temperature within normal range, full operation restored (Server %s)"
    --#ARGUMENTS       { 2, 0 }
    --#SEVERITY        INFORMATIONAL
    --#TIMEINDEX       1
    --#HELP            ""
    --#STATE           OPERATIONAL
    ::= 11047

-- EVT_CTRL_TEMP_ABOVE_OPTIMAL_RANGE

svrTrapCtrlTempAboveOptimalRange TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Temperature threshold exceeded for the adapter."
    --#TYPE            "Temperature threshold exceeded for the adapter"
    --#SUMMARY         "Adapter %s: Temperature threshold exceeded for the adapter. This may indicate inadequate cooling in the system chassis. Adapter has switched to lower performance mode (Server %s)"
    --#ARGUMENTS       { 2, 0 }
    --#SEVERITY        MINOR
    --#TIMEINDEX       1
    --#HELP            ""
    --#STATE           OPERATIONAL
    ::= 11048

-- EVT_HOST_WARNING_STATUS

svrTrapHostWarningStatus TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter defect or no adapter detected on host."
    --#TYPE            "Adapter defect or no adapter detected on host"
    --#SUMMARY         "Adapter defect or no adapter detected on host %s (Server %s)"
    --#ARGUMENTS       { 2, 0 }
    --#SEVERITY        MINOR
    --#TIMEINDEX       1
    --#HELP            ""
    --#STATE           OPERATIONAL
    ::= 11049

-- EVT_HOST_ERROR_STATUS

svrTrapHostErrorStatus TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Connection to host failed."
    --#TYPE            "Connection to host failed"
    --#SUMMARY         "Connection to host %s failed (Server %s)"
    --#ARGUMENTS       { 2, 0 }
    --#SEVERITY        MAJOR
    --#TIMEINDEX       1
    --#HELP            ""
    --#STATE           OPERATIONAL
    ::= 11050

-- EVT_HOST_OK_STATUS

svrTrapHostOkStatus TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Connection to host established."
    --#TYPE            "Connection to host established"
    --#SUMMARY         "Connection to host %s established (Server %s)"
    --#ARGUMENTS       { 2, 0 }
    --#SEVERITY        INFORMATIONAL
    --#TIMEINDEX       1
    --#HELP            ""
    --#STATE           OPERATIONAL
    ::= 11051

-- EVT_HA_MODE_HA_FEATURE_SET

svrTrapHAModeHAFeatureSet TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter supports high availability mode currently functioning with high availability feature set."
    --#TYPE            "Adapter supports high availability mode currently functioning with high availability feature set"
    --#SUMMARY         "Adapter %s: Adapter supports high availability mode, currently functioning with high availability feature set (Server %s)"
    --#ARGUMENTS       { 2, 0 }
    --#SEVERITY        INFORMATIONAL
    --#TIMEINDEX       1
    --#HELP            ""
    --#STATE           OPERATIONAL
    ::= 11052

-- EVT_HA_MODE_SC_FEATURE_SET

svrTrapHAModeSCFeatureSet TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter supports high availability mode currently functioning with single adapter feature set."
    --#TYPE            "Adapter supports high availability mode currently functioning with single adapter feature set"
    --#SUMMARY         "Adapter %s: Adapter supports high availability mode, currently functioning with single adapter feature set (Server %s)"
    --#ARGUMENTS       { 2, 0 }
    --#SEVERITY        INFORMATIONAL
    --#TIMEINDEX       1
    --#HELP            ""
    --#STATE           OPERATIONAL
    ::= 11053

-- EVT_NVCACHE_COMPONENT_MISMATCH

svrTrapFBUComponentMismatch TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "FBU components mismatch."
    --#TYPE            "FBU components mismatch"
    --#SUMMARY         "Adapter %s: FBU components mismatch. Write-back logical drives will be converted to write-through (Server %s)"
    --#ARGUMENTS       { 2, 0 }
    --#SEVERITY        MAJOR
    --#TIMEINDEX       1
    --#HELP            ""
    --#STATE           OPERATIONAL
    ::= 11054

-- EVT_CTRL_ENTER_MAINTENANCE_MODE

svrTrapCtrlEnterMaintenanceMode TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter has entered maintenance mode."
    --#TYPE            "Adapter has entered maintenance mode"
    --#SUMMARY         "Adapter %s: Adapter has entered maintenance mode (Server %s)"
    --#ARGUMENTS       { 2, 0 }
    --#SEVERITY        INFORMATIONAL
    --#TIMEINDEX       1
    --#HELP            ""
    --#STATE           OPERATIONAL
    ::= 11055

-- EVT_CTRL_EXIT_MAINTENANCE_MODE

svrTrapCtrlExitMaintenanceMode TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Adapter has returned to normal mode."
    --#TYPE            "Adapter has returned to normal mode"
    --#SUMMARY         "Adapter %s: Adapter has returned to normal mode (Server %s)"
    --#ARGUMENTS       { 2, 0 }
    --#SEVERITY        INFORMATIONAL
    --#TIMEINDEX       1
    --#HELP            ""
    --#STATE           OPERATIONAL
    ::= 11056

-- EVT_HA_TOPOLOGY_MODE

svrTrapHATopologyMode TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Topology is in mode."
    --#TYPE            "Topology is in mode"
    --#SUMMARY         "Adapter %s: Topology is in %s mode (Server %s)"
    --#ARGUMENTS       { 2, 3, 0 }
    --#SEVERITY        INFORMATIONAL
    --#TIMEINDEX       1
    --#HELP            ""
    --#STATE           OPERATIONAL
    ::= 11057

-- EVT_HA_TOPOLOGY_LD_INCOMPATIBLE

svrTrapHATopologyLDIncompatible TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cannot enter mode because logical drive would not be supported."
    --#TYPE            "Cannot enter mode because logical drive would not be supported"
    --#SUMMARY         "Adapter %s: Cannot enter %s mode because %s logical drive %s would not be supported (Server %s)"
    --#ARGUMENTS       { 2, 3, 4, 5, 0 }
    --#SEVERITY        MAJOR
    --#TIMEINDEX       1
    --#HELP            ""
    --#STATE           OPERATIONAL
    ::= 11058

-- EVT_HA_TOPOLOGY_PD_INCOMPATIBLE

svrTrapHATopologyPDIncompatible TRAP-TYPE
    ENTERPRISE svrNotifications
    VARIABLES {
        svrTrapInfoServerName,
        svrTrapInfoTime,
        svrTrapInfoPlaceHolder1,
        svrTrapInfoPlaceHolder2,
        svrTrapInfoPlaceHolder3,
        svrTrapInfoPlaceHolder4,
        svrTrapInfoPlaceHolder5,
        svrTrapInfoPlaceHolder6
        }
    DESCRIPTION     "Cannot enter mode because disk would not be supported."
    --#TYPE            "Cannot enter mode because disk would not be supported"
    --#SUMMARY         "Adapter %s: Cannot enter %s mode because %s disk (%s) would not be supported (Server %s)"
    --#ARGUMENTS       { 2, 3, 4, 5, 0 }
    --#SEVERITY        MAJOR
    --#TIMEINDEX       1
    --#HELP            ""
    --#STATE           OPERATIONAL
    ::= 11059


END
