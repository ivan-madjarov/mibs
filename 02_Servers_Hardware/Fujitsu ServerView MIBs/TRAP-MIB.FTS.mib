--------------------------------------------------------------------------------
-- FUJITSU KVM S4 APPLIANCE TRAP MIB
--
-- Copyright 2011 Fujitsu
--
-- Revision: 1.8.0
--
-- Last Modified: Thu, 08 Apr 2010
--
--------------------------------------------------------------------------------

FUJITSUS4-TRAP-MIB DEFINITIONS ::= BEGIN

IMPORTS
   Gauge,enterprises,TimeTicks,IpAddress,Counter,NetworkAddress
      FROM RFC1155-SMI
   OBJECT-TYPE
      FROM RFC-1212
   DisplayString,PhysAddress
      FROM RFC1213-MIB
   TRAP-TYPE
      FROM RFC-1215;

--------------------------------------------------------------------------------
-- Object Groupings
--------------------------------------------------------------------------------

fujitsu OBJECT IDENTIFIER ::= { enterprises 10418 }
fujitsus4 OBJECT IDENTIFIER ::= { fujitsu 18 }
fujitsus4Products OBJECT IDENTIFIER ::= { fujitsus4 51 }
fujitsus4Management OBJECT IDENTIFIER ::= { fujitsus4 52 }

-- Below is the value returned by each appliance in mib-2.system.sysObjectID
--
fujitsukvms40812 OBJECT IDENTIFIER ::= { fujitsus4Products 17 } -- 10418.18.51.17
fujitsukvms41622 OBJECT IDENTIFIER ::= { fujitsus4Products 23 } -- 10418.18.51.23
fujitsukvms43242 OBJECT IDENTIFIER ::= { fujitsus4Products 25 } -- 10418.18.51.25

fujitsus4TrapObject OBJECT IDENTIFIER ::= { fujitsus4Management 6 } -- 1.3.6.1.4.1.10418.18.52.6

--
-- A UTF8String represents a series of UTF-8 encoded characters. UTF-8 encoding
-- provides the ability to encode all characters defined in the Universal
-- Multiple-Octet Coded Character Set (UCS) and all characters defined in the
-- Unicode Standard. UCS is defined in international standard ISO 10646. Unicode
-- encompasses a subset of UCS. See http:
-- on Unicode. See RFC2279 for more information on UTF-8 encoding.
--

UTF8String ::= OCTET STRING

ImageFileUpgradeResultsEnum ::= INTEGER
{
   imageUpgradeTftpNoSocket(1), -- TFTP No Socket
   imageUpgradeTftpConnectFailure(2), -- TFTP server TFTP connect failed
   imageUpgradeTftpRequestDenied(3), -- TFTP server request denied
   imageUpgradeTftpBadPacket(4), -- TFTP err - non-data packet received
   imageUpgradeTftpOOS(5), -- TFTP err - too many packets out
                                        -- of sequence
   imageUpgradeTftpTooBig(6), -- TFTP err - transferred data exceeds
                                        -- file size
   imageUpgradeTftpTimeout(7), -- TFTP err - timeout during transfer,
                                        -- retries exceeded
   imageUpgradeAlreadyInProgress(8), -- Update already in progress
   imageUpgradeCannotStart(9), -- Update thread did not start
   imageUpgradeMemoryError(10), -- Update memory allocation error
   imageUpgradeTftpProtocolError(11), -- TFTP protocol error occurred could
                                        -- not complete transfer
   imageUpgradeBadType(12), -- The Image type does not match the
                                        -- region (BOOT or APP) to update
   imageUpgradeInvalidAppDowngrade(13), -- Invalid downgrade version
   imageUpgradeChecksumError(14), -- Checksum Error
   imageUpgradeFlashError(15), -- Flash Error
   imageUpgradeInternalError(16), -- Internal error
   imageUpgradeFileNotFound(17), -- File not found
   imageUpgradeBadHeader(18), -- Invalid image header
   imageUpgradeIncompatibleHeader(19), -- Header is not compatible
   imageUpgradeTftpXferFail(20), -- TFTP transfer failed
   imageUpgradeTftpSvrNoResponse(21), -- No response from TFTP server
   imageUpgradeNetworkUnreachable(22), -- Network unreachable
   imageUpgradeSuccess(9999) -- Success
}

--
-- An enumeration of KVM-IA upgrade results.
--

KVM-IAUpgradeResultsEnum ::= INTEGER
{
   kvmiaUpgradeNoFirmwareImage(1), -- No firmware image present
   kvmiaUpgradeLostContact(2), -- Lost communication with the KVM-IA
   kvmiaUpgradeFailedRestart(3), -- The KVM-IA did not restart after upgrade
   kvmiaUpgradeFailedVerify(4), -- The KVM-IA failed to upgrade to correct Version
   kvmiaUpgradeSuccess(9999) -- Success
}

--------------------------------------------------------------------------------
-- Trap Object Group (fujitsus4TrapObject) 1.3.6.1.4.1.10418.18.52.6
--
-- The following objects are implemented only for the generation of
-- TRAPs. The objects are sent in traps and are not accessible in
-- any other way.
--------------------------------------------------------------------------------

fujitsus4TrapObjectUserName OBJECT-TYPE
      SYNTAX UTF8String ( SIZE (3..16) )
      ACCESS not-accessible
      STATUS mandatory
  --% AVAILABILITY public
      DESCRIPTION
         "This object is sent in a trap to identify the name of the user
         for which the trap condition occured. If the trap condition occurred
         as a result of activity on the local port (OSD), then the value of this
         object will be the following string:

            Local User
         "
      ::= { fujitsus4TrapObject 1 }


fujitsus4TrapObjectTargetUserName OBJECT-TYPE
      SYNTAX UTF8String ( SIZE (3..16) )
      ACCESS not-accessible
      STATUS mandatory
  --% AVAILABILITY public
      DESCRIPTION
         "This object is sent in a trap to identify the name of the target
         user for which a trap condition occurred.
         "
      ::= { fujitsus4TrapObject 2 }


fujitsus4TrapObjectImageType OBJECT-TYPE
      SYNTAX UTF8String ( SIZE (0..64) )
      ACCESS not-accessible
      STATUS mandatory
  --% AVAILABILITY public
      DESCRIPTION
         "This object is sent in a trap to identify the type of software image
         for which the trap condition occured.
         "
      ::= { fujitsus4TrapObject 3 }


fujitsus4TrapObjectImageNewVersion OBJECT-TYPE
      SYNTAX UTF8String ( SIZE (0..32) )
      ACCESS not-accessible
      STATUS mandatory
  --% AVAILABILITY public
      DESCRIPTION
         "This object is sent in a trap to identify the version of the new
         software image the appliance is being upgraded to.
         "
      ::= { fujitsus4TrapObject 4 }


fujitsus4TrapObjectImageCurrentVersion OBJECT-TYPE
      SYNTAX UTF8String ( SIZE (0..32) )
      ACCESS not-accessible
      STATUS mandatory
  --% AVAILABILITY public
      DESCRIPTION
         "This object is sent in a trap to identify the version of the
         software image that the appliance is currently running.
         "
      ::= { fujitsus4TrapObject 5 }


fujitsus4TrapObjectSessionIdentifier OBJECT-TYPE
      SYNTAX UTF8String ( SIZE (0..32) )
      ACCESS not-accessible
      STATUS mandatory
  --% AVAILABILITY public
      DESCRIPTION
         "This object is sent in a trap to identify the session
         for which the trap condition occurred. The value will be
         the name of a target device if the target device name is known, otherwise
         the value will be the connection path to a target device.

         If the value is a connection path it will have the
         following format:

            KVM-IA i:Channel c

         Where i is the ID of the KVM-IA, and c is the cascade switch
         channel number (0 if there is no switch in the path).
         "
      ::= { fujitsus4TrapObject 6 }


fujitsus4TrapObjectKVM-IAId OBJECT-TYPE
      SYNTAX UTF8String ( SIZE (0..32) )
      ACCESS not-accessible
      STATUS mandatory
  --% AVAILABILITY public
      DESCRIPTION
         "This object is sent in a trap to identify the KVM-IA for
         which the trap condition occurred.
         "
      ::= { fujitsus4TrapObject 7 }


fujitsus4TrapObjectCascadeSwitchName OBJECT-TYPE
      SYNTAX UTF8String ( SIZE (0..15) )
      ACCESS not-accessible
      STATUS mandatory
  --% AVAILABILITY public
      DESCRIPTION
         "This object is sent in a trap to identify the cascade switch
         for which the trap condition occurred.
         "
      ::= { fujitsus4TrapObject 8 }


fujitsus4TrapObjectOldCascadeSwitchName OBJECT-TYPE
      SYNTAX UTF8String ( SIZE (0..15) )
      ACCESS not-accessible
      STATUS mandatory
  --% AVAILABILITY public
      DESCRIPTION
         "This object is sent in a trap to identify the old name of a
         cascade switch whose name was changed.
         "
      ::= { fujitsus4TrapObject 9 }


fujitsus4TrapObjectTargetDeviceName OBJECT-TYPE
      SYNTAX UTF8String ( SIZE (0..15) )
      ACCESS not-accessible
      STATUS mandatory
  --% AVAILABILITY public
      DESCRIPTION
         "This object is sent in a trap to identify the target device for
         which the trap condition occurred.
         "
      ::= { fujitsus4TrapObject 10 }


fujitsus4TrapObjectOldTargetDeviceName OBJECT-TYPE
      SYNTAX UTF8String ( SIZE (0..15) )
      ACCESS not-accessible
      STATUS mandatory
  --% AVAILABILITY public
      DESCRIPTION
         "This object is sent in a trap to identify the old name of
         a target device whose name was changed.
         "
      ::= { fujitsus4TrapObject 11 }


fujitsus4TrapObjectFileName OBJECT-TYPE
      SYNTAX DisplayString ( SIZE (0..255) )
      ACCESS not-accessible
      STATUS mandatory
  --% AVAILABILITY public
      DESCRIPTION
         "This object is sent in a trap to identify the name of a file
         for which the trap condition occurred.
         "
      ::= { fujitsus4TrapObject 12 }



fujitsus4TrapObjectLockReason OBJECT-TYPE
      SYNTAX UTF8String( SIZE (0..64) )
      ACCESS not-accessible
      STATUS mandatory
  --% AVAILABILITY public
      DESCRIPTION
         "This object is sent in a trap to explain the reason for which a
         user account has been locked.
         "
      ::= { fujitsus4TrapObject 13 }


fujitsus4TrapObjectUnlockReason OBJECT-TYPE
      SYNTAX UTF8String( SIZE (0..64) )
      ACCESS not-accessible
      STATUS mandatory
  --% AVAILABILITY public
      DESCRIPTION
         "This object is sent in a trap to explain the reason for which a
         user account has been unlocked.
         "
      ::= { fujitsus4TrapObject 14 }



fujitsus4TrapObjectUserAddress OBJECT-TYPE
      SYNTAX DisplayString( SIZE (0..40) )
      ACCESS not-accessible
      STATUS mandatory
  --% AVAILABILITY public
      DESCRIPTION
         "This object is sent in a trap to identify the user address for
         which a trap condition occurred.

         For a remote user, the value is the IPv4 or IPv6 IP address.
         For a local user, the value is the Local Port of the user.
         "
      ::= { fujitsus4TrapObject 15 }


fujitsus4TrapObjectKVM-IAImageUpgradeResult OBJECT-TYPE
      SYNTAX KVM-IAUpgradeResultsEnum
      ACCESS not-accessible
      STATUS mandatory
  --% AVAILABILITY public
      DESCRIPTION
         "This object is sent in a trap to report the result of a KVM-IA
         image upgrade.
         "
      ::= { fujitsus4TrapObject 16 }


fujitsus4TrapObjectTypeOfImage OBJECT-TYPE
      SYNTAX INTEGER {
                        boot(1),
                        app(2)
                     }
      ACCESS not-accessible
      STATUS mandatory
  --% AVAILABILITY public
      DESCRIPTION
         "This object is sent in a trap to report the type of software
         image for which the trap condition occurred.
         "
      ::= { fujitsus4TrapObject 17 }



fujitsus4TrapObjectVirtualMediaDriveAccessMode OBJECT-TYPE
      SYNTAX INTEGER {
                        readonly(1),
                        readwrite(2)
                     }
      ACCESS not-accessible
      STATUS mandatory
  --% AVAILABILITY public
      DESCRIPTION
         "This object is sent in a trap to report the access mode
          associated with a virtual drive for which
          the trap condition occurred.
         "
      ::= { fujitsus4TrapObject 18 }


fujitsus4TrapObjectVirtualMediaDriveType OBJECT-TYPE
      SYNTAX INTEGER {
                        floppyMemoryKey(1),
                        cdDvdRom(2),
                        generic(3)
                     }
      ACCESS not-accessible
      STATUS mandatory
  --% AVAILABILITY public
      DESCRIPTION
         "This object is sent in a trap to report the type associated
          with a virtual drive for which the trap condition
          occurred.
         "
      ::= { fujitsus4TrapObject 19 }



fujitsus4TrapObjectImageFileUpgradeResult OBJECT-TYPE
      SYNTAX ImageFileUpgradeResultsEnum
      ACCESS not-accessible
      STATUS mandatory
  --% AVAILABILITY public
      DESCRIPTION
         "This object is sent in a trap to report the results of a
          TFTP or ASMP image upgrade."
      ::= { fujitsus4TrapObject 20 }



fujitsus4TrapObjectPduDevicePort OBJECT-TYPE
      SYNTAX INTEGER (1..2)
      ACCESS not-accessible
      STATUS mandatory
  --% AVAILABILITY public
      DESCRIPTION
         "This object is sent in a trap to identify the appliance port 
         that the power device is attached to for which the trap condition
         occurred.
         "
      ::= { fujitsus4TrapObject 21 }


fujitsus4TrapObjectPduOutlet OBJECT-TYPE
      SYNTAX INTEGER (1..16)
      ACCESS not-accessible
      STATUS mandatory
  --% AVAILABILITY public
      DESCRIPTION
         "This object is sent in a trap to identify the power device outlet 
         number for which the trap condition occurred.
         "
      ::= { fujitsus4TrapObject 22 }



fujitsus4TrapObjectOldName OBJECT-TYPE
      SYNTAX UTF8String ( SIZE (0..64) )
      ACCESS not-accessible
      STATUS mandatory
  --% AVAILABILITY public
      DESCRIPTION
         "This object is sent in a trap to identify the old name of a port
         or power device outlet for which the trap condition occurred.
         "
      ::= { fujitsus4TrapObject 23 }


fujitsus4TrapObjectItemName OBJECT-TYPE
      SYNTAX UTF8String ( SIZE (0..64) )
      ACCESS not-accessible
      STATUS mandatory
  --% AVAILABILITY public
      DESCRIPTION
         "This object is sent in a trap to identify the name of a port
         or power device outlet for which the trap condition occurred.
         "
      ::= { fujitsus4TrapObject 24 }



fujitsus4TrapObjectPduDeviceInlet OBJECT-TYPE
      SYNTAX INTEGER
      ACCESS not-accessible
      STATUS mandatory
  --% AVAILABILITY public
      DESCRIPTION
         "This object is sent in a trap to identify the inlet of a power device 
         for which the trap condition occurred.
         "
      ::= { fujitsus4TrapObject 25 }

fujitsus4TrapObjectPduDeviceNumber OBJECT-TYPE
      SYNTAX INTEGER
      ACCESS not-accessible
      STATUS mandatory
  --% AVAILABILITY public
      DESCRIPTION
         "This object is sent in a trap to identify the power device number
         that is attached to an appliance port for which the trap
         condition occurred.
         "
      ::= { fujitsus4TrapObject 26 }



fujitsus4TrapObjectInputPort OBJECT-TYPE
      SYNTAX INTEGER
      ACCESS not-accessible
      STATUS mandatory
  --% AVAILABILITY public
      DESCRIPTION
         "This object is sent in a trap to identify the appliance input port
         number for which the trap condition occurred. An input port is defined
         here as an ARI port that interfaces the data traffic coming from
         or going directly or indirectly to a target device. The values range
         from 1 to the maximum number of ARI ports.
         "
      ::= { fujitsus4TrapObject 27 }


fujitsus4TrapObjectOldInputPort OBJECT-TYPE
      SYNTAX INTEGER
      ACCESS not-accessible
      STATUS mandatory
  --% AVAILABILITY public
      DESCRIPTION
         "This object is sent in a trap to identify the old appliance input port
         number for which the trap condition occurred. An input port is defined
         here as an ARI port that interfaces the data traffic coming from
         or going directly or indirectly to a target device. The values range
         from 1 to the maximum number of ARI ports.
         "
      ::= { fujitsus4TrapObject 28 }


fujitsus4TrapObjectPowerSupply OBJECT-TYPE
      SYNTAX DisplayString ( SIZE (0..5) )
      ACCESS not-accessible
      STATUS mandatory
  --% AVAILABILITY public
      DESCRIPTION
         "This object is sent in a trap to identify the power supply
         for which the trap condition occurred.
         "
      ::= { fujitsus4TrapObject 29 }


fujitsus4TrapObjectPreviousScreenResolution OBJECT-TYPE
      SYNTAX DisplayString ( SIZE (0..32) )
      ACCESS not-accessible
      STATUS mandatory
  --% AVAILABILITY public
      DESCRIPTION
         "This object is sent in a trap to identify the previous screen
         resolution of the target target device.
         "
      ::= { fujitsus4TrapObject 30 }


fujitsus4TrapObjectCurrentScreenResolution OBJECT-TYPE
      SYNTAX DisplayString ( SIZE (0..32) )
      ACCESS not-accessible
      STATUS mandatory
  --% AVAILABILITY public
      DESCRIPTION
         "This object is sent in a trap to identify the current screen
         resolution of the target server.
         "
      ::= { fujitsus4TrapObject 31 }


fujitsus4TrapObjectAggregatedTargetDeviceStatusChanged OBJECT-TYPE
      SYNTAX OCTET STRING ( SIZE (12..5122) )
      ACCESS not-accessible
      STATUS mandatory
  --% AVAILABILITY public
      DESCRIPTION
         "This object is sent in a trap to report server status changes. This
         object will report the status change of multiple servers (connection
         paths) in an aggregated encoding format as indicated below.

         Note that on bootup the appliance will send this object in the
         fujitsus4AggregatedTargetDeviceStatusChangedTrap containing the status of all
         connection paths in the appliance. Thereafter the appliance will
         send this object in the fujitsus4AggregatedTargetDeviceStatusChangedTrap containing
         only the connection paths whose status has changed.

         This object is composed of two sections, which are the header section
         and the connection path section. The header section provides version
         information and is the first 2 bytes of this object. The connection
         path section provides information on each of the connection paths and
         is defined in the bytes following the header.

         Header Section
         --------------

         Byte 1 = Start indicator for the header section. The value of the
                       start indicator is always zero. The value of the start
                       indicator provides means for management applications to
                       determine that this object has a header section. All
                       previous implementations of this object have a non-zero
                       value in the first byte.

         Byte 2 = Version of the aggregate object. The version provides
                       means to identify the format/structure of this aggregate
                       object. The format of the aggregate object, as described
                       here, is identified with a value of 3 for the version.


         Connection Path Section
         -----------------------

         The connection path section is composed of 1 or more connection paths.
         The information for each connection path is packed into 10 bytes as
         follows:

         Byte 1 = The appliance input port number associated with this
                       connection path. The input port is an ARI port that
                       interfaces the data traffic coming from or going directly
                       or indirectly to a target device or a power device.

                       Note that a power device will report the port number as
                       100 + the power device port number. For the first power
                       device port, Byte 1 will report 101 for the power device.
                       This will avoid potential port conflicts for ARI and
                       power device ports. In the event that additional power
                       device ports are available, the number will reflect the
                       power device port number (i.e. 101, 102, etc.)

         Byte 2 = The cascade switch channel number associated with this
                       connection path. The value will be 0 if a switch channel
                       is not associated with this connection path.

                       For power devices, this Byte will represent the power
                       device number. Byte 3 will contain the outlet number
                       for this connection path.

         Byte 3 ~ 8 = The EID of the KVM-IA associated with this connection path.
                       Each byte in this field will encode two digits of the
                       KVM-IA's EID number. For example, if the actual EID number
                       on the label attached to a KVM-IA is 520255-0346DC then
                       bytes 3 through 8 would contain the following hex values:

                          Byte 3 = 0x52
                          Byte 4 = 0x02
                          Byte 5 = 0x55
                          Byte 6 = 0x03
                          Byte 7 = 0x46
                          Byte 8 = 0xDC

                       Note that the dash character is not represented in
                       the encoded value.

                       For a power device, the first byte (Byte 3) will
                       represent the outlet number and the remaining 5 bytes
                       (Byte 4-8) will be 0.

         Byte 9 ~ the left most 4 bits

                     = The left most four bits of the 9th byte shall be used
                       to encode / decode the following integer value to
                       represent the power status of a connected server or the
                       power status of a power device outlet.

                       One of the following values can be reported:

                       1 = Off - The connection path does not have power,
                                    which could be the result of the following
                                    situation: the KVM-IA is unplugged or the
                                    KVM-IA is plugged in but receives no power
                                    from the target device.

                       2 = On - The connection path has power.


         Byte 9 ~ the right most 4 bits

                     = The right most four bits of the 9th byte shall be used
                       to encode / decode the following integer value to
                       represent the viewer session status of a connection path.
                       For a power device or power device outlet, this value is
                       always 1 since viewer sessions are not supported.

                       One of the following values can be reported:

                       1 = Idle - There is not a viewer session active on
                                      this connection path.

                       2 = Active - There is an active viewer session on this
                                      connection path.

                       3 = Blocked - The connection path is blocked meaning a
                                      viewer session cannot be established to
                                      this connection path because of another
                                      viewer session is currently using a
                                      resource required by this connection path
                                      in order to establish a connection path.
                                      A viewer session cannot be blocked by
                                      a virtual media session.

         Byte 10 ~ the left most 4 bits

                     = The left most four bits of the 10th byte shall be used
                       to encode / decode the following integer value to
                       represent the virtual media session status of a
                       connection path. For a power device or power device
                       outlet, this value is always 1 since virtual media
                       sessions are not supported.

                       One of the following values can be reported:

                       1 = Idle - There is not a virtual media session
                                      active on this connection path.

                       2 = Active - There is a virtual media session on this
                                      connection path.

                       3 = Blocked - The connection path is blocked meaning a
                                      virtual media session cannot be
                                      established to this connection path
                                      because of another virtual media session
                                      is currently using a resource required by
                                      this connection path in order to establish
                                      a connection path. A virtual media session
                                      cannot be blocked by a viewer session.

         Byte 10 ~ the right most 4 bits
                     = The right most four bits of the 10th byte shall be used
                       for future use and they will have a value of 0.

         Every connection path will be packed into this object in 10 byte
         increments one after the other. The connection paths do not have to be
         packed in any specific order. Note that the size of this object could
         conceivably be as large as shown in the following calculation with
         these assumptions.
            - 24 channel switch connected to each port of the appliance
            - 4 power devices connected to appliance, each having 32 outlets

         (((16 ports X 24 channels) + (4 power devices X 32 power device outlets))
            X 10 bytes) + (2 byte Header) = 5122.
         "
      ::= { fujitsus4TrapObject 32 }



fujitsus4TrapObjectPduDeviceCircuit OBJECT-TYPE
      SYNTAX INTEGER
      ACCESS not-accessible
      STATUS mandatory
  --% AVAILABILITY public
      DESCRIPTION
         "This object is sent in a trap to identify the circuit of a power 
         device for which the trap condition occurred.
         "
      ::= { fujitsus4TrapObject 33 }



fujitsus4TrapObjectSessionType OBJECT-TYPE
      SYNTAX DisplayString( SIZE (0..16) )
      ACCESS not-accessible
      STATUS mandatory
  --% AVAILABILITY public
      DESCRIPTION
         "This object is sent in a trap to identify the session type for
         which a trap condition occurred.

         The value is KVM for a KVM session,
         or Serial for a Serial session.
         "
      ::= { fujitsus4TrapObject 34 }

--------------------------------------------------------------------------------
-- Enterprise Traps
--------------------------------------------------------------------------------

fujitsus4RebootStartedTrap TRAP-TYPE
      ENTERPRISE fujitsus4Products
      VARIABLES { fujitsus4TrapObjectUserName }
      DESCRIPTION
         "The appliance is in the process of rebooting.

         The name of the user who initiated the reboot
         is contained in fujitsus4TrapObjectUserName.
         "

      --#SUMMARY "The appliance is rebooting. Command issued by user: %s."
      --#ARGUMENTS { 0 }
      --#SEVERITY INFORMATIONAL
      --#FACILITY KERNEL
      --#CATEGORY "Status Events"
      --% TrapTypeEnum=5
      ::= 1


fujitsus4UserLoginTrap TRAP-TYPE
      ENTERPRISE fujitsus4Products
      VARIABLES { fujitsus4TrapObjectUserName }
      DESCRIPTION
         "A user logged into the appliance.

         The name of the user who logged in
         is contained in fujitsus4TrapObjectUserName.
         "

      --#SUMMARY "User logged into the appliance. User: %s."
      --#ARGUMENTS { 0 }
      --#SEVERITY INFORMATIONAL
      --#FACILITY SECURITY
      --#CATEGORY "Status Events"
      --% TrapTypeEnum=6
      ::= 2


fujitsus4UserLogoutTrap TRAP-TYPE
      ENTERPRISE fujitsus4Products
      VARIABLES { fujitsus4TrapObjectUserName }
      DESCRIPTION
         "A user logged out of the appliance.

         The name of the user who logged out is contained
         in fujitsus4TrapObjectUserName.
         "

      --#SUMMARY "User logged out of the appliance. User: %s."
      --#ARGUMENTS { 0 }
      --#SEVERITY INFORMATIONAL
      --#FACILITY SECURITY
      --#CATEGORY "Status Events"
      --% TrapTypeEnum=7
      ::= 3


fujitsus4TargetSessionStartedTrap TRAP-TYPE
      ENTERPRISE fujitsus4Products
      VARIABLES {
                     fujitsus4TrapObjectUserName,
                     fujitsus4TrapObjectSessionIdentifier,
                     fujitsus4TrapObjectUserAddress,
                     fujitsus4TrapObjectSessionType
                  }
      DESCRIPTION
         "A target session has started. This may be a serial or KVM
         session, depending on the type of target.

         The name of the user who is connected to the session
         is contained in fujitsus4TrapObjectUserName.

         The session identifier is contained in
         fujitsus4TrapObjectSessionIdentifier.

         The user address is contained in
         fujitsus4TrapObjectUserAddress.

         The session type is contained in
         fujitsus4TrapObjectSessionType.
         "

      --#SUMMARY "Target session started. User: %s. Target device: %s. Address: %s. Type: %s."
      --#ARGUMENTS { 0, 1, 2, 3 }
      --#SEVERITY INFORMATIONAL
      --#FACILITY SECURITY
      --#CATEGORY "Status Events"
      --% TrapTypeEnum=8
      ::= 4


fujitsus4TargetSessionStoppedTrap TRAP-TYPE
      ENTERPRISE fujitsus4Products
      VARIABLES {
                     fujitsus4TrapObjectUserName,
                     fujitsus4TrapObjectSessionIdentifier,
                     fujitsus4TrapObjectUserAddress,
                     fujitsus4TrapObjectSessionType
                  }
      DESCRIPTION
         "A target session has stoppped. This may be a serial or KVM
         session, depending on the type of target.

         The name of the user who was connected to the session
         is contained in fujitsus4TrapObjectUserName.

         The session identifier is contained in
         fujitsus4TrapObjectSessionIdentifier.

         The user address is contained in
         fujitsus4TrapObjectUserAddress.

         The session type is contained in
         fujitsus4TrapObjectSessionType.
         "

      --#SUMMARY "Target session stopped. User: %s. Target device: %s. Address: %s. Type: %s."
      --#ARGUMENTS { 0, 1, 2, 3 }
      --#SEVERITY INFORMATIONAL
      --#FACILITY SECURITY
      --#CATEGORY "Status Events"
      --% TrapTypeEnum=9
      ::= 5


fujitsus4TargetSessionTerminatedTrap TRAP-TYPE
      ENTERPRISE fujitsus4Products
      VARIABLES {
                     fujitsus4TrapObjectUserName,
                     fujitsus4TrapObjectTargetUserName,
                     fujitsus4TrapObjectSessionIdentifier,
                     fujitsus4TrapObjectUserAddress,
                     fujitsus4TrapObjectSessionType
                  }
      DESCRIPTION
         "A target session has been terminated by another
         user. This may be a serial or KVM session, depending on the
         type of target.

         The name of the user who terminated the session is
         contained in fujitsus4TrapObjectUserName if available. An empty
         string is reported if a user name is not available.

         The name of the user who was terminated from the session
         is contained in fujitsus4TrapObjectTargetUserName.

         The session identifier is contained in
         fujitsus4TrapObjectSessionIdentifier.

         The user address is contained in
         fujitsus4TrapObjectUserAddress.

         The session type is contained in
         fujitsus4TrapObjectSessionType.
         "

      --#SUMMARY "Target session terminated. Commanded by user: %s. User: %s. Target device: %s. Address: %s. Type: %s."
      --#ARGUMENTS { 0, 1, 2, 3, 4 }
      --#SEVERITY INFORMATIONAL
      --#FACILITY SECURITY
      --#CATEGORY "Status Events"
      --% TrapTypeEnum=10
      ::= 6


fujitsus4LocalPortSessionStartedTrap TRAP-TYPE
      ENTERPRISE fujitsus4Products
      VARIABLES { fujitsus4TrapObjectSessionIdentifier }
      DESCRIPTION
         "A local port target session has started.

         The session identifier is contained in
         fujitsus4TrapObjectSessionIdentifier.

         This Trap is deprecated and is no longer used.
         "

      --#SUMMARY "Local port target session started. Target device: %s."
      --#ARGUMENTS { 0 }
      --#SEVERITY INFORMATIONAL
      --#FACILITY SECURITY
      --#CATEGORY "Status Events"
      --% TrapTypeEnum=11
      ::= 7


fujitsus4LocalPortSessionStoppedTrap TRAP-TYPE
      ENTERPRISE fujitsus4Products
      VARIABLES { fujitsus4TrapObjectSessionIdentifier }
      DESCRIPTION
         "A local port target session has stopped.

         The session identifier is contained in
         fujitsus4TrapObjectSessionIdentifier.

         This Trap is deprecated and is no longer used.
         "

      --#SUMMARY "Local port target session stopped. Target device: %s."
      --#ARGUMENTS { 0 }
      --#SEVERITY INFORMATIONAL
      --#FACILITY SECURITY
      --#CATEGORY "Status Events"
      --% TrapTypeEnum=12
      ::= 8


fujitsus4LocalPortSessionTerminatedTrap TRAP-TYPE
      ENTERPRISE fujitsus4Products
      VARIABLES {
                     fujitsus4TrapObjectUserName,
                     fujitsus4TrapObjectSessionIdentifier
                  }
      DESCRIPTION
         "A local port target session has been terminated by another
          user.

          The name of the user who terminated the session is
          contained in fujitsus4TrapObjectUserName.


          The session identifier is contained in
          fujitsus4TrapObjectSessionIdentifier.

          This Trap is deprecated and is no longer used.
         "

      --#SUMMARY "Local Port Target session terminated. Command issued by user: %s. Target device: %s."
      --#ARGUMENTS { 0, 1 }
      --#SEVERITY INFORMATIONAL
      --#FACILITY SECURITY
      --#CATEGORY "Status Events"
      --% TrapTypeEnum=13
      ::= 9


fujitsus4ImageFileUpgradeStarted TRAP-TYPE
      ENTERPRISE fujitsus4Products
      VARIABLES {
                     fujitsus4TrapObjectUserName,
                     fujitsus4TrapObjectFileName,
                     fujitsus4TrapObjectImageNewVersion,
                     fujitsus4TrapObjectImageCurrentVersion
                  }
      DESCRIPTION
         "The appliance has started an image upgrade.

         The name of the user who originally started the image upgrade is
         contained in fujitsus4TrapObjectUserName if available. An empty
         string is reported if a user name is not available.

         The URL of the file that was loaded is contained in
         fujitsus4TrapObjectFileName.

         The version of the image that the appliance is upgrading to is
         contained in fujitsus4TrapObjectImageNewVersion.

         The version of the image that the appliance is currently running
         is contained in fujitsus4TrapObjectImageCurrentVersion.
         "

      --#SUMMARY "Image upgrade started. Command issued by user: %s. File: %s. New version: %s. Current version: %s"
      --#ARGUMENTS { 0, 1, 2, 3 }
      --#SEVERITY INFORMATIONAL
      --#FACILITY SYSTEM
      --#CATEGORY "Status Events"
      --% TrapTypeEnum=14
      ::= 10


fujitsus4ImageFileUpgradeResultsTrap TRAP-TYPE
      ENTERPRISE fujitsus4Products
      VARIABLES { fujitsus4TrapObjectImageFileUpgradeResult }
      DESCRIPTION
         "The result of an image upgrade."

      --#SUMMARY "Image upgrade result: %d"
      --#ARGUMENTS { 0 }
      --#SEVERITY INFORMATIONAL
      --#FACILITY SYSTEM
      --#CATEGORY "Status Events"
      --% TrapTypeEnum=15
      ::= 11


fujitsus4UserAddedTrap TRAP-TYPE
      ENTERPRISE fujitsus4Products
      VARIABLES {
                     fujitsus4TrapObjectUserName,
                     fujitsus4TrapObjectTargetUserName
                  }
      DESCRIPTION
         "A new user has been added to the local user database.

         The name of the user who added the new user is contained
         in fujitsus4TrapObjectUserName.

         The name of the new user is contained in
         fujitsus4TrapObjectTargetUserName.
         "

      --#SUMMARY "New user added to local user database. Command issued by user: %s. New user: %s."
      --#ARGUMENTS { 0, 1 }
      --#SEVERITY INFORMATIONAL
      --#FACILITY SECURITY
      --#CATEGORY "Configuration Events"
      --% TrapTypeEnum=16
      ::= 12


fujitsus4UserDeletedTrap TRAP-TYPE
      ENTERPRISE fujitsus4Products
      VARIABLES {
                     fujitsus4TrapObjectUserName,
                     fujitsus4TrapObjectTargetUserName
                  }
      DESCRIPTION
         "A user has been deleted from the local user database.

         The name of the user who deleted the user is contained
         in fujitsus4TrapObjectUserName.

         The name of the user who was deleted is contained
         in fujitsus4TrapObjectTargetUserName.
         "

      --#SUMMARY "User deleted from local user database. Command issued by user: %s. Deleted user: %s."
      --#ARGUMENTS { 0, 1 }
      --#SEVERITY INFORMATIONAL
      --#FACILITY SECURITY
      --#CATEGORY "Configuration Events"
      --% TrapTypeEnum=17
      ::= 13


fujitsus4UserModifiedTrap TRAP-TYPE
      ENTERPRISE fujitsus4Products
      VARIABLES {
                     fujitsus4TrapObjectUserName,
                     fujitsus4TrapObjectTargetUserName
                  }
      DESCRIPTION
         "A user was modified.

         The name of the user who modified the user is contained
         in fujitsus4TrapObjectUserName.

         The name of the user who was modified is contained
         in fujitsus4TrapObjectTargetUserName.
         "

      --#SUMMARY "User modified in local user database. Command issued by user: %s. Modified user: %s."
      --#ARGUMENTS { 0, 1 }
      --#SEVERITY INFORMATIONAL
      --#FACILITY SECURITY
      --#CATEGORY "Configuration Events"
      --% TrapTypeEnum=18
      ::= 14



fujitsus4UserLockedTrap TRAP-TYPE
      ENTERPRISE fujitsus4Products
      VARIABLES {
                     fujitsus4TrapObjectTargetUserName,
                     fujitsus4TrapObjectLockReason
                  }
      DESCRIPTION
         "A user account has been locked.

         The name of the user who was locked is contained
         in fujitsus4TrapObjectTargetUserName.

         The reason for which the user account has been locked is contained
         in fujitsus4TrapObjectLockReason.
         "

      --#SUMMARY "User account has been locked. Locked user: %s. Reason: %s"
      --#ARGUMENTS { 0, 1 }
      --#SEVERITY MINOR
      --#FACILITY SECURITY
      --#CATEGORY "Status Events"
      --% TrapTypeEnum=19
      ::= 15


fujitsus4UserUnlockedTrap TRAP-TYPE
      ENTERPRISE fujitsus4Products
      VARIABLES {
                     fujitsus4TrapObjectUserName,
                     fujitsus4TrapObjectTargetUserName,
                     fujitsus4TrapObjectUnlockReason
                  }
      DESCRIPTION
         "A user account has been unlocked.

         The name of the user who unlocked the user is contained
         in fujitsus4TrapObjectUserName. When the user account is unlocked
         by an appliance reboot or by the expiration of the lockout period
         (as specified in the fujitsus4TrapObjectUnlockReason object), the
         name of the user will be blank.

         The name of the user who was unlocked is contained
         in fujitsus4TrapObjectTargetUserName.

         The reason for which the user account has been unlocked is contained
         in fujitsus4TrapObjectUnlockReason.
         "

      --#SUMMARY "User account has been unlocked. Command issued by user: %s. Unlocked user: %s. Reason: %s"
      --#ARGUMENTS { 0, 1, 2 }
      --#SEVERITY MINOR
      --#FACILITY SECURITY
      --#CATEGORY "Status Events"
      --% TrapTypeEnum=20
      ::= 16



fujitsus4UserAuthenticationFailureTrap TRAP-TYPE
      ENTERPRISE fujitsus4Products
      VARIABLES { fujitsus4TrapObjectUserName }
      DESCRIPTION
         "A user failed to authenticate with the appliance.

         The name of the user who failed to authenticate
         is contained in fujitsus4TrapObjectUserName.
         "

      --#SUMMARY "User authentication failed with the appliance. User: %s."
      --#ARGUMENTS { 0 }
      --#SEVERITY INFORMATIONAL
      --#FACILITY SECURITY
      --#CATEGORY "Status Events"
      --% TrapTypeEnum=21
      ::= 17


fujitsus4KVM-IAAddedTrap TRAP-TYPE
      ENTERPRISE fujitsus4Products
      VARIABLES { fujitsus4TrapObjectKVM-IAId }
      DESCRIPTION
         "A KVM-IA was added. The ID of the KVM-IA which was added is
         contained in fujitsus4TrapObjectKVM-IAId.
         "

      --#SUMMARY "KVM-IA added. KVM-IA ID: %s."
      --#ARGUMENTS { 0 }
      --#SEVERITY INFORMATIONAL
      --#FACILITY SYSTEM
      --#CATEGORY "Configuration Events"
      --% TrapTypeEnum=22
      ::= 18


fujitsus4KVM-IARemovedTrap TRAP-TYPE
      ENTERPRISE fujitsus4Products
      VARIABLES { fujitsus4TrapObjectKVM-IAId }
      DESCRIPTION
         "A KVM-IA was removed. The ID of the KVM-IA which was removed is
         contained in fujitsus4TrapObjectKVM-IAId.
         "

      --#SUMMARY "KVM-IA removed. KVM-IA ID: %s."
      --#ARGUMENTS { 0 }
      --#SEVERITY INFORMATIONAL
      --#FACILITY SYSTEM
      --#CATEGORY "Configuration Events"
      --% TrapTypeEnum=23
      ::= 19


fujitsus4KVM-IAMovedTrap TRAP-TYPE
      ENTERPRISE fujitsus4Products
      VARIABLES {
                    fujitsus4TrapObjectKVM-IAId,
                    fujitsus4TrapObjectTargetDeviceName,
                    fujitsus4TrapObjectInputPort,
                    fujitsus4TrapObjectOldInputPort
                  }
      DESCRIPTION
         "A KVM-IA was moved. 

         The ID of the KVM-IA which was moved is contained in fujitsus4TrapObjectKVM-IAId.

         The name of the target device attached to the KVM-IA is contained in
         fujitsus4TrapObjectTargetDeviceName.

         The input port number on the appliance that the KVM-IA is now
         connected to is contained in fujitsus4TrapObjectInputPort.

         The input port number on the appliance that the KVM-IA
         was previously connected to is contained in
         fujitsus4TrapObjectOldInputPort.
         "

      --#SUMMARY "KVM-IA moved. KVM-IA ID: %s."
      --#ARGUMENTS { 0 }
      --#SEVERITY INFORMATIONAL
      --#FACILITY SYSTEM
      --#CATEGORY "Configuration Events"
      --% TrapTypeEnum=24
      ::= 20


fujitsus4TargetDeviceNameChangedTrap TRAP-TYPE
      ENTERPRISE fujitsus4Products
      VARIABLES {
                     fujitsus4TrapObjectOldTargetDeviceName,
                     fujitsus4TrapObjectTargetDeviceName,
                     fujitsus4TrapObjectKVM-IAId
                  }
      DESCRIPTION
         "The name of a server has changed.

         The previous name of the server is contained in
         fujitsus4TrapObjectOldTargetDeviceName.

         The new name of the server is contained in
         fujitsus4TrapObjectTargetDeviceName.

         The ID of the KVM-IA the server is attached to is
         contained in fujitsus4TrapObjectKVM-IAId.
         "

      --#SUMMARY "Target device name changed. Old name: %s. New name: %s. Attached to KVM-IA: %s."
      --#ARGUMENTS { 0, 1, 2 }
      --#SEVERITY INFORMATIONAL
      --#FACILITY SYSTEM
      --#CATEGORY "Configuration Events"
      --% TrapTypeEnum=25
      ::= 21


fujitsus4CascadeSwitchAddedTrap TRAP-TYPE
      ENTERPRISE fujitsus4Products
      VARIABLES {
                    fujitsus4TrapObjectCascadeSwitchName,
                    fujitsus4TrapObjectKVM-IAId
                  }
      DESCRIPTION
         "A cascade switch was added. The name of the switch
         which was added is contained in fujitsus4TrapObjectCascadeSwitchName.

         The ID of the KVM-IA the switch was added to is contained
         in fujitsus4TrapObjectKVM-IAId.
         "

      --#SUMMARY "Cascade switch added. Cascade switch name: %s. Attached to KVM-IA: %s."
      --#ARGUMENTS { 0, 1 }
      --#SEVERITY INFORMATIONAL
      --#FACILITY SYSTEM
      --#CATEGORY "Configuration Events"
      --% TrapTypeEnum=26
      ::= 22


fujitsus4CascadeSwitchRemovedTrap TRAP-TYPE
      ENTERPRISE fujitsus4Products
      VARIABLES {
                    fujitsus4TrapObjectCascadeSwitchName,
                    fujitsus4TrapObjectKVM-IAId
                  }
      DESCRIPTION
         "A cascade switch was removed. The name of the switch
         which was removed is contained in
         fujitsus4TrapObjectCascadeSwitchName.

         The ID of the KVM-IA the switch was attached to is contained
         in fujitsus4TrapObjectKVM-IAId.
         "

      --#SUMMARY "Cascade switch removed. Cascade switch name: %s. Was attached to KVM-IA: %s."
      --#ARGUMENTS { 0, 1 }
      --#SEVERITY INFORMATIONAL
      --#FACILITY SYSTEM
      --#CATEGORY "Configuration Events"
      --% TrapTypeEnum=27
      ::= 23


fujitsus4CascadeSwitchNameChangedTrap TRAP-TYPE
      ENTERPRISE fujitsus4Products
      VARIABLES {
                     fujitsus4TrapObjectOldCascadeSwitchName,
                     fujitsus4TrapObjectCascadeSwitchName,
                     fujitsus4TrapObjectKVM-IAId
                  }
      DESCRIPTION
         "The name of a cascade switch has changed.

         The previous name of the cascade switch is contained in
         fujitsus4TrapObjectOldCascadeSwitchName.

         The new name of the cascade switch is contained in
         fujitsus4TrapObjectCascadeSwitchName.

         The ID of the KVM-IA the switch is attached to is contained
         in fujitsus4TrapObjectKVM-IAId.
         "

      --#SUMMARY "Cascade switch name changed. Old name: %s. New name: %s. Attached to KVM-IA: %s."
      --#ARGUMENTS { 0, 1, 2 }
      --#SEVERITY INFORMATIONAL
      --#FACILITY SYSTEM
      --#CATEGORY "Configuration Events"
      --% TrapTypeEnum=28
      ::= 24


fujitsus4ConfigurationFileLoadedTrap TRAP-TYPE
      ENTERPRISE fujitsus4Products
      VARIABLES {
                     fujitsus4TrapObjectUserName,
                     fujitsus4TrapObjectFileName
                  }
      DESCRIPTION
         "The appliance has loaded a configuration file.

         The name of the user who commanded the appliance to
         load the configuration file is contained in
         fujitsus4TrapObjectUserName.

         The URL of the file that was loaded is contained in
         fujitsus4TrapObjectFileName.
         "

      --#SUMMARY "Configuration file loaded in the appliance. Command issued by user: %s. Name of file loaded: %s."
      --#ARGUMENTS { 0, 1 }
      --#SEVERITY INFORMATIONAL
      --#FACILITY SYSTEM
      --#CATEGORY "Configuration Events"
      --% TrapTypeEnum=29
      ::= 25


fujitsus4UserDatabaseFileLoadedTrap TRAP-TYPE
      ENTERPRISE fujitsus4Products
      VARIABLES {
                     fujitsus4TrapObjectUserName,
                     fujitsus4TrapObjectFileName
                  }
      DESCRIPTION
         "The appliance has loaded a user database file.

          The name of the user who commanded the appliance to
          load the user database file is contained in
          fujitsus4TrapObjectUserName.

          The URL of the file that was loaded is contained in
          fujitsus4TrapObjectFileName.
         "

      --#SUMMARY "User database file loaded in the appliance. Command issued by user: %s. Name of file loaded: %s."
      --#ARGUMENTS { 0, 1 }
      --#SEVERITY INFORMATIONAL
      --#FACILITY SECURITY
      --#CATEGORY "Configuration Events"
      --% TrapTypeEnum=30
      ::= 26

--
-- KVM-IA Update Traps
--

fujitsus4KVM-IAImageUpgradeStarted TRAP-TYPE
      ENTERPRISE fujitsus4Products
      VARIABLES {
                     fujitsus4TrapObjectUserName,
                     fujitsus4TrapObjectTypeOfImage,
                     fujitsus4TrapObjectImageNewVersion,
                     fujitsus4TrapObjectImageCurrentVersion,
                     fujitsus4TrapObjectTargetDeviceName,
                     fujitsus4TrapObjectKVM-IAId
                  }
      DESCRIPTION
         "A software image upgrade has started on a KVM-IA.

         The name of the user who originally started the image upgrade is
         contained in fujitsus4TrapObjectUserName if available. An empty
         string is reported if a user name is not available.

         The type of software image being upgraded is contained in
         fujitsus4TrapObjectKVM-IATypeOfImage.

         The software image version the KVM-IA is upgrading to is
         contained in fujitsus4TrapObjectImageNewVersion.

         The software image version the KVM-IA is currently running
         is contained in fujitsus4TrapObjectImageCurrentVersion.

         The name of the server connected to the KVM-IA being upgraded is
         contained in fujitsus4TrapObjectTargetDeviceName.

         The ID of the KVM-IA being upgraded is contained in
         fujitsus4TrapObjectKVM-IAId
         "
      --#SUMMARY "KVM-IA image upgrade started. Command issued by user: %s. Image type: %d. New version: %s. Current version: %s. Target device: %s. KVM-IA ID: %s."
      --#ARGUMENTS { 0, 1, 2, 3, 4, 5 }
      --#SEVERITY INFORMATIONAL
      --#FACILITY SYSTEM
      --#CATEGORY "Status Events"
      --% TrapTypeEnum=32
      ::= 28


fujitsus4KVM-IAImageUpgradeResultTrap TRAP-TYPE
      ENTERPRISE fujitsus4Products
      VARIABLES {
                     fujitsus4TrapObjectKVM-IAImageUpgradeResult,
                     fujitsus4TrapObjectTargetUserName,
                     fujitsus4TrapObjectTypeOfImage,
                     fujitsus4TrapObjectImageNewVersion,
                     fujitsus4TrapObjectImageCurrentVersion,
                     fujitsus4TrapObjectTargetDeviceName,
                     fujitsus4TrapObjectKVM-IAId
                  }
      DESCRIPTION
         "The result of a KVM-IA software image upgrade.

         The image upgrade result is contained in
         fujitsus4TrapObjectKVM-IAImageUpgradeResult.

         The name of the user who originally started the image upgrade is
         contained in fujitsus4TrapObjectUserName if available. An empty
         string is reported if a user name is not available.

         The type of software image the upgrade result is for is contained in
         fujitsus4TrapObjectTypeOfImage.

         The software image version the KVM-IA attempted to upgrade to
         is contained in fujitsus4TrapObjectImageNewVersion.

         The software image version the KVM-IA is running is contained
         in fujitsus4TrapObjectImageCurrentVersion. If the software image
         upgrade was successful then this version will match the version
         reported in fujitsus4TrapObjectImageNewVersion.

         The name of the server connected to the KVM-IA is
         contained in fujitsus4TrapObjectTargetDeviceName.

         The ID of the KVM-IA the result is for is contained in
         fujitsus4TrapObjectKVM-IAId.

         "
      --#SUMMARY "KVM-IA image upgrade result. Result: %d. Upgrade was started by user: %s. Upgrade image type: %d. Upgrade version: %s. Running version: %s. Target device: %s. KVM-IA ID: %s."
      --#ARGUMENTS { 0, 1, 2, 3, 4, 5, 6 }
      --#SEVERITY INFORMATIONAL
      --#FACILITY SYSTEM
      --#CATEGORY "Status Events"
      --% TrapTypeEnum=33
      ::= 29


fujitsus4KVM-IARestartedTrap TRAP-TYPE
      ENTERPRISE fujitsus4Products
      VARIABLES {
                     fujitsus4TrapObjectTargetDeviceName,
                     fujitsus4TrapObjectKVM-IAId
                  }
      DESCRIPTION
         "A KVM-IA has restarted. A KVM-IA will restart after
          a KVM-IA image upgrade completes.

          The name of the server connected to the KVM-IA is
          contained in fujitsus4TrapObjectTargetDeviceName.

          The ID of the KVM-IA that restarted is for is contained in
          fujitsus4TrapObjectKVM-IAId.
         "
      --#SUMMARY "KVM-IA restarted. Target device: %s. KVM-IA ID: %s."
      --#ARGUMENTS { 0, 1 }
      --#SEVERITY INFORMATIONAL
      --#FACILITY SYSTEM
      --#CATEGORY "Status Events"
      --% TrapTypeEnum=34
      ::= 30



--
-- Virtual Media Traps
--

fujitsus4VirtualMediaSessionStartedTrap TRAP-TYPE
      ENTERPRISE fujitsus4Products
      VARIABLES {
                     fujitsus4TrapObjectUserName,
                     fujitsus4TrapObjectTargetDeviceName,
                     fujitsus4TrapObjectKVM-IAId,
                     fujitsus4TrapObjectUserAddress
                  }
      DESCRIPTION
         "A Virtual Media session to a server has started. A target
          session to the server must have been established by the same user
          prior to starting the VM session.

          The name of the user who connected to the VM session
          is contained in fujitsus4TrapObjectUserName.

          The name of the server the user connected to is contained in
          fujitsus4TrapObjectTargetDeviceName.

          The ID of the KVM-IA the target session is using is contained in
          fujitsus4TrapObjectKVM-IAId.

          The user address is contained in
          fujitsus4TrapObjectUserAddress.
        "
      --#SUMMARY "Virtual media session started. User: %s. Target device: %s. KVM-IA: %s. Address: %s."
      --#ARGUMENTS { 0, 1, 2, 3 }
      --#SEVERITY INFORMATIONAL
      --#FACILITY SECURITY
      --#CATEGORY "Status Events"
      --% TrapTypeEnum=35
      ::= 31


fujitsus4VirtualMediaSessionStoppedTrap TRAP-TYPE
      ENTERPRISE fujitsus4Products
      VARIABLES {
                     fujitsus4TrapObjectUserName,
                     fujitsus4TrapObjectTargetDeviceName,
                     fujitsus4TrapObjectUserAddress
                  }
      DESCRIPTION
         "A virtual media session to a server has stopped.

          The name of the user who was connected to the VM session
          is contained in fujitsus4TrapObjectUserName.

          The name of the server the user was connected to is contained in
          fujitsus4TrapObjectTargetDeviceName.

          The user address is contained in
          fujitsus4TrapObjectUserAddress.
         "
      --#SUMMARY "Virtual media session stopped. User: %s. Target device: %s. Address: %s."
      --#ARGUMENTS { 0, 1, 2 }
      --#SEVERITY INFORMATIONAL
      --#FACILITY SECURITY
      --#CATEGORY "Status Events"
      --% TrapTypeEnum=36
      ::= 32


fujitsus4VirtualMediaSessionTerminatedTrap TRAP-TYPE
      ENTERPRISE fujitsus4Products
      VARIABLES {
                     fujitsus4TrapObjectUserName,
                     fujitsus4TrapObjectTargetUserName,
                     fujitsus4TrapObjectTargetDeviceName,
                     fujitsus4TrapObjectUserAddress
                  }
      DESCRIPTION
         "A virtual media session has been terminated or preempted
          by another user.

          The name of the user who terminated or preempted the VM session is
          contained in fujitsus4TrapObjectUserName if available. An empty
          string is reported if a user name is not available. A user
          name will not be available if a remote session was terminated
          or preempted from the OSCAR interface and OSCAR authentication is
          disabled.

          The name of the user who was terminated or preempted from the VM
          session is contained in fujitsus4TrapObjectTargetUserName.

          The name of the server the user was connected to contained in
          fujitsus4TrapObjectTargetDeviceName.

          The user address is contained in
          fujitsus4TrapObjectUserAddress.
         "
      --#SUMMARY "Virtual media session terminated. Command issued by user: %s. Terminated user: %s. Target device: %s. Address: %s."
      --#ARGUMENTS { 0, 1, 2, 3 }
      --#SEVERITY INFORMATIONAL
      --#FACILITY SECURITY
      --#CATEGORY "Status Events"
      --% TrapTypeEnum=37
      ::= 33


fujitsus4VirtualMediaSessionReservedTrap TRAP-TYPE
      ENTERPRISE fujitsus4Products
      VARIABLES {
                     fujitsus4TrapObjectUserName,
                     fujitsus4TrapObjectTargetDeviceName,
                     fujitsus4TrapObjectUserAddress
                  }
      DESCRIPTION
         "A user established a reserved virtual media session.

         The name of the user who has established a reserved virtual media session
         is contained in fujitsus4TrapObjectUserName.

         The name of the server the user was connected to is contained in
         fujitsus4TrapObjectTargetDeviceName.

         The user address is contained in
         fujitsus4TrapObjectUserAddress.
         "
      --#SUMMARY "Virtual media session has been reserved. User: %s. Target device: %s. Address: %s."
      --#ARGUMENTS { 0, 1, 2 }
      --#SEVERITY INFORMATIONAL
      --#FACILITY SECURITY
      --#CATEGORY "Status Events"
      --% TrapTypeEnum=38
      ::= 34


fujitsus4VirtualMediaSessionUnreservedTrap TRAP-TYPE
      ENTERPRISE fujitsus4Products
      VARIABLES {
                     fujitsus4TrapObjectUserName,
                     fujitsus4TrapObjectTargetDeviceName,
                     fujitsus4TrapObjectUserAddress
                  }
      DESCRIPTION
         "A user established a non-reserved virtual media session.

         The name of the user who has established a non-reserved virtual media session
         is contained in fujitsus4TrapObjectUserName.

         The name of the server the user was connected to is contained in
         fujitsus4TrapObjectTargetDeviceName.

         The user address is contained in
         fujitsus4TrapObjectUserAddress.
         "
      --#SUMMARY "User has established a non-reserved virtual media session. User: %s. Target device: %s. Address: %s."
      --#ARGUMENTS { 0, 1, 2 }
      --#SEVERITY INFORMATIONAL
      --#FACILITY SECURITY
      --#CATEGORY "Status Events"
      --% TrapTypeEnum=39
      ::= 35


fujitsus4VirtualMediaDriveMapped TRAP-TYPE
      ENTERPRISE fujitsus4Products
      VARIABLES {
                     fujitsus4TrapObjectUserName,
                     fujitsus4TrapObjectTargetDeviceName,
                     fujitsus4TrapObjectVirtualMediaDriveType,
                     fujitsus4TrapObjectVirtualMediaDriveAccessMode,
                     fujitsus4TrapObjectUserAddress
                  }
      DESCRIPTION
         "A virtual media drive has been mapped.

         The name of the user who has established the virtual media session
         is contained in fujitsus4TrapObjectUserName.

         The name of the server the user was connected to is contained in
         fujitsus4TrapObjectTargetDeviceName.

         The type of drive that has been mapped is contained in
         fujitsus4TrapObjectVirtualMediaDriveType.

         The access mode for the drive that has been mapped is contained in
         fujitsus4TrapObjectVirtualMediaDriveAccessMode.

         The user address is contained in
         fujitsus4TrapObjectUserAddress.
         "
      --#SUMMARY "Virtual media has been mapped. User: %s. Target device: %s Type: %d. Access Mode: %d. Address: %s."
      --#ARGUMENTS { 0, 1, 2, 3, 4 }
      --#SEVERITY INFORMATIONAL
      --#FACILITY SYSTEM
      --#CATEGORY "Status Events"
      --% TrapTypeEnum=40
      ::= 36


fujitsus4VirtualMediaDriveUnmapped TRAP-TYPE
      ENTERPRISE fujitsus4Products
      VARIABLES {
                     fujitsus4TrapObjectUserName,
                     fujitsus4TrapObjectTargetDeviceName,
                     fujitsus4TrapObjectVirtualMediaDriveType,
                     fujitsus4TrapObjectVirtualMediaDriveAccessMode,
                     fujitsus4TrapObjectUserAddress
                  }
      DESCRIPTION
         "A virtual media drive has been unmapped.

         The name of the user who has established the virtual media session
         is contained in fujitsus4TrapObjectUserName.

         The name of the server the user was connected to is contained in
         fujitsus4TrapObjectTargetDeviceName.

         The type of drive that has been unmapped is contained in
         fujitsus4TrapObjectVirtualMediaDriveType.

         The access mode for the drive that has been unmapped is contained in
         fujitsus4TrapObjectVirtualMediaDriveAccessMode.

         The user address is contained in
         fujitsus4TrapObjectUserAddress.
         "
      --#SUMMARY "Virtual media has been unmapped. User: %s. Target device: %s Type: %d. Access Mode: %d. Address: %s."
      --#ARGUMENTS { 0, 1, 2, 3, 4 }
      --#SEVERITY INFORMATIONAL
      --#FACILITY SYSTEM
      --#CATEGORY "Status Events"
      --% TrapTypeEnum=41
      ::= 37


fujitsus4LocalPortVirtualMediaSessionStartedTrap TRAP-TYPE
      ENTERPRISE fujitsus4Products
      VARIABLES {
                     fujitsus4TrapObjectUserName,
                     fujitsus4TrapObjectTargetDeviceName,
                     fujitsus4TrapObjectKVM-IAId
                  }
      DESCRIPTION
         "A local user has started a Virtual Media session to a server. A target
          session to the server must have been established by a local user
          prior to starting the VM session.

          The name of the user who connected to the VM session
          is contained in fujitsus4TrapObjectUserName.

          The name of the server the user connected to is contained in
          fujitsus4TrapObjectTargetDeviceName.

          The ID of the KVM-IA the target session is using is contained in
          fujitsus4TrapObjectKVM-IAId.

          This Trap is deprecated and is no longer used.
        "
      --#SUMMARY "Local virtual media session started. User: %s. Target device: %s. KVM-IA: %s."
      --#ARGUMENTS { 0, 1, 2 }
      --#SEVERITY INFORMATIONAL
      --#FACILITY SECURITY
      --#CATEGORY "Status Events"
      --% TrapTypeEnum=42
      ::= 38


fujitsus4LocalPortVirtualMediaSessionStoppedTrap TRAP-TYPE
      ENTERPRISE fujitsus4Products
      VARIABLES {
                     fujitsus4TrapObjectUserName,
                     fujitsus4TrapObjectTargetDeviceName
                  }
      DESCRIPTION
         "A local user has stopped a Virtual Media session to a server.

          The name of the user who was connected to the VM session
          is contained in fujitsus4TrapObjectUserName.

          The name of the server the user was connected to is contained in
          fujitsus4TrapObjectTargetDeviceName.

          This Trap is deprecated and is no longer used.
         "
      --#SUMMARY "Local virtual media session stopped. User: %s. Target device: %s."
      --#ARGUMENTS { 0, 1 }
      --#SEVERITY INFORMATIONAL
      --#FACILITY SECURITY
      --#CATEGORY "Status Events"
      --% TrapTypeEnum=43
      ::= 39


fujitsus4LocalPortVirtualMediaSessionTerminatedTrap TRAP-TYPE
      ENTERPRISE fujitsus4Products
      VARIABLES {
                     fujitsus4TrapObjectUserName,
                     fujitsus4TrapObjectTargetDeviceName
                  }
      DESCRIPTION
         "A local virtual media session has been terminated or preempted
          by another user.

          The name of the user who terminated or preempted the VM session is
          contained in fujitsus4TrapObjectUserName if available. An empty
          string is reported if a user name is not available.

          The name of the server the user was connected to contained in
          fujitsus4TrapObjectTargetDeviceName.

          This Trap is deprecated and is no longer used.
         "
      --#TYPE "Local Port Virtual Media Session Terminated"
      --#SUMMARY "Local Port Virtual Media session terminated. Command issued by user: %s. Target device: %s."
      --#ARGUMENTS { 0, 1 }
      --#SEVERITY INFORMATIONAL
      --#FACILITY SECURITY
      --#CATEGORY "Status Events"
      --% TrapTypeEnum=44
      ::= 40


fujitsus4LocalPortVirtualMediaDriveMapped TRAP-TYPE
      ENTERPRISE fujitsus4Products
      VARIABLES { fujitsus4TrapObjectSessionIdentifier,
                    fujitsus4TrapObjectVirtualMediaDriveType,
                    fujitsus4TrapObjectVirtualMediaDriveAccessMode }
      DESCRIPTION
         "A user on the local port has mapped a virtual media drive to the server.

         The session identifier is contained in fujitsus4TrapObjectSessionIdentifier.

         The type of drive that has been unmapped is contained in
         fujitsus4TrapObjectVirtualMediaDriveType.

         The access mode for the drive that has been unmapped is contained in
         fujitsus4TrapObjectVirtualMediaDriveAccessMode.

         This Trap is deprecated and is no longer used.
         "

      --#TYPE "Local Port Virtual Media Drive Mapped Trap"
      --#SUMMARY "Virtual Media Drive Mapped on the local port. Target device: %s."
      --#ARGUMENTS { 0 }
      --#SEVERITY INFORMATIONAL
      --#FACILITY SYSTEM
      --#CATEGORY "Status Events"
      --% TrapTypeEnum=45
      ::= 41


fujitsus4LocalPortVirtualMediaDriveUnmapped TRAP-TYPE
      ENTERPRISE fujitsus4Products
      VARIABLES { fujitsus4TrapObjectSessionIdentifier,
                    fujitsus4TrapObjectVirtualMediaDriveType,
                    fujitsus4TrapObjectVirtualMediaDriveAccessMode }
      DESCRIPTION
         "A user on the local port has unmapped a virtual media drive to the server.

         The session identifier is contained in
         fujitsus4TrapObjectSessionIdentifier.

         The type of drive that has been unmapped is contained in
         fujitsus4TrapObjectVirtualMediaDriveType.

         The access mode for the drive that has been unmapped is contained in
         fujitsus4TrapObjectVirtualMediaDriveAccessMode.

         This Trap is deprecated and is no longer used.
         "

      --#TYPE "Local Port Virtual Media Drive Unmapped Trap"
      --#SUMMARY "Virtual Media Drive Unmapped on the local port. Target device: %s."
      --#ARGUMENTS { 0 }
      --#SEVERITY INFORMATIONAL
      --#FACILITY SYSTEM
      --#CATEGORY "Status Events"
      --% TrapTypeEnum=46
      ::= 42


fujitsus4LocalPortVirtualMediaSessionReservedTrap TRAP-TYPE
      ENTERPRISE fujitsus4Products
      VARIABLES {
                     fujitsus4TrapObjectTargetDeviceName
                  }
      DESCRIPTION
         "A local user has reserved a virtual media session.

          The name of the server the user was connected to is contained in
          fujitsus4TrapObjectTargetDeviceName.

          This Trap is deprecated and is no longer used.
         "
      --#TYPE "Local Port Virtual Media Session Reserved"
      --#SUMMARY "Local Port virtual media session has been reserved. Target device: %s."
      --#ARGUMENTS { 0 }
      --#SEVERITY INFORMATIONAL
      --#FACILITY SYSTEM
      --#CATEGORY "Status Events"
      --% TrapTypeEnum=47
      ::= 43


fujitsus4LocalPortVirtualMediaSessionUnreservedTrap TRAP-TYPE
      ENTERPRISE fujitsus4Products
      VARIABLES {
                     fujitsus4TrapObjectTargetDeviceName
                  }
      DESCRIPTION
         "A user has unreserved a local virtual media session.

          The name of the server the user was connected to is contained in
          fujitsus4TrapObjectTargetDeviceName.

          This Trap is deprecated and is no longer used.
         "
      --#TYPE "Local Port Virtual Media Session Unreserved"
      --#SUMMARY "Local Port virtual media session has been unreserved. Target device: %s."
      --#ARGUMENTS { 0 }
      --#SEVERITY INFORMATIONAL
      --#FACILITY SECURITY
      --#CATEGORY "Status Events"
      --% TrapTypeEnum=48
      ::= 44



fujitsus4ScreenResolutionChangedTrap TRAP-TYPE
      ENTERPRISE fujitsus4Products
      VARIABLES {
                     fujitsus4TrapObjectUserName,
                     fujitsus4TrapObjectTargetDeviceName,
                     fujitsus4TrapObjectPreviousScreenResolution,
                     fujitsus4TrapObjectCurrentScreenResolution,
                     fujitsus4TrapObjectSessionIdentifier
                  }
      DESCRIPTION
         "The screen resolution of a server was changed.

         The name of the user who changed the screen resolution is contained
         in fujitsus4TrapObjectUserName if available. An empty string is
         reported if a user name is not available. A user name will not be
         available if the target session controlling the server was started
         from the local interface and local authentication is disabled.

         The name of the server the screen resolution was changed on is
         contained in fujitsus4TrapObjectTargetDeviceName.

         The previous screen resolution is contained in
         fujitsus4TrapObjectPreviousScreenResolution.

         The new screen resolution is contained in
         fujitsus4TrapObjectCurrentScreenResolution.

         The session identifier is contained in
         fujitsus4TrapObjectSessionIdentifier.

         "
      --#SUMMARY "Screen resolution changed. User: %s. Target device: %s. Previous Resolution: %s. New Resolution: %s. Session: %s."
      --#ARGUMENTS { 0, 1, 2, 3, 4 }
      --#SEVERITY INFORMATIONAL
      --#FACILITY SYSTEM
      --#CATEGORY "Status Events"
      --% TrapTypeEnum=49
      ::= 45


fujitsus4AggregatedTargetDeviceStatusChangedTrap TRAP-TYPE
      ENTERPRISE fujitsus4Products
      VARIABLES { fujitsus4TrapObjectAggregatedTargetDeviceStatusChanged }
      DESCRIPTION
         "The status of one or more servers (connection paths) has
         changed.

         A list of connection paths whose status has changed is contained
         in fujitsus4TrapObjectAggregatedTargetDeviceStatusChanged.

         This trap is always sent by the appliance on bootup to report the
         current status of all connection paths. Thereafter the trap is sent
         when there is a change in connection path status and will include only
         those paths whose status has changed.
         "
      --#SUMMARY "Aggregate server status changed."
      --#SEVERITY INFORMATIONAL
      --#FACILITY SYSTEM
      --#CATEGORY "Status Events"
      --% TrapTypeEnum=50
      ::= 46


fujitsus4FactoryDefaultsSetTrap TRAP-TYPE
      ENTERPRISE fujitsus4Products
      DESCRIPTION
         "The appliance has been commanded to set itself to factory defaults.

         The appliance sends this trap after being commanded to set itself
         to factory defaults but prior to actually reverting to factory
         defaults.
         "
      --#SUMMARY "The appliance was commanded to set itself to factory defaults."
      --#SEVERITY INFORMATIONAL
      --#FACILITY SYSTEM
      --#CATEGORY "Configuration Events"
      --% TrapTypeEnum=51
      ::= 47


fujitsus4PowerSupplyFailureTrap TRAP-TYPE
      ENTERPRISE fujitsus4Products
      VARIABLES {
                     fujitsus4TrapObjectPowerSupply
                  }
      DESCRIPTION
         "A power supply failure has ocurred, for appliances with dual power supplies.

          The power supply which has failed is indicated in fujitsus4TrapObjectPowerSupply.
         "
      --#SUMMARY "Power Supply %s has failed"
      --#ARGUMENTS { 0 }
      --#SEVERITY INFORMATIONAL
      --#FACILITY SYSTEM
      --#CATEGORY "Status Events"
      --% TrapTypeEnum=52
      ::= 48


fujitsus4PowerSupplyRestoredTrap TRAP-TYPE
      ENTERPRISE fujitsus4Products
      VARIABLES {
                     fujitsus4TrapObjectPowerSupply
                  }
      DESCRIPTION
         "A power supply has been restored, for appliances with dual power supplies.

          The power supply which has been restored is indicated in fujitsus4TrapObjectPowerSupply.
         "
      --#SUMMARY "Power Supply %s has been restored"
      --#ARGUMENTS { 0 }
      --#SEVERITY INFORMATIONAL
      --#FACILITY SYSTEM
      --#CATEGORY "Status Events"
      --% TrapTypeEnum=53
      ::= 49



--
-- PDU Traps
--

fujitsus4PduDeviceOnlineTrap TRAP-TYPE
      ENTERPRISE fujitsus4Products
      VARIABLES {
                     fujitsus4TrapObjectPduDevicePort,
                     fujitsus4TrapObjectPduDeviceNumber
                  }
      DESCRIPTION
         "A power device attached to the appliance is detected to be online.

          This trap is sent upon initialization of the power device if it is
          online and responding. Subsequent traps are sent if the power device
          transitions from offline to online.

          The port number on the appliance that the power device is attached to
          is contained in fujitsus4TrapObjectPduDevicePort.

          The number of the power device that is connected to a port of the
          appliance is contained in fujitsus4TrapObjectPduDeviceNumber.
         "

      --#SUMMARY "A power device is online. Port number: %d. Power device number: %d."
      --#ARGUMENTS { 0, 1 }
      --#SEVERITY MINOR
      --#FACILITY SYSTEM
      --#CATEGORY "Status Events"
      --% TrapTypeEnum=54
      ::= 50


fujitsus4PduDeviceOfflineTrap TRAP-TYPE
      ENTERPRISE fujitsus4Products
      VARIABLES {
                     fujitsus4TrapObjectPduDevicePort,
                     fujitsus4TrapObjectPduDeviceNumber
                  }
      DESCRIPTION
         "A power device attached to the appliance is detected to be offline.

         This trap is sent upon initialization of the power device if it is not
         responding. Subsequent traps are sent if the power device transitions
         from online to offline.

         The port number on the appliance that the power device is attached to
         is contained in fujitsus4TrapObjectPduDevicePort.

         The number of the power device that is connected to a port of the
         appliance is contained in fujitsus4TrapObjectPduDeviceNumber.
       "

      --#SUMMARY "A power device is offline. Port number: %d. Power device number: %d."
      --#ARGUMENTS { 0, 1 }
      --#SEVERITY CRITICAL
      --#FACILITY SYSTEM
      --#CATEGORY "Error Events"
      --% TrapTypeEnum=55
      ::= 51


fujitsus4PduOutletOnCommandTrap TRAP-TYPE
      ENTERPRISE fujitsus4Products
      VARIABLES {
                     fujitsus4TrapObjectUserName,
                     fujitsus4TrapObjectTargetDeviceName,
                     fujitsus4TrapObjectPduDevicePort,
                     fujitsus4TrapObjectPduDeviceNumber,
                     fujitsus4TrapObjectPduOutlet
                  }
      DESCRIPTION
         "A outlet on a power device has been issued the on command.

         The port number on the appliance that the power device is attached to
         is contained in fujitsus4TrapObjectPduDevicePort.

         The outlet number that was issued the on command is contained
         in fujitsus4TrapObjectPduOutlet.

         The name of the server connected to the power device outlet is
         contained in fujitsus4TrapObjectTargetDeviceName.

         The number of the power device that is connected to a port of the
         appliance is contained in fujitsus4TrapObjectPduDeviceNumber.
         "

      --#SUMMARY "The on command was issued to a power device outlet. Command issued by user: %s. Target device: %s. Port number: %d. Power device number: %d. Outlet number: %d."
      --#ARGUMENTS { 0, 1, 2, 3, 4 }
      --#SEVERITY MINOR
      --#FACILITY SECURITY
      --#CATEGORY "Status Events"
      --% TrapTypeEnum=56
      ::= 52


fujitsus4PduOutletOffCommandTrap TRAP-TYPE
      ENTERPRISE fujitsus4Products
      VARIABLES {
                     fujitsus4TrapObjectUserName,
                     fujitsus4TrapObjectTargetDeviceName,
                     fujitsus4TrapObjectPduDevicePort,
                     fujitsus4TrapObjectPduDeviceNumber,
                     fujitsus4TrapObjectPduOutlet
                  }
      DESCRIPTION
         "A outlet on a power device has been issued the off command.

         The port number on the appliance that the power device is attached to
         is contained in fujitsus4TrapObjectPduDevicePort.

         The outlet number that was issued the off command is contained
         in fujitsus4TrapObjectPduOutlet.

         The name of the server connected to the power device outlet is
         contained in fujitsus4TrapObjectTargetDeviceName.

         The number of the power device that is connected to a port of the
         appliance is contained in fujitsus4TrapObjectPduDeviceNumber.
         "
      --#SUMMARY "The off command was issued to a power device outlet. Command issued by user: %s. Target device: %s. Port number: %d. Power device number: %d. Outlet number: %d."
      --#ARGUMENTS { 0, 1, 2, 3, 4 }
      --#SEVERITY MINOR
      --#FACILITY SECURITY
      --#CATEGORY "Status Events"
      --% TrapTypeEnum=57
      ::= 53


fujitsus4PduOutletRebootCommandTrap TRAP-TYPE
      ENTERPRISE fujitsus4Products
      VARIABLES {
                     fujitsus4TrapObjectUserName,
                     fujitsus4TrapObjectTargetDeviceName,
                     fujitsus4TrapObjectPduDevicePort,
                     fujitsus4TrapObjectPduDeviceNumber,
                     fujitsus4TrapObjectPduOutlet
                  }
      DESCRIPTION
         "A outlet on a power device has been issued the reboot command.

         The port number on the appliance that the power device is attached to
         is contained in fujitsus4TrapObjectPduDevicePort.

         The outlet number that was issued the reboot command is contained
         in fujitsus4TrapObjectPduOutlet.

         The name of the server connected to the power device outlet is
         contained in fujitsus4TrapObjectTargetDeviceName.

         The number of the power device that is connected to a port of the
         appliance is contained in fujitsus4TrapObjectPduDeviceNumber.
         "
      --#SUMMARY "The reboot command was issued to a power device outlet. Command issued by user: %s. Target device: %s. Port number: %d. Power device number: %d. Outlet number: %d."
      --#ARGUMENTS { 0, 1, 2, 3, 4 }
      --#SEVERITY INFORMATIONAL
      --#FACILITY SECURITY
      --#CATEGORY "Status Events"
      --% TrapTypeEnum=58
      ::= 54

fujitsus4PduStatusOutletOnTrap TRAP-TYPE
      ENTERPRISE fujitsus4Products
      VARIABLES {
                     fujitsus4TrapObjectTargetDeviceName,
                     fujitsus4TrapObjectPduDevicePort,
                     fujitsus4TrapObjectPduDeviceNumber,
                     fujitsus4TrapObjectPduOutlet
                  }
      DESCRIPTION
         "A power device outlet has changed to the on state.

         The port number on the appliance that the power device is attached to
         is contained in fujitsus4TrapObjectPduDevicePort.

         The outlet number that has changed to the on state is contained
         in fujitsus4TrapObjectPduOutlet.

         The name of the server connected to the power device outlet is
         contained in fujitsus4TrapObjectTargetDeviceName.

         The number of the power device that is connected to a port of the
         appliance is contained in fujitsus4TrapObjectPduDeviceNumber.
         "
      --#SUMMARY "Power device outlet state changed to on. Target device: %s. Port number: %d. Power device number: %d. Outlet number: %d."
      --#ARGUMENTS { 0, 1, 2, 3 }
      --#SEVERITY MINOR
      --#FACILITY SYSTEM
      --#CATEGORY "Status Events"
      --% TrapTypeEnum=61
      ::= 57


fujitsus4PduStatusOutletOffTrap TRAP-TYPE
      ENTERPRISE fujitsus4Products
      VARIABLES {
                     fujitsus4TrapObjectTargetDeviceName,
                     fujitsus4TrapObjectPduDevicePort,
                     fujitsus4TrapObjectPduDeviceNumber,
                     fujitsus4TrapObjectPduOutlet
                  }
      DESCRIPTION
         "A power device outlet has changed to the off state.

         The port number on the appliance that the power device is attached to
         is contained in fujitsus4TrapObjectPduDevicePort.

         The outlet number that has changed to the off state is contained
         in fujitsus4TrapObjectPduOutlet.

         The name of the server connected to the power device outlet is
         contained in fujitsus4TrapObjectTargetDeviceName.

         The number of the power device that is connected to a port of the
         appliance is contained in fujitsus4TrapObjectPduDeviceNumber.
         "
      --#SUMMARY "Power device outlet state changed to off. Target device: %s. Port number: %d. Power device number: %d. Outlet number: %d."
      --#ARGUMENTS { 0, 1, 2, 3 }
      --#SEVERITY MAJOR
      --#FACILITY SYSTEM
      --#CATEGORY "Status Events"
      --% TrapTypeEnum=62
      ::= 58


fujitsus4PduPortNameChangedTrap TRAP-TYPE
      ENTERPRISE fujitsus4Products
      VARIABLES {
                     fujitsus4TrapObjectOldName,
                     fujitsus4TrapObjectItemName,
                     fujitsus4TrapObjectPduDevicePort,
                     fujitsus4TrapObjectPduDeviceNumber
                  }
      DESCRIPTION
         "The name of a power device port has changed.

         The previous name of the power device port is contained in
         fujitsus4TrapObjectOldName.

         The new name of the power device port is contained in
         fujitsus4TrapObjectItemName.

         The port number on the appliance that the power device is attached to
         is contained in fujitsus4TrapObjectPduDevicePort.

         The number of the power device that is connected to a port of the
         appliance is contained in fujitsus4TrapObjectPduDeviceNumber.
         "
      --#SUMMARY "Power device port name changed. Old name: %s. New name: %s. Port number: %d. Power device number: %d."
      --#ARGUMENTS { 0, 1, 2, 3 }
      --#SEVERITY INFORMATIONAL
      --#FACILITY SYSTEM
      --#CATEGORY "Configuration Events"
      --% TrapTypeEnum=63
      ::= 59


fujitsus4PduOutletNameChangedTrap TRAP-TYPE
      ENTERPRISE fujitsus4Products
      VARIABLES {
                     fujitsus4TrapObjectOldName,
                     fujitsus4TrapObjectItemName,
                     fujitsus4TrapObjectPduDevicePort,
                     fujitsus4TrapObjectPduDeviceNumber,
                     fujitsus4TrapObjectPduOutlet
                  }
      DESCRIPTION
         "The name of a power device outlet has changed.

         The previous name of the power device outlet is contained in
         fujitsus4TrapObjectOldName.

         The new name of the power device outlet is contained in
         fujitsus4TrapObjectItemName.

         The port number on the appliance that the power device is attached to
         is contained in fujitsus4TrapObjectPduDevicePort.

         The number of the power device that is connected to a port of the
         appliance is contained in fujitsus4TrapObjectPduDeviceNumber.

         The outlet number of the power device is contained in
         fujitsus4TrapObjectPduOutlet.
         "
      --#SUMMARY "Power device outlet name changed. Old name: %s. New name: %s. Port number: %d. Power device number: %d. Outlet number: %d."
      --#ARGUMENTS { 0, 1, 2, 3, 4 }
      --#SEVERITY INFORMATIONAL
      --#FACILITY SYSTEM
      --#CATEGORY "Configuration Events"
      --% TrapTypeEnum=64
      ::= 60


fujitsus4PduInletTotalLoadHighTrap TRAP-TYPE
      ENTERPRISE fujitsus4Products
      VARIABLES {
                     fujitsus4TrapObjectPduDevicePort,
                     fujitsus4TrapObjectPduDeviceNumber,
                     fujitsus4TrapObjectPduDeviceInlet
                  }
      DESCRIPTION
         "A power device attached to the appliance has exceeded the maximum 
         threshold for total load of an inlet.

         The port number on the appliance that the power device is attached to
         is contained in fujitsus4TrapObjectPduDevicePort.

         The number of the power device that is connected to a port of the
         appliance is contained in fujitsus4TrapObjectPduDeviceNumber.

         The inlet of the power device is contained in
         fujitsus4TrapObjectPduDeviceInlet.
         "
      --#SUMMARY "Power device inlet exceeded the total load maximum threshold. Port number: %d. Power device number: %d. Inlet: %d."
      --#ARGUMENTS { 0, 1, 2 }
      --#SEVERITY MAJOR
      --#FACILITY SYSTEM
      --#CATEGORY "Threshold Events"
      --% TrapTypeEnum=65
      ::= 61


fujitsus4PduInletTotalLoadLowTrap TRAP-TYPE
      ENTERPRISE fujitsus4Products
      VARIABLES {
                     fujitsus4TrapObjectPduDevicePort,
                     fujitsus4TrapObjectPduDeviceNumber,
                     fujitsus4TrapObjectPduDeviceInlet
                  }
      DESCRIPTION
         "A power device attached to the appliance has gone beneath the minimum
          threshold for total load.

          The port number on the appliance that the power device is attached to
          is contained in fujitsus4TrapObjectPduDevicePort.

          The number of the power device that is connected to a port of the
          appliance is contained in fujitsus4TrapObjectPduDeviceNumber.

          The inlet of the power device is contained in
          fujitsus4TrapObjectPduDeviceInlet.
         "
      --#SUMMARY "Power device inlet exceeded the total load minimum threshold. Port number: %d. Power device number: %d. Inlet: %d."
      --#ARGUMENTS { 0, 1, 2 }
      --#SEVERITY MAJOR
      --#FACILITY SYSTEM
      --#CATEGORY "Threshold Events"
      --% TrapTypeEnum=66
      ::= 62


fujitsus4PduDeviceNameChangedTrap TRAP-TYPE
      ENTERPRISE fujitsus4Products
      VARIABLES {
                     fujitsus4TrapObjectOldName,
                     fujitsus4TrapObjectItemName,
                     fujitsus4TrapObjectPduDevicePort,
                     fujitsus4TrapObjectPduDeviceNumber
                  }
      DESCRIPTION
         "The name of a power device has changed.

         The previous name of the power device is contained in
         fujitsus4TrapObjectOldName.

         The new name of the power device is contained in
         fujitsus4TrapObjectItemName.

         The port number on the appliance that the power device is attached to
         is contained in fujitsus4TrapObjectPduDevicePort.

         The number of the power device that is connected to a port of the
         appliance is contained in fujitsus4TrapObjectPduDeviceNumber.
         "
      --#SUMMARY "Power device name changed. Old name: %s. New name: %s. Port number: %d. Power device number: %d."
      --#ARGUMENTS { 0, 1, 2, 3 }
      --#SEVERITY INFORMATIONAL
      --#FACILITY SYSTEM
      --#CATEGORY "Configuration Events"
      --% TrapTypeEnum=67
      ::= 63


fujitsus4PduInletNameChangedTrap TRAP-TYPE
      ENTERPRISE fujitsus4Products
      VARIABLES {
                     fujitsus4TrapObjectOldName,
                     fujitsus4TrapObjectItemName,
                     fujitsus4TrapObjectPduDevicePort,
                     fujitsus4TrapObjectPduDeviceNumber,
                     fujitsus4TrapObjectPduDeviceInlet
                  }
      DESCRIPTION
         "The name of a power device inlet has changed.

          The previous name of the power device inlet is contained in
          fujitsus4TrapObjectOldName.

          The new name of the power device inlet is contained in
          fujitsus4TrapObjectItemName.

          The port number on the appliance that the power device is attached to
          is contained in fujitsus4TrapObjectPduDevicePort.

          The number of the power device that is connected to a port of the
          appliance is contained in fujitsus4TrapObjectPduDeviceNumber.

          The inlet of the power device is contained in
          fujitsus4TrapObjectPduDeviceInlet.
         "
      --#SUMMARY "Power device inlet name changed. Old name: %s. New name: %s. Port number: %d. Power device number: %d. Inlet: %d."
      --#ARGUMENTS { 0, 1, 2, 3, 4 }
      --#SEVERITY INFORMATIONAL
      --#FACILITY SYSTEM
      --#CATEGORY "Configuration Events"
      --% TrapTypeEnum=68
      ::= 64



fujitsus4PduOutletLockCommandTrap TRAP-TYPE
      ENTERPRISE fujitsus4Products
      VARIABLES {
                     fujitsus4TrapObjectUserName,
                     fujitsus4TrapObjectTargetDeviceName,
                     fujitsus4TrapObjectPduDevicePort,
                     fujitsus4TrapObjectPduDeviceNumber,
                     fujitsus4TrapObjectPduOutlet
                  }
      DESCRIPTION
         "A outlet on a power device has been issued the lock command.

         The name of the user who originally started the image upgrade is
         contained in fujitsus4TrapObjectUserName if available. An empty
         string is reported if a user name is not available.

         The port number on the appliance that the power device is attached to
         is contained in fujitsus4TrapObjectPduDevicePort.

         The outlet number that was issued the lock command is contained
         in fujitsus4TrapObjectPduOutlet.

         The name of the server connected to the power device outlet is
         contained in fujitsus4TrapObjectTargetDeviceName.

         The number of the power device that is connected to a port of the
         appliance is contained in fujitsus4TrapObjectPduDeviceNumber.
         "
      --#SUMMARY "The lock command was issued to a power device outlet. Command issued by user: %s. Target device: %s. Port number: %d. Power device number: %d. Outlet number: %d."
      --#ARGUMENTS { 0, 1, 2, 3, 4 }
      --#SEVERITY MINOR
      --#FACILITY SECURITY
      --#CATEGORY "Status Events"
      --% TrapTypeEnum=69
      ::= 65


fujitsus4PduOutletUnlockCommandTrap TRAP-TYPE
      ENTERPRISE fujitsus4Products
      VARIABLES {
                     fujitsus4TrapObjectUserName,
                     fujitsus4TrapObjectTargetDeviceName,
                     fujitsus4TrapObjectPduDevicePort,
                     fujitsus4TrapObjectPduDeviceNumber,
                     fujitsus4TrapObjectPduOutlet
                  }
      DESCRIPTION
         "A outlet on a power device has been issued the unlock command.

         The name of the user who originally started the image upgrade is
         contained in fujitsus4TrapObjectUserName if available. An empty
         string is reported if a user name is not available.

         The port number on the appliance that the power device is attached to
         is contained in fujitsus4TrapObjectPduDevicePort.

         The outlet number that was issued the unlock command is contained
         in fujitsus4TrapObjectPduOutlet.

         The name of the server connected to the power device outlet is
         contained in fujitsus4TrapObjectTargetDeviceName.

         The number of the power device that is connected to a port of the
         appliance is contained in fujitsus4TrapObjectPduDeviceNumber.
         "
      --#SUMMARY "The unlock command was issued to a power device outlet. Command issued by user: %s. Target device: %s. Port number: %d. Power device number: %d. Outlet number: %d."
      --#ARGUMENTS { 0, 1, 2, 3, 4 }
      --#SEVERITY MINOR
      --#FACILITY SECURITY
      --#CATEGORY "Status Events"
      --% TrapTypeEnum=70
      ::= 66


fujitsus4PduStatusOutletLockTrap TRAP-TYPE
      ENTERPRISE fujitsus4Products
      VARIABLES {
                     fujitsus4TrapObjectTargetDeviceName,
                     fujitsus4TrapObjectPduDevicePort,
                     fujitsus4TrapObjectPduDeviceNumber,
                     fujitsus4TrapObjectPduOutlet
                  }
      DESCRIPTION
         "A power device outlet has changed to the lock state.

         The port number on the appliance that the power device is attached to
         is contained in fujitsus4TrapObjectPduDevicePort.

         The outlet number that has changed to the lock state is contained
         in fujitsus4TrapObjectPduOutlet.

         The name of the server connected to the power device outlet is
         contained in fujitsus4TrapObjectTargetDeviceName.

         The number of the power device that is connected to a port of the
         appliance is contained in fujitsus4TrapObjectPduDeviceNumber.
         "
      --#SUMMARY "Power device outlet state changed to lock. Target device: %s. Port number: %d. Power device number: %d. Outlet number: %d."
      --#ARGUMENTS { 0, 1, 2, 3 }
      --#SEVERITY MINOR
      --#FACILITY SYSTEM
      --#CATEGORY "Status Events"
      --% TrapTypeEnum=71
      ::= 67


fujitsus4PduStatusOutletUnlockTrap TRAP-TYPE
      ENTERPRISE fujitsus4Products
      VARIABLES {
                     fujitsus4TrapObjectTargetDeviceName,
                     fujitsus4TrapObjectPduDevicePort,
                     fujitsus4TrapObjectPduDeviceNumber,
                     fujitsus4TrapObjectPduOutlet
                  }
      DESCRIPTION
         "A power device outlet has changed to the unlock state.

         The port number on the appliance that the power device is attached to
         is contained in fujitsus4TrapObjectPduDevicePort.

         The outlet number that has changed to the unlock state is contained
         in fujitsus4TrapObjectPduOutlet.

         The name of the server connected to the power device outlet is
         contained in fujitsus4TrapObjectTargetDeviceName.

         The number of the power device that is connected to a port of the
         appliance is contained in fujitsus4TrapObjectPduDeviceNumber.
         "
      --#SUMMARY "Power device outlet state changed to unlock. Target device: %s. Port number: %d. Power device number: %d. Outlet number: %d."
      --#ARGUMENTS { 0, 1, 2, 3 }
      --#SEVERITY MINOR
      --#FACILITY SYSTEM
      --#CATEGORY "Status Events"
      --% TrapTypeEnum=72
      ::= 68


fujitsus4PduImageFileUpgradeStartedTrap TRAP-TYPE
      ENTERPRISE fujitsus4Products
      VARIABLES {
                     fujitsus4TrapObjectUserName,
                     fujitsus4TrapObjectTypeOfImage,
                     fujitsus4TrapObjectImageNewVersion,
                     fujitsus4TrapObjectImageCurrentVersion,
                     fujitsus4TrapObjectPduDevicePort,
                     fujitsus4TrapObjectPduDeviceNumber
                  }
      DESCRIPTION
         "The appliance has started an upgrade of the power device software image file.


         The name of the user who initiated the image upgrade is contained
         in fujitsus4TrapObjectUserName if available.

         The type of software image being upgraded is contained in
         fujitsus4TrapObjectTypeOfImage.

         The software image version the appliance is upgrading the power device to is
         contained in fujitsus4TrapObjectImageNewVersion.

         The software image version the power device is currently running
         is contained in fujitsus4TrapObjectImageCurrentVersion.

         The port number on the appliance that the power device is attached to
         is contained in fujitsus4TrapObjectPduDevicePort.

         The number of the power device that is connected to a port of the
         appliance is contained in fujitsus4TrapObjectPduDeviceNumber.
         "
      --#SUMMARY "Power Device Image upgrade started. Command issued by user: %s. Image type: %d. New version: %s. Current version: %s. Port number: %d. Power device number: %d."
      --#ARGUMENTS { 0, 1, 2, 3, 4, 5 }
      --#SEVERITY INFORMATIONAL
      --#FACILITY SYSTEM
      --#CATEGORY "Configuration Events"
      --% TrapTypeEnum=73
      ::= 69


fujitsus4PduImageFileUpgradeResultTrap TRAP-TYPE
      ENTERPRISE fujitsus4Products
      VARIABLES {
                     fujitsus4TrapObjectImageFileUpgradeResult,
                     fujitsus4TrapObjectUserName,
                     fujitsus4TrapObjectTypeOfImage,
                     fujitsus4TrapObjectImageNewVersion,
                     fujitsus4TrapObjectImageCurrentVersion,
                     fujitsus4TrapObjectPduDevicePort,
                     fujitsus4TrapObjectPduDeviceNumber

                  }
      DESCRIPTION
         "The result of a software image file upgrade for a power device. 

         The result is contained in fujitsus4TrapObjectImageFileUpgradeResult.

         The name of the user who originally started the image upgrade is
         contained in fujitsus4TrapObjectUserName if available. An empty
         string is reported if a user name is not available.

         The type of software image the upgrade result is for is contained in
         fujitsus4TrapObjectTypeOfImage.

         The software image version the appliance attempted to upgrade to
         is contained in fujitsus4TrapObjectImageNewVersion.

         The software image version the appliance is running is contained
         in fujitsus4TrapObjectImageCurrentVersion. If the software image
         upgrade was successful then this version will match the version
         reported in fujitsus4TrapObjectImageNewVersion.

         The port number on the appliance that the power device is attached to
         is contained in fujitsus4TrapObjectPduDevicePort.

         The number of the power device that is connected to a port of the
         appliance is contained in fujitsus4TrapObjectPduDeviceNumber.
         "
      --#SUMMARY "Power device image upgrade result. Result: %d. Upgrade was started by user: %s. Upgrade image type: %d. Upgrade version: %s. Running version: %s. Port number: %d. Power device number: %d."
      --#ARGUMENTS { 0, 1, 2, 3, 4, 5, 6 }
      --#SEVERITY INFORMATIONAL
      --#FACILITY SYSTEM
      --#CATEGORY "Configuration Events"
      --% TrapTypeEnum=74
      ::= 70



fujitsus4PduCircuitNameChangedTrap TRAP-TYPE
      ENTERPRISE fujitsus4Products
      VARIABLES {
                     fujitsus4TrapObjectOldName,
                     fujitsus4TrapObjectItemName,
                     fujitsus4TrapObjectPduDevicePort,
                     fujitsus4TrapObjectPduDeviceNumber,
                     fujitsus4TrapObjectPduDeviceCircuit
                  }
      DESCRIPTION
         "The name of a power device circuit has changed.

          The previous name of the power device circuit is contained in
          fujitsus4TrapObjectOldName.

          The new name of the power device circuit is contained in
          fujitsus4TrapObjectItemName.

          The port number on the appliance that the power device is attached to
          is contained in fujitsus4TrapObjectPduDevicePort.

          The number of the power device that is connected to a port of the
          appliance is contained in fujitsus4TrapObjectPduDeviceNumber.

          The circuit of the power device is contained in
          fujitsus4TrapObjectPduDeviceCircuit.
         "
      --#SUMMARY "Power device circuit name changed. Old name: %s. New name: %s. Port number: %d. Power device number: %d. Circuit: %d."
      --#ARGUMENTS { 0, 1, 2, 3, 4 }
      --#SEVERITY INFORMATIONAL
      --#FACILITY SYSTEM
      --#CATEGORY "Configuration Events"
      --% TrapTypeEnum=75
      ::= 71


fujitsus4PduDeviceTotalLoadHighTrap TRAP-TYPE
      ENTERPRISE fujitsus4Products
      VARIABLES {
                     fujitsus4TrapObjectPduDevicePort,
                     fujitsus4TrapObjectPduDeviceNumber
                  }
      DESCRIPTION
         "A power device attached to the appliance has exceeded the maximum 
         threshold for total load of the device.

         The port number on the appliance that the power device is attached to
         is contained in fujitsus4TrapObjectPduDevicePort.

         The number of the power device that is connected to a port of the
         appliance is contained in fujitsus4TrapObjectPduDeviceNumber.

         "
      --#SUMMARY "Power device exceeded the total load maximum threshold. Port number: %d. Power device number: %d. "
      --#ARGUMENTS { 0, 1 }
      --#SEVERITY MAJOR
      --#FACILITY SYSTEM
      --#CATEGORY "Threshold Events"
      --% TrapTypeEnum=76
      ::= 72


fujitsus4PduCircuitTotalLoadHighTrap TRAP-TYPE
      ENTERPRISE fujitsus4Products
      VARIABLES {
                     fujitsus4TrapObjectPduDevicePort,
                     fujitsus4TrapObjectPduDeviceNumber,
                     fujitsus4TrapObjectPduDeviceCircuit
                  }
      DESCRIPTION
         "A power device attached to the appliance has exceeded the maximum 
         threshold for total load of a circuit.

         The port number on the appliance that the power device is attached to
         is contained in fujitsus4TrapObjectPduDevicePort.

         The number of the power device that is connected to a port of the
         appliance is contained in fujitsus4TrapObjectPduDeviceNumber.

         The circuit of the power device is contained in
         fujitsus4TrapObjectPduDeviceCircuit.
         "
      --#SUMMARY "Power device circuit exceeded the total load maximum threshold. Port number: %d. Power device number: %d. Circuit: %d."
      --#ARGUMENTS { 0, 1, 2 }
      --#SEVERITY MAJOR
      --#FACILITY SYSTEM
      --#CATEGORY "Threshold Events"
      --% TrapTypeEnum=77
      ::= 73


fujitsus4PduOutletTotalLoadHighTrap TRAP-TYPE
      ENTERPRISE fujitsus4Products
      VARIABLES {
                     fujitsus4TrapObjectPduDevicePort,
                     fujitsus4TrapObjectPduDeviceNumber,
                     fujitsus4TrapObjectPduOutlet
                  }
      DESCRIPTION
         "A power device attached to the appliance has exceeded the maximum 
         threshold for total load of an Outlet.

         The port number on the appliance that the power device is attached to
         is contained in fujitsus4TrapObjectPduDevicePort.

         The number of the power device that is connected to a port of the
         appliance is contained in fujitsus4TrapObjectPduDeviceNumber.

         The circuit of the power device is contained in
         fujitsus4TrapObjectPduOutlet.
         "
      --#SUMMARY "Power device outlet exceeded the total load maximum threshold. Port number: %d. Power device number: %d. Outlet: %d."
      --#ARGUMENTS { 0, 1, 2 }
      --#SEVERITY MAJOR
      --#FACILITY SYSTEM
      --#CATEGORY "Threshold Events"
      --% TrapTypeEnum=78
      ::= 74



fujitsus4FanFailureTrap TRAP-TYPE
      ENTERPRISE fujitsus4Products
      DESCRIPTION
         "A fan failure has ocurred.
         "
      --#SUMMARY "Fan failure has been detected."
      --#ARGUMENTS { }
      --#SEVERITY MAJOR
      --#FACILITY SYSTEM
      --#CATEGORY "Status Events"
      --% TrapTypeEnum=79
      ::= 75


fujitsus4TemperatureRangeTrap TRAP-TYPE
      ENTERPRISE fujitsus4Products
      DESCRIPTION
         "Unit temperature outside operating range has been reached.

         This trap is generated for a high temperature or low temperature
         which is outside operating range.
         "
      --#SUMMARY "Temperature is outside operating range."
      --#ARGUMENTS { }
      --#SEVERITY MAJOR
      --#FACILITY SYSTEM
      --#CATEGORY "Status Events"
      --% TrapTypeEnum=80
      ::= 76

fujitsus4SmartCardInsertedTrap TRAP-TYPE
      ENTERPRISE fujitsus4Products
      VARIABLES {
                     fujitsus4TrapObjectUserName,
                     fujitsus4TrapObjectSessionIdentifier,
                     fujitsus4TrapObjectUserAddress
                  }
      DESCRIPTION
         "A smart card has been inserted. 

         The name of the user who is connected to the session
         is contained in fujitsus4TrapObjectUserName.

         The session identifier is contained in
         fujitsus4TrapObjectSessionIdentifier.

         The user address is contained in
         fujitsus4TrapObjectUserAddress.
         "

      --#SUMMARY "Smart Card inserted. User: %s. Target device: %s. Address: %s."
      --#ARGUMENTS { 0, 1, 2 }
      --#SEVERITY INFORMATIONAL
      --#FACILITY SECURITY
      --#CATEGORY "Status Events"
      --% TrapTypeEnum=81
      ::= 77

fujitsus4SmartCardRemovedTrap TRAP-TYPE
      ENTERPRISE fujitsus4Products
      VARIABLES {
                     fujitsus4TrapObjectUserName,
                     fujitsus4TrapObjectSessionIdentifier,
                     fujitsus4TrapObjectUserAddress
                  }
      DESCRIPTION
         "A smart card has been removed. 

         The name of the user who is connected to the session
         is contained in fujitsus4TrapObjectUserName.

         The session identifier is contained in
         fujitsus4TrapObjectSessionIdentifier.

         The user address is contained in
         fujitsus4TrapObjectUserAddress.
         "

      --#SUMMARY "Smart Card removed. User: %s. Target device: %s. Address: %s."
      --#ARGUMENTS { 0, 1, 2 }
      --#SEVERITY INFORMATIONAL
      --#FACILITY SECURITY
      --#CATEGORY "Status Events"
      --% TrapTypeEnum=82
      ::= 78

END
