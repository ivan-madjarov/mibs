INTEL-WFM-MIB DEFINITIONS ::= BEGIN

IMPORTS
	OBJECT-TYPE                            FROM RFC-1212
	mib-2                                  FROM RFC1213-MIB
	DisplayString                          FROM RFC1213-MIB
	PhysAddress                            FROM RFC1213-MIB
	Counter, Gauge, IpAddress, enterprises FROM RFC1155-SMI;

--
-- The Windows NT MIB compiler doesn't support IMPORTS.
-- So, include these definitions here. NT defines "DisplayString" as
-- OCTET STRING (SIZE(0..255)), in RFC1213 it has no explicit size.
--
-- DisplayString ::= OCTET STRING
-- PhysAddress   ::= OCTET STRING
-- enterprises     OBJECT IDENTIFIER ::= { iso org(3) dod(6) internet(1) private(4) 1 }
--


	wfm					OBJECT IDENTIFIER       ::= { enterprises    3183 }
	wfmProduct			OBJECT IDENTIFIER       ::= { wfm              1 }
	wfmTrapInfo			OBJECT IDENTIFIER       ::= { wfmProduct  1 }


wfmTrapDetails OBJECT-TYPE
	SYNTAX	OCTET STRING
	ACCESS	not-accessible
	STATUS	mandatory
	DESCRIPTION
"Wired for management trap details"
	::= { wfmTrapInfo 1 }

wfmTrapType OBJECT-TYPE
	SYNTAX	OCTET STRING
	ACCESS	not-accessible
	STATUS	mandatory
	DESCRIPTION
"Wired for management trap type"
	::= { wfmTrapInfo 2 }


wfmTempLowWarningOKWarnLNCGL TRAP-TYPE
  ENTERPRISE wfmTrapInfo
  VARIABLES {
    wfmTrapDetails,
    wfmTrapType
  }
  DESCRIPTION
  "Temp Low Warning (OK -> Warn):   (lower non critical going low)."
  --#TYPE         "Temp Low Warning (OK -> Warn) (LNC_GL)"
  --#SUMMARY      "%s"
  --#ARGUMENTS    { 1 }
  --#SEVERITY     MAJOR
  --#TIMEINDEX    1
  --#HELPTAG      0
  --#STATE        OPERATIONAL
  ::=  65792 

wfmTempOKLNCGH TRAP-TYPE
  ENTERPRISE wfmTrapInfo
  VARIABLES {
    wfmTrapDetails,
    wfmTrapType
  }
  DESCRIPTION
  "Temp OK (lower non critical going high)."
  --#TYPE         "Temp OK (LNC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  65793 

wfmTempLowCriticalWarnCritLCGL TRAP-TYPE
  ENTERPRISE wfmTrapInfo
  VARIABLES {
    wfmTrapDetails,
    wfmTrapType
  }
  DESCRIPTION
  "Temp Low Critical(Warn -> Crit):   (lower critical going low)."
  --#TYPE         "Temp Low Critical(Warn -> Crit) (LC_GL)"
  --#SUMMARY      "%s"
  --#ARGUMENTS    { 1 }
  --#SEVERITY     CRITICAL
  --#TIMEINDEX    1
  --#HELPTAG      0
  --#STATE        OPERATIONAL
  ::=  65794 

wfmTempLowWarningCritWarnLCGH TRAP-TYPE
  ENTERPRISE wfmTrapInfo
  VARIABLES {
    wfmTrapDetails,
    wfmTrapType
  }
  DESCRIPTION
  "Temp Low Warning (Crit -> Warn):   (lower critical going high)."
  --#TYPE         "Temp Low Warning (Crit -> Warn) (LC_GH)"
  --#SUMMARY      "%s"
  --#ARGUMENTS    { 1 }
  --#SEVERITY     MAJOR
  --#TIMEINDEX    1
  --#HELPTAG      0
  --#STATE        OPERATIONAL
  ::=  65795 

wfmTempLowCriticalCritNonRecoverLNRGL TRAP-TYPE
  ENTERPRISE wfmTrapInfo
  VARIABLES {
    wfmTrapDetails,
    wfmTrapType
  }
  DESCRIPTION
  "Temp Low Critical(Crit -> NonRecover) (lower non recover going low)."
  --#TYPE         "Temp Low Critical(Crit -> NonRecover) (LNR_GL)"
  --#SUMMARY      "%s"
  --#ARGUMENTS    { 1 }
  --#SEVERITY     CRITICAL
  --#TIMEINDEX    1
  --#HELPTAG      0
  --#STATE        OPERATIONAL
  ::=  65796 

wfmTempLowCriticalNonRecoverCritLNRGH TRAP-TYPE
  ENTERPRISE wfmTrapInfo
  VARIABLES {
    wfmTrapDetails,
    wfmTrapType
  }
  DESCRIPTION
  "Temp Low Critical(NonRecover -> Crit) (lower non recover going high)."
  --#TYPE         "Temp Low Critical(NonRecover -> Crit) (LNR_GH)"
  --#SUMMARY      "%s"
  --#ARGUMENTS    { 1 }
  --#SEVERITY     CRITICAL
  --#TIMEINDEX    1
  --#HELPTAG      0
  --#STATE        OPERATIONAL
  ::=  65797 

wfmTempOKUNCGL TRAP-TYPE
  ENTERPRISE wfmTrapInfo
  VARIABLES {
    wfmTrapDetails,
    wfmTrapType
  }
  DESCRIPTION
  "Temp OK (upper non critical going low)."
  --#TYPE         "Temp OK (UNC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  65798 

wfmTempHighWarningOKWarnUNCGH TRAP-TYPE
  ENTERPRISE wfmTrapInfo
  VARIABLES {
    wfmTrapDetails,
    wfmTrapType
  }
  DESCRIPTION
  "Temp High Warning (OK -> Warn):   (upper non critical going high)."
  --#TYPE         "Temp High Warning (OK -> Warn) (UNC_GH)"
  --#SUMMARY      "%s"
  --#ARGUMENTS    { 1 }
  --#SEVERITY     MAJOR
  --#TIMEINDEX    1
  --#HELPTAG      0
  --#STATE        OPERATIONAL
  ::=  65799 

wfmTempHighWarningCritWarnUCGL TRAP-TYPE
  ENTERPRISE wfmTrapInfo
  VARIABLES {
    wfmTrapDetails,
    wfmTrapType
  }
  DESCRIPTION
  "Temp High Warning (Crit -> Warn):   (upper critical going low)."
  --#TYPE         "Temp High Warning (Crit -> Warn) (UC_GL)"
  --#SUMMARY      "%s"
  --#ARGUMENTS    { 1 }
  --#SEVERITY     MAJOR
  --#TIMEINDEX    1
  --#HELPTAG      0
  --#STATE        OPERATIONAL
  ::=  65800 

wfmTempHighCriticalWarnCritUCGH TRAP-TYPE
  ENTERPRISE wfmTrapInfo
  VARIABLES {
    wfmTrapDetails,
    wfmTrapType
  }
  DESCRIPTION
  "Temp High Critical(Warn -> Crit):   (upper critical going high)."
  --#TYPE         "Temp High Critical(Warn -> Crit) (UC_GH)"
  --#SUMMARY      "%s"
  --#ARGUMENTS    { 1 }
  --#SEVERITY     CRITICAL
  --#TIMEINDEX    1
  --#HELPTAG      0
  --#STATE        OPERATIONAL
  ::=  65801 

wfmTempHighCriticalNonRecoverCritUNRGL TRAP-TYPE
  ENTERPRISE wfmTrapInfo
  VARIABLES {
    wfmTrapDetails,
    wfmTrapType
  }
  DESCRIPTION
  "Temp High Critical(NonRecover -> Crit):   (upper non recover going low)."
  --#TYPE         "Temp High Critical(NonRecover -> Crit) (UNR_GL)"
  --#SUMMARY      "%s"
  --#ARGUMENTS    { 1 }
  --#SEVERITY     CRITICAL
  --#TIMEINDEX    1
  --#HELPTAG      0
  --#STATE        OPERATIONAL
  ::=  65802 

wfmTempHighCriticalCritNonRecoverUNRGH TRAP-TYPE
  ENTERPRISE wfmTrapInfo
  VARIABLES {
    wfmTrapDetails,
    wfmTrapType
  }
  DESCRIPTION
  "Temp High Critical(Crit -> NonRecover):   (upper non recover going high)."
  --#TYPE         "Temp High Critical(Crit -> NonRecover) (UNR_GH)"
  --#SUMMARY      "%s"
  --#ARGUMENTS    { 1 }
  --#SEVERITY     CRITICAL
  --#TIMEINDEX    1
  --#HELPTAG      0
  --#STATE        OPERATIONAL
  ::=  65803 

wfmTempOKLNCGL TRAP-TYPE
  ENTERPRISE wfmTrapInfo
  VARIABLES {
    wfmTrapDetails,
    wfmTrapType
  }
  DESCRIPTION
  "Temp OK (lower non critical going low de-asserted)."
  --#TYPE         "Temp OK (LNC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  65920 

wfmTempLowWarningOKWarnLNCGH TRAP-TYPE
  ENTERPRISE wfmTrapInfo
  VARIABLES {
    wfmTrapDetails,
    wfmTrapType
  }
  DESCRIPTION
  "Temp Low Warning (OK -> Warn):   (lower non critical going high de-asserted)."
  --#TYPE         "Temp Low Warning (OK -> Warn) (LNC_GHD)"
  --#SUMMARY      "%s"
  --#ARGUMENTS    { 1 }
  --#SEVERITY     MAJOR
  --#TIMEINDEX    1
  --#HELPTAG      0
  --#STATE        OPERATIONAL
  ::=  65921 

wfmTempLowWarningCritWarnLCGL TRAP-TYPE
  ENTERPRISE wfmTrapInfo
  VARIABLES {
    wfmTrapDetails,
    wfmTrapType
  }
  DESCRIPTION
  "Temp Low Warning (Crit -> Warn):   (lower critical going low de-asserted)."
  --#TYPE         "Temp Low Warning (Crit -> Warn) (LC_GLD)"
  --#SUMMARY      "%s"
  --#ARGUMENTS    { 1 }
  --#SEVERITY     MAJOR
  --#TIMEINDEX    1
  --#HELPTAG      0
  --#STATE        OPERATIONAL
  ::=  65922 

wfmTempLowCriticalWarnCritLCGH TRAP-TYPE
  ENTERPRISE wfmTrapInfo
  VARIABLES {
    wfmTrapDetails,
    wfmTrapType
  }
  DESCRIPTION
  "Temp Low Critical(Warn -> Crit):   (lower critical going high de-asserted)."
  --#TYPE         "Temp Low Critical(Warn -> Crit) (LC_GHD)"
  --#SUMMARY      "%s"
  --#ARGUMENTS    { 1 }
  --#SEVERITY     CRITICAL
  --#TIMEINDEX    1
  --#HELPTAG      0
  --#STATE        OPERATIONAL
  ::=  65923 

wfmTempLowCriticalNonRecoverCritLNRGL TRAP-TYPE
  ENTERPRISE wfmTrapInfo
  VARIABLES {
    wfmTrapDetails,
    wfmTrapType
  }
  DESCRIPTION
  "Temp Low Critical(NonRecover -> Crit) (lower non recover going low de-asserted)."
  --#TYPE         "Temp Low Critical(NonRecover -> Crit) (LNR_GLD)"
  --#SUMMARY      "%s"
  --#ARGUMENTS    { 1 }
  --#SEVERITY     CRITICAL
  --#TIMEINDEX    1
  --#HELPTAG      0
  --#STATE        OPERATIONAL
  ::=  65924 

wfmTempLowCriticalCritNonRecoverLNRGH TRAP-TYPE
  ENTERPRISE wfmTrapInfo
  VARIABLES {
    wfmTrapDetails,
    wfmTrapType
  }
  DESCRIPTION
  "Temp Low Critical(Crit -> NonRecover) (lower non recover going high de-asserted)."
  --#TYPE         "Temp Low Critical(Crit -> NonRecover) (LNR_GHD)"
  --#SUMMARY      "%s"
  --#ARGUMENTS    { 1 }
  --#SEVERITY     CRITICAL
  --#TIMEINDEX    1
  --#HELPTAG      0
  --#STATE        OPERATIONAL
  ::=  65925 

wfmTempHighWarningOKWarnUNCGL TRAP-TYPE
  ENTERPRISE wfmTrapInfo
  VARIABLES {
    wfmTrapDetails,
    wfmTrapType
  }
  DESCRIPTION
  "Temp High Warning (OK -> Warn):   (upper non critical going low de-asserted)."
  --#TYPE         "Temp High Warning (OK -> Warn) (UNC_GLD)"
  --#SUMMARY      "%s"
  --#ARGUMENTS    { 1 }
  --#SEVERITY     MAJOR
  --#TIMEINDEX    1
  --#HELPTAG      0
  --#STATE        OPERATIONAL
  ::=  65926 

wfmTempOKUNCGH TRAP-TYPE
  ENTERPRISE wfmTrapInfo
  VARIABLES {
    wfmTrapDetails,
    wfmTrapType
  }
  DESCRIPTION
  "Temp OK (upper non critical going high de-asserted)."
  --#TYPE         "Temp OK (UNC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  65927 

wfmTempHighCriticalWarnCritUCGL TRAP-TYPE
  ENTERPRISE wfmTrapInfo
  VARIABLES {
    wfmTrapDetails,
    wfmTrapType
  }
  DESCRIPTION
  "Temp High Critical(Warn -> Crit):   (upper critical going low de-asserted)."
  --#TYPE         "Temp High Critical(Warn -> Crit) (UC_GLD)"
  --#SUMMARY      "%s"
  --#ARGUMENTS    { 1 }
  --#SEVERITY     CRITICAL
  --#TIMEINDEX    1
  --#HELPTAG      0
  --#STATE        OPERATIONAL
  ::=  65928 

wfmTempHighWarningCritWarnUCGH TRAP-TYPE
  ENTERPRISE wfmTrapInfo
  VARIABLES {
    wfmTrapDetails,
    wfmTrapType
  }
  DESCRIPTION
  "Temp High Warning (Crit -> Warn):   (upper critical going high de-asserted)."
  --#TYPE         "Temp High Warning (Crit -> Warn) (UC_GHD)"
  --#SUMMARY      "%s"
  --#ARGUMENTS    { 1 }
  --#SEVERITY     MAJOR
  --#TIMEINDEX    1
  --#HELPTAG      0
  --#STATE        OPERATIONAL
  ::=  65929 

wfmTempHighCriticalCritNonRecoverUNRGL TRAP-TYPE
  ENTERPRISE wfmTrapInfo
  VARIABLES {
    wfmTrapDetails,
    wfmTrapType
  }
  DESCRIPTION
  "Temp High Critical(Crit -> NonRecover):   (upper non recover going low de-asserted)."
  --#TYPE         "Temp High Critical(Crit -> NonRecover) (UNR_GLD)"
  --#SUMMARY      "%s"
  --#ARGUMENTS    { 1 }
  --#SEVERITY     CRITICAL
  --#TIMEINDEX    1
  --#HELPTAG      0
  --#STATE        OPERATIONAL
  ::=  65930 

wfmTempHighCriticalNonRecoverCritUNRGH TRAP-TYPE
  ENTERPRISE wfmTrapInfo
  VARIABLES {
    wfmTrapDetails,
    wfmTrapType
  }
  DESCRIPTION
  "Temp High Critical(NonRecover -> Crit):   (upper non recover going high de-asserted)."
  --#TYPE         "Temp High Critical(NonRecover -> Crit) (UNR_GHD)"
  --#SUMMARY      "%s"
  --#ARGUMENTS    { 1 }
  --#SEVERITY     CRITICAL
  --#TIMEINDEX    1
  --#HELPTAG      0
  --#STATE        OPERATIONAL
  ::=  65931 

wfmThermalTripN1 TRAP-TYPE
  ENTERPRISE wfmTrapInfo
  VARIABLES {
    wfmTrapDetails,
    wfmTrapType
  }
  DESCRIPTION
  "Thermal trip."
  --#TYPE         "Thermal trip"
  --#SUMMARY      "%s"
  --#ARGUMENTS    { 1 }
  --#SEVERITY     CRITICAL
  --#TIMEINDEX    1
  --#HELPTAG      0
  --#STATE        OPERATIONAL
  ::=  66049 

wfmTemperatureOKassert TRAP-TYPE
  ENTERPRISE wfmTrapInfo
  VARIABLES {
    wfmTrapDetails,
    wfmTrapType
  }
  DESCRIPTION
  "Temperature OK (digital assert sensor)."
  --#TYPE         "Temperature OK (assert)"
  --#SUMMARY      "%s"
  --#ARGUMENTS    { 1 }
  --#SEVERITY     INFORMATIONAL
  --#TIMEINDEX    1
  --#HELP         "Note: This is no error condition."
  --#HELPTAG      0
  --#STATE        OPERATIONAL
  ::=  66304 

wfmTemperatureFailedassert TRAP-TYPE
  ENTERPRISE wfmTrapInfo
  VARIABLES {
    wfmTrapDetails,
    wfmTrapType
  }
  DESCRIPTION
  "Temperature Failed (digital assert sensor)."
  --#TYPE         "Temperature Failed (assert)"
  --#SUMMARY      "%s"
  --#ARGUMENTS    { 1 }
  --#SEVERITY     CRITICAL
  --#TIMEINDEX    1
  --#HELPTAG      0
  --#STATE        OPERATIONAL
  ::=  66305 

wfmTemperatureOKpredictive TRAP-TYPE
  ENTERPRISE wfmTrapInfo
  VARIABLES {
    wfmTrapDetails,
    wfmTrapType
  }
  DESCRIPTION
  "Temperature OK (digital predictive sensor)."
  --#TYPE         "Temperature OK (predictive)"
  --#SUMMARY      "%s"
  --#ARGUMENTS    { 1 }
  --#SEVERITY     INFORMATIONAL
  --#TIMEINDEX    1
  --#HELP         "Note: This is no error condition."
  --#HELPTAG      0
  --#STATE        OPERATIONAL
  ::=  66560 

wfmTemperatureFailedpredictive TRAP-TYPE
  ENTERPRISE wfmTrapInfo
  VARIABLES {
    wfmTrapDetails,
    wfmTrapType
  }
  DESCRIPTION
  "Temperature Failed (digital predictive sensor)."
  --#TYPE         "Temperature Failed (predictive)"
  --#SUMMARY      "%s"
  --#ARGUMENTS    { 1 }
  --#SEVERITY     MAJOR
  --#TIMEINDEX    1
  --#HELPTAG      0
  --#STATE        OPERATIONAL
  ::=  66561 

wfmTemperatureWithinLimit TRAP-TYPE
  ENTERPRISE wfmTrapInfo
  VARIABLES {
    wfmTrapDetails,
    wfmTrapType
  }
  DESCRIPTION
  "Temperature within limit."
  --#TYPE         "Temperature within limit"
  --#SUMMARY      "%s"
  --#ARGUMENTS    { 1 }
  --#SEVERITY     INFORMATIONAL
  --#TIMEINDEX    1
  --#HELP         "Note: This is no error condition."
  --#HELPTAG      0
  --#STATE        OPERATIONAL
  ::=  66816 

wfmTemperatureLimitExceeded TRAP-TYPE
  ENTERPRISE wfmTrapInfo
  VARIABLES {
    wfmTrapDetails,
    wfmTrapType
  }
  DESCRIPTION
  "Temperature limit exceeded."
  --#TYPE         "Temperature limit exceeded"
  --#SUMMARY      "%s"
  --#ARGUMENTS    { 1 }
  --#SEVERITY     CRITICAL
  --#TIMEINDEX    1
  --#HELPTAG      0
  --#STATE        OPERATIONAL
  ::=  66817 

wfmTemperaturePerformanceOK TRAP-TYPE
  ENTERPRISE wfmTrapInfo
  VARIABLES {
    wfmTrapDetails,
    wfmTrapType
  }
  DESCRIPTION
  "Temperature performance OK."
  --#TYPE         "Temperature performance OK"
  --#SUMMARY      "%s"
  --#ARGUMENTS    { 1 }
  --#SEVERITY     INFORMATIONAL
  --#TIMEINDEX    1
  --#HELP         "Note: This is no error condition."
  --#HELPTAG      0
  --#STATE        OPERATIONAL
  ::=  67072 

wfmTemperaturePerformanceLags TRAP-TYPE
  ENTERPRISE wfmTrapInfo
  VARIABLES {
    wfmTrapDetails,
    wfmTrapType
  }
  DESCRIPTION
  "Temperature performance lags."
  --#TYPE         "Temperature performance lags"
  --#SUMMARY      "%s"
  --#ARGUMENTS    { 1 }
  --#SEVERITY     CRITICAL
  --#TIMEINDEX    1
  --#HELPTAG      0
  --#STATE        OPERATIONAL
  ::=  67073 

wfmTemperatureRemoved TRAP-TYPE
  ENTERPRISE wfmTrapInfo
  VARIABLES {
    wfmTrapDetails,
    wfmTrapType
  }
  DESCRIPTION
  "Temperature removed."
  --#TYPE         "Temperature removed"
  --#SUMMARY      "%s"
  --#ARGUMENTS    { 1 }
  --#SEVERITY     INFORMATIONAL
  --#TIMEINDEX    1
  --#HELP         "Note: This is no error condition."
  --#HELPTAG      0
  --#STATE        OPERATIONAL
  ::=  67584 

wfmTemperatureRestoredreplaced TRAP-TYPE
  ENTERPRISE wfmTrapInfo
  VARIABLES {
    wfmTrapDetails,
    wfmTrapType
  }
  DESCRIPTION
  "Temperature restored/replaced."
  --#TYPE         "Temperature restored/replaced"
  --#SUMMARY      "%s"
  --#ARGUMENTS    { 1 }
  --#SEVERITY     INFORMATIONAL
  --#TIMEINDEX    1
  --#HELP         "Note: This is no error condition."
  --#HELPTAG      0
  --#STATE        OPERATIONAL
  ::=  67585 

wfmTemperatureDisabled TRAP-TYPE
  ENTERPRISE wfmTrapInfo
  VARIABLES {
    wfmTrapDetails,
    wfmTrapType
  }
  DESCRIPTION
  "Temperature disabled."
  --#TYPE         "Temperature disabled"
  --#SUMMARY      "%s"
  --#ARGUMENTS    { 1 }
  --#SEVERITY     INFORMATIONAL
  --#TIMEINDEX    1
  --#HELP         "Note: This is no error condition."
  --#HELPTAG      0
  --#STATE        OPERATIONAL
  ::=  67840 

wfmTemperatureEnabled TRAP-TYPE
  ENTERPRISE wfmTrapInfo
  VARIABLES {
    wfmTrapDetails,
    wfmTrapType
  }
  DESCRIPTION
  "Temperature enabled."
  --#TYPE         "Temperature enabled"
  --#SUMMARY      "%s"
  --#ARGUMENTS    { 1 }
  --#SEVERITY     INFORMATIONAL
  --#TIMEINDEX    1
  --#HELP         "Note: This is no error condition."
  --#HELPTAG      0
  --#STATE        OPERATIONAL
  ::=  67841 

wfmVoltageLowWarningOKWarnLNCGL TRAP-TYPE
  ENTERPRISE wfmTrapInfo
  VARIABLES {
    wfmTrapDetails,
    wfmTrapType
  }
  DESCRIPTION
  "Voltage Low - Warning (OK -> Warn):   (lower non critical going low)."
  --#TYPE         "Voltage Low - Warning (OK -> Warn) (LNC_GL)"
  --#SUMMARY      "%s"
  --#ARGUMENTS    { 1 }
  --#SEVERITY     MAJOR
  --#TIMEINDEX    1
  --#HELPTAG      0
  --#STATE        OPERATIONAL
  ::=  131328 

wfmVoltageOKLNCGH TRAP-TYPE
  ENTERPRISE wfmTrapInfo
  VARIABLES {
    wfmTrapDetails,
    wfmTrapType
  }
  DESCRIPTION
  "Voltage OK (lower non critical going high)."
  --#TYPE         "Voltage OK (LNC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  131329 

wfmVoltageLowCriticalWarnCritLCGL TRAP-TYPE
  ENTERPRISE wfmTrapInfo
  VARIABLES {
    wfmTrapDetails,
    wfmTrapType
  }
  DESCRIPTION
  "Voltage Low - Critical(Warn -> Crit):   (lower critical going low)."
  --#TYPE         "Voltage Low - Critical(Warn -> Crit) (LC_GL)"
  --#SUMMARY      "%s"
  --#ARGUMENTS    { 1 }
  --#SEVERITY     CRITICAL
  --#TIMEINDEX    1
  --#HELPTAG      0
  --#STATE        OPERATIONAL
  ::=  131330 

wfmVoltageLowNoLongerCriticalLCGH TRAP-TYPE
  ENTERPRISE wfmTrapInfo
  VARIABLES {
    wfmTrapDetails,
    wfmTrapType
  }
  DESCRIPTION
  "Voltage Low - no longer Critical:   (lower critical going high)."
  --#TYPE         "Voltage Low - no longer Critical (LC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  131331 

wfmVoltageLowCriticalCritNonRecoverLNRGL TRAP-TYPE
  ENTERPRISE wfmTrapInfo
  VARIABLES {
    wfmTrapDetails,
    wfmTrapType
  }
  DESCRIPTION
  "Voltage Low - Critical(Crit -> NonRecover) (lower non recover going low)."
  --#TYPE         "Voltage Low - Critical(Crit -> NonRecover) (LNR_GL)"
  --#SUMMARY      "%s"
  --#ARGUMENTS    { 1 }
  --#SEVERITY     CRITICAL
  --#TIMEINDEX    1
  --#HELPTAG      0
  --#STATE        OPERATIONAL
  ::=  131332 

wfmVoltageLowCriticalNonRecoverCritLNRGH TRAP-TYPE
  ENTERPRISE wfmTrapInfo
  VARIABLES {
    wfmTrapDetails,
    wfmTrapType
  }
  DESCRIPTION
  "Voltage Low - Critical(NonRecover -> Crit) (lower non recover going high)."
  --#TYPE         "Voltage Low - Critical(NonRecover -> Crit) (LNR_GH)"
  --#SUMMARY      "%s"
  --#ARGUMENTS    { 1 }
  --#SEVERITY     CRITICAL
  --#TIMEINDEX    1
  --#HELPTAG      0
  --#STATE        OPERATIONAL
  ::=  131333 

wfmVoltageOKUNCGL TRAP-TYPE
  ENTERPRISE wfmTrapInfo
  VARIABLES {
    wfmTrapDetails,
    wfmTrapType
  }
  DESCRIPTION
  "Voltage OK (upper non critical going low)."
  --#TYPE         "Voltage OK (UNC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  131334 

wfmVoltageHighWarningOKWarnUNCGH TRAP-TYPE
  ENTERPRISE wfmTrapInfo
  VARIABLES {
    wfmTrapDetails,
    wfmTrapType
  }
  DESCRIPTION
  "Voltage High - Warning (OK -> Warn):   (upper non critical going high)."
  --#TYPE         "Voltage High - Warning (OK -> Warn) (UNC_GH)"
  --#SUMMARY      "%s"
  --#ARGUMENTS    { 1 }
  --#SEVERITY     MAJOR
  --#TIMEINDEX    1
  --#HELPTAG      0
  --#STATE        OPERATIONAL
  ::=  131335 

wfmVoltageHighNoLongerCriticalUCGL TRAP-TYPE
  ENTERPRISE wfmTrapInfo
  VARIABLES {
    wfmTrapDetails,
    wfmTrapType
  }
  DESCRIPTION
  "Voltage High - no longer Critical:   (upper critical going low)."
  --#TYPE         "Voltage High - no longer Critical (UC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  131336 

wfmVoltageHighCriticalWarnCritUCGH TRAP-TYPE
  ENTERPRISE wfmTrapInfo
  VARIABLES {
    wfmTrapDetails,
    wfmTrapType
  }
  DESCRIPTION
  "Voltage High - Critical(Warn -> Crit):   (upper critical going high)."
  --#TYPE         "Voltage High - Critical(Warn -> Crit) (UC_GH)"
  --#SUMMARY      "%s"
  --#ARGUMENTS    { 1 }
  --#SEVERITY     CRITICAL
  --#TIMEINDEX    1
  --#HELPTAG      0
  --#STATE        OPERATIONAL
  ::=  131337 

wfmVoltageHighCriticalNonRecoverCritUNRGL TRAP-TYPE
  ENTERPRISE wfmTrapInfo
  VARIABLES {
    wfmTrapDetails,
    wfmTrapType
  }
  DESCRIPTION
  "Voltage High - Critical(NonRecover -> Crit):   (upper non recover going low)."
  --#TYPE         "Voltage High - Critical(NonRecover -> Crit) (UNR_GL)"
  --#SUMMARY      "%s"
  --#ARGUMENTS    { 1 }
  --#SEVERITY     CRITICAL
  --#TIMEINDEX    1
  --#HELPTAG      0
  --#STATE        OPERATIONAL
  ::=  131338 

wfmVoltageHighCriticalCritNonRecoverUNRGH TRAP-TYPE
  ENTERPRISE wfmTrapInfo
  VARIABLES {
    wfmTrapDetails,
    wfmTrapType
  }
  DESCRIPTION
  "Voltage High - Critical(Crit -> NonRecover):   (upper non recover going high)."
  --#TYPE         "Voltage High - Critical(Crit -> NonRecover) (UNR_GH)"
  --#SUMMARY      "%s"
  --#ARGUMENTS    { 1 }
  --#SEVERITY     CRITICAL
  --#TIMEINDEX    1
  --#HELPTAG      0
  --#STATE        OPERATIONAL
  ::=  131339 

wfmVoltageOKLNCGL TRAP-TYPE
  ENTERPRISE wfmTrapInfo
  VARIABLES {
    wfmTrapDetails,
    wfmTrapType
  }
  DESCRIPTION
  "Voltage OK (lower non critical going low de-asserted)."
  --#TYPE         "Voltage OK (LNC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  131456 

wfmVoltageLowWarningOKWarnLNCGH TRAP-TYPE
  ENTERPRISE wfmTrapInfo
  VARIABLES {
    wfmTrapDetails,
    wfmTrapType
  }
  DESCRIPTION
  "Voltage Low - Warning (OK -> Warn):   (lower non critical going high de-asserted)."
  --#TYPE         "Voltage Low - Warning (OK -> Warn) (LNC_GHD)"
  --#SUMMARY      "%s"
  --#ARGUMENTS    { 1 }
  --#SEVERITY     MAJOR
  --#TIMEINDEX    1
  --#HELPTAG      0
  --#STATE        OPERATIONAL
  ::=  131457 

wfmVoltageLowNoLongerCriticalLCGL TRAP-TYPE
  ENTERPRISE wfmTrapInfo
  VARIABLES {
    wfmTrapDetails,
    wfmTrapType
  }
  DESCRIPTION
  "Voltage Low - no longer Critical:   (lower critical going low de-asserted)."
  --#TYPE         "Voltage Low - no longer Critical (LC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  131458 

wfmVoltageLowCriticalWarnCritLCGH TRAP-TYPE
  ENTERPRISE wfmTrapInfo
  VARIABLES {
    wfmTrapDetails,
    wfmTrapType
  }
  DESCRIPTION
  "Voltage Low - Critical(Warn -> Crit):   (lower critical going high de-asserted)."
  --#TYPE         "Voltage Low - Critical(Warn -> Crit) (LC_GHD)"
  --#SUMMARY      "%s"
  --#ARGUMENTS    { 1 }
  --#SEVERITY     CRITICAL
  --#TIMEINDEX    1
  --#HELPTAG      0
  --#STATE        OPERATIONAL
  ::=  131459 

wfmVoltageLowCriticalNonRecoverCritLNRGL TRAP-TYPE
  ENTERPRISE wfmTrapInfo
  VARIABLES {
    wfmTrapDetails,
    wfmTrapType
  }
  DESCRIPTION
  "Voltage Low - Critical(NonRecover -> Crit) (lower non recover going low de-asserted)."
  --#TYPE         "Voltage Low - Critical(NonRecover -> Crit) (LNR_GLD)"
  --#SUMMARY      "%s"
  --#ARGUMENTS    { 1 }
  --#SEVERITY     CRITICAL
  --#TIMEINDEX    1
  --#HELPTAG      0
  --#STATE        OPERATIONAL
  ::=  131460 

wfmVoltageLowCriticalCritNonRecoverLNRGH TRAP-TYPE
  ENTERPRISE wfmTrapInfo
  VARIABLES {
    wfmTrapDetails,
    wfmTrapType
  }
  DESCRIPTION
  "Voltage Low - Critical(Crit -> NonRecover) (lower non recover going high de-asserted)."
  --#TYPE         "Voltage Low - Critical(Crit -> NonRecover) (LNR_GHD)"
  --#SUMMARY      "%s"
  --#ARGUMENTS    { 1 }
  --#SEVERITY     CRITICAL
  --#TIMEINDEX    1
  --#HELPTAG      0
  --#STATE        OPERATIONAL
  ::=  131461 

wfmVoltageHighWarningOKWarnUNCGL TRAP-TYPE
  ENTERPRISE wfmTrapInfo
  VARIABLES {
    wfmTrapDetails,
    wfmTrapType
  }
  DESCRIPTION
  "Voltage High - Warning (OK -> Warn):   (upper non critical going low de-asserted)."
  --#TYPE         "Voltage High - Warning (OK -> Warn) (UNC_GLD)"
  --#SUMMARY      "%s"
  --#ARGUMENTS    { 1 }
  --#SEVERITY     MAJOR
  --#TIMEINDEX    1
  --#HELPTAG      0
  --#STATE        OPERATIONAL
  ::=  131462 

wfmVoltageOKUNCGH TRAP-TYPE
  ENTERPRISE wfmTrapInfo
  VARIABLES {
    wfmTrapDetails,
    wfmTrapType
  }
  DESCRIPTION
  "Voltage OK (upper non critical going high de-asserted)."
  --#TYPE         "Voltage OK (UNC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  131463 

wfmVoltageHighCriticalWarnCritUCGL TRAP-TYPE
  ENTERPRISE wfmTrapInfo
  VARIABLES {
    wfmTrapDetails,
    wfmTrapType
  }
  DESCRIPTION
  "Voltage High - Critical(Warn -> Crit):   (upper critical going low de-asserted)."
  --#TYPE         "Voltage High - Critical(Warn -> Crit) (UC_GLD)"
  --#SUMMARY      "%s"
  --#ARGUMENTS    { 1 }
  --#SEVERITY     CRITICAL
  --#TIMEINDEX    1
  --#HELPTAG      0
  --#STATE        OPERATIONAL
  ::=  131464 

wfmVoltageHighNoLongerCriticalUCGH TRAP-TYPE
  ENTERPRISE wfmTrapInfo
  VARIABLES {
    wfmTrapDetails,
    wfmTrapType
  }
  DESCRIPTION
  "Voltage High - no longer Critical:   (upper critical going high de-asserted)."
  --#TYPE         "Voltage High - no longer Critical (UC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  131465 

wfmVoltageHighCriticalCritNonRecoverUNRGL TRAP-TYPE
  ENTERPRISE wfmTrapInfo
  VARIABLES {
    wfmTrapDetails,
    wfmTrapType
  }
  DESCRIPTION
  "Voltage High - Critical(Crit -> NonRecover):   (upper non recover going low de-asserted)."
  --#TYPE         "Voltage High - Critical(Crit -> NonRecover) (UNR_GLD)"
  --#SUMMARY      "%s"
  --#ARGUMENTS    { 1 }
  --#SEVERITY     CRITICAL
  --#TIMEINDEX    1
  --#HELPTAG      0
  --#STATE        OPERATIONAL
  ::=  131466 

wfmVoltageHighCriticalNonRecoverCritUNRGH TRAP-TYPE
  ENTERPRISE wfmTrapInfo
  VARIABLES {
    wfmTrapDetails,
    wfmTrapType
  }
  DESCRIPTION
  "Voltage High - Critical(NonRecover -> Crit):   (upper non recover going high de-asserted)."
  --#TYPE         "Voltage High - Critical(NonRecover -> Crit) (UNR_GHD)"
  --#SUMMARY      "%s"
  --#ARGUMENTS    { 1 }
  --#SEVERITY     CRITICAL
  --#TIMEINDEX    1
  --#HELPTAG      0
  --#STATE        OPERATIONAL
  ::=  131467 

wfmVoltageOKassert TRAP-TYPE
  ENTERPRISE wfmTrapInfo
  VARIABLES {
    wfmTrapDetails,
    wfmTrapType
  }
  DESCRIPTION
  "Voltage OK (digital assert sensor)."
  --#TYPE         "Voltage OK (assert)"
  --#SUMMARY      "%s"
  --#ARGUMENTS    { 1 }
  --#SEVERITY     INFORMATIONAL
  --#TIMEINDEX    1
  --#HELP         "Note: This is no error condition."
  --#HELPTAG      0
  --#STATE        OPERATIONAL
  ::=  131840 

wfmVoltageFailedassert TRAP-TYPE
  ENTERPRISE wfmTrapInfo
  VARIABLES {
    wfmTrapDetails,
    wfmTrapType
  }
  DESCRIPTION
  "Voltage Failed (digital assert sensor)."
  --#TYPE         "Voltage Failed (assert)"
  --#SUMMARY      "%s"
  --#ARGUMENTS    { 1 }
  --#SEVERITY     CRITICAL
  --#TIMEINDEX    1
  --#HELPTAG      0
  --#STATE        OPERATIONAL
  ::=  131841 

wfmVoltageOKpredictive TRAP-TYPE
  ENTERPRISE wfmTrapInfo
  VARIABLES {
    wfmTrapDetails,
    wfmTrapType
  }
  DESCRIPTION
  "Voltage OK (digital predictive sensor)."
  --#TYPE         "Voltage OK (predictive)"
  --#SUMMARY      "%s"
  --#ARGUMENTS    { 1 }
  --#SEVERITY     INFORMATIONAL
  --#TIMEINDEX    1
  --#HELP         "Note: This is no error condition."
  --#HELPTAG      0
  --#STATE        OPERATIONAL
  ::=  132096 

wfmVoltageFailedpredictive TRAP-TYPE
  ENTERPRISE wfmTrapInfo
  VARIABLES {
    wfmTrapDetails,
    wfmTrapType
  }
  DESCRIPTION
  "Voltage Failed (digital predictive sensor)."
  --#TYPE         "Voltage Failed (predictive)"
  --#SUMMARY      "%s"
  --#ARGUMENTS    { 1 }
  --#SEVERITY     MAJOR
  --#TIMEINDEX    1
  --#HELPTAG      0
  --#STATE        OPERATIONAL
  ::=  132097 

wfmVoltageWithinLimit TRAP-TYPE
  ENTERPRISE wfmTrapInfo
  VARIABLES {
    wfmTrapDetails,
    wfmTrapType
  }
  DESCRIPTION
  "Voltage within limit."
  --#TYPE         "Voltage within limit"
  --#SUMMARY      "%s"
  --#ARGUMENTS    { 1 }
  --#SEVERITY     INFORMATIONAL
  --#TIMEINDEX    1
  --#HELP         "Note: This is no error condition."
  --#HELPTAG      0
  --#STATE        OPERATIONAL
  ::=  132352 

wfmVoltageLimitExceeded TRAP-TYPE
  ENTERPRISE wfmTrapInfo
  VARIABLES {
    wfmTrapDetails,
    wfmTrapType
  }
  DESCRIPTION
  "Voltage limit exceeded."
  --#TYPE         "Voltage limit exceeded"
  --#SUMMARY      "%s"
  --#ARGUMENTS    { 1 }
  --#SEVERITY     CRITICAL
  --#TIMEINDEX    1
  --#HELPTAG      0
  --#STATE        OPERATIONAL
  ::=  132353 

wfmVoltagePerformanceOK TRAP-TYPE
  ENTERPRISE wfmTrapInfo
  VARIABLES {
    wfmTrapDetails,
    wfmTrapType
  }
  DESCRIPTION
  "Voltage performance OK."
  --#TYPE         "Voltage performance OK"
  --#SUMMARY      "%s"
  --#ARGUMENTS    { 1 }
  --#SEVERITY     INFORMATIONAL
  --#TIMEINDEX    1
  --#HELP         "Note: This is no error condition."
  --#HELPTAG      0
  --#STATE        OPERATIONAL
  ::=  132608 

wfmVoltagePerformanceLags TRAP-TYPE
  ENTERPRISE wfmTrapInfo
  VARIABLES {
    wfmTrapDetails,
    wfmTrapType
  }
  DESCRIPTION
  "Voltage performance lags."
  --#TYPE         "Voltage performance lags"
  --#SUMMARY      "%s"
  --#ARGUMENTS    { 1 }
  --#SEVERITY     CRITICAL
  --#TIMEINDEX    1
  --#HELPTAG      0
  --#STATE        OPERATIONAL
  ::=  132609 

wfmVoltageRemoved TRAP-TYPE
  ENTERPRISE wfmTrapInfo
  VARIABLES {
    wfmTrapDetails,
    wfmTrapType
  }
  DESCRIPTION
  "Voltage removed."
  --#TYPE         "Voltage removed"
  --#SUMMARY      "%s"
  --#ARGUMENTS    { 1 }
  --#SEVERITY     INFORMATIONAL
  --#TIMEINDEX    1
  --#HELP         "Note: This is no error condition."
  --#HELPTAG      0
  --#STATE        OPERATIONAL
  ::=  133120 

wfmVoltageRestoredreplaced TRAP-TYPE
  ENTERPRISE wfmTrapInfo
  VARIABLES {
    wfmTrapDetails,
    wfmTrapType
  }
  DESCRIPTION
  "Voltage restored/replaced."
  --#TYPE         "Voltage restored/replaced"
  --#SUMMARY      "%s"
  --#ARGUMENTS    { 1 }
  --#SEVERITY     INFORMATIONAL
  --#TIMEINDEX    1
  --#HELP         "Note: This is no error condition."
  --#HELPTAG      0
  --#STATE        OPERATIONAL
  ::=  133121 

wfmVoltageDisabled TRAP-TYPE
  ENTERPRISE wfmTrapInfo
  VARIABLES {
    wfmTrapDetails,
    wfmTrapType
  }
  DESCRIPTION
  "Voltage disabled."
  --#TYPE         "Voltage disabled"
  --#SUMMARY      "%s"
  --#ARGUMENTS    { 1 }
  --#SEVERITY     INFORMATIONAL
  --#TIMEINDEX    1
  --#HELP         "Note: This is no error condition."
  --#HELPTAG      0
  --#STATE        OPERATIONAL
  ::=  133376 

wfmVoltageEnabled TRAP-TYPE
  ENTERPRISE wfmTrapInfo
  VARIABLES {
    wfmTrapDetails,
    wfmTrapType
  }
  DESCRIPTION
  "Voltage enabled."
  --#TYPE         "Voltage enabled"
  --#SUMMARY      "%s"
  --#ARGUMENTS    { 1 }
  --#SEVERITY     INFORMATIONAL
  --#TIMEINDEX    1
  --#HELP         "Note: This is no error condition."
  --#HELPTAG      0
  --#STATE        OPERATIONAL
  ::=  133377 

wfmVoltageFault TRAP-TYPE
  ENTERPRISE wfmTrapInfo
  VARIABLES {
    wfmTrapDetails,
    wfmTrapType
  }
  DESCRIPTION
  "Voltage fault"
  --#TYPE         "Voltage fault"
  --#SUMMARY      "%s"
  --#ARGUMENTS    { 1 }
  --#SEVERITY     CRITICAL
  --#TIMEINDEX    1
  --#HELPTAG      0
  --#STATE        OPERATIONAL
  ::=  159489 

wfmCurrentLowWarningLNCGL TRAP-TYPE
  ENTERPRISE wfmTrapInfo
  VARIABLES {
    wfmTrapDetails,
    wfmTrapType
  }
  DESCRIPTION
  "Current Low Warning (lower non critical going low)."
  --#TYPE         "Current Low Warning (LNC_GL)"
  --#SUMMARY      "%s"
  --#ARGUMENTS    { 1 }
  --#SEVERITY     MAJOR
  --#TIMEINDEX    1
  --#HELPTAG      0
  --#STATE        OPERATIONAL
  ::=  196864 

wfmCurrentOKLNCGH TRAP-TYPE
  ENTERPRISE wfmTrapInfo
  VARIABLES {
    wfmTrapDetails,
    wfmTrapType
  }
  DESCRIPTION
  "Current OK (lower non critical going high)."
  --#TYPE         "Current OK (LNC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  196865 

wfmCurrentCriticalLowLCGL TRAP-TYPE
  ENTERPRISE wfmTrapInfo
  VARIABLES {
    wfmTrapDetails,
    wfmTrapType
  }
  DESCRIPTION
  "Current Critical Low (lower critical going low)."
  --#TYPE         "Current Critical Low (LC_GL)"
  --#SUMMARY      "%s"
  --#ARGUMENTS    { 1 }
  --#SEVERITY     CRITICAL
  --#TIMEINDEX    1
  --#HELPTAG      0
  --#STATE        OPERATIONAL
  ::=  196866 

wfmCurrentNoLongerCriticalButLowLCGH TRAP-TYPE
  ENTERPRISE wfmTrapInfo
  VARIABLES {
    wfmTrapDetails,
    wfmTrapType
  }
  DESCRIPTION
  "Current no longer Critical but Low (lower critical going high)."
  --#TYPE         "Current no longer Critical but Low (LC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  196867 

wfmCurrentLowDamageLNRGL TRAP-TYPE
  ENTERPRISE wfmTrapInfo
  VARIABLES {
    wfmTrapDetails,
    wfmTrapType
  }
  DESCRIPTION
  "Current Low Damage (lower non recover going low)."
  --#TYPE         "Current Low Damage (LNR_GL)"
  --#SUMMARY      "%s"
  --#ARGUMENTS    { 1 }
  --#SEVERITY     CRITICAL
  --#TIMEINDEX    1
  --#HELPTAG      0
  --#STATE        OPERATIONAL
  ::=  196868 

wfmCurrentNoLongerDamageButCriticalLowLNRGH TRAP-TYPE
  ENTERPRISE wfmTrapInfo
  VARIABLES {
    wfmTrapDetails,
    wfmTrapType
  }
  DESCRIPTION
  "Current no longer Damage but Critical Low (lower non recover going high)."
  --#TYPE         "Current no longer Damage but Critical Low (LNR_GH)"
  --#SUMMARY      "%s"
  --#ARGUMENTS    { 1 }
  --#SEVERITY     CRITICAL
  --#TIMEINDEX    1
  --#HELPTAG      0
  --#STATE        OPERATIONAL
  ::=  196869 

wfmCurrentOKUNCGL TRAP-TYPE
  ENTERPRISE wfmTrapInfo
  VARIABLES {
    wfmTrapDetails,
    wfmTrapType
  }
  DESCRIPTION
  "Current OK (upper non critical going low)."
  --#TYPE         "Current OK (UNC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  196870 

wfmCurrentHighWarningUNCGH TRAP-TYPE
  ENTERPRISE wfmTrapInfo
  VARIABLES {
    wfmTrapDetails,
    wfmTrapType
  }
  DESCRIPTION
  "Current High Warning (upper non critical going high)."
  --#TYPE         "Current High Warning (UNC_GH)"
  --#SUMMARY      "%s"
  --#ARGUMENTS    { 1 }
  --#SEVERITY     MAJOR
  --#TIMEINDEX    1
  --#HELPTAG      0
  --#STATE        OPERATIONAL
  ::=  196871 

wfmCurrentNoLongerCriticalButHighUCGL TRAP-TYPE
  ENTERPRISE wfmTrapInfo
  VARIABLES {
    wfmTrapDetails,
    wfmTrapType
  }
  DESCRIPTION
  "Current no longer Critical but High (upper critical going low)."
  --#TYPE         "Current no longer Critical but High (UC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  196872 

wfmCurrentHighCriticalUCGH TRAP-TYPE
  ENTERPRISE wfmTrapInfo
  VARIABLES {
    wfmTrapDetails,
    wfmTrapType
  }
  DESCRIPTION
  "Current High Critical (upper critical going high)."
  --#TYPE         "Current High Critical (UC_GH)"
  --#SUMMARY      "%s"
  --#ARGUMENTS    { 1 }
  --#SEVERITY     CRITICAL
  --#TIMEINDEX    1
  --#HELPTAG      0
  --#STATE        OPERATIONAL
  ::=  196873 

wfmCurrentNoLongerDamageButCriticalHighUNRGL TRAP-TYPE
  ENTERPRISE wfmTrapInfo
  VARIABLES {
    wfmTrapDetails,
    wfmTrapType
  }
  DESCRIPTION
  "Current no longer Damage but Critical High (upper non recover going low)."
  --#TYPE         "Current no longer Damage but Critical High (UNR_GL)"
  --#SUMMARY      "%s"
  --#ARGUMENTS    { 1 }
  --#SEVERITY     CRITICAL
  --#TIMEINDEX    1
  --#HELPTAG      0
  --#STATE        OPERATIONAL
  ::=  196874 

wfmCurrentHighDamageUNRGH TRAP-TYPE
  ENTERPRISE wfmTrapInfo
  VARIABLES {
    wfmTrapDetails,
    wfmTrapType
  }
  DESCRIPTION
  "Current High Damage (upper non recover going high)."
  --#TYPE         "Current High Damage (UNR_GH)"
  --#SUMMARY      "%s"
  --#ARGUMENTS    { 1 }
  --#SEVERITY     CRITICAL
  --#TIMEINDEX    1
  --#HELPTAG      0
  --#STATE        OPERATIONAL
  ::=  196875 

wfmCurrentOKLNCGL TRAP-TYPE
  ENTERPRISE wfmTrapInfo
  VARIABLES {
    wfmTrapDetails,
    wfmTrapType
  }
  DESCRIPTION
  "Current OK (lower non critical going low de-asserted)."
  --#TYPE         "Current OK (LNC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  196992 

wfmCurrentLowWarningLNCGH TRAP-TYPE
  ENTERPRISE wfmTrapInfo
  VARIABLES {
    wfmTrapDetails,
    wfmTrapType
  }
  DESCRIPTION
  "Current Low Warning (lower non critical going high de-asserted)."
  --#TYPE         "Current Low Warning (LNC_GHD)"
  --#SUMMARY      "%s"
  --#ARGUMENTS    { 1 }
  --#SEVERITY     MAJOR
  --#TIMEINDEX    1
  --#HELPTAG      0
  --#STATE        OPERATIONAL
  ::=  196993 

wfmCurrentNoLongerCriticalButLowLCGL TRAP-TYPE
  ENTERPRISE wfmTrapInfo
  VARIABLES {
    wfmTrapDetails,
    wfmTrapType
  }
  DESCRIPTION
  "Current no longer Critical but Low (lower critical going low de-asserted)."
  --#TYPE         "Current no longer Critical but Low (LC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  196994 

wfmCurrentCriticalLowLCGH TRAP-TYPE
  ENTERPRISE wfmTrapInfo
  VARIABLES {
    wfmTrapDetails,
    wfmTrapType
  }
  DESCRIPTION
  "Current Critical Low (lower critical going high de-asserted)."
  --#TYPE         "Current Critical Low (LC_GHD)"
  --#SUMMARY      "%s"
  --#ARGUMENTS    { 1 }
  --#SEVERITY     CRITICAL
  --#TIMEINDEX    1
  --#HELPTAG      0
  --#STATE        OPERATIONAL
  ::=  196995 

wfmCurrentNoLongerDamageButCriticalLowLNRGL TRAP-TYPE
  ENTERPRISE wfmTrapInfo
  VARIABLES {
    wfmTrapDetails,
    wfmTrapType
  }
  DESCRIPTION
  "Current no longer Damage but Critical Low (lower non recover going low de-asserted)."
  --#TYPE         "Current no longer Damage but Critical Low (LNR_GLD)"
  --#SUMMARY      "%s"
  --#ARGUMENTS    { 1 }
  --#SEVERITY     CRITICAL
  --#TIMEINDEX    1
  --#HELPTAG      0
  --#STATE        OPERATIONAL
  ::=  196996 

wfmCurrentLowDamageLNRGH TRAP-TYPE
  ENTERPRISE wfmTrapInfo
  VARIABLES {
    wfmTrapDetails,
    wfmTrapType
  }
  DESCRIPTION
  "Current Low Damage (lower non recover going high de-asserted)."
  --#TYPE         "Current Low Damage (LNR_GHD)"
  --#SUMMARY      "%s"
  --#ARGUMENTS    { 1 }
  --#SEVERITY     CRITICAL
  --#TIMEINDEX    1
  --#HELPTAG      0
  --#STATE        OPERATIONAL
  ::=  196997 

wfmCurrentHighWarningUNCGL TRAP-TYPE
  ENTERPRISE wfmTrapInfo
  VARIABLES {
    wfmTrapDetails,
    wfmTrapType
  }
  DESCRIPTION
  "Current High Warning (upper non critical going low de-asserted)."
  --#TYPE         "Current High Warning (UNC_GLD)"
  --#SUMMARY      "%s"
  --#ARGUMENTS    { 1 }
  --#SEVERITY     MAJOR
  --#TIMEINDEX    1
  --#HELPTAG      0
  --#STATE        OPERATIONAL
  ::=  196998 

wfmCurrentOKUNCGH TRAP-TYPE
  ENTERPRISE wfmTrapInfo
  VARIABLES {
    wfmTrapDetails,
    wfmTrapType
  }
  DESCRIPTION
  "Current OK (upper non critical going high de-asserted)."
  --#TYPE         "Current OK (UNC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  196999 

wfmCurrentCriticalHighUCGL TRAP-TYPE
  ENTERPRISE wfmTrapInfo
  VARIABLES {
    wfmTrapDetails,
    wfmTrapType
  }
  DESCRIPTION
  "Current Critical High (upper critical going low de-asserted)."
  --#TYPE         "Current Critical High (UC_GLD)"
  --#SUMMARY      "%s"
  --#ARGUMENTS    { 1 }
  --#SEVERITY     CRITICAL
  --#TIMEINDEX    1
  --#HELPTAG      0
  --#STATE        OPERATIONAL
  ::=  197000 

wfmCurrentNoLongerCriticalButHighUCGH TRAP-TYPE
  ENTERPRISE wfmTrapInfo
  VARIABLES {
    wfmTrapDetails,
    wfmTrapType
  }
  DESCRIPTION
  "Current no longer Critical but High (upper critical going high de-asserted)."
  --#TYPE         "Current no longer Critical but High (UC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  197001 

wfmCurrentHighDamageUNRGL TRAP-TYPE
  ENTERPRISE wfmTrapInfo
  VARIABLES {
    wfmTrapDetails,
    wfmTrapType
  }
  DESCRIPTION
  "Current High Damage (upper non recover going low de-asserted)."
  --#TYPE         "Current High Damage (UNR_GLD)"
  --#SUMMARY      "%s"
  --#ARGUMENTS    { 1 }
  --#SEVERITY     CRITICAL
  --#TIMEINDEX    1
  --#HELPTAG      0
  --#STATE        OPERATIONAL
  ::=  197002 

wfmCurrentNoLongerDamageButCriticalHighUNRGH TRAP-TYPE
  ENTERPRISE wfmTrapInfo
  VARIABLES {
    wfmTrapDetails,
    wfmTrapType
  }
  DESCRIPTION
  "Current no longer Damage but Critical High (upper non recover going high de-asserted)."
  --#TYPE         "Current no longer Damage but Critical High (UNR_GHD)"
  --#SUMMARY      "%s"
  --#ARGUMENTS    { 1 }
  --#SEVERITY     CRITICAL
  --#TIMEINDEX    1
  --#HELPTAG      0
  --#STATE        OPERATIONAL
  ::=  197003 

wfmCurrentOK TRAP-TYPE
  ENTERPRISE wfmTrapInfo
  VARIABLES {
    wfmTrapDetails,
    wfmTrapType
  }
  DESCRIPTION
  "Current OK."
  --#TYPE         "Current OK"
  --#SUMMARY      "%s"
  --#ARGUMENTS    { 1 }
  --#SEVERITY     INFORMATIONAL
  --#TIMEINDEX    1
  --#HELP         "Note: This is no error condition."
  --#HELPTAG      0
  --#STATE        OPERATIONAL
  ::=  197376 

wfmCurrentFailed TRAP-TYPE
  ENTERPRISE wfmTrapInfo
  VARIABLES {
    wfmTrapDetails,
    wfmTrapType
  }
  DESCRIPTION
  "Current Failed."
  --#TYPE         "Current Failed"
  --#SUMMARY      "%s"
  --#ARGUMENTS    { 1 }
  --#SEVERITY     CRITICAL
  --#TIMEINDEX    1
  --#HELPTAG      0
  --#STATE        OPERATIONAL
  ::=  197377 

wfmCurrentOKFromPredictiveFail TRAP-TYPE
  ENTERPRISE wfmTrapInfo
  VARIABLES {
    wfmTrapDetails,
    wfmTrapType
  }
  DESCRIPTION
  "Current OK from predictive Fail."
  --#TYPE         "Current OK from predictive Fail"
  --#SUMMARY      "%s"
  --#ARGUMENTS    { 1 }
  --#SEVERITY     INFORMATIONAL
  --#TIMEINDEX    1
  --#HELP         "Note: This is no error condition."
  --#HELPTAG      0
  --#STATE        OPERATIONAL
  ::=  197632 

wfmCurrentPredictiveFail TRAP-TYPE
  ENTERPRISE wfmTrapInfo
  VARIABLES {
    wfmTrapDetails,
    wfmTrapType
  }
  DESCRIPTION
  "Current predictive Fail."
  --#TYPE         "Current predictive Fail"
  --#SUMMARY      "%s"
  --#ARGUMENTS    { 1 }
  --#SEVERITY     MAJOR
  --#TIMEINDEX    1
  --#HELPTAG      0
  --#STATE        OPERATIONAL
  ::=  197633 

wfmCurrentWithinLimit TRAP-TYPE
  ENTERPRISE wfmTrapInfo
  VARIABLES {
    wfmTrapDetails,
    wfmTrapType
  }
  DESCRIPTION
  "Current within limit."
  --#TYPE         "Current within limit"
  --#SUMMARY      "%s"
  --#ARGUMENTS    { 1 }
  --#SEVERITY     INFORMATIONAL
  --#TIMEINDEX    1
  --#HELP         "Note: This is no error condition."
  --#HELPTAG      0
  --#STATE        OPERATIONAL
  ::=  197888 

wfmCurrentLimitExceeded TRAP-TYPE
  ENTERPRISE wfmTrapInfo
  VARIABLES {
    wfmTrapDetails,
    wfmTrapType
  }
  DESCRIPTION
  "Current limit exceeded."
  --#TYPE         "Current limit exceeded"
  --#SUMMARY      "%s"
  --#ARGUMENTS    { 1 }
  --#SEVERITY     CRITICAL
  --#TIMEINDEX    1
  --#HELPTAG      0
  --#STATE        OPERATIONAL
  ::=  197889 

wfmCurrentPerformanceOK TRAP-TYPE
  ENTERPRISE wfmTrapInfo
  VARIABLES {
    wfmTrapDetails,
    wfmTrapType
  }
  DESCRIPTION
  "Current performance OK."
  --#TYPE         "Current performance OK"
  --#SUMMARY      "%s"
  --#ARGUMENTS    { 1 }
  --#SEVERITY     INFORMATIONAL
  --#TIMEINDEX    1
  --#HELP         "Note: This is no error condition."
  --#HELPTAG      0
  --#STATE        OPERATIONAL
  ::=  198144 

wfmCurrentPerformanceLags TRAP-TYPE
  ENTERPRISE wfmTrapInfo
  VARIABLES {
    wfmTrapDetails,
    wfmTrapType
  }
  DESCRIPTION
  "Current performance lags."
  --#TYPE         "Current performance lags"
  --#SUMMARY      "%s"
  --#ARGUMENTS    { 1 }
  --#SEVERITY     CRITICAL
  --#TIMEINDEX    1
  --#HELPTAG      0
  --#STATE        OPERATIONAL
  ::=  198145 

wfmCurrentRemoved TRAP-TYPE
  ENTERPRISE wfmTrapInfo
  VARIABLES {
    wfmTrapDetails,
    wfmTrapType
  }
  DESCRIPTION
  "Current removed."
  --#TYPE         "Current removed"
  --#SUMMARY      "%s"
  --#ARGUMENTS    { 1 }
  --#SEVERITY     INFORMATIONAL
  --#TIMEINDEX    1
  --#HELP         "Note: This is no error condition."
  --#HELPTAG      0
  --#STATE        OPERATIONAL
  ::=  198656 

wfmCurrentRestoredreplaced TRAP-TYPE
  ENTERPRISE wfmTrapInfo
  VARIABLES {
    wfmTrapDetails,
    wfmTrapType
  }
  DESCRIPTION
  "Current restored/replaced."
  --#TYPE         "Current restored/replaced"
  --#SUMMARY      "%s"
  --#ARGUMENTS    { 1 }
  --#SEVERITY     INFORMATIONAL
  --#TIMEINDEX    1
  --#HELP         "Note: This is no error condition."
  --#HELPTAG      0
  --#STATE        OPERATIONAL
  ::=  198657 

wfmCurrentDisabled TRAP-TYPE
  ENTERPRISE wfmTrapInfo
  VARIABLES {
    wfmTrapDetails,
    wfmTrapType
  }
  DESCRIPTION
  "Current disabled."
  --#TYPE         "Current disabled"
  --#SUMMARY      "%s"
  --#ARGUMENTS    { 1 }
  --#SEVERITY     INFORMATIONAL
  --#TIMEINDEX    1
  --#HELP         "Note: This is no error condition."
  --#HELPTAG      0
  --#STATE        OPERATIONAL
  ::=  198912 

wfmCurrentEnabled TRAP-TYPE
  ENTERPRISE wfmTrapInfo
  VARIABLES {
    wfmTrapDetails,
    wfmTrapType
  }
  DESCRIPTION
  "Current enabled."
  --#TYPE         "Current enabled"
  --#SUMMARY      "%s"
  --#ARGUMENTS    { 1 }
  --#SEVERITY     INFORMATIONAL
  --#TIMEINDEX    1
  --#HELP         "Note: This is no error condition."
  --#HELPTAG      0
  --#STATE        OPERATIONAL
  ::=  198913 

wfmFanPreFailOKWarnLNCGL TRAP-TYPE
  ENTERPRISE wfmTrapInfo
  VARIABLES {
    wfmTrapDetails,
    wfmTrapType
  }
  DESCRIPTION
  "Fan Pre-Fail (OK -> Warn):   (lower non critical going low)."
  --#TYPE         "Fan Pre-Fail (OK -> Warn) (LNC_GL)"
  --#SUMMARY      "%s"
  --#ARGUMENTS    { 1 }
  --#SEVERITY     MAJOR
  --#TIMEINDEX    1
  --#HELPTAG      0
  --#STATE        OPERATIONAL
  ::=  262400 

wfmFanIsWorkingOKLNCGH TRAP-TYPE
  ENTERPRISE wfmTrapInfo
  VARIABLES {
    wfmTrapDetails,
    wfmTrapType
  }
  DESCRIPTION
  "Fan is working (OK) (lower non critical going high)."
  --#TYPE         "Fan is working (OK) (LNC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  262401 

wfmFanFailedWarnCritLCGL TRAP-TYPE
  ENTERPRISE wfmTrapInfo
  VARIABLES {
    wfmTrapDetails,
    wfmTrapType
  }
  DESCRIPTION
  "Fan Failed  (Warn -> Crit):   (lower critical going low)."
  --#TYPE         "Fan Failed  (Warn -> Crit) (LC_GL)"
  --#SUMMARY      "%s"
  --#ARGUMENTS    { 1 }
  --#SEVERITY     CRITICAL
  --#TIMEINDEX    1
  --#HELPTAG      0
  --#STATE        OPERATIONAL
  ::=  262402 

wfmFanPreFailCritWarnLCGH TRAP-TYPE
  ENTERPRISE wfmTrapInfo
  VARIABLES {
    wfmTrapDetails,
    wfmTrapType
  }
  DESCRIPTION
  "Fan Pre-Fail(Crit -> Warn):   (lower critical going high)."
  --#TYPE         "Fan Pre-Fail(Crit -> Warn) (LC_GH)"
  --#SUMMARY      "%s"
  --#ARGUMENTS    { 1 }
  --#SEVERITY     MAJOR
  --#TIMEINDEX    1
  --#HELPTAG      0
  --#STATE        OPERATIONAL
  ::=  262403 

wfmFanFailedCritNonRecoverLNRGL TRAP-TYPE
  ENTERPRISE wfmTrapInfo
  VARIABLES {
    wfmTrapDetails,
    wfmTrapType
  }
  DESCRIPTION
  "Fan Failed  (Crit -> NonRecover) (lower non recover going low)."
  --#TYPE         "Fan Failed  (Crit -> NonRecover) (LNR_GL)"
  --#SUMMARY      "%s"
  --#ARGUMENTS    { 1 }
  --#SEVERITY     CRITICAL
  --#TIMEINDEX    1
  --#HELPTAG      0
  --#STATE        OPERATIONAL
  ::=  262404 

wfmFanFailedNonRecoverCritLNRGH TRAP-TYPE
  ENTERPRISE wfmTrapInfo
  VARIABLES {
    wfmTrapDetails,
    wfmTrapType
  }
  DESCRIPTION
  "Fan Failed  (NonRecover -> Crit) (lower non recover going high)."
  --#TYPE         "Fan Failed  (NonRecover -> Crit) (LNR_GH)"
  --#SUMMARY      "%s"
  --#ARGUMENTS    { 1 }
  --#SEVERITY     CRITICAL
  --#TIMEINDEX    1
  --#HELPTAG      0
  --#STATE        OPERATIONAL
  ::=  262405 

wfmFanIsWorkingOKLNCGL TRAP-TYPE
  ENTERPRISE wfmTrapInfo
  VARIABLES {
    wfmTrapDetails,
    wfmTrapType
  }
  DESCRIPTION
  "Fan is working (OK) (lower non critical going low de-asserted)."
  --#TYPE         "Fan is working (OK) (LNC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  262528 

wfmFanPreFailOKWarnLNCGH TRAP-TYPE
  ENTERPRISE wfmTrapInfo
  VARIABLES {
    wfmTrapDetails,
    wfmTrapType
  }
  DESCRIPTION
  "Fan Pre-Fail(OK -> Warn):   (lower non critical going high de-asserted)."
  --#TYPE         "Fan Pre-Fail(OK -> Warn) (LNC_GHD)"
  --#SUMMARY      "%s"
  --#ARGUMENTS    { 1 }
  --#SEVERITY     MAJOR
  --#TIMEINDEX    1
  --#HELPTAG      0
  --#STATE        OPERATIONAL
  ::=  262529 

wfmFanPreFailCritWarnLCGL TRAP-TYPE
  ENTERPRISE wfmTrapInfo
  VARIABLES {
    wfmTrapDetails,
    wfmTrapType
  }
  DESCRIPTION
  "Fan Pre-Fail(Crit -> Warn):   (lower critical going low de-asserted)."
  --#TYPE         "Fan Pre-Fail(Crit -> Warn) (LC_GLD)"
  --#SUMMARY      "%s"
  --#ARGUMENTS    { 1 }
  --#SEVERITY     MAJOR
  --#TIMEINDEX    1
  --#HELPTAG      0
  --#STATE        OPERATIONAL
  ::=  262530 

wfmFanFailedWarnCritLCGH TRAP-TYPE
  ENTERPRISE wfmTrapInfo
  VARIABLES {
    wfmTrapDetails,
    wfmTrapType
  }
  DESCRIPTION
  "Fan Failed  (Warn -> Crit):   (lower critical going high de-asserted)."
  --#TYPE         "Fan Failed  (Warn -> Crit) (LC_GHD)"
  --#SUMMARY      "%s"
  --#ARGUMENTS    { 1 }
  --#SEVERITY     CRITICAL
  --#TIMEINDEX    1
  --#HELPTAG      0
  --#STATE        OPERATIONAL
  ::=  262531 

wfmFanFailedNonRecoverCritLNRGL TRAP-TYPE
  ENTERPRISE wfmTrapInfo
  VARIABLES {
    wfmTrapDetails,
    wfmTrapType
  }
  DESCRIPTION
  "Fan Failed  (NonRecover -> Crit) (lower non recover going low de-asserted)."
  --#TYPE         "Fan Failed  (NonRecover -> Crit) (LNR_GLD)"
  --#SUMMARY      "%s"
  --#ARGUMENTS    { 1 }
  --#SEVERITY     CRITICAL
  --#TIMEINDEX    1
  --#HELPTAG      0
  --#STATE        OPERATIONAL
  ::=  262532 

wfmFanFailedCritNonRecoverLNRGH TRAP-TYPE
  ENTERPRISE wfmTrapInfo
  VARIABLES {
    wfmTrapDetails,
    wfmTrapType
  }
  DESCRIPTION
  "Fan Failed  (Crit -> NonRecover) (lower non recover going high de-asserted)."
  --#TYPE         "Fan Failed  (Crit -> NonRecover) (LNR_GHD)"
  --#SUMMARY      "%s"
  --#ARGUMENTS    { 1 }
  --#SEVERITY     CRITICAL
  --#TIMEINDEX    1
  --#HELPTAG      0
  --#STATE        OPERATIONAL
  ::=  262533 

wfmFanOK TRAP-TYPE
  ENTERPRISE wfmTrapInfo
  VARIABLES {
    wfmTrapDetails,
    wfmTrapType
  }
  DESCRIPTION
  "Fan OK."
  --#TYPE         "Fan OK"
  --#SUMMARY      "%s"
  --#ARGUMENTS    { 1 }
  --#SEVERITY     INFORMATIONAL
  --#TIMEINDEX    1
  --#HELP         "Note: This is no error condition."
  --#HELPTAG      0
  --#STATE        OPERATIONAL
  ::=  262912 

wfmFanFailed TRAP-TYPE
  ENTERPRISE wfmTrapInfo
  VARIABLES {
    wfmTrapDetails,
    wfmTrapType
  }
  DESCRIPTION
  "Fan Failed."
  --#TYPE         "Fan Failed"
  --#SUMMARY      "%s"
  --#ARGUMENTS    { 1 }
  --#SEVERITY     CRITICAL
  --#TIMEINDEX    1
  --#HELPTAG      0
  --#STATE        OPERATIONAL
  ::=  262913 

wfmFanPredictiveFailureDeasserted TRAP-TYPE
  ENTERPRISE wfmTrapInfo
  VARIABLES {
    wfmTrapDetails,
    wfmTrapType
  }
  DESCRIPTION
  "Fan predictive failure deasserted."
  --#TYPE         "Fan predictive failure deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  263168 

wfmFanPredictiveFailureAsserted TRAP-TYPE
  ENTERPRISE wfmTrapInfo
  VARIABLES {
    wfmTrapDetails,
    wfmTrapType
  }
  DESCRIPTION
  "Fan predictive failure asserted."
  --#TYPE         "Fan predictive failure asserted"
  --#SUMMARY      "%s"
  --#ARGUMENTS    { 1 }
  --#SEVERITY     MAJOR
  --#TIMEINDEX    1
  --#HELPTAG      0
  --#STATE        OPERATIONAL
  ::=  263169 

wfmFanPerformanceOK TRAP-TYPE
  ENTERPRISE wfmTrapInfo
  VARIABLES {
    wfmTrapDetails,
    wfmTrapType
  }
  DESCRIPTION
  "Fan performance OK."
  --#TYPE         "Fan performance OK"
  --#SUMMARY      "%s"
  --#ARGUMENTS    { 1 }
  --#SEVERITY     INFORMATIONAL
  --#TIMEINDEX    1
  --#HELP         "Note: This is no error condition."
  --#HELPTAG      0
  --#STATE        OPERATIONAL
  ::=  263680 

wfmFanPerformanceLags TRAP-TYPE
  ENTERPRISE wfmTrapInfo
  VARIABLES {
    wfmTrapDetails,
    wfmTrapType
  }
  DESCRIPTION
  "Fan performance lags."
  --#TYPE         "Fan performance lags"
  --#SUMMARY      "%s"
  --#ARGUMENTS    { 1 }
  --#SEVERITY     MAJOR
  --#TIMEINDEX    1
  --#HELPTAG      0
  --#STATE        OPERATIONAL
  ::=  263681 

wfmFanRemoved TRAP-TYPE
  ENTERPRISE wfmTrapInfo
  VARIABLES {
    wfmTrapDetails,
    wfmTrapType
  }
  DESCRIPTION
  "Fan removed."
  --#TYPE         "Fan removed"
  --#SUMMARY      "%s"
  --#ARGUMENTS    { 1 }
  --#SEVERITY     INFORMATIONAL
  --#TIMEINDEX    1
  --#HELP         "Note: This is no error condition."
  --#HELPTAG      0
  --#STATE        OPERATIONAL
  ::=  264192 

wfmFanRestoredreplaced TRAP-TYPE
  ENTERPRISE wfmTrapInfo
  VARIABLES {
    wfmTrapDetails,
    wfmTrapType
  }
  DESCRIPTION
  "Fan restored/replaced."
  --#TYPE         "Fan restored/replaced"
  --#SUMMARY      "%s"
  --#ARGUMENTS    { 1 }
  --#SEVERITY     INFORMATIONAL
  --#TIMEINDEX    1
  --#HELP         "Note: This is no error condition."
  --#HELPTAG      0
  --#STATE        OPERATIONAL
  ::=  264193 

wfmFanDisabled TRAP-TYPE
  ENTERPRISE wfmTrapInfo
  VARIABLES {
    wfmTrapDetails,
    wfmTrapType
  }
  DESCRIPTION
  "Fan disabled."
  --#TYPE         "Fan disabled"
  --#SUMMARY      "%s"
  --#ARGUMENTS    { 1 }
  --#SEVERITY     INFORMATIONAL
  --#TIMEINDEX    1
  --#HELP         "Note: This is no error condition."
  --#HELPTAG      0
  --#STATE        OPERATIONAL
  ::=  264448 

wfmFanEnabled TRAP-TYPE
  ENTERPRISE wfmTrapInfo
  VARIABLES {
    wfmTrapDetails,
    wfmTrapType
  }
  DESCRIPTION
  "Fan enabled."
  --#TYPE         "Fan enabled"
  --#SUMMARY      "%s"
  --#ARGUMENTS    { 1 }
  --#SEVERITY     INFORMATIONAL
  --#TIMEINDEX    1
  --#HELP         "Note: This is no error condition."
  --#HELPTAG      0
  --#STATE        OPERATIONAL
  ::=  264449 

wfmFanFullyRedundant TRAP-TYPE
  ENTERPRISE wfmTrapInfo
  VARIABLES {
    wfmTrapDetails,
    wfmTrapType
  }
  DESCRIPTION
  "Fan fully redundant ."
  --#TYPE         "Fan fully redundant"
  --#SUMMARY      "%s"
  --#ARGUMENTS    { 1 }
  --#SEVERITY     INFORMATIONAL
  --#TIMEINDEX    1
  --#HELP         "Note: This is no error condition."
  --#HELPTAG      0
  --#STATE        OPERATIONAL
  ::=  264960 

wfmFanRedundancyLostN1 TRAP-TYPE
  ENTERPRISE wfmTrapInfo
  VARIABLES {
    wfmTrapDetails,
    wfmTrapType
  }
  DESCRIPTION
  "Fan redundancy lost ."
  --#TYPE         "Fan redundancy lost"
  --#SUMMARY      "%s"
  --#ARGUMENTS    { 1 }
  --#SEVERITY     INFORMATIONAL
  --#TIMEINDEX    1
  --#HELP         "Note: This is no error condition."
  --#HELPTAG      0
  --#STATE        OPERATIONAL
  ::=  264961 

wfmFanRedundancyDegraded TRAP-TYPE
  ENTERPRISE wfmTrapInfo
  VARIABLES {
    wfmTrapDetails,
    wfmTrapType
  }
  DESCRIPTION
  "Fan redundancy degraded."
  --#TYPE         "Fan redundancy degraded"
  --#SUMMARY      "%s"
  --#ARGUMENTS    { 1 }
  --#SEVERITY     INFORMATIONAL
  --#TIMEINDEX    1
  --#HELP         "Note: This is no error condition."
  --#HELPTAG      0
  --#STATE        OPERATIONAL
  ::=  264962 

wfmFanNonRedundantfromRedundant TRAP-TYPE
  ENTERPRISE wfmTrapInfo
  VARIABLES {
    wfmTrapDetails,
    wfmTrapType
  }
  DESCRIPTION
  "Fan non redundant (from redundant)."
  --#TYPE         "Fan non redundant (from redundant)"
  --#SUMMARY      "%s"
  --#ARGUMENTS    { 1 }
  --#SEVERITY     INFORMATIONAL
  --#TIMEINDEX    1
  --#HELP         "Note: This is no error condition."
  --#HELPTAG      0
  --#STATE        OPERATIONAL
  ::=  264963 

wfmFanNonRedundantsufficientResources TRAP-TYPE
  ENTERPRISE wfmTrapInfo
  VARIABLES {
    wfmTrapDetails,
    wfmTrapType
  }
  DESCRIPTION
  "Fan non redundant (sufficient resources)."
  --#TYPE         "Fan non redundant (sufficient resources)"
  --#SUMMARY      "%s"
  --#ARGUMENTS    { 1 }
  --#SEVERITY     INFORMATIONAL
  --#TIMEINDEX    1
  --#HELP         "Note: This is no error condition."
  --#HELPTAG      0
  --#STATE        OPERATIONAL
  ::=  264964 

wfmFanNonRedundantinsufficientResources TRAP-TYPE
  ENTERPRISE wfmTrapInfo
  VARIABLES {
    wfmTrapDetails,
    wfmTrapType
  }
  DESCRIPTION
  "Fan non redundant (insufficient resources)."
  --#TYPE         "Fan non redundant (insufficient resources)"
  --#SUMMARY      "%s"
  --#ARGUMENTS    { 1 }
  --#SEVERITY     INFORMATIONAL
  --#TIMEINDEX    1
  --#HELP         "Note: This is no error condition."
  --#HELPTAG      0
  --#STATE        OPERATIONAL
  ::=  264965 

wfmFanRedundancyDegradedfromRedundant TRAP-TYPE
  ENTERPRISE wfmTrapInfo
  VARIABLES {
    wfmTrapDetails,
    wfmTrapType
  }
  DESCRIPTION
  "Fan redundancy degraded (from redundant)."
  --#TYPE         "Fan redundancy degraded (from redundant)"
  --#SUMMARY      "%s"
  --#ARGUMENTS    { 1 }
  --#SEVERITY     INFORMATIONAL
  --#TIMEINDEX    1
  --#HELP         "Note: This is no error condition."
  --#HELPTAG      0
  --#STATE        OPERATIONAL
  ::=  264966 

wfmFanRedundancyDegradedfromNonRedundant TRAP-TYPE
  ENTERPRISE wfmTrapInfo
  VARIABLES {
    wfmTrapDetails,
    wfmTrapType
  }
  DESCRIPTION
  "Fan redundancy degraded (from non redundant)."
  --#TYPE         "Fan redundancy degraded (from non redundant)"
  --#SUMMARY      "%s"
  --#ARGUMENTS    { 1 }
  --#SEVERITY     INFORMATIONAL
  --#TIMEINDEX    1
  --#HELP         "Note: This is no error condition."
  --#HELPTAG      0
  --#STATE        OPERATIONAL
  ::=  264967 

wfmFanRedundancyLostN2 TRAP-TYPE
  ENTERPRISE wfmTrapInfo
  VARIABLES {
    wfmTrapDetails,
    wfmTrapType
  }
  DESCRIPTION
  "Fan redundancy lost"
  --#TYPE         "Fan redundancy lost"
  --#SUMMARY      "%s"
  --#ARGUMENTS    { 1 }
  --#SEVERITY     MINOR
  --#TIMEINDEX    1
  --#HELPTAG      0
  --#STATE        OPERATIONAL
  ::=  265088 

wfmFanRedundancyRegained TRAP-TYPE
  ENTERPRISE wfmTrapInfo
  VARIABLES {
    wfmTrapDetails,
    wfmTrapType
  }
  DESCRIPTION
  "Fan redundancy regained"
  --#TYPE         "Fan redundancy regained"
  --#SUMMARY      "%s"
  --#ARGUMENTS    { 1 }
  --#SEVERITY     INFORMATIONAL
  --#TIMEINDEX    1
  --#HELP         "Note: This is no error condition."
  --#HELPTAG      0
  --#STATE        OPERATIONAL
  ::=  265089 

wfmFANSensorSpecificErrorReported TRAP-TYPE
  ENTERPRISE wfmTrapInfo
  VARIABLES {
    wfmTrapDetails,
    wfmTrapType
  }
  DESCRIPTION
  "FAN Sensor specific Error reported."
  --#TYPE         "FAN Sensor specific Error reported"
  --#SUMMARY      "%s"
  --#ARGUMENTS    { 1 }
  --#SEVERITY     INFORMATIONAL
  --#TIMEINDEX    1
  --#HELP         "Note: This is no error condition."
  --#HELPTAG      0
  --#STATE        OPERATIONAL
  ::=  290560 

wfmMemoryFanBoxErrorReported TRAP-TYPE
  ENTERPRISE wfmTrapInfo
  VARIABLES {
    wfmTrapDetails,
    wfmTrapType
  }
  DESCRIPTION
  "Memory fan box error reported."
  --#TYPE         "Memory fan box error reported"
  --#SUMMARY      "%s"
  --#ARGUMENTS    { 1 }
  --#SEVERITY     INFORMATIONAL
  --#TIMEINDEX    1
  --#HELP         "Note: This is no error condition."
  --#HELPTAG      0
  --#STATE        OPERATIONAL
  ::=  290563 

wfmPhysicalIntrusionclosed TRAP-TYPE
  ENTERPRISE wfmTrapInfo
  VARIABLES {
    wfmTrapDetails,
    wfmTrapType
  }
  DESCRIPTION
  "Physical intrusion (closed)."
  --#TYPE         "Physical intrusion (closed)"
  --#SUMMARY      "%s"
  --#ARGUMENTS    { 1 }
  --#SEVERITY     INFORMATIONAL
  --#TIMEINDEX    1
  --#HELP         "Note: This is no error condition."
  --#HELPTAG      0
  --#STATE        OPERATIONAL
  ::=  328448 

wfmPhysicalIntrusionopened TRAP-TYPE
  ENTERPRISE wfmTrapInfo
  VARIABLES {
    wfmTrapDetails,
    wfmTrapType
  }
  DESCRIPTION
  "Physical intrusion (opened)."
  --#TYPE         "Physical intrusion (opened)"
  --#SUMMARY      "%s"
  --#ARGUMENTS    { 1 }
  --#SEVERITY     MINOR
  --#TIMEINDEX    1
  --#HELPTAG      0
  --#STATE        OPERATIONAL
  ::=  328449 

wfmIntrusionSensorAbsent TRAP-TYPE
  ENTERPRISE wfmTrapInfo
  VARIABLES {
    wfmTrapDetails,
    wfmTrapType
  }
  DESCRIPTION
  "Intrusion sensor absent"
  --#TYPE         "Intrusion sensor absent"
  --#SUMMARY      "%s"
  --#ARGUMENTS    { 1 }
  --#SEVERITY     INFORMATIONAL
  --#TIMEINDEX    1
  --#HELP         "Note: This is no error condition."
  --#HELPTAG      0
  --#STATE        OPERATIONAL
  ::=  330240 

wfmIntrusionSensorPresent TRAP-TYPE
  ENTERPRISE wfmTrapInfo
  VARIABLES {
    wfmTrapDetails,
    wfmTrapType
  }
  DESCRIPTION
  "Intrusion sensor present"
  --#TYPE         "Intrusion sensor present"
  --#SUMMARY      "%s"
  --#ARGUMENTS    { 1 }
  --#SEVERITY     INFORMATIONAL
  --#TIMEINDEX    1
  --#HELP         "Note: This is no error condition."
  --#HELPTAG      0
  --#STATE        OPERATIONAL
  ::=  330241 

wfmChassisIntrusionopened TRAP-TYPE
  ENTERPRISE wfmTrapInfo
  VARIABLES {
    wfmTrapDetails,
    wfmTrapType
  }
  DESCRIPTION
  "Chassis Intrusion (opened)."
  --#TYPE         "Chassis Intrusion (opened)"
  --#SUMMARY      "%s"
  --#ARGUMENTS    { 1 }
  --#SEVERITY     MAJOR
  --#TIMEINDEX    1
  --#HELPTAG      0
  --#STATE        OPERATIONAL
  ::=  356096 

wfmDriveBayIntrusionopened TRAP-TYPE
  ENTERPRISE wfmTrapInfo
  VARIABLES {
    wfmTrapDetails,
    wfmTrapType
  }
  DESCRIPTION
  "DriveBay Intrusion (opened)."
  --#TYPE         "DriveBay Intrusion (opened)"
  --#SUMMARY      "%s"
  --#ARGUMENTS    { 1 }
  --#SEVERITY     MINOR
  --#TIMEINDEX    1
  --#HELPTAG      0
  --#STATE        OPERATIONAL
  ::=  356097 

wfmIOAreaIntrusionopened TRAP-TYPE
  ENTERPRISE wfmTrapInfo
  VARIABLES {
    wfmTrapDetails,
    wfmTrapType
  }
  DESCRIPTION
  "I/O area Intrusion (opened)."
  --#TYPE         "I/O area Intrusion (opened)"
  --#SUMMARY      "%s"
  --#ARGUMENTS    { 1 }
  --#SEVERITY     MINOR
  --#TIMEINDEX    1
  --#HELPTAG      0
  --#STATE        OPERATIONAL
  ::=  356098 

wfmCPUAreaIntrusionopened TRAP-TYPE
  ENTERPRISE wfmTrapInfo
  VARIABLES {
    wfmTrapDetails,
    wfmTrapType
  }
  DESCRIPTION
  "CPU area Intrusion (opened)."
  --#TYPE         "CPU area Intrusion (opened)"
  --#SUMMARY      "%s"
  --#ARGUMENTS    { 1 }
  --#SEVERITY     MINOR
  --#TIMEINDEX    1
  --#HELPTAG      0
  --#STATE        OPERATIONAL
  ::=  356099 

wfmLANLeashLostCableUnplugged TRAP-TYPE
  ENTERPRISE wfmTrapInfo
  VARIABLES {
    wfmTrapDetails,
    wfmTrapType
  }
  DESCRIPTION
  "LAN Leash lost (Cable unplugged)."
  --#TYPE         "LAN Leash lost (Cable unplugged)"
  --#SUMMARY      "%s"
  --#ARGUMENTS    { 1 }
  --#SEVERITY     MINOR
  --#TIMEINDEX    1
  --#HELPTAG      0
  --#STATE        OPERATIONAL
  ::=  356100 

wfmUnautorizedDock TRAP-TYPE
  ENTERPRISE wfmTrapInfo
  VARIABLES {
    wfmTrapDetails,
    wfmTrapType
  }
  DESCRIPTION
  "Unautorized dock."
  --#TYPE         "Unautorized dock"
  --#SUMMARY      "%s"
  --#ARGUMENTS    { 1 }
  --#SEVERITY     MINOR
  --#TIMEINDEX    1
  --#HELPTAG      0
  --#STATE        OPERATIONAL
  ::=  356101 

wfmFANAreaIntrusionopened TRAP-TYPE
  ENTERPRISE wfmTrapInfo
  VARIABLES {
    wfmTrapDetails,
    wfmTrapType
  }
  DESCRIPTION
  "FAN Area Intrusion (opened)."
  --#TYPE         "FAN Area Intrusion (opened)"
  --#SUMMARY      "%s"
  --#ARGUMENTS    { 1 }
  --#SEVERITY     MINOR
  --#TIMEINDEX    1
  --#HELPTAG      0
  --#STATE        OPERATIONAL
  ::=  356102 

wfmChassisIntrusionclosed TRAP-TYPE
  ENTERPRISE wfmTrapInfo
  VARIABLES {
    wfmTrapDetails,
    wfmTrapType
  }
  DESCRIPTION
  "Chassis Intrusion (closed)."
  --#TYPE         "Chassis Intrusion (closed)"
  --#SUMMARY      "%s"
  --#ARGUMENTS    { 1 }
  --#SEVERITY     INFORMATIONAL
  --#TIMEINDEX    1
  --#HELP         "Note: This is no error condition."
  --#HELPTAG      0
  --#STATE        OPERATIONAL
  ::=  356224 

wfmDriveBayIntrusionclosed TRAP-TYPE
  ENTERPRISE wfmTrapInfo
  VARIABLES {
    wfmTrapDetails,
    wfmTrapType
  }
  DESCRIPTION
  "DriveBay Intrusion (closed)."
  --#TYPE         "DriveBay Intrusion (closed)"
  --#SUMMARY      "%s"
  --#ARGUMENTS    { 1 }
  --#SEVERITY     INFORMATIONAL
  --#TIMEINDEX    1
  --#HELP         "Note: This is no error condition."
  --#HELPTAG      0
  --#STATE        OPERATIONAL
  ::=  356225 

wfmIOAreaIntrusionclosed TRAP-TYPE
  ENTERPRISE wfmTrapInfo
  VARIABLES {
    wfmTrapDetails,
    wfmTrapType
  }
  DESCRIPTION
  "I/O area Intrusion (closed)."
  --#TYPE         "I/O area Intrusion (closed)"
  --#SUMMARY      "%s"
  --#ARGUMENTS    { 1 }
  --#SEVERITY     INFORMATIONAL
  --#TIMEINDEX    1
  --#HELP         "Note: This is no error condition."
  --#HELPTAG      0
  --#STATE        OPERATIONAL
  ::=  356226 

wfmCPUAreaIntrusionclosed TRAP-TYPE
  ENTERPRISE wfmTrapInfo
  VARIABLES {
    wfmTrapDetails,
    wfmTrapType
  }
  DESCRIPTION
  "CPU area Intrusion (closed)."
  --#TYPE         "CPU area Intrusion (closed)"
  --#SUMMARY      "%s"
  --#ARGUMENTS    { 1 }
  --#SEVERITY     INFORMATIONAL
  --#TIMEINDEX    1
  --#HELP         "Note: This is no error condition."
  --#HELPTAG      0
  --#STATE        OPERATIONAL
  ::=  356227 

wfmLANLeashReconnected TRAP-TYPE
  ENTERPRISE wfmTrapInfo
  VARIABLES {
    wfmTrapDetails,
    wfmTrapType
  }
  DESCRIPTION
  "LAN Leash reconnected."
  --#TYPE         "LAN Leash reconnected"
  --#SUMMARY      "%s"
  --#ARGUMENTS    { 1 }
  --#SEVERITY     INFORMATIONAL
  --#TIMEINDEX    1
  --#HELP         "Note: This is no error condition."
  --#HELPTAG      0
  --#STATE        OPERATIONAL
  ::=  356228 

wfmUnautorizedUndock TRAP-TYPE
  ENTERPRISE wfmTrapInfo
  VARIABLES {
    wfmTrapDetails,
    wfmTrapType
  }
  DESCRIPTION
  "Unautorized undock."
  --#TYPE         "Unautorized undock"
  --#SUMMARY      "%s"
  --#ARGUMENTS    { 1 }
  --#SEVERITY     INFORMATIONAL
  --#TIMEINDEX    1
  --#HELP         "Note: This is no error condition."
  --#HELPTAG      0
  --#STATE        OPERATIONAL
  ::=  356229 

wfmFANAreaIntrusionclosed TRAP-TYPE
  ENTERPRISE wfmTrapInfo
  VARIABLES {
    wfmTrapDetails,
    wfmTrapType
  }
  DESCRIPTION
  "FAN Area Intrusion (closed)."
  --#TYPE         "FAN Area Intrusion (closed)"
  --#SUMMARY      "%s"
  --#ARGUMENTS    { 1 }
  --#SEVERITY     INFORMATIONAL
  --#TIMEINDEX    1
  --#HELP         "Note: This is no error condition."
  --#HELPTAG      0
  --#STATE        OPERATIONAL
  ::=  356230 

wfmSecureModeViolationAttemptDeasserted TRAP-TYPE
  ENTERPRISE wfmTrapInfo
  VARIABLES {
    wfmTrapDetails,
    wfmTrapType
  }
  DESCRIPTION
  "Secure mode violation attempt: deasserted."
  --#TYPE         "Secure mode violation attempt: deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  393984 

wfmSecureModeViolationAttemptAsserted TRAP-TYPE
  ENTERPRISE wfmTrapInfo
  VARIABLES {
    wfmTrapDetails,
    wfmTrapType
  }
  DESCRIPTION
  "Secure mode violation attempt: asserted."
  --#TYPE         "Secure mode violation attempt: asserted"
  --#SUMMARY      "%s"
  --#ARGUMENTS    { 1 }
  --#SEVERITY     INFORMATIONAL
  --#TIMEINDEX    1
  --#HELP         "Note: This is no error condition."
  --#HELPTAG      0
  --#STATE        OPERATIONAL
  ::=  393985 

wfmSecureModeViolationAttemptFrontPanelButtonPressed TRAP-TYPE
  ENTERPRISE wfmTrapInfo
  VARIABLES {
    wfmTrapDetails,
    wfmTrapType
  }
  DESCRIPTION
  "Secure mode violation attempt: front panel button pressed."
  --#TYPE         "Secure mode violation attempt: front panel button pressed"
  --#SUMMARY      "%s"
  --#ARGUMENTS    { 1 }
  --#SEVERITY     INFORMATIONAL
  --#TIMEINDEX    1
  --#HELP         "Note: This is no error condition."
  --#HELPTAG      0
  --#STATE        OPERATIONAL
  ::=  421632 

wfmSecureModeViolationAttemptPrebootUSERPasswordWrong TRAP-TYPE
  ENTERPRISE wfmTrapInfo
  VARIABLES {
    wfmTrapDetails,
    wfmTrapType
  }
  DESCRIPTION
  "Secure mode violation attempt: Pre-boot USER password wrong."
  --#TYPE         "Secure mode violation attempt: Pre-boot USER password wrong"
  --#SUMMARY      "%s"
  --#ARGUMENTS    { 1 }
  --#SEVERITY     INFORMATIONAL
  --#TIMEINDEX    1
  --#HELP         "Note: This is no error condition."
  --#HELPTAG      0
  --#STATE        OPERATIONAL
  ::=  421633 

wfmSecureModeViolationAttemptPrebootSETUPPasswordWrong TRAP-TYPE
  ENTERPRISE wfmTrapInfo
  VARIABLES {
    wfmTrapDetails,
    wfmTrapType
  }
  DESCRIPTION
  "Secure mode violation attempt: Pre-boot SETUP password wrong."
  --#TYPE         "Secure mode violation attempt: Pre-boot SETUP password wrong"
  --#SUMMARY      "%s"
  --#ARGUMENTS    { 1 }
  --#SEVERITY     INFORMATIONAL
  --#TIMEINDEX    1
  --#HELP         "Note: This is no error condition."
  --#HELPTAG      0
  --#STATE        OPERATIONAL
  ::=  421634 

wfmSecureModeViolationAttemptPrebootNETWORKPasswordWrong TRAP-TYPE
  ENTERPRISE wfmTrapInfo
  VARIABLES {
    wfmTrapDetails,
    wfmTrapType
  }
  DESCRIPTION
  "Secure mode violation attempt: Pre-boot NETWORK password wrong."
  --#TYPE         "Secure mode violation attempt: Pre-boot NETWORK password wrong"
  --#SUMMARY      "%s"
  --#ARGUMENTS    { 1 }
  --#SEVERITY     INFORMATIONAL
  --#TIMEINDEX    1
  --#HELP         "Note: This is no error condition."
  --#HELPTAG      0
  --#STATE        OPERATIONAL
  ::=  421635 

wfmSecureModeViolationAttemptPrebootOTHERPasswordWrong TRAP-TYPE
  ENTERPRISE wfmTrapInfo
  VARIABLES {
    wfmTrapDetails,
    wfmTrapType
  }
  DESCRIPTION
  "Secure mode violation attempt: Pre-boot OTHER password wrong."
  --#TYPE         "Secure mode violation attempt: Pre-boot OTHER password wrong"
  --#SUMMARY      "%s"
  --#ARGUMENTS    { 1 }
  --#SEVERITY     INFORMATIONAL
  --#TIMEINDEX    1
  --#HELP         "Note: This is no error condition."
  --#HELPTAG      0
  --#STATE        OPERATIONAL
  ::=  421636 

wfmSecureModeViolationAttemptOutofbandAccessPasswordWrong TRAP-TYPE
  ENTERPRISE wfmTrapInfo
  VARIABLES {
    wfmTrapDetails,
    wfmTrapType
  }
  DESCRIPTION
  "Secure mode violation attempt: Out-of-band access password wrong."
  --#TYPE         "Secure mode violation attempt: Out-of-band access password wrong"
  --#SUMMARY      "%s"
  --#ARGUMENTS    { 1 }
  --#SEVERITY     INFORMATIONAL
  --#TIMEINDEX    1
  --#HELP         "Note: This is no error condition."
  --#HELPTAG      0
  --#STATE        OPERATIONAL
  ::=  421637 

wfmCPUPredictiveFailure TRAP-TYPE
  ENTERPRISE wfmTrapInfo
  VARIABLES {
    wfmTrapDetails,
    wfmTrapType
  }
  DESCRIPTION
  "CPU Predictive Failure."
  --#TYPE         "CPU Predictive Failure"
  --#SUMMARY      "%s"
  --#ARGUMENTS    { 1 }
  --#SEVERITY     MAJOR
  --#TIMEINDEX    1
  --#HELPTAG      0
  --#STATE        OPERATIONAL
  ::=  459777 

wfmCPUInternalError TRAP-TYPE
  ENTERPRISE wfmTrapInfo
  VARIABLES {
    wfmTrapDetails,
    wfmTrapType
  }
  DESCRIPTION
  "CPU internal error."
  --#TYPE         "CPU internal error"
  --#SUMMARY      "%s"
  --#ARGUMENTS    { 1 }
  --#SEVERITY     CRITICAL
  --#TIMEINDEX    1
  --#HELPTAG      0
  --#STATE        OPERATIONAL
  ::=  487168 

wfmCPUThermalTripFailure TRAP-TYPE
  ENTERPRISE wfmTrapInfo
  VARIABLES {
    wfmTrapDetails,
    wfmTrapType
  }
  DESCRIPTION
  "CPU thermal trip failure."
  --#TYPE         "CPU thermal trip failure"
  --#SUMMARY      "%s"
  --#ARGUMENTS    { 1 }
  --#SEVERITY     CRITICAL
  --#TIMEINDEX    1
  --#HELPTAG      0
  --#STATE        OPERATIONAL
  ::=  487169 

wfmCPUFailedBuiltinSelftestDisabledFRB1 TRAP-TYPE
  ENTERPRISE wfmTrapInfo
  VARIABLES {
    wfmTrapDetails,
    wfmTrapType
  }
  DESCRIPTION
  "CPU failed built-in selftest; disabled (FRB1)."
  --#TYPE         "CPU failed built-in selftest; disabled (FRB1)"
  --#SUMMARY      "%s"
  --#ARGUMENTS    { 1 }
  --#SEVERITY     CRITICAL
  --#TIMEINDEX    1
  --#HELPTAG      0
  --#STATE        OPERATIONAL
  ::=  487170 

wfmCPUHungDuringPOSTDisabledFRB2 TRAP-TYPE
  ENTERPRISE wfmTrapInfo
  VARIABLES {
    wfmTrapDetails,
    wfmTrapType
  }
  DESCRIPTION
  "CPU hung during POST; disabled (FRB2)."
  --#TYPE         "CPU hung during POST; disabled (FRB2)"
  --#SUMMARY      "%s"
  --#ARGUMENTS    { 1 }
  --#SEVERITY     CRITICAL
  --#TIMEINDEX    1
  --#HELPTAG      0
  --#STATE        OPERATIONAL
  ::=  487171 

wfmCPUStartupinitializationFailureDisabledFRB3 TRAP-TYPE
  ENTERPRISE wfmTrapInfo
  VARIABLES {
    wfmTrapDetails,
    wfmTrapType
  }
  DESCRIPTION
  "CPU startup/initialization failure; disabled (FRB3)."
  --#TYPE         "CPU startup/initialization failure; disabled (FRB3)"
  --#SUMMARY      "%s"
  --#ARGUMENTS    { 1 }
  --#SEVERITY     CRITICAL
  --#TIMEINDEX    1
  --#HELPTAG      0
  --#STATE        OPERATIONAL
  ::=  487172 

wfmCPUConfigurationError TRAP-TYPE
  ENTERPRISE wfmTrapInfo
  VARIABLES {
    wfmTrapDetails,
    wfmTrapType
  }
  DESCRIPTION
  "CPU configuration error."
  --#TYPE         "CPU configuration error"
  --#SUMMARY      "%s"
  --#ARGUMENTS    { 1 }
  --#SEVERITY     MAJOR
  --#TIMEINDEX    1
  --#HELPTAG      0
  --#STATE        OPERATIONAL
  ::=  487173 

wfmUncorrectableCPUcomplexError TRAP-TYPE
  ENTERPRISE wfmTrapInfo
  VARIABLES {
    wfmTrapDetails,
    wfmTrapType
  }
  DESCRIPTION
  "Uncorrectable CPU-complex error."
  --#TYPE         "Uncorrectable CPU-complex error"
  --#SUMMARY      "%s"
  --#ARGUMENTS    { 1 }
  --#SEVERITY     CRITICAL
  --#TIMEINDEX    1
  --#HELPTAG      0
  --#STATE        OPERATIONAL
  ::=  487174 

wfmCPUPresenceDetected TRAP-TYPE
  ENTERPRISE wfmTrapInfo
  VARIABLES {
    wfmTrapDetails,
    wfmTrapType
  }
  DESCRIPTION
  "CPU presence detected."
  --#TYPE         "CPU presence detected"
  --#SUMMARY      "%s"
  --#ARGUMENTS    { 1 }
  --#SEVERITY     INFORMATIONAL
  --#TIMEINDEX    1
  --#HELP         "Note: This is no error condition."
  --#HELPTAG      0
  --#STATE        OPERATIONAL
  ::=  487175 

wfmCPUDisabled TRAP-TYPE
  ENTERPRISE wfmTrapInfo
  VARIABLES {
    wfmTrapDetails,
    wfmTrapType
  }
  DESCRIPTION
  "CPU Disabled."
  --#TYPE         "CPU Disabled"
  --#SUMMARY      "%s"
  --#ARGUMENTS    { 1 }
  --#SEVERITY     INFORMATIONAL
  --#TIMEINDEX    1
  --#HELP         "Note: This is no error condition."
  --#HELPTAG      0
  --#STATE        OPERATIONAL
  ::=  487176 

wfmCPUTerminatorPresenceDetected TRAP-TYPE
  ENTERPRISE wfmTrapInfo
  VARIABLES {
    wfmTrapDetails,
    wfmTrapType
  }
  DESCRIPTION
  "CPU terminator presence detected."
  --#TYPE         "CPU terminator presence detected"
  --#SUMMARY      "%s"
  --#ARGUMENTS    { 1 }
  --#SEVERITY     INFORMATIONAL
  --#TIMEINDEX    1
  --#HELP         "Note: This is no error condition."
  --#HELPTAG      0
  --#STATE        OPERATIONAL
  ::=  487177 

wfmCPUThrottledstart TRAP-TYPE
  ENTERPRISE wfmTrapInfo
  VARIABLES {
    wfmTrapDetails,
    wfmTrapType
  }
  DESCRIPTION
  "CPU throttled (start)."
  --#TYPE         "CPU throttled (start)"
  --#SUMMARY      "%s"
  --#ARGUMENTS    { 1 }
  --#SEVERITY     MAJOR
  --#TIMEINDEX    1
  --#HELPTAG      0
  --#STATE        OPERATIONAL
  ::=  487178 

wfmMachineCheckExceptionUncorrectable TRAP-TYPE
  ENTERPRISE wfmTrapInfo
  VARIABLES {
    wfmTrapDetails,
    wfmTrapType
  }
  DESCRIPTION
  "Machine Check Exception (Uncorrectable)"
  --#TYPE         "Machine Check Exception (Uncorrectable)"
  --#SUMMARY      "%s"
  --#ARGUMENTS    { 1 }
  --#SEVERITY     CRITICAL
  --#TIMEINDEX    1
  --#HELPTAG      0
  --#STATE        OPERATIONAL
  ::=  487179 

wfmCPUThermalTripAlertDeasserted TRAP-TYPE
  ENTERPRISE wfmTrapInfo
  VARIABLES {
    wfmTrapDetails,
    wfmTrapType
  }
  DESCRIPTION
  "CPU thermal trip alert deasserted"
  --#TYPE         "CPU thermal trip alert deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  487297 

wfmCPUNotPresent TRAP-TYPE
  ENTERPRISE wfmTrapInfo
  VARIABLES {
    wfmTrapDetails,
    wfmTrapType
  }
  DESCRIPTION
  "CPU not present."
  --#TYPE         "CPU not present"
  --#SUMMARY      "%s"
  --#ARGUMENTS    { 1 }
  --#SEVERITY     INFORMATIONAL
  --#TIMEINDEX    1
  --#HELP         "Note: This is no error condition."
  --#HELPTAG      0
  --#STATE        OPERATIONAL
  ::=  487303 

wfmCPUEnabled TRAP-TYPE
  ENTERPRISE wfmTrapInfo
  VARIABLES {
    wfmTrapDetails,
    wfmTrapType
  }
  DESCRIPTION
  "CPU Enabled."
  --#TYPE         "CPU Enabled"
  --#SUMMARY      "%s"
  --#ARGUMENTS    { 1 }
  --#SEVERITY     INFORMATIONAL
  --#TIMEINDEX    1
  --#HELP         "Note: This is no error condition."
  --#HELPTAG      0
  --#STATE        OPERATIONAL
  ::=  487304 

wfmCPUTerminatorNotDetected TRAP-TYPE
  ENTERPRISE wfmTrapInfo
  VARIABLES {
    wfmTrapDetails,
    wfmTrapType
  }
  DESCRIPTION
  "CPU terminator not detected."
  --#TYPE         "CPU terminator not detected"
  --#SUMMARY      "%s"
  --#ARGUMENTS    { 1 }
  --#SEVERITY     INFORMATIONAL
  --#TIMEINDEX    1
  --#HELP         "Note: This is no error condition."
  --#HELPTAG      0
  --#STATE        OPERATIONAL
  ::=  487305 

wfmCPUThrottleEnd TRAP-TYPE
  ENTERPRISE wfmTrapInfo
  VARIABLES {
    wfmTrapDetails,
    wfmTrapType
  }
  DESCRIPTION
  "CPU throttle end."
  --#TYPE         "CPU throttle end"
  --#SUMMARY      "%s"
  --#ARGUMENTS    { 1 }
  --#SEVERITY     INFORMATIONAL
  --#TIMEINDEX    1
  --#HELP         "Note: This is no error condition."
  --#HELPTAG      0
  --#STATE        OPERATIONAL
  ::=  487306 

wfmCPUCATERRDetectedReasonUnknown TRAP-TYPE
  ENTERPRISE wfmTrapInfo
  VARIABLES {
    wfmTrapDetails,
    wfmTrapType
  }
  DESCRIPTION
  "CPU CATERR detected, reason unknown"
  --#TYPE         "CPU CATERR detected, reason unknown"
  --#SUMMARY      "%s"
  --#ARGUMENTS    { 1 }
  --#SEVERITY     CRITICAL
  --#TIMEINDEX    1
  --#HELPTAG      0
  --#STATE        OPERATIONAL
  ::=  487424 

wfmCPUTemperatureIsAboveCriticalTemperaturePoint TRAP-TYPE
  ENTERPRISE wfmTrapInfo
  VARIABLES {
    wfmTrapDetails,
    wfmTrapType
  }
  DESCRIPTION
  "CPU temperature is above critical temperature point"
  --#TYPE         "CPU temperature is above critical temperature point"
  --#SUMMARY      "%s"
  --#ARGUMENTS    { 1 }
  --#SEVERITY     MAJOR
  --#TIMEINDEX    1
  --#HELPTAG      0
  --#STATE        OPERATIONAL
  ::=  488960 

wfmCPUPROCHOTSignalIsAsserted TRAP-TYPE
  ENTERPRISE wfmTrapInfo
  VARIABLES {
    wfmTrapDetails,
    wfmTrapType
  }
  DESCRIPTION
  "CPU PROCHOT signal is asserted"
  --#TYPE         "CPU PROCHOT signal is asserted"
  --#SUMMARY      "%s"
  --#ARGUMENTS    { 1 }
  --#SEVERITY     MINOR
  --#TIMEINDEX    1
  --#HELPTAG      0
  --#STATE        OPERATIONAL
  ::=  488961 

wfmCPUThermalThrottlingFunctionalityIsActivated TRAP-TYPE
  ENTERPRISE wfmTrapInfo
  VARIABLES {
    wfmTrapDetails,
    wfmTrapType
  }
  DESCRIPTION
  "CPU thermal throttling functionality is activated"
  --#TYPE         "CPU thermal throttling functionality is activated"
  --#SUMMARY      "%s"
  --#ARGUMENTS    { 1 }
  --#SEVERITY     MINOR
  --#TIMEINDEX    1
  --#HELPTAG      0
  --#STATE        OPERATIONAL
  ::=  488962 

wfmCPUTemperatureIsBelowCriticalTemperaturePoint TRAP-TYPE
  ENTERPRISE wfmTrapInfo
  VARIABLES {
    wfmTrapDetails,
    wfmTrapType
  }
  DESCRIPTION
  "CPU temperature is below critical temperature point"
  --#TYPE         "CPU temperature is below critical temperature point"
  --#SUMMARY      "%s"
  --#ARGUMENTS    { 1 }
  --#SEVERITY     MINOR
  --#TIMEINDEX    1
  --#HELPTAG      0
  --#STATE        OPERATIONAL
  ::=  489088 

wfmCPUPROCHOTSignalIsDeasserted TRAP-TYPE
  ENTERPRISE wfmTrapInfo
  VARIABLES {
    wfmTrapDetails,
    wfmTrapType
  }
  DESCRIPTION
  "CPU PROCHOT signal is deasserted"
  --#TYPE         "CPU PROCHOT signal is deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  489089 

wfmCPUThermalThrottlingFunctionalityIsDeactivated TRAP-TYPE
  ENTERPRISE wfmTrapInfo
  VARIABLES {
    wfmTrapDetails,
    wfmTrapType
  }
  DESCRIPTION
  "CPU thermal throttling functionality is deactivated"
  --#TYPE         "CPU thermal throttling functionality is deactivated"
  --#SUMMARY      "%s"
  --#ARGUMENTS    { 1 }
  --#SEVERITY     INFORMATIONAL
  --#TIMEINDEX    1
  --#HELP         "Note: This is no error condition."
  --#HELPTAG      0
  --#STATE        OPERATIONAL
  ::=  489090 

wfmPowerSupplyInserted TRAP-TYPE
  ENTERPRISE wfmTrapInfo
  VARIABLES {
    wfmTrapDetails,
    wfmTrapType
  }
  DESCRIPTION
  "Power supply inserted."
  --#TYPE         "Power supply inserted"
  --#SUMMARY      "%s"
  --#ARGUMENTS    { 1 }
  --#SEVERITY     INFORMATIONAL
  --#TIMEINDEX    1
  --#HELP         "Note: This is no error condition."
  --#HELPTAG      0
  --#STATE        OPERATIONAL
  ::=  552704 

wfmPowerSupplyAuxDCPowerFail TRAP-TYPE
  ENTERPRISE wfmTrapInfo
  VARIABLES {
    wfmTrapDetails,
    wfmTrapType
  }
  DESCRIPTION
  "Power supply Aux/DC power fail."
  --#TYPE         "Power supply Aux/DC power fail"
  --#SUMMARY      "%s"
  --#ARGUMENTS    { 1 }
  --#SEVERITY     CRITICAL
  --#TIMEINDEX    1
  --#HELPTAG      0
  --#STATE        OPERATIONAL
  ::=  552705 

wfmPowerSupplyPredictiveFailureAsserted TRAP-TYPE
  ENTERPRISE wfmTrapInfo
  VARIABLES {
    wfmTrapDetails,
    wfmTrapType
  }
  DESCRIPTION
  "Power supply predictive failure asserted."
  --#TYPE         "Power supply predictive failure asserted"
  --#SUMMARY      "%s"
  --#ARGUMENTS    { 1 }
  --#SEVERITY     CRITICAL
  --#TIMEINDEX    1
  --#HELPTAG      0
  --#STATE        OPERATIONAL
  ::=  552706 

wfmPowerSupplyInputLostACDC TRAP-TYPE
  ENTERPRISE wfmTrapInfo
  VARIABLES {
    wfmTrapDetails,
    wfmTrapType
  }
  DESCRIPTION
  "Power supply input lost (AC/DC)."
  --#TYPE         "Power supply input lost (AC/DC)"
  --#SUMMARY      "%s"
  --#ARGUMENTS    { 1 }
  --#SEVERITY     CRITICAL
  --#TIMEINDEX    1
  --#HELPTAG      0
  --#STATE        OPERATIONAL
  ::=  552707 

wfmPowerSupplyInputLostOrOutofrange TRAP-TYPE
  ENTERPRISE wfmTrapInfo
  VARIABLES {
    wfmTrapDetails,
    wfmTrapType
  }
  DESCRIPTION
  "Power supply input lost or out-of-range."
  --#TYPE         "Power supply input lost or out-of-range"
  --#SUMMARY      "%s"
  --#ARGUMENTS    { 1 }
  --#SEVERITY     CRITICAL
  --#TIMEINDEX    1
  --#HELPTAG      0
  --#STATE        OPERATIONAL
  ::=  552708 

wfmPowerSupplyInputOutofrangeButPresent TRAP-TYPE
  ENTERPRISE wfmTrapInfo
  VARIABLES {
    wfmTrapDetails,
    wfmTrapType
  }
  DESCRIPTION
  "Power supply input out-of-range, but present."
  --#TYPE         "Power supply input out-of-range, but present"
  --#SUMMARY      "%s"
  --#ARGUMENTS    { 1 }
  --#SEVERITY     CRITICAL
  --#TIMEINDEX    1
  --#HELPTAG      0
  --#STATE        OPERATIONAL
  ::=  552709 

wfmPowerSupplyConfigurationError TRAP-TYPE
  ENTERPRISE wfmTrapInfo
  VARIABLES {
    wfmTrapDetails,
    wfmTrapType
  }
  DESCRIPTION
  "Power supply configuration error."
  --#TYPE         "Power supply configuration error"
  --#SUMMARY      "%s"
  --#ARGUMENTS    { 1 }
  --#SEVERITY     MAJOR
  --#TIMEINDEX    1
  --#HELPTAG      0
  --#STATE        OPERATIONAL
  ::=  552710 

wfmPowerSupplyRemoved TRAP-TYPE
  ENTERPRISE wfmTrapInfo
  VARIABLES {
    wfmTrapDetails,
    wfmTrapType
  }
  DESCRIPTION
  "Power supply removed."
  --#TYPE         "Power supply removed"
  --#SUMMARY      "%s"
  --#ARGUMENTS    { 1 }
  --#SEVERITY     INFORMATIONAL
  --#TIMEINDEX    1
  --#HELP         "Note: This is no error condition."
  --#HELPTAG      0
  --#STATE        OPERATIONAL
  ::=  552832 

wfmPowerSupplyAuxDCPowerOK TRAP-TYPE
  ENTERPRISE wfmTrapInfo
  VARIABLES {
    wfmTrapDetails,
    wfmTrapType
  }
  DESCRIPTION
  "Power supply Aux/DC power OK."
  --#TYPE         "Power supply Aux/DC power OK"
  --#SUMMARY      "%s"
  --#ARGUMENTS    { 1 }
  --#SEVERITY     INFORMATIONAL
  --#TIMEINDEX    1
  --#HELP         "Note: This is no error condition."
  --#HELPTAG      0
  --#STATE        OPERATIONAL
  ::=  552833 

wfmPowerSupplyPredictiveFailureDeasserted TRAP-TYPE
  ENTERPRISE wfmTrapInfo
  VARIABLES {
    wfmTrapDetails,
    wfmTrapType
  }
  DESCRIPTION
  "Power supply predictive failure deasserted."
  --#TYPE         "Power supply predictive failure deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  552834 

wfmPowerSupplyInputOKACDC TRAP-TYPE
  ENTERPRISE wfmTrapInfo
  VARIABLES {
    wfmTrapDetails,
    wfmTrapType
  }
  DESCRIPTION
  "Power supply input OK (AC/DC)."
  --#TYPE         "Power supply input OK (AC/DC)"
  --#SUMMARY      "%s"
  --#ARGUMENTS    { 1 }
  --#SEVERITY     INFORMATIONAL
  --#TIMEINDEX    1
  --#HELP         "Note: This is no error condition."
  --#HELPTAG      0
  --#STATE        OPERATIONAL
  ::=  552835 

wfmPowerSupplyInputOKOrWithinRange TRAP-TYPE
  ENTERPRISE wfmTrapInfo
  VARIABLES {
    wfmTrapDetails,
    wfmTrapType
  }
  DESCRIPTION
  "Power supply input OK or within range."
  --#TYPE         "Power supply input OK or within range"
  --#SUMMARY      "%s"
  --#ARGUMENTS    { 1 }
  --#SEVERITY     INFORMATIONAL
  --#TIMEINDEX    1
  --#HELP         "Note: This is no error condition."
  --#HELPTAG      0
  --#STATE        OPERATIONAL
  ::=  552836 

wfmPowerSupplyInputOKfromOutofrange TRAP-TYPE
  ENTERPRISE wfmTrapInfo
  VARIABLES {
    wfmTrapDetails,
    wfmTrapType
  }
  DESCRIPTION
  "Power supply input OK (from out-of-range)."
  --#TYPE         "Power supply input OK (from out-of-range)"
  --#SUMMARY      "%s"
  --#ARGUMENTS    { 1 }
  --#SEVERITY     INFORMATIONAL
  --#TIMEINDEX    1
  --#HELP         "Note: This is no error condition."
  --#HELPTAG      0
  --#STATE        OPERATIONAL
  ::=  552837 

wfmPowerSupplyConfigOK TRAP-TYPE
  ENTERPRISE wfmTrapInfo
  VARIABLES {
    wfmTrapDetails,
    wfmTrapType
  }
  DESCRIPTION
  "Power supply config OK."
  --#TYPE         "Power supply config OK"
  --#SUMMARY      "%s"
  --#ARGUMENTS    { 1 }
  --#SEVERITY     INFORMATIONAL
  --#TIMEINDEX    1
  --#HELP         "Note: This is no error condition."
  --#HELPTAG      0
  --#STATE        OPERATIONAL
  ::=  552838 

wfmLimitNotExceededForPowerUnitN1 TRAP-TYPE
  ENTERPRISE wfmTrapInfo
  VARIABLES {
    wfmTrapDetails,
    wfmTrapType
  }
  DESCRIPTION
  "Limit not exceeded for power unit"
  --#TYPE         "Limit not exceeded for power unit"
  --#SUMMARY      "%s"
  --#ARGUMENTS    { 1 }
  --#SEVERITY     INFORMATIONAL
  --#TIMEINDEX    1
  --#HELP         "Note: This is no error condition."
  --#HELPTAG      0
  --#STATE        OPERATIONAL
  ::=  591104 

wfmLimitExceededForPowerUnit TRAP-TYPE
  ENTERPRISE wfmTrapInfo
  VARIABLES {
    wfmTrapDetails,
    wfmTrapType
  }
  DESCRIPTION
  "Limit exceeded for power unit"
  --#TYPE         "Limit exceeded for power unit"
  --#SUMMARY      "%s"
  --#ARGUMENTS    { 1 }
  --#SEVERITY     MAJOR
  --#TIMEINDEX    1
  --#HELPTAG      0
  --#STATE        OPERATIONAL
  ::=  591105 

wfmLimitNotExceededForPowerUnitN2 TRAP-TYPE
  ENTERPRISE wfmTrapInfo
  VARIABLES {
    wfmTrapDetails,
    wfmTrapType
  }
  DESCRIPTION
  "Limit not exceeded for power unit"
  --#TYPE         "Limit not exceeded for power unit"
  --#SUMMARY      "%s"
  --#ARGUMENTS    { 1 }
  --#SEVERITY     INFORMATIONAL
  --#TIMEINDEX    1
  --#HELP         "Note: This is no error condition."
  --#HELPTAG      0
  --#STATE        OPERATIONAL
  ::=  591233 

wfmPowerUnitRunning TRAP-TYPE
  ENTERPRISE wfmTrapInfo
  VARIABLES {
    wfmTrapDetails,
    wfmTrapType
  }
  DESCRIPTION
  "Power unit: Running."
  --#TYPE         "Power unit: Running"
  --#SUMMARY      "%s"
  --#ARGUMENTS    { 1 }
  --#SEVERITY     INFORMATIONAL
  --#TIMEINDEX    1
  --#HELP         "Note: This is no error condition."
  --#HELPTAG      0
  --#STATE        OPERATIONAL
  ::=  592384 

wfmPowerUnitInTest TRAP-TYPE
  ENTERPRISE wfmTrapInfo
  VARIABLES {
    wfmTrapDetails,
    wfmTrapType
  }
  DESCRIPTION
  "Power unit: In test."
  --#TYPE         "Power unit: In test"
  --#SUMMARY      "%s"
  --#ARGUMENTS    { 1 }
  --#SEVERITY     INFORMATIONAL
  --#TIMEINDEX    1
  --#HELP         "Note: This is no error condition."
  --#HELPTAG      0
  --#STATE        OPERATIONAL
  ::=  592385 

wfmPowerUnitPowerOFF TRAP-TYPE
  ENTERPRISE wfmTrapInfo
  VARIABLES {
    wfmTrapDetails,
    wfmTrapType
  }
  DESCRIPTION
  "Power unit: Power OFF."
  --#TYPE         "Power unit: Power OFF"
  --#SUMMARY      "%s"
  --#ARGUMENTS    { 1 }
  --#SEVERITY     INFORMATIONAL
  --#TIMEINDEX    1
  --#HELP         "Note: This is no error condition."
  --#HELPTAG      0
  --#STATE        OPERATIONAL
  ::=  592386 

wfmPowerUnitOffline TRAP-TYPE
  ENTERPRISE wfmTrapInfo
  VARIABLES {
    wfmTrapDetails,
    wfmTrapType
  }
  DESCRIPTION
  "Power unit: Off-line."
  --#TYPE         "Power unit: Off-line"
  --#SUMMARY      "%s"
  --#ARGUMENTS    { 1 }
  --#SEVERITY     INFORMATIONAL
  --#TIMEINDEX    1
  --#HELP         "Note: This is no error condition."
  --#HELPTAG      0
  --#STATE        OPERATIONAL
  ::=  592387 

wfmPowerUnitOnline TRAP-TYPE
  ENTERPRISE wfmTrapInfo
  VARIABLES {
    wfmTrapDetails,
    wfmTrapType
  }
  DESCRIPTION
  "Power unit: On-line."
  --#TYPE         "Power unit: On-line"
  --#SUMMARY      "%s"
  --#ARGUMENTS    { 1 }
  --#SEVERITY     INFORMATIONAL
  --#TIMEINDEX    1
  --#HELP         "Note: This is no error condition."
  --#HELPTAG      0
  --#STATE        OPERATIONAL
  ::=  592388 

wfmPowerUnitOffduty TRAP-TYPE
  ENTERPRISE wfmTrapInfo
  VARIABLES {
    wfmTrapDetails,
    wfmTrapType
  }
  DESCRIPTION
  "Power unit: Off-duty."
  --#TYPE         "Power unit: Off-duty"
  --#SUMMARY      "%s"
  --#ARGUMENTS    { 1 }
  --#SEVERITY     INFORMATIONAL
  --#TIMEINDEX    1
  --#HELP         "Note: This is no error condition."
  --#HELPTAG      0
  --#STATE        OPERATIONAL
  ::=  592389 

wfmPowerUnitCriticalNumberOfPS TRAP-TYPE
  ENTERPRISE wfmTrapInfo
  VARIABLES {
    wfmTrapDetails,
    wfmTrapType
  }
  DESCRIPTION
  "Power unit critical number of PS."
  --#TYPE         "Power unit critical number of PS"
  --#SUMMARY      "%s"
  --#ARGUMENTS    { 1 }
  --#SEVERITY     INFORMATIONAL
  --#TIMEINDEX    1
  --#HELP         "Note: This is no error condition."
  --#HELPTAG      0
  --#STATE        OPERATIONAL
  ::=  592390 

wfmPowerUnitPowerSave TRAP-TYPE
  ENTERPRISE wfmTrapInfo
  VARIABLES {
    wfmTrapDetails,
    wfmTrapType
  }
  DESCRIPTION
  "Power unit: Power Save."
  --#TYPE         "Power unit: Power Save"
  --#SUMMARY      "%s"
  --#ARGUMENTS    { 1 }
  --#SEVERITY     INFORMATIONAL
  --#TIMEINDEX    1
  --#HELP         "Note: This is no error condition."
  --#HELPTAG      0
  --#STATE        OPERATIONAL
  ::=  592391 

wfmPowerUnitInstallError TRAP-TYPE
  ENTERPRISE wfmTrapInfo
  VARIABLES {
    wfmTrapDetails,
    wfmTrapType
  }
  DESCRIPTION
  "Power unit: Install. Error."
  --#TYPE         "Power unit: Install. Error"
  --#SUMMARY      "%s"
  --#ARGUMENTS    { 1 }
  --#SEVERITY     INFORMATIONAL
  --#TIMEINDEX    1
  --#HELP         "Note: This is no error condition."
  --#HELPTAG      0
  --#STATE        OPERATIONAL
  ::=  592392 

wfmPowerUnitRedundancyRegained TRAP-TYPE
  ENTERPRISE wfmTrapInfo
  VARIABLES {
    wfmTrapDetails,
    wfmTrapType
  }
  DESCRIPTION
  "Power unit redundancy regained."
  --#TYPE         "Power unit redundancy regained"
  --#SUMMARY      "%s"
  --#ARGUMENTS    { 1 }
  --#SEVERITY     INFORMATIONAL
  --#TIMEINDEX    1
  --#HELP         "Note: This is no error condition."
  --#HELPTAG      0
  --#STATE        OPERATIONAL
  ::=  592640 

wfmPowerUnitRedundancyLostN1 TRAP-TYPE
  ENTERPRISE wfmTrapInfo
  VARIABLES {
    wfmTrapDetails,
    wfmTrapType
  }
  DESCRIPTION
  "Power unit redundancy lost."
  --#TYPE         "Power unit redundancy lost"
  --#SUMMARY      "%s"
  --#ARGUMENTS    { 1 }
  --#SEVERITY     MAJOR
  --#TIMEINDEX    1
  --#HELPTAG      0
  --#STATE        OPERATIONAL
  ::=  592641 

wfmPowerUnitRedundancyDegraded TRAP-TYPE
  ENTERPRISE wfmTrapInfo
  VARIABLES {
    wfmTrapDetails,
    wfmTrapType
  }
  DESCRIPTION
  "Power unit: redundancy degraded."
  --#TYPE         "Power unit: redundancy degraded"
  --#SUMMARY      "%s"
  --#ARGUMENTS    { 1 }
  --#SEVERITY     INFORMATIONAL
  --#TIMEINDEX    1
  --#HELP         "Note: This is no error condition."
  --#HELPTAG      0
  --#STATE        OPERATIONAL
  ::=  592642 

wfmPowerUnitNonRedunfromRedun TRAP-TYPE
  ENTERPRISE wfmTrapInfo
  VARIABLES {
    wfmTrapDetails,
    wfmTrapType
  }
  DESCRIPTION
  "Power unit: non redun. (from redun.)."
  --#TYPE         "Power unit: non redun. (from redun.)"
  --#SUMMARY      "%s"
  --#ARGUMENTS    { 1 }
  --#SEVERITY     INFORMATIONAL
  --#TIMEINDEX    1
  --#HELP         "Note: This is no error condition."
  --#HELPTAG      0
  --#STATE        OPERATIONAL
  ::=  592643 

wfmPowerUnitSufficientResources TRAP-TYPE
  ENTERPRISE wfmTrapInfo
  VARIABLES {
    wfmTrapDetails,
    wfmTrapType
  }
  DESCRIPTION
  "Power unit: sufficient resources."
  --#TYPE         "Power unit: sufficient resources"
  --#SUMMARY      "%s"
  --#ARGUMENTS    { 1 }
  --#SEVERITY     INFORMATIONAL
  --#TIMEINDEX    1
  --#HELP         "Note: This is no error condition."
  --#HELPTAG      0
  --#STATE        OPERATIONAL
  ::=  592644 

wfmPowerUnitInsufficientResources TRAP-TYPE
  ENTERPRISE wfmTrapInfo
  VARIABLES {
    wfmTrapDetails,
    wfmTrapType
  }
  DESCRIPTION
  "Power unit: insufficient resources."
  --#TYPE         "Power unit: insufficient resources"
  --#SUMMARY      "%s"
  --#ARGUMENTS    { 1 }
  --#SEVERITY     MAJOR
  --#TIMEINDEX    1
  --#HELPTAG      0
  --#STATE        OPERATIONAL
  ::=  592645 

wfmPowerUnitDegradedfromRedun TRAP-TYPE
  ENTERPRISE wfmTrapInfo
  VARIABLES {
    wfmTrapDetails,
    wfmTrapType
  }
  DESCRIPTION
  "Power unit: degraded (from redun.)."
  --#TYPE         "Power unit: degraded (from redun.)"
  --#SUMMARY      "%s"
  --#ARGUMENTS    { 1 }
  --#SEVERITY     INFORMATIONAL
  --#TIMEINDEX    1
  --#HELP         "Note: This is no error condition."
  --#HELPTAG      0
  --#STATE        OPERATIONAL
  ::=  592646 

wfmPowerUnitDegradedfromNonRedun TRAP-TYPE
  ENTERPRISE wfmTrapInfo
  VARIABLES {
    wfmTrapDetails,
    wfmTrapType
  }
  DESCRIPTION
  "Power unit: degraded (from non redun.)."
  --#TYPE         "Power unit: degraded (from non redun.)"
  --#SUMMARY      "%s"
  --#ARGUMENTS    { 1 }
  --#SEVERITY     INFORMATIONAL
  --#TIMEINDEX    1
  --#HELP         "Note: This is no error condition."
  --#HELPTAG      0
  --#STATE        OPERATIONAL
  ::=  592647 

wfmPowerUnitRedundancyLostN2 TRAP-TYPE
  ENTERPRISE wfmTrapInfo
  VARIABLES {
    wfmTrapDetails,
    wfmTrapType
  }
  DESCRIPTION
  "Power unit redundancy lost"
  --#TYPE         "Power unit redundancy lost"
  --#SUMMARY      "%s"
  --#ARGUMENTS    { 1 }
  --#SEVERITY     MAJOR
  --#TIMEINDEX    1
  --#HELPTAG      0
  --#STATE        OPERATIONAL
  ::=  592768 

wfmPowerUnitPowerOffPowerDown TRAP-TYPE
  ENTERPRISE wfmTrapInfo
  VARIABLES {
    wfmTrapDetails,
    wfmTrapType
  }
  DESCRIPTION
  "Power Unit - Power Off / Power Down."
  --#TYPE         "Power Unit - Power Off / Power Down"
  --#SUMMARY      "%s"
  --#ARGUMENTS    { 1 }
  --#SEVERITY     INFORMATIONAL
  --#TIMEINDEX    1
  --#HELP         "Note: This is no error condition."
  --#HELPTAG      0
  --#STATE        OPERATIONAL
  ::=  618240 

wfmPowerUnitPowerCycleAsserted TRAP-TYPE
  ENTERPRISE wfmTrapInfo
  VARIABLES {
    wfmTrapDetails,
    wfmTrapType
  }
  DESCRIPTION
  "Power Unit - Power cycle asserted."
  --#TYPE         "Power Unit - Power cycle asserted"
  --#SUMMARY      "%s"
  --#ARGUMENTS    { 1 }
  --#SEVERITY     INFORMATIONAL
  --#TIMEINDEX    1
  --#HELP         "Note: This is no error condition."
  --#HELPTAG      0
  --#STATE        OPERATIONAL
  ::=  618241 

wfmPowerUnit240VAPowerDown TRAP-TYPE
  ENTERPRISE wfmTrapInfo
  VARIABLES {
    wfmTrapDetails,
    wfmTrapType
  }
  DESCRIPTION
  "Power Unit - 240 VA Power Down."
  --#TYPE         "Power Unit - 240 VA Power Down"
  --#SUMMARY      "%s"
  --#ARGUMENTS    { 1 }
  --#SEVERITY     INFORMATIONAL
  --#TIMEINDEX    1
  --#HELP         "Note: This is no error condition."
  --#HELPTAG      0
  --#STATE        OPERATIONAL
  ::=  618242 

wfmInterlockPowerDown TRAP-TYPE
  ENTERPRISE wfmTrapInfo
  VARIABLES {
    wfmTrapDetails,
    wfmTrapType
  }
  DESCRIPTION
  "Interlock Power down."
  --#TYPE         "Interlock Power down"
  --#SUMMARY      "%s"
  --#ARGUMENTS    { 1 }
  --#SEVERITY     INFORMATIONAL
  --#TIMEINDEX    1
  --#HELP         "Note: This is no error condition."
  --#HELPTAG      0
  --#STATE        OPERATIONAL
  ::=  618243 

wfmPowerUnitACLost TRAP-TYPE
  ENTERPRISE wfmTrapInfo
  VARIABLES {
    wfmTrapDetails,
    wfmTrapType
  }
  DESCRIPTION
  "Power Unit - A/C lost."
  --#TYPE         "Power Unit - A/C lost"
  --#SUMMARY      "%s"
  --#ARGUMENTS    { 1 }
  --#SEVERITY     CRITICAL
  --#TIMEINDEX    1
  --#HELPTAG      0
  --#STATE        OPERATIONAL
  ::=  618244 

wfmPowerUnitSoftPowerControlFailure TRAP-TYPE
  ENTERPRISE wfmTrapInfo
  VARIABLES {
    wfmTrapDetails,
    wfmTrapType
  }
  DESCRIPTION
  "Power Unit - Soft Power Control failure."
  --#TYPE         "Power Unit - Soft Power Control failure"
  --#SUMMARY      "%s"
  --#ARGUMENTS    { 1 }
  --#SEVERITY     MAJOR
  --#TIMEINDEX    1
  --#HELPTAG      0
  --#STATE        OPERATIONAL
  ::=  618245 

wfmPowerUnitFailure TRAP-TYPE
  ENTERPRISE wfmTrapInfo
  VARIABLES {
    wfmTrapDetails,
    wfmTrapType
  }
  DESCRIPTION
  "Power Unit failure."
  --#TYPE         "Power Unit failure"
  --#SUMMARY      "%s"
  --#ARGUMENTS    { 1 }
  --#SEVERITY     MAJOR
  --#TIMEINDEX    1
  --#HELPTAG      0
  --#STATE        OPERATIONAL
  ::=  618246 

wfmPowerUnitPredictiveFailure TRAP-TYPE
  ENTERPRISE wfmTrapInfo
  VARIABLES {
    wfmTrapDetails,
    wfmTrapType
  }
  DESCRIPTION
  "Power Unit predictive failure."
  --#TYPE         "Power Unit predictive failure"
  --#SUMMARY      "%s"
  --#ARGUMENTS    { 1 }
  --#SEVERITY     MAJOR
  --#TIMEINDEX    1
  --#HELPTAG      0
  --#STATE        OPERATIONAL
  ::=  618247 

wfmPowerUnitPowerOn TRAP-TYPE
  ENTERPRISE wfmTrapInfo
  VARIABLES {
    wfmTrapDetails,
    wfmTrapType
  }
  DESCRIPTION
  "Power Unit - Power On."
  --#TYPE         "Power Unit - Power On"
  --#SUMMARY      "%s"
  --#ARGUMENTS    { 1 }
  --#SEVERITY     INFORMATIONAL
  --#TIMEINDEX    1
  --#HELP         "Note: This is no error condition."
  --#HELPTAG      0
  --#STATE        OPERATIONAL
  ::=  618368 

wfmPowerUnitPowerCycleDeasserted TRAP-TYPE
  ENTERPRISE wfmTrapInfo
  VARIABLES {
    wfmTrapDetails,
    wfmTrapType
  }
  DESCRIPTION
  "Power Unit - Power cycle deasserted."
  --#TYPE         "Power Unit - Power cycle deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  618369 

wfmPowerUnit240VAPowerRestored TRAP-TYPE
  ENTERPRISE wfmTrapInfo
  VARIABLES {
    wfmTrapDetails,
    wfmTrapType
  }
  DESCRIPTION
  "Power Unit - 240 VA Power restored."
  --#TYPE         "Power Unit - 240 VA Power restored"
  --#SUMMARY      "%s"
  --#ARGUMENTS    { 1 }
  --#SEVERITY     INFORMATIONAL
  --#TIMEINDEX    1
  --#HELP         "Note: This is no error condition."
  --#HELPTAG      0
  --#STATE        OPERATIONAL
  ::=  618370 

wfmInterlockPowerRestored TRAP-TYPE
  ENTERPRISE wfmTrapInfo
  VARIABLES {
    wfmTrapDetails,
    wfmTrapType
  }
  DESCRIPTION
  "Interlock Power restored."
  --#TYPE         "Interlock Power restored"
  --#SUMMARY      "%s"
  --#ARGUMENTS    { 1 }
  --#SEVERITY     INFORMATIONAL
  --#TIMEINDEX    1
  --#HELP         "Note: This is no error condition."
  --#HELPTAG      0
  --#STATE        OPERATIONAL
  ::=  618371 

wfmPowerUnitPowerRestored TRAP-TYPE
  ENTERPRISE wfmTrapInfo
  VARIABLES {
    wfmTrapDetails,
    wfmTrapType
  }
  DESCRIPTION
  "Power Unit - Power restored."
  --#TYPE         "Power Unit - Power restored"
  --#SUMMARY      "%s"
  --#ARGUMENTS    { 1 }
  --#SEVERITY     INFORMATIONAL
  --#TIMEINDEX    1
  --#HELP         "Note: This is no error condition."
  --#HELPTAG      0
  --#STATE        OPERATIONAL
  ::=  618372 

wfmPowerUnitOKfromControlFailure TRAP-TYPE
  ENTERPRISE wfmTrapInfo
  VARIABLES {
    wfmTrapDetails,
    wfmTrapType
  }
  DESCRIPTION
  "Power Unit - OK (from control failure)."
  --#TYPE         "Power Unit - OK (from control failure)"
  --#SUMMARY      "%s"
  --#ARGUMENTS    { 1 }
  --#SEVERITY     INFORMATIONAL
  --#TIMEINDEX    1
  --#HELP         "Note: This is no error condition."
  --#HELPTAG      0
  --#STATE        OPERATIONAL
  ::=  618373 

wfmPowerUnitOK TRAP-TYPE
  ENTERPRISE wfmTrapInfo
  VARIABLES {
    wfmTrapDetails,
    wfmTrapType
  }
  DESCRIPTION
  "Power Unit - OK."
  --#TYPE         "Power Unit - OK"
  --#SUMMARY      "%s"
  --#ARGUMENTS    { 1 }
  --#SEVERITY     INFORMATIONAL
  --#TIMEINDEX    1
  --#HELP         "Note: This is no error condition."
  --#HELPTAG      0
  --#STATE        OPERATIONAL
  ::=  618374 

wfmPowerUnitOKfromPredictiveFailure TRAP-TYPE
  ENTERPRISE wfmTrapInfo
  VARIABLES {
    wfmTrapDetails,
    wfmTrapType
  }
  DESCRIPTION
  "Power Unit - OK (from predictive failure)."
  --#TYPE         "Power Unit - OK (from predictive failure)"
  --#SUMMARY      "%s"
  --#ARGUMENTS    { 1 }
  --#SEVERITY     INFORMATIONAL
  --#TIMEINDEX    1
  --#HELP         "Note: This is no error condition."
  --#HELPTAG      0
  --#STATE        OPERATIONAL
  ::=  618375 

wfmPowerUnitPerformanceMightBeDecreasedInCaseOfAPSUFails TRAP-TYPE
  ENTERPRISE wfmTrapInfo
  VARIABLES {
    wfmTrapDetails,
    wfmTrapType
  }
  DESCRIPTION
  "Power Unit - Performance might be decreased in case of a PSU fails"
  --#TYPE         "Power Unit - Performance might be decreased in case of a PSU fails"
  --#SUMMARY      "%s"
  --#ARGUMENTS    { 1 }
  --#SEVERITY     MINOR
  --#TIMEINDEX    1
  --#HELPTAG      0
  --#STATE        OPERATIONAL
  ::=  618497 

wfmCoolingDevicePreFailOKWarnLNCGL TRAP-TYPE
  ENTERPRISE wfmTrapInfo
  VARIABLES {
    wfmTrapDetails,
    wfmTrapType
  }
  DESCRIPTION
  "Cooling Device Pre-Fail (OK -> Warn):   (lower non critical going low)."
  --#TYPE         "Cooling Device Pre-Fail (OK -> Warn) (LNC_GL)"
  --#SUMMARY      "%s"
  --#ARGUMENTS    { 1 }
  --#SEVERITY     MAJOR
  --#TIMEINDEX    1
  --#HELPTAG      0
  --#STATE        OPERATIONAL
  ::=  655616 

wfmCoolingDeviceIsWorkingOKLNCGH TRAP-TYPE
  ENTERPRISE wfmTrapInfo
  VARIABLES {
    wfmTrapDetails,
    wfmTrapType
  }
  DESCRIPTION
  "Cooling Device is working (OK) (lower non critical going high)."
  --#TYPE         "Cooling Device is working (OK) (LNC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  655617 

wfmCoolingDeviceFailedWarnCritLCGL TRAP-TYPE
  ENTERPRISE wfmTrapInfo
  VARIABLES {
    wfmTrapDetails,
    wfmTrapType
  }
  DESCRIPTION
  "Cooling Device Failed  (Warn -> Crit):   (lower critical going low)."
  --#TYPE         "Cooling Device Failed  (Warn -> Crit) (LC_GL)"
  --#SUMMARY      "%s"
  --#ARGUMENTS    { 1 }
  --#SEVERITY     CRITICAL
  --#TIMEINDEX    1
  --#HELPTAG      0
  --#STATE        OPERATIONAL
  ::=  655618 

wfmCoolingDevicePreFailCritWarnLCGH TRAP-TYPE
  ENTERPRISE wfmTrapInfo
  VARIABLES {
    wfmTrapDetails,
    wfmTrapType
  }
  DESCRIPTION
  "Cooling Device Pre-Fail(Crit -> Warn):   (lower critical going high)."
  --#TYPE         "Cooling Device Pre-Fail(Crit -> Warn) (LC_GH)"
  --#SUMMARY      "%s"
  --#ARGUMENTS    { 1 }
  --#SEVERITY     MAJOR
  --#TIMEINDEX    1
  --#HELPTAG      0
  --#STATE        OPERATIONAL
  ::=  655619 

wfmCoolingDeviceFailedCritNonRecoverLNRGL TRAP-TYPE
  ENTERPRISE wfmTrapInfo
  VARIABLES {
    wfmTrapDetails,
    wfmTrapType
  }
  DESCRIPTION
  "Cooling Device Failed  (Crit -> NonRecover) (lower non recover going low)."
  --#TYPE         "Cooling Device Failed  (Crit -> NonRecover) (LNR_GL)"
  --#SUMMARY      "%s"
  --#ARGUMENTS    { 1 }
  --#SEVERITY     CRITICAL
  --#TIMEINDEX    1
  --#HELPTAG      0
  --#STATE        OPERATIONAL
  ::=  655620 

wfmCoolingDeviceFailedNonRecoverCritLNRGH TRAP-TYPE
  ENTERPRISE wfmTrapInfo
  VARIABLES {
    wfmTrapDetails,
    wfmTrapType
  }
  DESCRIPTION
  "Cooling Device Failed  (NonRecover -> Crit) (lower non recover going high)."
  --#TYPE         "Cooling Device Failed  (NonRecover -> Crit) (LNR_GH)"
  --#SUMMARY      "%s"
  --#ARGUMENTS    { 1 }
  --#SEVERITY     CRITICAL
  --#TIMEINDEX    1
  --#HELPTAG      0
  --#STATE        OPERATIONAL
  ::=  655621 

wfmCoolingDeviceIsWorkingOKLNCGL TRAP-TYPE
  ENTERPRISE wfmTrapInfo
  VARIABLES {
    wfmTrapDetails,
    wfmTrapType
  }
  DESCRIPTION
  "Cooling Device is working (OK) (lower non critical going low de-asserted)."
  --#TYPE         "Cooling Device is working (OK) (LNC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  655744 

wfmCoolingDevicePreFailOKWarnLNCGH TRAP-TYPE
  ENTERPRISE wfmTrapInfo
  VARIABLES {
    wfmTrapDetails,
    wfmTrapType
  }
  DESCRIPTION
  "Cooling Device Pre-Fail(OK -> Warn):   (lower non critical going high de-asserted)."
  --#TYPE         "Cooling Device Pre-Fail(OK -> Warn) (LNC_GHD)"
  --#SUMMARY      "%s"
  --#ARGUMENTS    { 1 }
  --#SEVERITY     MAJOR
  --#TIMEINDEX    1
  --#HELPTAG      0
  --#STATE        OPERATIONAL
  ::=  655745 

wfmCoolingDevicePreFailCritWarnLCGL TRAP-TYPE
  ENTERPRISE wfmTrapInfo
  VARIABLES {
    wfmTrapDetails,
    wfmTrapType
  }
  DESCRIPTION
  "Cooling Device Pre-Fail(Crit -> Warn):   (lower critical going low de-asserted)."
  --#TYPE         "Cooling Device Pre-Fail(Crit -> Warn) (LC_GLD)"
  --#SUMMARY      "%s"
  --#ARGUMENTS    { 1 }
  --#SEVERITY     MAJOR
  --#TIMEINDEX    1
  --#HELPTAG      0
  --#STATE        OPERATIONAL
  ::=  655746 

wfmCoolingDeviceFailedWarnCritLCGH TRAP-TYPE
  ENTERPRISE wfmTrapInfo
  VARIABLES {
    wfmTrapDetails,
    wfmTrapType
  }
  DESCRIPTION
  "Cooling Device Failed  (Warn -> Crit):   (lower critical going high de-asserted)."
  --#TYPE         "Cooling Device Failed  (Warn -> Crit) (LC_GHD)"
  --#SUMMARY      "%s"
  --#ARGUMENTS    { 1 }
  --#SEVERITY     CRITICAL
  --#TIMEINDEX    1
  --#HELPTAG      0
  --#STATE        OPERATIONAL
  ::=  655747 

wfmCoolingDeviceFailedNonRecoverCritLNRGL TRAP-TYPE
  ENTERPRISE wfmTrapInfo
  VARIABLES {
    wfmTrapDetails,
    wfmTrapType
  }
  DESCRIPTION
  "Cooling Device Failed  (NonRecover -> Crit) (lower non recover going low de-asserted)."
  --#TYPE         "Cooling Device Failed  (NonRecover -> Crit) (LNR_GLD)"
  --#SUMMARY      "%s"
  --#ARGUMENTS    { 1 }
  --#SEVERITY     CRITICAL
  --#TIMEINDEX    1
  --#HELPTAG      0
  --#STATE        OPERATIONAL
  ::=  655748 

wfmCoolingDeviceFailedCritNonRecoverLNRGH TRAP-TYPE
  ENTERPRISE wfmTrapInfo
  VARIABLES {
    wfmTrapDetails,
    wfmTrapType
  }
  DESCRIPTION
  "Cooling Device Failed  (Crit -> NonRecover) (lower non recover going high de-asserted)."
  --#TYPE         "Cooling Device Failed  (Crit -> NonRecover) (LNR_GHD)"
  --#SUMMARY      "%s"
  --#ARGUMENTS    { 1 }
  --#SEVERITY     CRITICAL
  --#TIMEINDEX    1
  --#HELPTAG      0
  --#STATE        OPERATIONAL
  ::=  655749 

wfmCoolingDeviceOK TRAP-TYPE
  ENTERPRISE wfmTrapInfo
  VARIABLES {
    wfmTrapDetails,
    wfmTrapType
  }
  DESCRIPTION
  "Cooling Device OK."
  --#TYPE         "Cooling Device OK"
  --#SUMMARY      "%s"
  --#ARGUMENTS    { 1 }
  --#SEVERITY     INFORMATIONAL
  --#TIMEINDEX    1
  --#HELP         "Note: This is no error condition."
  --#HELPTAG      0
  --#STATE        OPERATIONAL
  ::=  656128 

wfmCoolingDeviceFailed TRAP-TYPE
  ENTERPRISE wfmTrapInfo
  VARIABLES {
    wfmTrapDetails,
    wfmTrapType
  }
  DESCRIPTION
  "Cooling Device Failed."
  --#TYPE         "Cooling Device Failed"
  --#SUMMARY      "%s"
  --#ARGUMENTS    { 1 }
  --#SEVERITY     CRITICAL
  --#TIMEINDEX    1
  --#HELPTAG      0
  --#STATE        OPERATIONAL
  ::=  656129 

wfmCoolingDevicePredictiveFailureDeasserted TRAP-TYPE
  ENTERPRISE wfmTrapInfo
  VARIABLES {
    wfmTrapDetails,
    wfmTrapType
  }
  DESCRIPTION
  "Cooling Device predictive failure deasserted."
  --#TYPE         "Cooling Device predictive failure deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  656384 

wfmCoolingDevicePredictiveFailureAsserted TRAP-TYPE
  ENTERPRISE wfmTrapInfo
  VARIABLES {
    wfmTrapDetails,
    wfmTrapType
  }
  DESCRIPTION
  "Cooling Device predictive failure asserted."
  --#TYPE         "Cooling Device predictive failure asserted"
  --#SUMMARY      "%s"
  --#ARGUMENTS    { 1 }
  --#SEVERITY     MAJOR
  --#TIMEINDEX    1
  --#HELPTAG      0
  --#STATE        OPERATIONAL
  ::=  656385 

wfmCoolingDevicePerformanceOK TRAP-TYPE
  ENTERPRISE wfmTrapInfo
  VARIABLES {
    wfmTrapDetails,
    wfmTrapType
  }
  DESCRIPTION
  "Cooling Device performance OK."
  --#TYPE         "Cooling Device performance OK"
  --#SUMMARY      "%s"
  --#ARGUMENTS    { 1 }
  --#SEVERITY     INFORMATIONAL
  --#TIMEINDEX    1
  --#HELP         "Note: This is no error condition."
  --#HELPTAG      0
  --#STATE        OPERATIONAL
  ::=  656896 

wfmCoolingDevicePerformanceLags TRAP-TYPE
  ENTERPRISE wfmTrapInfo
  VARIABLES {
    wfmTrapDetails,
    wfmTrapType
  }
  DESCRIPTION
  "Cooling Device performance lags."
  --#TYPE         "Cooling Device performance lags"
  --#SUMMARY      "%s"
  --#ARGUMENTS    { 1 }
  --#SEVERITY     MAJOR
  --#TIMEINDEX    1
  --#HELPTAG      0
  --#STATE        OPERATIONAL
  ::=  656897 

wfmCoolingDeviceRemoved TRAP-TYPE
  ENTERPRISE wfmTrapInfo
  VARIABLES {
    wfmTrapDetails,
    wfmTrapType
  }
  DESCRIPTION
  "Cooling Device removed."
  --#TYPE         "Cooling Device removed"
  --#SUMMARY      "%s"
  --#ARGUMENTS    { 1 }
  --#SEVERITY     INFORMATIONAL
  --#TIMEINDEX    1
  --#HELP         "Note: This is no error condition."
  --#HELPTAG      0
  --#STATE        OPERATIONAL
  ::=  657408 

wfmCoolingDeviceRestoredreplaced TRAP-TYPE
  ENTERPRISE wfmTrapInfo
  VARIABLES {
    wfmTrapDetails,
    wfmTrapType
  }
  DESCRIPTION
  "Cooling Device restored/replaced."
  --#TYPE         "Cooling Device restored/replaced"
  --#SUMMARY      "%s"
  --#ARGUMENTS    { 1 }
  --#SEVERITY     INFORMATIONAL
  --#TIMEINDEX    1
  --#HELP         "Note: This is no error condition."
  --#HELPTAG      0
  --#STATE        OPERATIONAL
  ::=  657409 

wfmCoolingDeviceDisabled TRAP-TYPE
  ENTERPRISE wfmTrapInfo
  VARIABLES {
    wfmTrapDetails,
    wfmTrapType
  }
  DESCRIPTION
  "Cooling Device disabled."
  --#TYPE         "Cooling Device disabled"
  --#SUMMARY      "%s"
  --#ARGUMENTS    { 1 }
  --#SEVERITY     INFORMATIONAL
  --#TIMEINDEX    1
  --#HELP         "Note: This is no error condition."
  --#HELPTAG      0
  --#STATE        OPERATIONAL
  ::=  657664 

wfmCoolingDeviceEnabled TRAP-TYPE
  ENTERPRISE wfmTrapInfo
  VARIABLES {
    wfmTrapDetails,
    wfmTrapType
  }
  DESCRIPTION
  "Cooling Device enabled."
  --#TYPE         "Cooling Device enabled"
  --#SUMMARY      "%s"
  --#ARGUMENTS    { 1 }
  --#SEVERITY     INFORMATIONAL
  --#TIMEINDEX    1
  --#HELP         "Note: This is no error condition."
  --#HELPTAG      0
  --#STATE        OPERATIONAL
  ::=  657665 

wfmCoolingDeviceFullyRedundant TRAP-TYPE
  ENTERPRISE wfmTrapInfo
  VARIABLES {
    wfmTrapDetails,
    wfmTrapType
  }
  DESCRIPTION
  "Cooling Device fully redundant ."
  --#TYPE         "Cooling Device fully redundant"
  --#SUMMARY      "%s"
  --#ARGUMENTS    { 1 }
  --#SEVERITY     INFORMATIONAL
  --#TIMEINDEX    1
  --#HELP         "Note: This is no error condition."
  --#HELPTAG      0
  --#STATE        OPERATIONAL
  ::=  658176 

wfmCoolingDeviceRedundancyLost TRAP-TYPE
  ENTERPRISE wfmTrapInfo
  VARIABLES {
    wfmTrapDetails,
    wfmTrapType
  }
  DESCRIPTION
  "Cooling Device redundancy lost ."
  --#TYPE         "Cooling Device redundancy lost"
  --#SUMMARY      "%s"
  --#ARGUMENTS    { 1 }
  --#SEVERITY     INFORMATIONAL
  --#TIMEINDEX    1
  --#HELP         "Note: This is no error condition."
  --#HELPTAG      0
  --#STATE        OPERATIONAL
  ::=  658177 

wfmCoolingDeviceRedundancyDegraded TRAP-TYPE
  ENTERPRISE wfmTrapInfo
  VARIABLES {
    wfmTrapDetails,
    wfmTrapType
  }
  DESCRIPTION
  "Cooling Device redundancy degraded."
  --#TYPE         "Cooling Device redundancy degraded"
  --#SUMMARY      "%s"
  --#ARGUMENTS    { 1 }
  --#SEVERITY     INFORMATIONAL
  --#TIMEINDEX    1
  --#HELP         "Note: This is no error condition."
  --#HELPTAG      0
  --#STATE        OPERATIONAL
  ::=  658178 

wfmCoolingDeviceNonRedundantfromRedundant TRAP-TYPE
  ENTERPRISE wfmTrapInfo
  VARIABLES {
    wfmTrapDetails,
    wfmTrapType
  }
  DESCRIPTION
  "Cooling Device non redundant (from redundant)."
  --#TYPE         "Cooling Device non redundant (from redundant)"
  --#SUMMARY      "%s"
  --#ARGUMENTS    { 1 }
  --#SEVERITY     INFORMATIONAL
  --#TIMEINDEX    1
  --#HELP         "Note: This is no error condition."
  --#HELPTAG      0
  --#STATE        OPERATIONAL
  ::=  658179 

wfmCoolingDeviceNonRedundantsufficientResources TRAP-TYPE
  ENTERPRISE wfmTrapInfo
  VARIABLES {
    wfmTrapDetails,
    wfmTrapType
  }
  DESCRIPTION
  "Cooling Device non redundant (sufficient resources)."
  --#TYPE         "Cooling Device non redundant (sufficient resources)"
  --#SUMMARY      "%s"
  --#ARGUMENTS    { 1 }
  --#SEVERITY     INFORMATIONAL
  --#TIMEINDEX    1
  --#HELP         "Note: This is no error condition."
  --#HELPTAG      0
  --#STATE        OPERATIONAL
  ::=  658180 

wfmCoolingDeviceNonRedundantinsufficientResources TRAP-TYPE
  ENTERPRISE wfmTrapInfo
  VARIABLES {
    wfmTrapDetails,
    wfmTrapType
  }
  DESCRIPTION
  "Cooling Device non redundant (insufficient resources)."
  --#TYPE         "Cooling Device non redundant (insufficient resources)"
  --#SUMMARY      "%s"
  --#ARGUMENTS    { 1 }
  --#SEVERITY     INFORMATIONAL
  --#TIMEINDEX    1
  --#HELP         "Note: This is no error condition."
  --#HELPTAG      0
  --#STATE        OPERATIONAL
  ::=  658181 

wfmCoolingDeviceRedundancyDegradedfromRedundant TRAP-TYPE
  ENTERPRISE wfmTrapInfo
  VARIABLES {
    wfmTrapDetails,
    wfmTrapType
  }
  DESCRIPTION
  "Cooling Device redundancy degraded (from redundant)."
  --#TYPE         "Cooling Device redundancy degraded (from redundant)"
  --#SUMMARY      "%s"
  --#ARGUMENTS    { 1 }
  --#SEVERITY     INFORMATIONAL
  --#TIMEINDEX    1
  --#HELP         "Note: This is no error condition."
  --#HELPTAG      0
  --#STATE        OPERATIONAL
  ::=  658182 

wfmCoolingDeviceRedundancyDegradedfromNonRedundant TRAP-TYPE
  ENTERPRISE wfmTrapInfo
  VARIABLES {
    wfmTrapDetails,
    wfmTrapType
  }
  DESCRIPTION
  "Cooling Device redundancy degraded (from non redundant)."
  --#TYPE         "Cooling Device redundancy degraded (from non redundant)"
  --#SUMMARY      "%s"
  --#ARGUMENTS    { 1 }
  --#SEVERITY     INFORMATIONAL
  --#TIMEINDEX    1
  --#HELP         "Note: This is no error condition."
  --#HELPTAG      0
  --#STATE        OPERATIONAL
  ::=  658183 

wfmMultipleFanFailure TRAP-TYPE
  ENTERPRISE wfmTrapInfo
  VARIABLES {
    wfmTrapDetails,
    wfmTrapType
  }
  DESCRIPTION
  "Multiple fan failure."
  --#TYPE         "Multiple fan failure"
  --#SUMMARY      "%s"
  --#ARGUMENTS    { 1 }
  --#SEVERITY     INFORMATIONAL
  --#TIMEINDEX    1
  --#HELP         "Note: This is no error condition."
  --#HELPTAG      0
  --#STATE        OPERATIONAL
  ::=  683776 

wfmPressureLowWarningOKWarnLNCGL TRAP-TYPE
  ENTERPRISE wfmTrapInfo
  VARIABLES {
    wfmTrapDetails,
    wfmTrapType
  }
  DESCRIPTION
  "Pressure Low - Warning (OK -> Warn):   (lower non critical going low)."
  --#TYPE         "Pressure Low - Warning (OK -> Warn) (LNC_GL)"
  --#SUMMARY      "%s"
  --#ARGUMENTS    { 1 }
  --#SEVERITY     MAJOR
  --#TIMEINDEX    1
  --#HELPTAG      0
  --#STATE        OPERATIONAL
  ::=  721152 

wfmPressureOKLNCGH TRAP-TYPE
  ENTERPRISE wfmTrapInfo
  VARIABLES {
    wfmTrapDetails,
    wfmTrapType
  }
  DESCRIPTION
  "Pressure OK (lower non critical going high)."
  --#TYPE         "Pressure OK (LNC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  721153 

wfmPressureLowCriticalWarnCritLCGL TRAP-TYPE
  ENTERPRISE wfmTrapInfo
  VARIABLES {
    wfmTrapDetails,
    wfmTrapType
  }
  DESCRIPTION
  "Pressure Low - Critical(Warn -> Crit):   (lower critical going low)."
  --#TYPE         "Pressure Low - Critical(Warn -> Crit) (LC_GL)"
  --#SUMMARY      "%s"
  --#ARGUMENTS    { 1 }
  --#SEVERITY     CRITICAL
  --#TIMEINDEX    1
  --#HELPTAG      0
  --#STATE        OPERATIONAL
  ::=  721154 

wfmPressureLowNoLongerCriticalLCGH TRAP-TYPE
  ENTERPRISE wfmTrapInfo
  VARIABLES {
    wfmTrapDetails,
    wfmTrapType
  }
  DESCRIPTION
  "Pressure Low - no longer Critical:   (lower critical going high)."
  --#TYPE         "Pressure Low - no longer Critical (LC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  721155 

wfmPressureLowCriticalCritNonRecoverLNRGL TRAP-TYPE
  ENTERPRISE wfmTrapInfo
  VARIABLES {
    wfmTrapDetails,
    wfmTrapType
  }
  DESCRIPTION
  "Pressure Low - Critical(Crit -> NonRecover) (lower non recover going low)."
  --#TYPE         "Pressure Low - Critical(Crit -> NonRecover) (LNR_GL)"
  --#SUMMARY      "%s"
  --#ARGUMENTS    { 1 }
  --#SEVERITY     CRITICAL
  --#TIMEINDEX    1
  --#HELPTAG      0
  --#STATE        OPERATIONAL
  ::=  721156 

wfmPressureLowCriticalNonRecoverCritLNRGH TRAP-TYPE
  ENTERPRISE wfmTrapInfo
  VARIABLES {
    wfmTrapDetails,
    wfmTrapType
  }
  DESCRIPTION
  "Pressure Low - Critical(NonRecover -> Crit) (lower non recover going high)."
  --#TYPE         "Pressure Low - Critical(NonRecover -> Crit) (LNR_GH)"
  --#SUMMARY      "%s"
  --#ARGUMENTS    { 1 }
  --#SEVERITY     CRITICAL
  --#TIMEINDEX    1
  --#HELPTAG      0
  --#STATE        OPERATIONAL
  ::=  721157 

wfmPressureOKUNCGL TRAP-TYPE
  ENTERPRISE wfmTrapInfo
  VARIABLES {
    wfmTrapDetails,
    wfmTrapType
  }
  DESCRIPTION
  "Pressure OK (upper non critical going low)."
  --#TYPE         "Pressure OK (UNC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  721158 

wfmPressureHighWarningOKWarnUNCGH TRAP-TYPE
  ENTERPRISE wfmTrapInfo
  VARIABLES {
    wfmTrapDetails,
    wfmTrapType
  }
  DESCRIPTION
  "Pressure High - Warning (OK -> Warn):   (upper non critical going high)."
  --#TYPE         "Pressure High - Warning (OK -> Warn) (UNC_GH)"
  --#SUMMARY      "%s"
  --#ARGUMENTS    { 1 }
  --#SEVERITY     MAJOR
  --#TIMEINDEX    1
  --#HELPTAG      0
  --#STATE        OPERATIONAL
  ::=  721159 

wfmPressureHighNoLongerCriticalUCGL TRAP-TYPE
  ENTERPRISE wfmTrapInfo
  VARIABLES {
    wfmTrapDetails,
    wfmTrapType
  }
  DESCRIPTION
  "Pressure High - no longer Critical:   (upper critical going low)."
  --#TYPE         "Pressure High - no longer Critical (UC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  721160 

wfmPressureHighCriticalWarnCritUCGH TRAP-TYPE
  ENTERPRISE wfmTrapInfo
  VARIABLES {
    wfmTrapDetails,
    wfmTrapType
  }
  DESCRIPTION
  "Pressure High - Critical(Warn -> Crit):   (upper critical going high)."
  --#TYPE         "Pressure High - Critical(Warn -> Crit) (UC_GH)"
  --#SUMMARY      "%s"
  --#ARGUMENTS    { 1 }
  --#SEVERITY     CRITICAL
  --#TIMEINDEX    1
  --#HELPTAG      0
  --#STATE        OPERATIONAL
  ::=  721161 

wfmPressureHighCriticalNonRecoverCritUNRGL TRAP-TYPE
  ENTERPRISE wfmTrapInfo
  VARIABLES {
    wfmTrapDetails,
    wfmTrapType
  }
  DESCRIPTION
  "Pressure High - Critical(NonRecover -> Crit):   (upper non recover going low)."
  --#TYPE         "Pressure High - Critical(NonRecover -> Crit) (UNR_GL)"
  --#SUMMARY      "%s"
  --#ARGUMENTS    { 1 }
  --#SEVERITY     CRITICAL
  --#TIMEINDEX    1
  --#HELPTAG      0
  --#STATE        OPERATIONAL
  ::=  721162 

wfmPressureHighCriticalCritNonRecoverUNRGH TRAP-TYPE
  ENTERPRISE wfmTrapInfo
  VARIABLES {
    wfmTrapDetails,
    wfmTrapType
  }
  DESCRIPTION
  "Pressure High - Critical(Crit -> NonRecover):   (upper non recover going high)."
  --#TYPE         "Pressure High - Critical(Crit -> NonRecover) (UNR_GH)"
  --#SUMMARY      "%s"
  --#ARGUMENTS    { 1 }
  --#SEVERITY     CRITICAL
  --#TIMEINDEX    1
  --#HELPTAG      0
  --#STATE        OPERATIONAL
  ::=  721163 

wfmPressureOKLNCGL TRAP-TYPE
  ENTERPRISE wfmTrapInfo
  VARIABLES {
    wfmTrapDetails,
    wfmTrapType
  }
  DESCRIPTION
  "Pressure OK (lower non critical going low de-asserted)."
  --#TYPE         "Pressure OK (LNC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  721280 

wfmPressureLowWarningOKWarnLNCGH TRAP-TYPE
  ENTERPRISE wfmTrapInfo
  VARIABLES {
    wfmTrapDetails,
    wfmTrapType
  }
  DESCRIPTION
  "Pressure Low - Warning (OK -> Warn):   (lower non critical going high de-asserted)."
  --#TYPE         "Pressure Low - Warning (OK -> Warn) (LNC_GHD)"
  --#SUMMARY      "%s"
  --#ARGUMENTS    { 1 }
  --#SEVERITY     MAJOR
  --#TIMEINDEX    1
  --#HELPTAG      0
  --#STATE        OPERATIONAL
  ::=  721281 

wfmPressureLowNoLongerCriticalLCGL TRAP-TYPE
  ENTERPRISE wfmTrapInfo
  VARIABLES {
    wfmTrapDetails,
    wfmTrapType
  }
  DESCRIPTION
  "Pressure Low - no longer Critical:   (lower critical going low de-asserted)."
  --#TYPE         "Pressure Low - no longer Critical (LC_GLD)"
  --#SUMMARY      "%s"
  --#ARGUMENTS    { 1 }
  --#SEVERITY     MAJOR
  --#TIMEINDEX    1
  --#HELPTAG      0
  --#STATE        OPERATIONAL
  ::=  721282 

wfmPressureLowCriticalWarnCritLCGH TRAP-TYPE
  ENTERPRISE wfmTrapInfo
  VARIABLES {
    wfmTrapDetails,
    wfmTrapType
  }
  DESCRIPTION
  "Pressure Low - Critical(Warn -> Crit):   (lower critical going high de-asserted)."
  --#TYPE         "Pressure Low - Critical(Warn -> Crit) (LC_GHD)"
  --#SUMMARY      "%s"
  --#ARGUMENTS    { 1 }
  --#SEVERITY     CRITICAL
  --#TIMEINDEX    1
  --#HELPTAG      0
  --#STATE        OPERATIONAL
  ::=  721283 

wfmPressureLowCriticalNonRecoverCritLNRGL TRAP-TYPE
  ENTERPRISE wfmTrapInfo
  VARIABLES {
    wfmTrapDetails,
    wfmTrapType
  }
  DESCRIPTION
  "Pressure Low - Critical(NonRecover -> Crit) (lower non recover going low de-asserted)."
  --#TYPE         "Pressure Low - Critical(NonRecover -> Crit) (LNR_GLD)"
  --#SUMMARY      "%s"
  --#ARGUMENTS    { 1 }
  --#SEVERITY     CRITICAL
  --#TIMEINDEX    1
  --#HELPTAG      0
  --#STATE        OPERATIONAL
  ::=  721284 

wfmPressureLowCriticalCritNonRecoverLNRGH TRAP-TYPE
  ENTERPRISE wfmTrapInfo
  VARIABLES {
    wfmTrapDetails,
    wfmTrapType
  }
  DESCRIPTION
  "Pressure Low - Critical(Crit -> NonRecover) (lower non recover going high de-asserted)."
  --#TYPE         "Pressure Low - Critical(Crit -> NonRecover) (LNR_GHD)"
  --#SUMMARY      "%s"
  --#ARGUMENTS    { 1 }
  --#SEVERITY     CRITICAL
  --#TIMEINDEX    1
  --#HELPTAG      0
  --#STATE        OPERATIONAL
  ::=  721285 

wfmPressureHighWarningOKWarnUNCGL TRAP-TYPE
  ENTERPRISE wfmTrapInfo
  VARIABLES {
    wfmTrapDetails,
    wfmTrapType
  }
  DESCRIPTION
  "Pressure High - Warning (OK -> Warn):   (upper non critical going low de-asserted)."
  --#TYPE         "Pressure High - Warning (OK -> Warn) (UNC_GLD)"
  --#SUMMARY      "%s"
  --#ARGUMENTS    { 1 }
  --#SEVERITY     MAJOR
  --#TIMEINDEX    1
  --#HELPTAG      0
  --#STATE        OPERATIONAL
  ::=  721286 

wfmPressureOKUNCGH TRAP-TYPE
  ENTERPRISE wfmTrapInfo
  VARIABLES {
    wfmTrapDetails,
    wfmTrapType
  }
  DESCRIPTION
  "Pressure OK (upper non critical going high de-asserted)."
  --#TYPE         "Pressure OK (UNC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  721287 

wfmPressureHighCriticalWarnCritUCGL TRAP-TYPE
  ENTERPRISE wfmTrapInfo
  VARIABLES {
    wfmTrapDetails,
    wfmTrapType
  }
  DESCRIPTION
  "Pressure High - Critical(Warn -> Crit):   (upper critical going low de-asserted)."
  --#TYPE         "Pressure High - Critical(Warn -> Crit) (UC_GLD)"
  --#SUMMARY      "%s"
  --#ARGUMENTS    { 1 }
  --#SEVERITY     CRITICAL
  --#TIMEINDEX    1
  --#HELPTAG      0
  --#STATE        OPERATIONAL
  ::=  721288 

wfmPressureHighNoLongerCriticalUCGH TRAP-TYPE
  ENTERPRISE wfmTrapInfo
  VARIABLES {
    wfmTrapDetails,
    wfmTrapType
  }
  DESCRIPTION
  "Pressure High - no longer Critical:   (upper critical going high de-asserted)."
  --#TYPE         "Pressure High - no longer Critical (UC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  721289 

wfmPressureHighCriticalCritNonRecoverUNRGL TRAP-TYPE
  ENTERPRISE wfmTrapInfo
  VARIABLES {
    wfmTrapDetails,
    wfmTrapType
  }
  DESCRIPTION
  "Pressure High - Critical(Crit -> NonRecover):   (upper non recover going low de-asserted)."
  --#TYPE         "Pressure High - Critical(Crit -> NonRecover) (UNR_GLD)"
  --#SUMMARY      "%s"
  --#ARGUMENTS    { 1 }
  --#SEVERITY     CRITICAL
  --#TIMEINDEX    1
  --#HELPTAG      0
  --#STATE        OPERATIONAL
  ::=  721290 

wfmPressureHighCriticalNonRecoverCritUNRGH TRAP-TYPE
  ENTERPRISE wfmTrapInfo
  VARIABLES {
    wfmTrapDetails,
    wfmTrapType
  }
  DESCRIPTION
  "Pressure High - Critical(NonRecover -> Crit):   (upper non recover going high de-asserted)."
  --#TYPE         "Pressure High - Critical(NonRecover -> Crit) (UNR_GHD)"
  --#SUMMARY      "%s"
  --#ARGUMENTS    { 1 }
  --#SEVERITY     CRITICAL
  --#TIMEINDEX    1
  --#HELPTAG      0
  --#STATE        OPERATIONAL
  ::=  721291 

wfmPressureOKassert TRAP-TYPE
  ENTERPRISE wfmTrapInfo
  VARIABLES {
    wfmTrapDetails,
    wfmTrapType
  }
  DESCRIPTION
  "Pressure OK (digital assert sensor)."
  --#TYPE         "Pressure OK (assert)"
  --#SUMMARY      "%s"
  --#ARGUMENTS    { 1 }
  --#SEVERITY     INFORMATIONAL
  --#TIMEINDEX    1
  --#HELP         "Note: This is no error condition."
  --#HELPTAG      0
  --#STATE        OPERATIONAL
  ::=  721664 

wfmPressureFailedassert TRAP-TYPE
  ENTERPRISE wfmTrapInfo
  VARIABLES {
    wfmTrapDetails,
    wfmTrapType
  }
  DESCRIPTION
  "Pressure Failed (digital assert sensor)."
  --#TYPE         "Pressure Failed (assert)"
  --#SUMMARY      "%s"
  --#ARGUMENTS    { 1 }
  --#SEVERITY     CRITICAL
  --#TIMEINDEX    1
  --#HELPTAG      0
  --#STATE        OPERATIONAL
  ::=  721665 

wfmDeassertionOfAOtherUnitsBasedSensor TRAP-TYPE
  ENTERPRISE wfmTrapInfo
  VARIABLES {
    wfmTrapDetails,
    wfmTrapType
  }
  DESCRIPTION
  "Deassertion of a other units based sensor"
  --#TYPE         "Deassertion of a other units based sensor"
  --#SUMMARY      "%s"
  --#ARGUMENTS    { 1 }
  --#SEVERITY     INFORMATIONAL
  --#TIMEINDEX    1
  --#HELP         "Note: This is no error condition."
  --#HELPTAG      0
  --#STATE        OPERATIONAL
  ::=  721793 

wfmPressureOKpredictive TRAP-TYPE
  ENTERPRISE wfmTrapInfo
  VARIABLES {
    wfmTrapDetails,
    wfmTrapType
  }
  DESCRIPTION
  "Pressure OK (digital predictive sensor)."
  --#TYPE         "Pressure OK (predictive)"
  --#SUMMARY      "%s"
  --#ARGUMENTS    { 1 }
  --#SEVERITY     INFORMATIONAL
  --#TIMEINDEX    1
  --#HELP         "Note: This is no error condition."
  --#HELPTAG      0
  --#STATE        OPERATIONAL
  ::=  721920 

wfmPressureFailedpredictive TRAP-TYPE
  ENTERPRISE wfmTrapInfo
  VARIABLES {
    wfmTrapDetails,
    wfmTrapType
  }
  DESCRIPTION
  "Pressure Failed (digital predictive sensor)."
  --#TYPE         "Pressure Failed (predictive)"
  --#SUMMARY      "%s"
  --#ARGUMENTS    { 1 }
  --#SEVERITY     MAJOR
  --#TIMEINDEX    1
  --#HELPTAG      0
  --#STATE        OPERATIONAL
  ::=  721921 

wfmPressureWithinLimit TRAP-TYPE
  ENTERPRISE wfmTrapInfo
  VARIABLES {
    wfmTrapDetails,
    wfmTrapType
  }
  DESCRIPTION
  "Pressure within limit."
  --#TYPE         "Pressure within limit"
  --#SUMMARY      "%s"
  --#ARGUMENTS    { 1 }
  --#SEVERITY     INFORMATIONAL
  --#TIMEINDEX    1
  --#HELP         "Note: This is no error condition."
  --#HELPTAG      0
  --#STATE        OPERATIONAL
  ::=  722176 

wfmPressureLimitExceeded TRAP-TYPE
  ENTERPRISE wfmTrapInfo
  VARIABLES {
    wfmTrapDetails,
    wfmTrapType
  }
  DESCRIPTION
  "Pressure limit exceeded."
  --#TYPE         "Pressure limit exceeded"
  --#SUMMARY      "%s"
  --#ARGUMENTS    { 1 }
  --#SEVERITY     CRITICAL
  --#TIMEINDEX    1
  --#HELPTAG      0
  --#STATE        OPERATIONAL
  ::=  722177 

wfmPressurePerformanceOK TRAP-TYPE
  ENTERPRISE wfmTrapInfo
  VARIABLES {
    wfmTrapDetails,
    wfmTrapType
  }
  DESCRIPTION
  "Pressure performance OK."
  --#TYPE         "Pressure performance OK"
  --#SUMMARY      "%s"
  --#ARGUMENTS    { 1 }
  --#SEVERITY     INFORMATIONAL
  --#TIMEINDEX    1
  --#HELP         "Note: This is no error condition."
  --#HELPTAG      0
  --#STATE        OPERATIONAL
  ::=  722432 

wfmPressurePerformanceLags TRAP-TYPE
  ENTERPRISE wfmTrapInfo
  VARIABLES {
    wfmTrapDetails,
    wfmTrapType
  }
  DESCRIPTION
  "Pressure performance lags."
  --#TYPE         "Pressure performance lags"
  --#SUMMARY      "%s"
  --#ARGUMENTS    { 1 }
  --#SEVERITY     CRITICAL
  --#TIMEINDEX    1
  --#HELPTAG      0
  --#STATE        OPERATIONAL
  ::=  722433 

wfmPressureRemoved TRAP-TYPE
  ENTERPRISE wfmTrapInfo
  VARIABLES {
    wfmTrapDetails,
    wfmTrapType
  }
  DESCRIPTION
  "Pressure removed."
  --#TYPE         "Pressure removed"
  --#SUMMARY      "%s"
  --#ARGUMENTS    { 1 }
  --#SEVERITY     INFORMATIONAL
  --#TIMEINDEX    1
  --#HELP         "Note: This is no error condition."
  --#HELPTAG      0
  --#STATE        OPERATIONAL
  ::=  722944 

wfmPressureRestoredreplaced TRAP-TYPE
  ENTERPRISE wfmTrapInfo
  VARIABLES {
    wfmTrapDetails,
    wfmTrapType
  }
  DESCRIPTION
  "Pressure restored/replaced."
  --#TYPE         "Pressure restored/replaced"
  --#SUMMARY      "%s"
  --#ARGUMENTS    { 1 }
  --#SEVERITY     INFORMATIONAL
  --#TIMEINDEX    1
  --#HELP         "Note: This is no error condition."
  --#HELPTAG      0
  --#STATE        OPERATIONAL
  ::=  722945 

wfmPressureDisabled TRAP-TYPE
  ENTERPRISE wfmTrapInfo
  VARIABLES {
    wfmTrapDetails,
    wfmTrapType
  }
  DESCRIPTION
  "Pressure disabled."
  --#TYPE         "Pressure disabled"
  --#SUMMARY      "%s"
  --#ARGUMENTS    { 1 }
  --#SEVERITY     INFORMATIONAL
  --#TIMEINDEX    1
  --#HELP         "Note: This is no error condition."
  --#HELPTAG      0
  --#STATE        OPERATIONAL
  ::=  723200 

wfmPressureEnabled TRAP-TYPE
  ENTERPRISE wfmTrapInfo
  VARIABLES {
    wfmTrapDetails,
    wfmTrapType
  }
  DESCRIPTION
  "Pressure enabled."
  --#TYPE         "Pressure enabled"
  --#SUMMARY      "%s"
  --#ARGUMENTS    { 1 }
  --#SEVERITY     INFORMATIONAL
  --#TIMEINDEX    1
  --#HELP         "Note: This is no error condition."
  --#HELPTAG      0
  --#STATE        OPERATIONAL
  ::=  723201 

wfmMemoryPDAEventModule TRAP-TYPE
  ENTERPRISE wfmTrapInfo
  VARIABLES {
    wfmTrapDetails,
    wfmTrapType
  }
  DESCRIPTION
  "Memory - PDA event Module."
  --#TYPE         "Memory - PDA event Module"
  --#SUMMARY      "%s"
  --#ARGUMENTS    { 1 }
  --#SEVERITY     MAJOR
  --#TIMEINDEX    1
  --#HELPTAG      0
  --#STATE        OPERATIONAL
  ::=  787457 

wfmMemoryFullyRedundant TRAP-TYPE
  ENTERPRISE wfmTrapInfo
  VARIABLES {
    wfmTrapDetails,
    wfmTrapType
  }
  DESCRIPTION
  "Memory: Fully redundant."
  --#TYPE         "Memory: Fully redundant"
  --#SUMMARY      "%s"
  --#ARGUMENTS    { 1 }
  --#SEVERITY     INFORMATIONAL
  --#TIMEINDEX    1
  --#HELP         "Note: This is no error condition."
  --#HELPTAG      0
  --#STATE        OPERATIONAL
  ::=  789248 

wfmMemoryRedundancyLostN1 TRAP-TYPE
  ENTERPRISE wfmTrapInfo
  VARIABLES {
    wfmTrapDetails,
    wfmTrapType
  }
  DESCRIPTION
  "Memory: Redundancy lost."
  --#TYPE         "Memory: Redundancy lost"
  --#SUMMARY      "%s"
  --#ARGUMENTS    { 1 }
  --#SEVERITY     MAJOR
  --#TIMEINDEX    1
  --#HELPTAG      0
  --#STATE        OPERATIONAL
  ::=  789249 

wfmMemoryRedundancyDegraded TRAP-TYPE
  ENTERPRISE wfmTrapInfo
  VARIABLES {
    wfmTrapDetails,
    wfmTrapType
  }
  DESCRIPTION
  "Memory: Redundancy degraded."
  --#TYPE         "Memory: Redundancy degraded"
  --#SUMMARY      "%s"
  --#ARGUMENTS    { 1 }
  --#SEVERITY     INFORMATIONAL
  --#TIMEINDEX    1
  --#HELP         "Note: This is no error condition."
  --#HELPTAG      0
  --#STATE        OPERATIONAL
  ::=  789250 

wfmMemoryNonredundantfromRedun TRAP-TYPE
  ENTERPRISE wfmTrapInfo
  VARIABLES {
    wfmTrapDetails,
    wfmTrapType
  }
  DESCRIPTION
  "Memory: Non-redundant: (from redun.)."
  --#TYPE         "Memory: Non-redundant: (from redun.)"
  --#SUMMARY      "%s"
  --#ARGUMENTS    { 1 }
  --#SEVERITY     INFORMATIONAL
  --#TIMEINDEX    1
  --#HELP         "Note: This is no error condition."
  --#HELPTAG      0
  --#STATE        OPERATIONAL
  ::=  789251 

wfmMemoryNonredundantSufficientResources TRAP-TYPE
  ENTERPRISE wfmTrapInfo
  VARIABLES {
    wfmTrapDetails,
    wfmTrapType
  }
  DESCRIPTION
  "Memory: Non-redundant: sufficient resources."
  --#TYPE         "Memory: Non-redundant: sufficient resources"
  --#SUMMARY      "%s"
  --#ARGUMENTS    { 1 }
  --#SEVERITY     INFORMATIONAL
  --#TIMEINDEX    1
  --#HELP         "Note: This is no error condition."
  --#HELPTAG      0
  --#STATE        OPERATIONAL
  ::=  789252 

wfmMemoryNonredundantInsufficientResources TRAP-TYPE
  ENTERPRISE wfmTrapInfo
  VARIABLES {
    wfmTrapDetails,
    wfmTrapType
  }
  DESCRIPTION
  "Memory: Non-redundant: insufficient resources."
  --#TYPE         "Memory: Non-redundant: insufficient resources"
  --#SUMMARY      "%s"
  --#ARGUMENTS    { 1 }
  --#SEVERITY     MAJOR
  --#TIMEINDEX    1
  --#HELPTAG      0
  --#STATE        OPERATIONAL
  ::=  789253 

wfmMemoryRedundancyDegradedfromRedun TRAP-TYPE
  ENTERPRISE wfmTrapInfo
  VARIABLES {
    wfmTrapDetails,
    wfmTrapType
  }
  DESCRIPTION
  "Memory: Redundancy degraded (from redun.)."
  --#TYPE         "Memory: Redundancy degraded (from redun.)"
  --#SUMMARY      "%s"
  --#ARGUMENTS    { 1 }
  --#SEVERITY     INFORMATIONAL
  --#TIMEINDEX    1
  --#HELP         "Note: This is no error condition."
  --#HELPTAG      0
  --#STATE        OPERATIONAL
  ::=  789254 

wfmMemoryRedundancyDegradedfromNonRedun TRAP-TYPE
  ENTERPRISE wfmTrapInfo
  VARIABLES {
    wfmTrapDetails,
    wfmTrapType
  }
  DESCRIPTION
  "Memory: Redundancy degraded (from non redun.)."
  --#TYPE         "Memory: Redundancy degraded (from non redun.)"
  --#SUMMARY      "%s"
  --#ARGUMENTS    { 1 }
  --#SEVERITY     INFORMATIONAL
  --#TIMEINDEX    1
  --#HELP         "Note: This is no error condition."
  --#HELPTAG      0
  --#STATE        OPERATIONAL
  ::=  789255 

wfmMemoryRedundancyLostN2 TRAP-TYPE
  ENTERPRISE wfmTrapInfo
  VARIABLES {
    wfmTrapDetails,
    wfmTrapType
  }
  DESCRIPTION
  "Memory redundancy lost"
  --#TYPE         "Memory redundancy lost"
  --#SUMMARY      "%s"
  --#ARGUMENTS    { 1 }
  --#SEVERITY     MAJOR
  --#TIMEINDEX    1
  --#HELPTAG      0
  --#STATE        OPERATIONAL
  ::=  789376 

wfmMemoryRedundancyRegained TRAP-TYPE
  ENTERPRISE wfmTrapInfo
  VARIABLES {
    wfmTrapDetails,
    wfmTrapType
  }
  DESCRIPTION
  "Memory redundancy regained"
  --#TYPE         "Memory redundancy regained"
  --#SUMMARY      "%s"
  --#ARGUMENTS    { 1 }
  --#SEVERITY     INFORMATIONAL
  --#TIMEINDEX    1
  --#HELP         "Note: This is no error condition."
  --#HELPTAG      0
  --#STATE        OPERATIONAL
  ::=  789377 

wfmMemorySinglebitError TRAP-TYPE
  ENTERPRISE wfmTrapInfo
  VARIABLES {
    wfmTrapDetails,
    wfmTrapType
  }
  DESCRIPTION
  "Memory - Single-bit error."
  --#TYPE         "Memory - Single-bit error"
  --#SUMMARY      "%s"
  --#ARGUMENTS    { 1 }
  --#SEVERITY     MINOR
  --#TIMEINDEX    1
  --#HELPTAG      0
  --#STATE        OPERATIONAL
  ::=  814848 

wfmMemoryMultibitError TRAP-TYPE
  ENTERPRISE wfmTrapInfo
  VARIABLES {
    wfmTrapDetails,
    wfmTrapType
  }
  DESCRIPTION
  "Memory - Multi-bit error."
  --#TYPE         "Memory - Multi-bit error"
  --#SUMMARY      "%s"
  --#ARGUMENTS    { 1 }
  --#SEVERITY     CRITICAL
  --#TIMEINDEX    1
  --#HELPTAG      0
  --#STATE        OPERATIONAL
  ::=  814849 

wfmMemoryParityError TRAP-TYPE
  ENTERPRISE wfmTrapInfo
  VARIABLES {
    wfmTrapDetails,
    wfmTrapType
  }
  DESCRIPTION
  "Memory - Parity error."
  --#TYPE         "Memory - Parity error"
  --#SUMMARY      "%s"
  --#ARGUMENTS    { 1 }
  --#SEVERITY     CRITICAL
  --#TIMEINDEX    1
  --#HELPTAG      0
  --#STATE        OPERATIONAL
  ::=  814850 

wfmMemoryScrubFailed TRAP-TYPE
  ENTERPRISE wfmTrapInfo
  VARIABLES {
    wfmTrapDetails,
    wfmTrapType
  }
  DESCRIPTION
  "Memory - scrub failed."
  --#TYPE         "Memory - scrub failed"
  --#SUMMARY      "%s"
  --#ARGUMENTS    { 1 }
  --#SEVERITY     INFORMATIONAL
  --#TIMEINDEX    1
  --#HELP         "Note: This is no error condition."
  --#HELPTAG      0
  --#STATE        OPERATIONAL
  ::=  814851 

wfmMemoryDeviceDisabled TRAP-TYPE
  ENTERPRISE wfmTrapInfo
  VARIABLES {
    wfmTrapDetails,
    wfmTrapType
  }
  DESCRIPTION
  "Memory - device disabled."
  --#TYPE         "Memory - device disabled"
  --#SUMMARY      "%s"
  --#ARGUMENTS    { 1 }
  --#SEVERITY     MAJOR
  --#TIMEINDEX    1
  --#HELPTAG      0
  --#STATE        OPERATIONAL
  ::=  814852 

wfmMemoryErrorLoggingLimitReached TRAP-TYPE
  ENTERPRISE wfmTrapInfo
  VARIABLES {
    wfmTrapDetails,
    wfmTrapType
  }
  DESCRIPTION
  "Memory - error logging limit reached."
  --#TYPE         "Memory - error logging limit reached"
  --#SUMMARY      "%s"
  --#ARGUMENTS    { 1 }
  --#SEVERITY     MAJOR
  --#TIMEINDEX    1
  --#HELPTAG      0
  --#STATE        OPERATIONAL
  ::=  814853 

wfmMemoryPresenceDetected TRAP-TYPE
  ENTERPRISE wfmTrapInfo
  VARIABLES {
    wfmTrapDetails,
    wfmTrapType
  }
  DESCRIPTION
  "Memory - presence detected."
  --#TYPE         "Memory - presence detected"
  --#SUMMARY      "%s"
  --#ARGUMENTS    { 1 }
  --#SEVERITY     INFORMATIONAL
  --#TIMEINDEX    1
  --#HELP         "Note: This is no error condition."
  --#HELPTAG      0
  --#STATE        OPERATIONAL
  ::=  814854 

wfmMemoryConfigurationError TRAP-TYPE
  ENTERPRISE wfmTrapInfo
  VARIABLES {
    wfmTrapDetails,
    wfmTrapType
  }
  DESCRIPTION
  "Memory - configuration error."
  --#TYPE         "Memory - configuration error"
  --#SUMMARY      "%s"
  --#ARGUMENTS    { 1 }
  --#SEVERITY     MAJOR
  --#TIMEINDEX    1
  --#HELPTAG      0
  --#STATE        OPERATIONAL
  ::=  814855 

wfmMemorySpare TRAP-TYPE
  ENTERPRISE wfmTrapInfo
  VARIABLES {
    wfmTrapDetails,
    wfmTrapType
  }
  DESCRIPTION
  "Memory - spare."
  --#TYPE         "Memory - spare"
  --#SUMMARY      "%s"
  --#ARGUMENTS    { 1 }
  --#SEVERITY     INFORMATIONAL
  --#TIMEINDEX    1
  --#HELP         "Note: This is no error condition."
  --#HELPTAG      0
  --#STATE        OPERATIONAL
  ::=  814856 

wfmMemoryAutomaticallyThrottled TRAP-TYPE
  ENTERPRISE wfmTrapInfo
  VARIABLES {
    wfmTrapDetails,
    wfmTrapType
  }
  DESCRIPTION
  "Memory - Automatically Throttled."
  --#TYPE         "Memory - Automatically Throttled"
  --#SUMMARY      "%s"
  --#ARGUMENTS    { 1 }
  --#SEVERITY     MAJOR
  --#TIMEINDEX    1
  --#HELPTAG      0
  --#STATE        OPERATIONAL
  ::=  814857 

wfmMemoryCriticalOvertemperature TRAP-TYPE
  ENTERPRISE wfmTrapInfo
  VARIABLES {
    wfmTrapDetails,
    wfmTrapType
  }
  DESCRIPTION
  "Memory - Critical Overtemperature."
  --#TYPE         "Memory - Critical Overtemperature"
  --#SUMMARY      "%s"
  --#ARGUMENTS    { 1 }
  --#SEVERITY     CRITICAL
  --#TIMEINDEX    1
  --#HELPTAG      0
  --#STATE        OPERATIONAL
  ::=  814858 

wfmMemoryDeviceManuallyDisabled TRAP-TYPE
  ENTERPRISE wfmTrapInfo
  VARIABLES {
    wfmTrapDetails,
    wfmTrapType
  }
  DESCRIPTION
  "Memory device manually disabled"
  --#TYPE         "Memory device manually disabled"
  --#SUMMARY      "%s"
  --#ARGUMENTS    { 1 }
  --#SEVERITY     INFORMATIONAL
  --#TIMEINDEX    1
  --#HELP         "Note: This is no error condition."
  --#HELPTAG      0
  --#STATE        OPERATIONAL
  ::=  814859 

wfmPOSTMemoryIsConfiguredInSafeMode TRAP-TYPE
  ENTERPRISE wfmTrapInfo
  VARIABLES {
    wfmTrapDetails,
    wfmTrapType
  }
  DESCRIPTION
  "POST - Memory is configured in safe mode"
  --#TYPE         "POST - Memory is configured in safe mode"
  --#SUMMARY      "%s"
  --#ARGUMENTS    { 1 }
  --#SEVERITY     CRITICAL
  --#TIMEINDEX    1
  --#HELPTAG      0
  --#STATE        OPERATIONAL
  ::=  814860 

wfmMemoryDeviceEnabled TRAP-TYPE
  ENTERPRISE wfmTrapInfo
  VARIABLES {
    wfmTrapDetails,
    wfmTrapType
  }
  DESCRIPTION
  "Memory - device enabled."
  --#TYPE         "Memory - device enabled"
  --#SUMMARY      "%s"
  --#ARGUMENTS    { 1 }
  --#SEVERITY     INFORMATIONAL
  --#TIMEINDEX    1
  --#HELP         "Note: This is no error condition."
  --#HELPTAG      0
  --#STATE        OPERATIONAL
  ::=  814980 

wfmMemoryDeviceRemoved TRAP-TYPE
  ENTERPRISE wfmTrapInfo
  VARIABLES {
    wfmTrapDetails,
    wfmTrapType
  }
  DESCRIPTION
  "Memory - device removed."
  --#TYPE         "Memory - device removed"
  --#SUMMARY      "%s"
  --#ARGUMENTS    { 1 }
  --#SEVERITY     INFORMATIONAL
  --#TIMEINDEX    1
  --#HELP         "Note: This is no error condition."
  --#HELPTAG      0
  --#STATE        OPERATIONAL
  ::=  814982 

wfmMemoryThrottlingEnd TRAP-TYPE
  ENTERPRISE wfmTrapInfo
  VARIABLES {
    wfmTrapDetails,
    wfmTrapType
  }
  DESCRIPTION
  "Memory - Throttling end."
  --#TYPE         "Memory - Throttling end"
  --#SUMMARY      "%s"
  --#ARGUMENTS    { 1 }
  --#SEVERITY     INFORMATIONAL
  --#TIMEINDEX    1
  --#HELP         "Note: This is no error condition."
  --#HELPTAG      0
  --#STATE        OPERATIONAL
  ::=  814985 

wfmMemoryTemperatureOK TRAP-TYPE
  ENTERPRISE wfmTrapInfo
  VARIABLES {
    wfmTrapDetails,
    wfmTrapType
  }
  DESCRIPTION
  "Memory - Temperature OK."
  --#TYPE         "Memory - Temperature OK"
  --#SUMMARY      "%s"
  --#ARGUMENTS    { 1 }
  --#SEVERITY     INFORMATIONAL
  --#TIMEINDEX    1
  --#HELP         "Note: This is no error condition."
  --#HELPTAG      0
  --#STATE        OPERATIONAL
  ::=  814986 

wfmHotswapCageRemoved TRAP-TYPE
  ENTERPRISE wfmTrapInfo
  VARIABLES {
    wfmTrapDetails,
    wfmTrapType
  }
  DESCRIPTION
  "Hotswap cage removed."
  --#TYPE         "Hotswap cage removed"
  --#SUMMARY      "%s"
  --#ARGUMENTS    { 1 }
  --#SEVERITY     INFORMATIONAL
  --#TIMEINDEX    1
  --#HELP         "Note: This is no error condition."
  --#HELPTAG      0
  --#STATE        OPERATIONAL
  ::=  854016 

wfmHotswapCageInserted TRAP-TYPE
  ENTERPRISE wfmTrapInfo
  VARIABLES {
    wfmTrapDetails,
    wfmTrapType
  }
  DESCRIPTION
  "Hotswap cage inserted."
  --#TYPE         "Hotswap cage inserted"
  --#SUMMARY      "%s"
  --#ARGUMENTS    { 1 }
  --#SEVERITY     INFORMATIONAL
  --#TIMEINDEX    1
  --#HELP         "Note: This is no error condition."
  --#HELPTAG      0
  --#STATE        OPERATIONAL
  ::=  854017 

wfmDiskDriveDrivePresence TRAP-TYPE
  ENTERPRISE wfmTrapInfo
  VARIABLES {
    wfmTrapDetails,
    wfmTrapType
  }
  DESCRIPTION
  "DiskDrive: Drive Presence."
  --#TYPE         "DiskDrive: Drive Presence"
  --#SUMMARY      "%s"
  --#ARGUMENTS    { 1 }
  --#SEVERITY     INFORMATIONAL
  --#TIMEINDEX    1
  --#HELP         "Note: This is no error condition."
  --#HELPTAG      0
  --#STATE        OPERATIONAL
  ::=  880384 

wfmDiskDriveDriveFault TRAP-TYPE
  ENTERPRISE wfmTrapInfo
  VARIABLES {
    wfmTrapDetails,
    wfmTrapType
  }
  DESCRIPTION
  "DiskDrive: Drive Fault."
  --#TYPE         "DiskDrive: Drive Fault"
  --#SUMMARY      "%s"
  --#ARGUMENTS    { 1 }
  --#SEVERITY     CRITICAL
  --#TIMEINDEX    1
  --#HELPTAG      0
  --#STATE        OPERATIONAL
  ::=  880385 

wfmDiskDrivePredictiveFailure TRAP-TYPE
  ENTERPRISE wfmTrapInfo
  VARIABLES {
    wfmTrapDetails,
    wfmTrapType
  }
  DESCRIPTION
  "DiskDrive: Predictive Failure."
  --#TYPE         "DiskDrive: Predictive Failure"
  --#SUMMARY      "%s"
  --#ARGUMENTS    { 1 }
  --#SEVERITY     MAJOR
  --#TIMEINDEX    1
  --#HELPTAG      0
  --#STATE        OPERATIONAL
  ::=  880386 

wfmDiskDriveHotSpare TRAP-TYPE
  ENTERPRISE wfmTrapInfo
  VARIABLES {
    wfmTrapDetails,
    wfmTrapType
  }
  DESCRIPTION
  "DiskDrive: Hot Spare."
  --#TYPE         "DiskDrive: Hot Spare"
  --#SUMMARY      "%s"
  --#ARGUMENTS    { 1 }
  --#SEVERITY     INFORMATIONAL
  --#TIMEINDEX    1
  --#HELP         "Note: This is no error condition."
  --#HELPTAG      0
  --#STATE        OPERATIONAL
  ::=  880387 

wfmDiskDriveConsistencyCheckParityCheckInProgress TRAP-TYPE
  ENTERPRISE wfmTrapInfo
  VARIABLES {
    wfmTrapDetails,
    wfmTrapType
  }
  DESCRIPTION
  "DiskDrive: Consistency Check / Parity Check in progress."
  --#TYPE         "DiskDrive: Consistency Check / Parity Check in progress"
  --#SUMMARY      "%s"
  --#ARGUMENTS    { 1 }
  --#SEVERITY     INFORMATIONAL
  --#TIMEINDEX    1
  --#HELP         "Note: This is no error condition."
  --#HELPTAG      0
  --#STATE        OPERATIONAL
  ::=  880388 

wfmDiskDriveInCriticalArray TRAP-TYPE
  ENTERPRISE wfmTrapInfo
  VARIABLES {
    wfmTrapDetails,
    wfmTrapType
  }
  DESCRIPTION
  "DiskDrive: In Critical Array ."
  --#TYPE         "DiskDrive: In Critical Array"
  --#SUMMARY      "%s"
  --#ARGUMENTS    { 1 }
  --#SEVERITY     CRITICAL
  --#TIMEINDEX    1
  --#HELPTAG      0
  --#STATE        OPERATIONAL
  ::=  880389 

wfmDiskDriveInFailedArray TRAP-TYPE
  ENTERPRISE wfmTrapInfo
  VARIABLES {
    wfmTrapDetails,
    wfmTrapType
  }
  DESCRIPTION
  "DiskDrive: In Failed Array."
  --#TYPE         "DiskDrive: In Failed Array"
  --#SUMMARY      "%s"
  --#ARGUMENTS    { 1 }
  --#SEVERITY     CRITICAL
  --#TIMEINDEX    1
  --#HELPTAG      0
  --#STATE        OPERATIONAL
  ::=  880390 

wfmDiskDriveRebuildRemapInProgress TRAP-TYPE
  ENTERPRISE wfmTrapInfo
  VARIABLES {
    wfmTrapDetails,
    wfmTrapType
  }
  DESCRIPTION
  "DiskDrive: Rebuild/Remap in progress."
  --#TYPE         "DiskDrive: Rebuild/Remap in progress"
  --#SUMMARY      "%s"
  --#ARGUMENTS    { 1 }
  --#SEVERITY     INFORMATIONAL
  --#TIMEINDEX    1
  --#HELP         "Note: This is no error condition."
  --#HELPTAG      0
  --#STATE        OPERATIONAL
  ::=  880391 

wfmDiskDriveRebuildRemapAbortedwasNotCompletedNormally TRAP-TYPE
  ENTERPRISE wfmTrapInfo
  VARIABLES {
    wfmTrapDetails,
    wfmTrapType
  }
  DESCRIPTION
  "DiskDrive: Rebuild/Remap Aborted (was not completed normally)."
  --#TYPE         "DiskDrive: Rebuild/Remap Aborted (was not completed normally)"
  --#SUMMARY      "%s"
  --#ARGUMENTS    { 1 }
  --#SEVERITY     INFORMATIONAL
  --#TIMEINDEX    1
  --#HELP         "Note: This is no error condition."
  --#HELPTAG      0
  --#STATE        OPERATIONAL
  ::=  880392 

wfmHDDReady TRAP-TYPE
  ENTERPRISE wfmTrapInfo
  VARIABLES {
    wfmTrapDetails,
    wfmTrapType
  }
  DESCRIPTION
  "HDD - Ready"
  --#TYPE         "HDD - Ready"
  --#SUMMARY      "%s"
  --#ARGUMENTS    { 1 }
  --#SEVERITY     INFORMATIONAL
  --#TIMEINDEX    1
  --#HELP         "Note: This is no error condition."
  --#HELPTAG      0
  --#STATE        OPERATIONAL
  ::=  884481 

wfmHDDHotSpare TRAP-TYPE
  ENTERPRISE wfmTrapInfo
  VARIABLES {
    wfmTrapDetails,
    wfmTrapType
  }
  DESCRIPTION
  "HDD - Hot Spare"
  --#TYPE         "HDD - Hot Spare"
  --#SUMMARY      "%s"
  --#ARGUMENTS    { 1 }
  --#SEVERITY     INFORMATIONAL
  --#TIMEINDEX    1
  --#HELP         "Note: This is no error condition."
  --#HELPTAG      0
  --#STATE        OPERATIONAL
  ::=  884482 

wfmHDDRebuilding TRAP-TYPE
  ENTERPRISE wfmTrapInfo
  VARIABLES {
    wfmTrapDetails,
    wfmTrapType
  }
  DESCRIPTION
  "HDD - Rebuilding"
  --#TYPE         "HDD - Rebuilding"
  --#SUMMARY      "%s"
  --#ARGUMENTS    { 1 }
  --#SEVERITY     INFORMATIONAL
  --#TIMEINDEX    1
  --#HELP         "Note: This is no error condition."
  --#HELPTAG      0
  --#STATE        OPERATIONAL
  ::=  884483 

wfmHDDFormatting TRAP-TYPE
  ENTERPRISE wfmTrapInfo
  VARIABLES {
    wfmTrapDetails,
    wfmTrapType
  }
  DESCRIPTION
  "HDD - Formatting"
  --#TYPE         "HDD - Formatting"
  --#SUMMARY      "%s"
  --#ARGUMENTS    { 1 }
  --#SEVERITY     INFORMATIONAL
  --#TIMEINDEX    1
  --#HELP         "Note: This is no error condition."
  --#HELPTAG      0
  --#STATE        OPERATIONAL
  ::=  884484 

wfmHDDOffline TRAP-TYPE
  ENTERPRISE wfmTrapInfo
  VARIABLES {
    wfmTrapDetails,
    wfmTrapType
  }
  DESCRIPTION
  "HDD - Offline"
  --#TYPE         "HDD - Offline"
  --#SUMMARY      "%s"
  --#ARGUMENTS    { 1 }
  --#SEVERITY     CRITICAL
  --#TIMEINDEX    1
  --#HELPTAG      0
  --#STATE        OPERATIONAL
  ::=  884485 

wfmHDDFailed TRAP-TYPE
  ENTERPRISE wfmTrapInfo
  VARIABLES {
    wfmTrapDetails,
    wfmTrapType
  }
  DESCRIPTION
  "HDD - Failed"
  --#TYPE         "HDD - Failed"
  --#SUMMARY      "%s"
  --#ARGUMENTS    { 1 }
  --#SEVERITY     CRITICAL
  --#TIMEINDEX    1
  --#HELPTAG      0
  --#STATE        OPERATIONAL
  ::=  884486 

wfmHDDDead TRAP-TYPE
  ENTERPRISE wfmTrapInfo
  VARIABLES {
    wfmTrapDetails,
    wfmTrapType
  }
  DESCRIPTION
  "HDD - Dead"
  --#TYPE         "HDD - Dead"
  --#SUMMARY      "%s"
  --#ARGUMENTS    { 1 }
  --#SEVERITY     CRITICAL
  --#TIMEINDEX    1
  --#HELPTAG      0
  --#STATE        OPERATIONAL
  ::=  884487 

wfmHDDRemoved TRAP-TYPE
  ENTERPRISE wfmTrapInfo
  VARIABLES {
    wfmTrapDetails,
    wfmTrapType
  }
  DESCRIPTION
  "HDD - Removed"
  --#TYPE         "HDD - Removed"
  --#SUMMARY      "%s"
  --#ARGUMENTS    { 1 }
  --#SEVERITY     INFORMATIONAL
  --#TIMEINDEX    1
  --#HELP         "Note: This is no error condition."
  --#HELPTAG      0
  --#STATE        OPERATIONAL
  ::=  884488 

wfmHDDPrefail TRAP-TYPE
  ENTERPRISE wfmTrapInfo
  VARIABLES {
    wfmTrapDetails,
    wfmTrapType
  }
  DESCRIPTION
  "HDD - Prefail"
  --#TYPE         "HDD - Prefail"
  --#SUMMARY      "%s"
  --#ARGUMENTS    { 1 }
  --#SEVERITY     MAJOR
  --#TIMEINDEX    1
  --#HELPTAG      0
  --#STATE        OPERATIONAL
  ::=  884489 

wfmHDDAdded TRAP-TYPE
  ENTERPRISE wfmTrapInfo
  VARIABLES {
    wfmTrapDetails,
    wfmTrapType
  }
  DESCRIPTION
  "HDD - Added"
  --#TYPE         "HDD - Added"
  --#SUMMARY      "%s"
  --#ARGUMENTS    { 1 }
  --#SEVERITY     INFORMATIONAL
  --#TIMEINDEX    1
  --#HELP         "Note: This is no error condition."
  --#HELPTAG      0
  --#STATE        OPERATIONAL
  ::=  884490 

wfmPOSTMemoryResizedConfigChanged TRAP-TYPE
  ENTERPRISE wfmTrapInfo
  VARIABLES {
    wfmTrapDetails,
    wfmTrapType
  }
  DESCRIPTION
  "POST - Memory Resized/Config changed."
  --#TYPE         "POST - Memory Resized/Config changed"
  --#SUMMARY      "%s"
  --#ARGUMENTS    { 1 }
  --#SEVERITY     MAJOR
  --#TIMEINDEX    1
  --#HELPTAG      0
  --#STATE        OPERATIONAL
  ::=  945920 

wfmPOSTError TRAP-TYPE
  ENTERPRISE wfmTrapInfo
  VARIABLES {
    wfmTrapDetails,
    wfmTrapType
  }
  DESCRIPTION
  "POST - Error."
  --#TYPE         "POST - Error"
  --#SUMMARY      "%s"
  --#ARGUMENTS    { 1 }
  --#SEVERITY     CRITICAL
  --#TIMEINDEX    1
  --#HELPTAG      0
  --#STATE        OPERATIONAL
  ::=  1011456 

wfmPOSTSystemFirmwareHANG TRAP-TYPE
  ENTERPRISE wfmTrapInfo
  VARIABLES {
    wfmTrapDetails,
    wfmTrapType
  }
  DESCRIPTION
  "POST - System Firmware HANG."
  --#TYPE         "POST - System Firmware HANG"
  --#SUMMARY      "%s"
  --#ARGUMENTS    { 1 }
  --#SEVERITY     CRITICAL
  --#TIMEINDEX    1
  --#HELPTAG      0
  --#STATE        OPERATIONAL
  ::=  1011457 

wfmPOSTSystemFirmwarePROGRESS TRAP-TYPE
  ENTERPRISE wfmTrapInfo
  VARIABLES {
    wfmTrapDetails,
    wfmTrapType
  }
  DESCRIPTION
  "POST - System Firmware PROGRESS."
  --#TYPE         "POST - System Firmware PROGRESS"
  --#SUMMARY      "%s"
  --#ARGUMENTS    { 1 }
  --#SEVERITY     INFORMATIONAL
  --#TIMEINDEX    1
  --#HELP         "Note: This is no error condition."
  --#HELPTAG      0
  --#STATE        OPERATIONAL
  ::=  1011458 

wfmStorageBladeInitializationFailed TRAP-TYPE
  ENTERPRISE wfmTrapInfo
  VARIABLES {
    wfmTrapDetails,
    wfmTrapType
  }
  DESCRIPTION
  "Storage Blade Initialization Failed"
  --#TYPE         "Storage Blade Initialization Failed"
  --#SUMMARY      "%s"
  --#ARGUMENTS    { 1 }
  --#SEVERITY     MAJOR
  --#TIMEINDEX    1
  --#HELPTAG      0
  --#STATE        OPERATIONAL
  ::=  1011459 

wfmCorrectableMemoryErrorLoggingDisabled TRAP-TYPE
  ENTERPRISE wfmTrapInfo
  VARIABLES {
    wfmTrapDetails,
    wfmTrapType
  }
  DESCRIPTION
  "Correctable memory error logging disabled."
  --#TYPE         "Correctable memory error logging disabled"
  --#SUMMARY      "%s"
  --#ARGUMENTS    { 1 }
  --#SEVERITY     INFORMATIONAL
  --#TIMEINDEX    1
  --#HELP         "Note: This is no error condition."
  --#HELPTAG      0
  --#STATE        OPERATIONAL
  ::=  1076992 

wfmLoggingDisabledForErrorType TRAP-TYPE
  ENTERPRISE wfmTrapInfo
  VARIABLES {
    wfmTrapDetails,
    wfmTrapType
  }
  DESCRIPTION
  "Logging disabled for error type."
  --#TYPE         "Logging disabled for error type"
  --#SUMMARY      "%s"
  --#ARGUMENTS    { 1 }
  --#SEVERITY     INFORMATIONAL
  --#TIMEINDEX    1
  --#HELP         "Note: This is no error condition."
  --#HELPTAG      0
  --#STATE        OPERATIONAL
  ::=  1076993 

wfmEventLogCleared TRAP-TYPE
  ENTERPRISE wfmTrapInfo
  VARIABLES {
    wfmTrapDetails,
    wfmTrapType
  }
  DESCRIPTION
  "Event log cleared."
  --#TYPE         "Event log cleared"
  --#SUMMARY      "%s"
  --#ARGUMENTS    { 1 }
  --#SEVERITY     INFORMATIONAL
  --#TIMEINDEX    1
  --#HELP         "Note: This is no error condition."
  --#HELPTAG      0
  --#STATE        OPERATIONAL
  ::=  1076994 

wfmAllEventLoggingDisabled TRAP-TYPE
  ENTERPRISE wfmTrapInfo
  VARIABLES {
    wfmTrapDetails,
    wfmTrapType
  }
  DESCRIPTION
  "All Event logging disabled."
  --#TYPE         "All Event logging disabled"
  --#SUMMARY      "%s"
  --#ARGUMENTS    { 1 }
  --#SEVERITY     INFORMATIONAL
  --#TIMEINDEX    1
  --#HELP         "Note: This is no error condition."
  --#HELPTAG      0
  --#STATE        OPERATIONAL
  ::=  1076995 

wfmSELFull TRAP-TYPE
  ENTERPRISE wfmTrapInfo
  VARIABLES {
    wfmTrapDetails,
    wfmTrapType
  }
  DESCRIPTION
  "SEL full."
  --#TYPE         "SEL full"
  --#SUMMARY      "%s"
  --#ARGUMENTS    { 1 }
  --#SEVERITY     INFORMATIONAL
  --#TIMEINDEX    1
  --#HELP         "Note: This is no error condition."
  --#HELPTAG      0
  --#STATE        OPERATIONAL
  ::=  1076996 

wfmSELAlmostFull TRAP-TYPE
  ENTERPRISE wfmTrapInfo
  VARIABLES {
    wfmTrapDetails,
    wfmTrapType
  }
  DESCRIPTION
  "SEL almost full."
  --#TYPE         "SEL almost full"
  --#SUMMARY      "%s"
  --#ARGUMENTS    { 1 }
  --#SEVERITY     INFORMATIONAL
  --#TIMEINDEX    1
  --#HELP         "Note: This is no error condition."
  --#HELPTAG      0
  --#STATE        OPERATIONAL
  ::=  1076997 

wfmCorrectableMemoryErrorLoggingEnabled TRAP-TYPE
  ENTERPRISE wfmTrapInfo
  VARIABLES {
    wfmTrapDetails,
    wfmTrapType
  }
  DESCRIPTION
  "Correctable memory error logging enabled."
  --#TYPE         "Correctable memory error logging enabled"
  --#SUMMARY      "%s"
  --#ARGUMENTS    { 1 }
  --#SEVERITY     INFORMATIONAL
  --#TIMEINDEX    1
  --#HELP         "Note: This is no error condition."
  --#HELPTAG      0
  --#STATE        OPERATIONAL
  ::=  1077120 

wfmLoggingEnabledForErrorType TRAP-TYPE
  ENTERPRISE wfmTrapInfo
  VARIABLES {
    wfmTrapDetails,
    wfmTrapType
  }
  DESCRIPTION
  "Logging enabled for error type."
  --#TYPE         "Logging enabled for error type"
  --#SUMMARY      "%s"
  --#ARGUMENTS    { 1 }
  --#SEVERITY     INFORMATIONAL
  --#TIMEINDEX    1
  --#HELP         "Note: This is no error condition."
  --#HELPTAG      0
  --#STATE        OPERATIONAL
  ::=  1077121 

wfmAllEventLoggingEnabled TRAP-TYPE
  ENTERPRISE wfmTrapInfo
  VARIABLES {
    wfmTrapDetails,
    wfmTrapType
  }
  DESCRIPTION
  "All Event logging enabled."
  --#TYPE         "All Event logging enabled"
  --#SUMMARY      "%s"
  --#ARGUMENTS    { 1 }
  --#SEVERITY     INFORMATIONAL
  --#TIMEINDEX    1
  --#HELP         "Note: This is no error condition."
  --#HELPTAG      0
  --#STATE        OPERATIONAL
  ::=  1077123 

wfmWatchdogBIOSWatchdogReset TRAP-TYPE
  ENTERPRISE wfmTrapInfo
  VARIABLES {
    wfmTrapDetails,
    wfmTrapType
  }
  DESCRIPTION
  "Watchdog: BIOS Watchdog Reset."
  --#TYPE         "Watchdog: BIOS Watchdog Reset"
  --#SUMMARY      "%s"
  --#ARGUMENTS    { 1 }
  --#SEVERITY     INFORMATIONAL
  --#TIMEINDEX    1
  --#HELP         "Note: This is no error condition."
  --#HELPTAG      0
  --#STATE        OPERATIONAL
  ::=  1142528 

wfmWatchdogOSWatchdogReset TRAP-TYPE
  ENTERPRISE wfmTrapInfo
  VARIABLES {
    wfmTrapDetails,
    wfmTrapType
  }
  DESCRIPTION
  "Watchdog: OS Watchdog Reset."
  --#TYPE         "Watchdog: OS Watchdog Reset"
  --#SUMMARY      "%s"
  --#ARGUMENTS    { 1 }
  --#SEVERITY     CRITICAL
  --#TIMEINDEX    1
  --#HELPTAG      0
  --#STATE        OPERATIONAL
  ::=  1142529 

wfmWatchdogOSWatchdogShutdown TRAP-TYPE
  ENTERPRISE wfmTrapInfo
  VARIABLES {
    wfmTrapDetails,
    wfmTrapType
  }
  DESCRIPTION
  "Watchdog: OS Watchdog Shutdown."
  --#TYPE         "Watchdog: OS Watchdog Shutdown"
  --#SUMMARY      "%s"
  --#ARGUMENTS    { 1 }
  --#SEVERITY     CRITICAL
  --#TIMEINDEX    1
  --#HELPTAG      0
  --#STATE        OPERATIONAL
  ::=  1142530 

wfmWatchdogOSWatchdogPowerDown TRAP-TYPE
  ENTERPRISE wfmTrapInfo
  VARIABLES {
    wfmTrapDetails,
    wfmTrapType
  }
  DESCRIPTION
  "Watchdog: OS Watchdog Power Down."
  --#TYPE         "Watchdog: OS Watchdog Power Down"
  --#SUMMARY      "%s"
  --#ARGUMENTS    { 1 }
  --#SEVERITY     CRITICAL
  --#TIMEINDEX    1
  --#HELPTAG      0
  --#STATE        OPERATIONAL
  ::=  1142531 

wfmWatchdogOSWatchdogPowerCycle TRAP-TYPE
  ENTERPRISE wfmTrapInfo
  VARIABLES {
    wfmTrapDetails,
    wfmTrapType
  }
  DESCRIPTION
  "Watchdog: OS Watchdog Power Cycle."
  --#TYPE         "Watchdog: OS Watchdog Power Cycle"
  --#SUMMARY      "%s"
  --#ARGUMENTS    { 1 }
  --#SEVERITY     CRITICAL
  --#TIMEINDEX    1
  --#HELPTAG      0
  --#STATE        OPERATIONAL
  ::=  1142532 

wfmWatchdogOSWatchdogNMIDiagnosticInt TRAP-TYPE
  ENTERPRISE wfmTrapInfo
  VARIABLES {
    wfmTrapDetails,
    wfmTrapType
  }
  DESCRIPTION
  "Watchdog: OS Watchdog NMI/Diagnostic Int.."
  --#TYPE         "Watchdog: OS Watchdog NMI/Diagnostic Int."
  --#SUMMARY      "%s"
  --#ARGUMENTS    { 1 }
  --#SEVERITY     CRITICAL
  --#TIMEINDEX    1
  --#HELPTAG      0
  --#STATE        OPERATIONAL
  ::=  1142533 

wfmWatchdogOSWatchdogStatusExpired TRAP-TYPE
  ENTERPRISE wfmTrapInfo
  VARIABLES {
    wfmTrapDetails,
    wfmTrapType
  }
  DESCRIPTION
  "Watchdog: OS Watchdog Status Expired."
  --#TYPE         "Watchdog: OS Watchdog Status Expired"
  --#SUMMARY      "%s"
  --#ARGUMENTS    { 1 }
  --#SEVERITY     CRITICAL
  --#TIMEINDEX    1
  --#HELPTAG      0
  --#STATE        OPERATIONAL
  ::=  1142534 

wfmWatchdogOSWatchdogPretimeoutInterruptNonNMI TRAP-TYPE
  ENTERPRISE wfmTrapInfo
  VARIABLES {
    wfmTrapDetails,
    wfmTrapType
  }
  DESCRIPTION
  "Watchdog: OS Watchdog pre-timeout Interrupt, non-NMI."
  --#TYPE         "Watchdog: OS Watchdog pre-timeout Interrupt, non-NMI"
  --#SUMMARY      "%s"
  --#ARGUMENTS    { 1 }
  --#SEVERITY     INFORMATIONAL
  --#TIMEINDEX    1
  --#HELP         "Note: This is no error condition."
  --#HELPTAG      0
  --#STATE        OPERATIONAL
  ::=  1142535 

wfmPowerOff TRAP-TYPE
  ENTERPRISE wfmTrapInfo
  VARIABLES {
    wfmTrapDetails,
    wfmTrapType
  }
  DESCRIPTION
  "Power Off"
  --#TYPE         "Power Off"
  --#SUMMARY      "%s"
  --#ARGUMENTS    { 1 }
  --#SEVERITY     INFORMATIONAL
  --#TIMEINDEX    1
  --#HELP         "Note: This is no error condition."
  --#HELPTAG      0
  --#STATE        OPERATIONAL
  ::=  1182210 

wfmSystemReconfigured TRAP-TYPE
  ENTERPRISE wfmTrapInfo
  VARIABLES {
    wfmTrapDetails,
    wfmTrapType
  }
  DESCRIPTION
  "System reconfigured."
  --#TYPE         "System reconfigured"
  --#SUMMARY      "%s"
  --#ARGUMENTS    { 1 }
  --#SEVERITY     MINOR
  --#TIMEINDEX    1
  --#HELPTAG      0
  --#STATE        OPERATIONAL
  ::=  1208064 

wfmSystemBootPOSTComplete TRAP-TYPE
  ENTERPRISE wfmTrapInfo
  VARIABLES {
    wfmTrapDetails,
    wfmTrapType
  }
  DESCRIPTION
  "System boot (POST complete)."
  --#TYPE         "System boot (POST complete)"
  --#SUMMARY      "%s"
  --#ARGUMENTS    { 1 }
  --#SEVERITY     INFORMATIONAL
  --#TIMEINDEX    1
  --#HELP         "Note: This is no error condition."
  --#HELPTAG      0
  --#STATE        OPERATIONAL
  ::=  1208065 

wfmUndeterminedSystemHardwareFailure TRAP-TYPE
  ENTERPRISE wfmTrapInfo
  VARIABLES {
    wfmTrapDetails,
    wfmTrapType
  }
  DESCRIPTION
  "Undetermined system hardware failure."
  --#TYPE         "Undetermined system hardware failure"
  --#SUMMARY      "%s"
  --#ARGUMENTS    { 1 }
  --#SEVERITY     CRITICAL
  --#TIMEINDEX    1
  --#HELPTAG      0
  --#STATE        OPERATIONAL
  ::=  1208066 

wfmEntryAddedToAuxiliaryLog TRAP-TYPE
  ENTERPRISE wfmTrapInfo
  VARIABLES {
    wfmTrapDetails,
    wfmTrapType
  }
  DESCRIPTION
  "Entry added to Auxiliary Log."
  --#TYPE         "Entry added to Auxiliary Log"
  --#SUMMARY      "%s"
  --#ARGUMENTS    { 1 }
  --#SEVERITY     INFORMATIONAL
  --#TIMEINDEX    1
  --#HELP         "Note: This is no error condition."
  --#HELPTAG      0
  --#STATE        OPERATIONAL
  ::=  1208067 

wfmPlatformEventPETAction TRAP-TYPE
  ENTERPRISE wfmTrapInfo
  VARIABLES {
    wfmTrapDetails,
    wfmTrapType
  }
  DESCRIPTION
  "Platform Event (PET) Action."
  --#TYPE         "Platform Event (PET) Action"
  --#SUMMARY      "%s"
  --#ARGUMENTS    { 1 }
  --#SEVERITY     INFORMATIONAL
  --#TIMEINDEX    1
  --#HELP         "Note: This is no error condition."
  --#HELPTAG      0
  --#STATE        OPERATIONAL
  ::=  1208068 

wfmTimestampClockSynchEvent TRAP-TYPE
  ENTERPRISE wfmTrapInfo
  VARIABLES {
    wfmTrapDetails,
    wfmTrapType
  }
  DESCRIPTION
  "Timestamp Clock Synch event."
  --#TYPE         "Timestamp Clock Synch event"
  --#SUMMARY      "%s"
  --#ARGUMENTS    { 1 }
  --#SEVERITY     INFORMATIONAL
  --#TIMEINDEX    1
  --#HELP         "Note: This is no error condition."
  --#HELPTAG      0
  --#STATE        OPERATIONAL
  ::=  1208069 

wfmSystemReconfigurationEventDetected TRAP-TYPE
  ENTERPRISE wfmTrapInfo
  VARIABLES {
    wfmTrapDetails,
    wfmTrapType
  }
  DESCRIPTION
  "System reconfiguration event detected."
  --#TYPE         "System reconfiguration event detected"
  --#SUMMARY      "%s"
  --#ARGUMENTS    { 1 }
  --#SEVERITY     INFORMATIONAL
  --#TIMEINDEX    1
  --#HELP         "Note: This is no error condition."
  --#HELPTAG      0
  --#STATE        OPERATIONAL
  ::=  1208070 

wfmLowNoiseModeIsNotSupportedWithTheCurrentSystemConfiguration TRAP-TYPE
  ENTERPRISE wfmTrapInfo
  VARIABLES {
    wfmTrapDetails,
    wfmTrapType
  }
  DESCRIPTION
  "Low Noise Mode is not supported with the current system configuration"
  --#TYPE         "Low Noise Mode is not supported with the current system configuration"
  --#SUMMARY      "%s"
  --#ARGUMENTS    { 1 }
  --#SEVERITY     MINOR
  --#TIMEINDEX    1
  --#HELPTAG      0
  --#STATE        OPERATIONAL
  ::=  1208071 

wfmTimestampClockSynchronization TRAP-TYPE
  ENTERPRISE wfmTrapInfo
  VARIABLES {
    wfmTrapDetails,
    wfmTrapType
  }
  DESCRIPTION
  "Timestamp clock synchronization"
  --#TYPE         "Timestamp clock synchronization"
  --#SUMMARY      "%s"
  --#ARGUMENTS    { 1 }
  --#SEVERITY     INFORMATIONAL
  --#TIMEINDEX    1
  --#HELP         "Note: This is no error condition."
  --#HELPTAG      0
  --#STATE        OPERATIONAL
  ::=  1208197 

wfmFrontPanelNMIDiagnosticInterrupt TRAP-TYPE
  ENTERPRISE wfmTrapInfo
  VARIABLES {
    wfmTrapDetails,
    wfmTrapType
  }
  DESCRIPTION
  "Front Panel NMI / Diagnostic Interrupt."
  --#TYPE         "Front Panel NMI / Diagnostic Interrupt"
  --#SUMMARY      "%s"
  --#ARGUMENTS    { 1 }
  --#SEVERITY     CRITICAL
  --#TIMEINDEX    1
  --#HELPTAG      0
  --#STATE        OPERATIONAL
  ::=  1273600 

wfmBusTimeout TRAP-TYPE
  ENTERPRISE wfmTrapInfo
  VARIABLES {
    wfmTrapDetails,
    wfmTrapType
  }
  DESCRIPTION
  "Bus timeout."
  --#TYPE         "Bus timeout"
  --#SUMMARY      "%s"
  --#ARGUMENTS    { 1 }
  --#SEVERITY     CRITICAL
  --#TIMEINDEX    1
  --#HELPTAG      0
  --#STATE        OPERATIONAL
  ::=  1273601 

wfmIOChannelCheckNMI TRAP-TYPE
  ENTERPRISE wfmTrapInfo
  VARIABLES {
    wfmTrapDetails,
    wfmTrapType
  }
  DESCRIPTION
  "I/O channel check NMI."
  --#TYPE         "I/O channel check NMI"
  --#SUMMARY      "%s"
  --#ARGUMENTS    { 1 }
  --#SEVERITY     CRITICAL
  --#TIMEINDEX    1
  --#HELPTAG      0
  --#STATE        OPERATIONAL
  ::=  1273602 

wfmSoftwareNMI TRAP-TYPE
  ENTERPRISE wfmTrapInfo
  VARIABLES {
    wfmTrapDetails,
    wfmTrapType
  }
  DESCRIPTION
  "Software NMI."
  --#TYPE         "Software NMI"
  --#SUMMARY      "%s"
  --#ARGUMENTS    { 1 }
  --#SEVERITY     CRITICAL
  --#TIMEINDEX    1
  --#HELPTAG      0
  --#STATE        OPERATIONAL
  ::=  1273603 

wfmPCIPERR TRAP-TYPE
  ENTERPRISE wfmTrapInfo
  VARIABLES {
    wfmTrapDetails,
    wfmTrapType
  }
  DESCRIPTION
  "PCI PERR."
  --#TYPE         "PCI PERR"
  --#SUMMARY      "%s"
  --#ARGUMENTS    { 1 }
  --#SEVERITY     CRITICAL
  --#TIMEINDEX    1
  --#HELPTAG      0
  --#STATE        OPERATIONAL
  ::=  1273604 

wfmPCISERR TRAP-TYPE
  ENTERPRISE wfmTrapInfo
  VARIABLES {
    wfmTrapDetails,
    wfmTrapType
  }
  DESCRIPTION
  "PCI SERR."
  --#TYPE         "PCI SERR"
  --#SUMMARY      "%s"
  --#ARGUMENTS    { 1 }
  --#SEVERITY     CRITICAL
  --#TIMEINDEX    1
  --#HELPTAG      0
  --#STATE        OPERATIONAL
  ::=  1273605 

wfmEISAFailsafeTimerExpired TRAP-TYPE
  ENTERPRISE wfmTrapInfo
  VARIABLES {
    wfmTrapDetails,
    wfmTrapType
  }
  DESCRIPTION
  "EISA Failsafe timer expired."
  --#TYPE         "EISA Failsafe timer expired"
  --#SUMMARY      "%s"
  --#ARGUMENTS    { 1 }
  --#SEVERITY     CRITICAL
  --#TIMEINDEX    1
  --#HELPTAG      0
  --#STATE        OPERATIONAL
  ::=  1273606 

wfmCorrectableBusError TRAP-TYPE
  ENTERPRISE wfmTrapInfo
  VARIABLES {
    wfmTrapDetails,
    wfmTrapType
  }
  DESCRIPTION
  "Correctable bus error."
  --#TYPE         "Correctable bus error"
  --#SUMMARY      "%s"
  --#ARGUMENTS    { 1 }
  --#SEVERITY     MAJOR
  --#TIMEINDEX    1
  --#HELPTAG      0
  --#STATE        OPERATIONAL
  ::=  1273607 

wfmUncorrectableBusError TRAP-TYPE
  ENTERPRISE wfmTrapInfo
  VARIABLES {
    wfmTrapDetails,
    wfmTrapType
  }
  DESCRIPTION
  "Uncorrectable bus error."
  --#TYPE         "Uncorrectable bus error"
  --#SUMMARY      "%s"
  --#ARGUMENTS    { 1 }
  --#SEVERITY     CRITICAL
  --#TIMEINDEX    1
  --#HELPTAG      0
  --#STATE        OPERATIONAL
  ::=  1273608 

wfmFatalNMIPort61hBit7 TRAP-TYPE
  ENTERPRISE wfmTrapInfo
  VARIABLES {
    wfmTrapDetails,
    wfmTrapType
  }
  DESCRIPTION
  "Fatal NMI (Port 61h Bit 7)."
  --#TYPE         "Fatal NMI (Port 61h Bit 7)"
  --#SUMMARY      "%s"
  --#ARGUMENTS    { 1 }
  --#SEVERITY     CRITICAL
  --#TIMEINDEX    1
  --#HELPTAG      0
  --#STATE        OPERATIONAL
  ::=  1273609 

wfmPCIDataLinkProtocolError TRAP-TYPE
  ENTERPRISE wfmTrapInfo
  VARIABLES {
    wfmTrapDetails,
    wfmTrapType
  }
  DESCRIPTION
  "PCI: Data Link Protocol Error"
  --#TYPE         "PCI: Data Link Protocol Error"
  --#SUMMARY      "%s"
  --#ARGUMENTS    { 1 }
  --#SEVERITY     CRITICAL
  --#TIMEINDEX    1
  --#HELPTAG      0
  --#STATE        OPERATIONAL
  ::=  1273856 

wfmPCISurpriseDownErrorStatus TRAP-TYPE
  ENTERPRISE wfmTrapInfo
  VARIABLES {
    wfmTrapDetails,
    wfmTrapType
  }
  DESCRIPTION
  "PCI: Surprise Down Error Status"
  --#TYPE         "PCI: Surprise Down Error Status"
  --#SUMMARY      "%s"
  --#ARGUMENTS    { 1 }
  --#SEVERITY     CRITICAL
  --#TIMEINDEX    1
  --#HELPTAG      0
  --#STATE        OPERATIONAL
  ::=  1273857 

wfmPCIUnexpectedCompletion TRAP-TYPE
  ENTERPRISE wfmTrapInfo
  VARIABLES {
    wfmTrapDetails,
    wfmTrapType
  }
  DESCRIPTION
  "PCI: Unexpected Completion"
  --#TYPE         "PCI: Unexpected Completion"
  --#SUMMARY      "%s"
  --#ARGUMENTS    { 1 }
  --#SEVERITY     CRITICAL
  --#TIMEINDEX    1
  --#HELPTAG      0
  --#STATE        OPERATIONAL
  ::=  1273858 

wfmPCIUnsupportedRequest TRAP-TYPE
  ENTERPRISE wfmTrapInfo
  VARIABLES {
    wfmTrapDetails,
    wfmTrapType
  }
  DESCRIPTION
  "PCI: Unsupported Request"
  --#TYPE         "PCI: Unsupported Request"
  --#SUMMARY      "%s"
  --#ARGUMENTS    { 1 }
  --#SEVERITY     CRITICAL
  --#TIMEINDEX    1
  --#HELPTAG      0
  --#STATE        OPERATIONAL
  ::=  1273859 

wfmPCIPoisonedTLP TRAP-TYPE
  ENTERPRISE wfmTrapInfo
  VARIABLES {
    wfmTrapDetails,
    wfmTrapType
  }
  DESCRIPTION
  "PCI: Poisoned TLP"
  --#TYPE         "PCI: Poisoned TLP"
  --#SUMMARY      "%s"
  --#ARGUMENTS    { 1 }
  --#SEVERITY     CRITICAL
  --#TIMEINDEX    1
  --#HELPTAG      0
  --#STATE        OPERATIONAL
  ::=  1273860 

wfmPCIFlowControlProtocolError TRAP-TYPE
  ENTERPRISE wfmTrapInfo
  VARIABLES {
    wfmTrapDetails,
    wfmTrapType
  }
  DESCRIPTION
  "PCI: Flow Control Protocol Error"
  --#TYPE         "PCI: Flow Control Protocol Error"
  --#SUMMARY      "%s"
  --#ARGUMENTS    { 1 }
  --#SEVERITY     CRITICAL
  --#TIMEINDEX    1
  --#HELPTAG      0
  --#STATE        OPERATIONAL
  ::=  1273861 

wfmPCICompletionTimeout TRAP-TYPE
  ENTERPRISE wfmTrapInfo
  VARIABLES {
    wfmTrapDetails,
    wfmTrapType
  }
  DESCRIPTION
  "PCI: Completion Time-out"
  --#TYPE         "PCI: Completion Time-out"
  --#SUMMARY      "%s"
  --#ARGUMENTS    { 1 }
  --#SEVERITY     CRITICAL
  --#TIMEINDEX    1
  --#HELPTAG      0
  --#STATE        OPERATIONAL
  ::=  1273862 

wfmPCICompleterAbort TRAP-TYPE
  ENTERPRISE wfmTrapInfo
  VARIABLES {
    wfmTrapDetails,
    wfmTrapType
  }
  DESCRIPTION
  "PCI: Completer Abort"
  --#TYPE         "PCI: Completer Abort"
  --#SUMMARY      "%s"
  --#ARGUMENTS    { 1 }
  --#SEVERITY     CRITICAL
  --#TIMEINDEX    1
  --#HELPTAG      0
  --#STATE        OPERATIONAL
  ::=  1273863 

wfmPCIReceiverBufferOverflow TRAP-TYPE
  ENTERPRISE wfmTrapInfo
  VARIABLES {
    wfmTrapDetails,
    wfmTrapType
  }
  DESCRIPTION
  "PCI: Receiver Buffer Overflow"
  --#TYPE         "PCI: Receiver Buffer Overflow"
  --#SUMMARY      "%s"
  --#ARGUMENTS    { 1 }
  --#SEVERITY     CRITICAL
  --#TIMEINDEX    1
  --#HELPTAG      0
  --#STATE        OPERATIONAL
  ::=  1273864 

wfmPCIACSViolation TRAP-TYPE
  ENTERPRISE wfmTrapInfo
  VARIABLES {
    wfmTrapDetails,
    wfmTrapType
  }
  DESCRIPTION
  "PCI: ACS Violation"
  --#TYPE         "PCI: ACS Violation"
  --#SUMMARY      "%s"
  --#ARGUMENTS    { 1 }
  --#SEVERITY     CRITICAL
  --#TIMEINDEX    1
  --#HELPTAG      0
  --#STATE        OPERATIONAL
  ::=  1273865 

wfmPCIMalformedTLP TRAP-TYPE
  ENTERPRISE wfmTrapInfo
  VARIABLES {
    wfmTrapDetails,
    wfmTrapType
  }
  DESCRIPTION
  "PCI: Malformed TLP"
  --#TYPE         "PCI: Malformed TLP"
  --#SUMMARY      "%s"
  --#ARGUMENTS    { 1 }
  --#SEVERITY     CRITICAL
  --#TIMEINDEX    1
  --#HELPTAG      0
  --#STATE        OPERATIONAL
  ::=  1273866 

wfmPCIECRCError TRAP-TYPE
  ENTERPRISE wfmTrapInfo
  VARIABLES {
    wfmTrapDetails,
    wfmTrapType
  }
  DESCRIPTION
  "PCI: ECRC Error"
  --#TYPE         "PCI: ECRC Error"
  --#SUMMARY      "%s"
  --#ARGUMENTS    { 1 }
  --#SEVERITY     CRITICAL
  --#TIMEINDEX    1
  --#HELPTAG      0
  --#STATE        OPERATIONAL
  ::=  1274368 

wfmPCIUncorrectableInternalError TRAP-TYPE
  ENTERPRISE wfmTrapInfo
  VARIABLES {
    wfmTrapDetails,
    wfmTrapType
  }
  DESCRIPTION
  "PCI: Uncorrectable Internal Error"
  --#TYPE         "PCI: Uncorrectable Internal Error"
  --#SUMMARY      "%s"
  --#ARGUMENTS    { 1 }
  --#SEVERITY     CRITICAL
  --#TIMEINDEX    1
  --#HELPTAG      0
  --#STATE        OPERATIONAL
  ::=  1274369 

wfmPCIMCBlockedTLP TRAP-TYPE
  ENTERPRISE wfmTrapInfo
  VARIABLES {
    wfmTrapDetails,
    wfmTrapType
  }
  DESCRIPTION
  "PCI: MC Blocked TLP"
  --#TYPE         "PCI: MC Blocked TLP"
  --#SUMMARY      "%s"
  --#ARGUMENTS    { 1 }
  --#SEVERITY     CRITICAL
  --#TIMEINDEX    1
  --#HELPTAG      0
  --#STATE        OPERATIONAL
  ::=  1274370 

wfmPCIAtomicOpEgressBlocked TRAP-TYPE
  ENTERPRISE wfmTrapInfo
  VARIABLES {
    wfmTrapDetails,
    wfmTrapType
  }
  DESCRIPTION
  "PCI: AtomicOp Egress Blocked"
  --#TYPE         "PCI: AtomicOp Egress Blocked"
  --#SUMMARY      "%s"
  --#ARGUMENTS    { 1 }
  --#SEVERITY     CRITICAL
  --#TIMEINDEX    1
  --#HELPTAG      0
  --#STATE        OPERATIONAL
  ::=  1274371 

wfmPCITLPPrefixBlockedError TRAP-TYPE
  ENTERPRISE wfmTrapInfo
  VARIABLES {
    wfmTrapDetails,
    wfmTrapType
  }
  DESCRIPTION
  "PCI: TLP Prefix Blocked Error"
  --#TYPE         "PCI: TLP Prefix Blocked Error"
  --#SUMMARY      "%s"
  --#ARGUMENTS    { 1 }
  --#SEVERITY     CRITICAL
  --#TIMEINDEX    1
  --#HELPTAG      0
  --#STATE        OPERATIONAL
  ::=  1274372 

wfmLegacyPCIMasterDataPERROnPCIBus TRAP-TYPE
  ENTERPRISE wfmTrapInfo
  VARIABLES {
    wfmTrapDetails,
    wfmTrapType
  }
  DESCRIPTION
  "Legacy PCI Master Data PERR on PCI bus"
  --#TYPE         "Legacy PCI Master Data PERR on PCI bus"
  --#SUMMARY      "%s"
  --#ARGUMENTS    { 1 }
  --#SEVERITY     CRITICAL
  --#TIMEINDEX    1
  --#HELPTAG      0
  --#STATE        OPERATIONAL
  ::=  1274624 

wfmLegacyPCITargetAbortOnPCIBus TRAP-TYPE
  ENTERPRISE wfmTrapInfo
  VARIABLES {
    wfmTrapDetails,
    wfmTrapType
  }
  DESCRIPTION
  "Legacy PCI Target Abort on PCI bus"
  --#TYPE         "Legacy PCI Target Abort on PCI bus"
  --#SUMMARY      "%s"
  --#ARGUMENTS    { 1 }
  --#SEVERITY     CRITICAL
  --#TIMEINDEX    1
  --#HELPTAG      0
  --#STATE        OPERATIONAL
  ::=  1274625 

wfmLegacyPCIReceivedTargetAbortOnPCIBus TRAP-TYPE
  ENTERPRISE wfmTrapInfo
  VARIABLES {
    wfmTrapDetails,
    wfmTrapType
  }
  DESCRIPTION
  "Legacy PCI Received Target Abort on PCI bus"
  --#TYPE         "Legacy PCI Received Target Abort on PCI bus"
  --#SUMMARY      "%s"
  --#ARGUMENTS    { 1 }
  --#SEVERITY     CRITICAL
  --#TIMEINDEX    1
  --#HELPTAG      0
  --#STATE        OPERATIONAL
  ::=  1274626 

wfmLegacyPCIReceivedMasterAbortOnPCIBus TRAP-TYPE
  ENTERPRISE wfmTrapInfo
  VARIABLES {
    wfmTrapDetails,
    wfmTrapType
  }
  DESCRIPTION
  "Legacy PCI Received Master Abort on PCI bus"
  --#TYPE         "Legacy PCI Received Master Abort on PCI bus"
  --#SUMMARY      "%s"
  --#ARGUMENTS    { 1 }
  --#SEVERITY     CRITICAL
  --#TIMEINDEX    1
  --#HELPTAG      0
  --#STATE        OPERATIONAL
  ::=  1274627 

wfmDriverMonitorError TRAP-TYPE
  ENTERPRISE wfmTrapInfo
  VARIABLES {
    wfmTrapDetails,
    wfmTrapType
  }
  DESCRIPTION
  "Driver Monitor  Error"
  --#TYPE         "Driver Monitor Error"
  --#SUMMARY      "%s"
  --#ARGUMENTS    { 1 }
  --#SEVERITY     MAJOR
  --#TIMEINDEX    1
  --#HELPTAG      0
  --#STATE        OPERATIONAL
  ::=  1274880 

wfmDriverMonitorWarning TRAP-TYPE
  ENTERPRISE wfmTrapInfo
  VARIABLES {
    wfmTrapDetails,
    wfmTrapType
  }
  DESCRIPTION
  "Driver Monitor  Warning"
  --#TYPE         "Driver Monitor Warning"
  --#SUMMARY      "%s"
  --#ARGUMENTS    { 1 }
  --#SEVERITY     MINOR
  --#TIMEINDEX    1
  --#HELPTAG      0
  --#STATE        OPERATIONAL
  ::=  1274881 

wfmDriverMonitorInformation TRAP-TYPE
  ENTERPRISE wfmTrapInfo
  VARIABLES {
    wfmTrapDetails,
    wfmTrapType
  }
  DESCRIPTION
  "Driver Monitor  Information"
  --#TYPE         "Driver Monitor Information"
  --#SUMMARY      "%s"
  --#ARGUMENTS    { 1 }
  --#SEVERITY     INFORMATIONAL
  --#TIMEINDEX    1
  --#HELP         "Note: This is no error condition."
  --#HELPTAG      0
  --#STATE        OPERATIONAL
  ::=  1274882 

wfmContactButtonAsserted TRAP-TYPE
  ENTERPRISE wfmTrapInfo
  VARIABLES {
    wfmTrapDetails,
    wfmTrapType
  }
  DESCRIPTION
  "Contact/Button asserted."
  --#TYPE         "Contact/Button asserted"
  --#SUMMARY      "%s"
  --#ARGUMENTS    { 1 }
  --#SEVERITY     INFORMATIONAL
  --#TIMEINDEX    1
  --#HELP         "Note: This is no error condition."
  --#HELPTAG      0
  --#STATE        OPERATIONAL
  ::=  1311488 

wfmContactButtonDeasserted TRAP-TYPE
  ENTERPRISE wfmTrapInfo
  VARIABLES {
    wfmTrapDetails,
    wfmTrapType
  }
  DESCRIPTION
  "Contact/Button deasserted."
  --#TYPE         "Contact/Button deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  1311489 

wfmPOWERButtonPressed TRAP-TYPE
  ENTERPRISE wfmTrapInfo
  VARIABLES {
    wfmTrapDetails,
    wfmTrapType
  }
  DESCRIPTION
  "POWER Button pressed."
  --#TYPE         "POWER Button pressed"
  --#SUMMARY      "%s"
  --#ARGUMENTS    { 1 }
  --#SEVERITY     INFORMATIONAL
  --#TIMEINDEX    1
  --#HELP         "Note: This is no error condition."
  --#HELPTAG      0
  --#STATE        OPERATIONAL
  ::=  1339136 

wfmSLEEPButtonPressed TRAP-TYPE
  ENTERPRISE wfmTrapInfo
  VARIABLES {
    wfmTrapDetails,
    wfmTrapType
  }
  DESCRIPTION
  "SLEEP Button pressed."
  --#TYPE         "SLEEP Button pressed"
  --#SUMMARY      "%s"
  --#ARGUMENTS    { 1 }
  --#SEVERITY     INFORMATIONAL
  --#TIMEINDEX    1
  --#HELP         "Note: This is no error condition."
  --#HELPTAG      0
  --#STATE        OPERATIONAL
  ::=  1339137 

wfmRESETButtonPressed TRAP-TYPE
  ENTERPRISE wfmTrapInfo
  VARIABLES {
    wfmTrapDetails,
    wfmTrapType
  }
  DESCRIPTION
  "RESET Button pressed."
  --#TYPE         "RESET Button pressed"
  --#SUMMARY      "%s"
  --#ARGUMENTS    { 1 }
  --#SEVERITY     INFORMATIONAL
  --#TIMEINDEX    1
  --#HELP         "Note: This is no error condition."
  --#HELPTAG      0
  --#STATE        OPERATIONAL
  ::=  1339138 

wfmFRULatchOpen TRAP-TYPE
  ENTERPRISE wfmTrapInfo
  VARIABLES {
    wfmTrapDetails,
    wfmTrapType
  }
  DESCRIPTION
  "FRU - latch open."
  --#TYPE         "FRU - latch open"
  --#SUMMARY      "%s"
  --#ARGUMENTS    { 1 }
  --#SEVERITY     INFORMATIONAL
  --#TIMEINDEX    1
  --#HELP         "Note: This is no error condition."
  --#HELPTAG      0
  --#STATE        OPERATIONAL
  ::=  1339139 

wfmFRUServiceRequested TRAP-TYPE
  ENTERPRISE wfmTrapInfo
  VARIABLES {
    wfmTrapDetails,
    wfmTrapType
  }
  DESCRIPTION
  "FRU - service requested."
  --#TYPE         "FRU - service requested"
  --#SUMMARY      "%s"
  --#ARGUMENTS    { 1 }
  --#SEVERITY     INFORMATIONAL
  --#TIMEINDEX    1
  --#HELP         "Note: This is no error condition."
  --#HELPTAG      0
  --#STATE        OPERATIONAL
  ::=  1339140 

wfmModuleOK TRAP-TYPE
  ENTERPRISE wfmTrapInfo
  VARIABLES {
    wfmTrapDetails,
    wfmTrapType
  }
  DESCRIPTION
  "Module OK."
  --#TYPE         "Module OK"
  --#SUMMARY      "%s"
  --#ARGUMENTS    { 1 }
  --#SEVERITY     INFORMATIONAL
  --#TIMEINDEX    1
  --#HELP         "Note: This is no error condition."
  --#HELPTAG      0
  --#STATE        OPERATIONAL
  ::=  1377024 

wfmModuleFailed TRAP-TYPE
  ENTERPRISE wfmTrapInfo
  VARIABLES {
    wfmTrapDetails,
    wfmTrapType
  }
  DESCRIPTION
  "Module failed."
  --#TYPE         "Module failed"
  --#SUMMARY      "%s"
  --#ARGUMENTS    { 1 }
  --#SEVERITY     INFORMATIONAL
  --#TIMEINDEX    1
  --#HELP         "Note: This is no error condition."
  --#HELPTAG      0
  --#STATE        OPERATIONAL
  ::=  1377025 

wfmSCSIDuplexBoardHasBeenRemoved TRAP-TYPE
  ENTERPRISE wfmTrapInfo
  VARIABLES {
    wfmTrapDetails,
    wfmTrapType
  }
  DESCRIPTION
  "SCSI Duplex Board has been removed."
  --#TYPE         "SCSI Duplex Board has been removed"
  --#SUMMARY      "%s"
  --#ARGUMENTS    { 1 }
  --#SEVERITY     INFORMATIONAL
  --#TIMEINDEX    1
  --#HELP         "Note: This is no error condition."
  --#HELPTAG      0
  --#STATE        OPERATIONAL
  ::=  1378304 

wfmSCSIDuplexBoardHasBeenInserted TRAP-TYPE
  ENTERPRISE wfmTrapInfo
  VARIABLES {
    wfmTrapDetails,
    wfmTrapType
  }
  DESCRIPTION
  "SCSI Duplex Board has been inserted."
  --#TYPE         "SCSI Duplex Board has been inserted"
  --#SUMMARY      "%s"
  --#ARGUMENTS    { 1 }
  --#SEVERITY     INFORMATIONAL
  --#TIMEINDEX    1
  --#HELP         "Note: This is no error condition."
  --#HELPTAG      0
  --#STATE        OPERATIONAL
  ::=  1378305 

wfmModuleDisabled TRAP-TYPE
  ENTERPRISE wfmTrapInfo
  VARIABLES {
    wfmTrapDetails,
    wfmTrapType
  }
  DESCRIPTION
  "Module disabled."
  --#TYPE         "Module disabled"
  --#SUMMARY      "%s"
  --#ARGUMENTS    { 1 }
  --#SEVERITY     INFORMATIONAL
  --#TIMEINDEX    1
  --#HELP         "Note: This is no error condition."
  --#HELPTAG      0
  --#STATE        OPERATIONAL
  ::=  1378560 

wfmModuleEnabled TRAP-TYPE
  ENTERPRISE wfmTrapInfo
  VARIABLES {
    wfmTrapDetails,
    wfmTrapType
  }
  DESCRIPTION
  "Module enabled."
  --#TYPE         "Module enabled"
  --#SUMMARY      "%s"
  --#ARGUMENTS    { 1 }
  --#SEVERITY     INFORMATIONAL
  --#TIMEINDEX    1
  --#HELP         "Note: This is no error condition."
  --#HELPTAG      0
  --#STATE        OPERATIONAL
  ::=  1378561 

wfmInstallError TRAP-TYPE
  ENTERPRISE wfmTrapInfo
  VARIABLES {
    wfmTrapDetails,
    wfmTrapType
  }
  DESCRIPTION
  "Install error"
  --#TYPE         "Install error"
  --#SUMMARY      "%s"
  --#ARGUMENTS    { 1 }
  --#SEVERITY     MAJOR
  --#TIMEINDEX    1
  --#HELPTAG      0
  --#STATE        OPERATIONAL
  ::=  1378824 

wfmInstallationOk TRAP-TYPE
  ENTERPRISE wfmTrapInfo
  VARIABLES {
    wfmTrapDetails,
    wfmTrapType
  }
  DESCRIPTION
  "Installation ok"
  --#TYPE         "Installation ok"
  --#SUMMARY      "%s"
  --#ARGUMENTS    { 1 }
  --#SEVERITY     INFORMATIONAL
  --#TIMEINDEX    1
  --#HELP         "Note: This is no error condition."
  --#HELPTAG      0
  --#STATE        OPERATIONAL
  ::=  1378952 

wfmRAIDControllerControllerCachePinnedForMissingOrOfflineLogic TRAP-TYPE
  ENTERPRISE wfmTrapInfo
  VARIABLES {
    wfmTrapDetails,
    wfmTrapType
  }
  DESCRIPTION
  "RAID controller: Controller cache pinned for missing or offline logical drives"
  --#TYPE         "RAID controller: Controller cache pinned for missing or offline logical drives"
  --#SUMMARY      "%s"
  --#ARGUMENTS    { 1 }
  --#SEVERITY     MAJOR
  --#TIMEINDEX    1
  --#HELPTAG      0
  --#STATE        OPERATIONAL
  ::=  1408257 

wfmHDOnControllerOnline TRAP-TYPE
  ENTERPRISE wfmTrapInfo
  VARIABLES {
    wfmTrapDetails,
    wfmTrapType
  }
  DESCRIPTION
  "HD on Controller online."
  --#TYPE         "HD on Controller online"
  --#SUMMARY      "%s"
  --#ARGUMENTS    { 1 }
  --#SEVERITY     INFORMATIONAL
  --#TIMEINDEX    1
  --#HELP         "Note: This is no error condition."
  --#HELPTAG      0
  --#STATE        OPERATIONAL
  ::=  1408768 

wfmHDOnControllerReady TRAP-TYPE
  ENTERPRISE wfmTrapInfo
  VARIABLES {
    wfmTrapDetails,
    wfmTrapType
  }
  DESCRIPTION
  "HD on Controller ready."
  --#TYPE         "HD on Controller ready"
  --#SUMMARY      "%s"
  --#ARGUMENTS    { 1 }
  --#SEVERITY     INFORMATIONAL
  --#TIMEINDEX    1
  --#HELP         "Note: This is no error condition."
  --#HELPTAG      0
  --#STATE        OPERATIONAL
  ::=  1408769 

wfmHDOnControllerHotSpare TRAP-TYPE
  ENTERPRISE wfmTrapInfo
  VARIABLES {
    wfmTrapDetails,
    wfmTrapType
  }
  DESCRIPTION
  "HD on Controller hot spare."
  --#TYPE         "HD on Controller hot spare"
  --#SUMMARY      "%s"
  --#ARGUMENTS    { 1 }
  --#SEVERITY     INFORMATIONAL
  --#TIMEINDEX    1
  --#HELP         "Note: This is no error condition."
  --#HELPTAG      0
  --#STATE        OPERATIONAL
  ::=  1408770 

wfmHDOnControllerRebuilding TRAP-TYPE
  ENTERPRISE wfmTrapInfo
  VARIABLES {
    wfmTrapDetails,
    wfmTrapType
  }
  DESCRIPTION
  "HD on Controller rebuilding."
  --#TYPE         "HD on Controller rebuilding"
  --#SUMMARY      "%s"
  --#ARGUMENTS    { 1 }
  --#SEVERITY     INFORMATIONAL
  --#TIMEINDEX    1
  --#HELP         "Note: This is no error condition."
  --#HELPTAG      0
  --#STATE        OPERATIONAL
  ::=  1408771 

wfmHDOnControllerFormatting TRAP-TYPE
  ENTERPRISE wfmTrapInfo
  VARIABLES {
    wfmTrapDetails,
    wfmTrapType
  }
  DESCRIPTION
  "HD on Controller formatting."
  --#TYPE         "HD on Controller formatting"
  --#SUMMARY      "%s"
  --#ARGUMENTS    { 1 }
  --#SEVERITY     INFORMATIONAL
  --#TIMEINDEX    1
  --#HELP         "Note: This is no error condition."
  --#HELPTAG      0
  --#STATE        OPERATIONAL
  ::=  1408772 

wfmHDOnControllerOffline TRAP-TYPE
  ENTERPRISE wfmTrapInfo
  VARIABLES {
    wfmTrapDetails,
    wfmTrapType
  }
  DESCRIPTION
  "HD on Controller offline."
  --#TYPE         "HD on Controller offline"
  --#SUMMARY      "%s"
  --#ARGUMENTS    { 1 }
  --#SEVERITY     CRITICAL
  --#TIMEINDEX    1
  --#HELPTAG      0
  --#STATE        OPERATIONAL
  ::=  1408773 

wfmHDOnControllerFailed TRAP-TYPE
  ENTERPRISE wfmTrapInfo
  VARIABLES {
    wfmTrapDetails,
    wfmTrapType
  }
  DESCRIPTION
  "HD on Controller failed."
  --#TYPE         "HD on Controller failed"
  --#SUMMARY      "%s"
  --#ARGUMENTS    { 1 }
  --#SEVERITY     CRITICAL
  --#TIMEINDEX    1
  --#HELPTAG      0
  --#STATE        OPERATIONAL
  ::=  1408774 

wfmHDOnControllerDead TRAP-TYPE
  ENTERPRISE wfmTrapInfo
  VARIABLES {
    wfmTrapDetails,
    wfmTrapType
  }
  DESCRIPTION
  "HD on Controller dead."
  --#TYPE         "HD on Controller dead"
  --#SUMMARY      "%s"
  --#ARGUMENTS    { 1 }
  --#SEVERITY     CRITICAL
  --#TIMEINDEX    1
  --#HELPTAG      0
  --#STATE        OPERATIONAL
  ::=  1408775 

wfmHDOnControllerRemoved TRAP-TYPE
  ENTERPRISE wfmTrapInfo
  VARIABLES {
    wfmTrapDetails,
    wfmTrapType
  }
  DESCRIPTION
  "HD on Controller removed."
  --#TYPE         "HD on Controller removed"
  --#SUMMARY      "%s"
  --#ARGUMENTS    { 1 }
  --#SEVERITY     INFORMATIONAL
  --#TIMEINDEX    1
  --#HELP         "Note: This is no error condition."
  --#HELPTAG      0
  --#STATE        OPERATIONAL
  ::=  1408776 

wfmHDOnControllerPrefail TRAP-TYPE
  ENTERPRISE wfmTrapInfo
  VARIABLES {
    wfmTrapDetails,
    wfmTrapType
  }
  DESCRIPTION
  "HD on Controller prefail."
  --#TYPE         "HD on Controller prefail"
  --#SUMMARY      "%s"
  --#ARGUMENTS    { 1 }
  --#SEVERITY     MAJOR
  --#TIMEINDEX    1
  --#HELPTAG      0
  --#STATE        OPERATIONAL
  ::=  1408777 

wfmHDOnControllerAdded TRAP-TYPE
  ENTERPRISE wfmTrapInfo
  VARIABLES {
    wfmTrapDetails,
    wfmTrapType
  }
  DESCRIPTION
  "HD on Controller added."
  --#TYPE         "HD on Controller added"
  --#SUMMARY      "%s"
  --#ARGUMENTS    { 1 }
  --#SEVERITY     INFORMATIONAL
  --#TIMEINDEX    1
  --#HELP         "Note: This is no error condition."
  --#HELPTAG      0
  --#STATE        OPERATIONAL
  ::=  1408778 

wfmMicroControllerRunning TRAP-TYPE
  ENTERPRISE wfmTrapInfo
  VARIABLES {
    wfmTrapDetails,
    wfmTrapType
  }
  DESCRIPTION
  "Micro Controller: Running."
  --#TYPE         "Micro Controller: Running"
  --#SUMMARY      "%s"
  --#ARGUMENTS    { 1 }
  --#SEVERITY     INFORMATIONAL
  --#TIMEINDEX    1
  --#HELP         "Note: This is no error condition."
  --#HELPTAG      0
  --#STATE        OPERATIONAL
  ::=  1444352 

wfmMicroControllerInTest TRAP-TYPE
  ENTERPRISE wfmTrapInfo
  VARIABLES {
    wfmTrapDetails,
    wfmTrapType
  }
  DESCRIPTION
  "Micro Controller: In test."
  --#TYPE         "Micro Controller: In test"
  --#SUMMARY      "%s"
  --#ARGUMENTS    { 1 }
  --#SEVERITY     INFORMATIONAL
  --#TIMEINDEX    1
  --#HELP         "Note: This is no error condition."
  --#HELPTAG      0
  --#STATE        OPERATIONAL
  ::=  1444353 

wfmMicroControllerPowerOFF TRAP-TYPE
  ENTERPRISE wfmTrapInfo
  VARIABLES {
    wfmTrapDetails,
    wfmTrapType
  }
  DESCRIPTION
  "Micro Controller: Power OFF."
  --#TYPE         "Micro Controller: Power OFF"
  --#SUMMARY      "%s"
  --#ARGUMENTS    { 1 }
  --#SEVERITY     INFORMATIONAL
  --#TIMEINDEX    1
  --#HELP         "Note: This is no error condition."
  --#HELPTAG      0
  --#STATE        OPERATIONAL
  ::=  1444354 

wfmMicroControllerOffline TRAP-TYPE
  ENTERPRISE wfmTrapInfo
  VARIABLES {
    wfmTrapDetails,
    wfmTrapType
  }
  DESCRIPTION
  "Micro Controller: Off-line."
  --#TYPE         "Micro Controller: Off-line"
  --#SUMMARY      "%s"
  --#ARGUMENTS    { 1 }
  --#SEVERITY     INFORMATIONAL
  --#TIMEINDEX    1
  --#HELP         "Note: This is no error condition."
  --#HELPTAG      0
  --#STATE        OPERATIONAL
  ::=  1444355 

wfmMicroControllerOnline TRAP-TYPE
  ENTERPRISE wfmTrapInfo
  VARIABLES {
    wfmTrapDetails,
    wfmTrapType
  }
  DESCRIPTION
  "Micro Controller: On-line."
  --#TYPE         "Micro Controller: On-line"
  --#SUMMARY      "%s"
  --#ARGUMENTS    { 1 }
  --#SEVERITY     INFORMATIONAL
  --#TIMEINDEX    1
  --#HELP         "Note: This is no error condition."
  --#HELPTAG      0
  --#STATE        OPERATIONAL
  ::=  1444356 

wfmMicroControllerOffduty TRAP-TYPE
  ENTERPRISE wfmTrapInfo
  VARIABLES {
    wfmTrapDetails,
    wfmTrapType
  }
  DESCRIPTION
  "Micro Controller: Off-duty."
  --#TYPE         "Micro Controller: Off-duty"
  --#SUMMARY      "%s"
  --#ARGUMENTS    { 1 }
  --#SEVERITY     INFORMATIONAL
  --#TIMEINDEX    1
  --#HELP         "Note: This is no error condition."
  --#HELPTAG      0
  --#STATE        OPERATIONAL
  ::=  1444357 

wfmMicroControllerDegraded TRAP-TYPE
  ENTERPRISE wfmTrapInfo
  VARIABLES {
    wfmTrapDetails,
    wfmTrapType
  }
  DESCRIPTION
  "Micro Controller: Degraded."
  --#TYPE         "Micro Controller: Degraded"
  --#SUMMARY      "%s"
  --#ARGUMENTS    { 1 }
  --#SEVERITY     MAJOR
  --#TIMEINDEX    1
  --#HELPTAG      0
  --#STATE        OPERATIONAL
  ::=  1444358 

wfmMicroControllerPowerSave TRAP-TYPE
  ENTERPRISE wfmTrapInfo
  VARIABLES {
    wfmTrapDetails,
    wfmTrapType
  }
  DESCRIPTION
  "Micro Controller: Power Save."
  --#TYPE         "Micro Controller: Power Save"
  --#SUMMARY      "%s"
  --#ARGUMENTS    { 1 }
  --#SEVERITY     INFORMATIONAL
  --#TIMEINDEX    1
  --#HELP         "Note: This is no error condition."
  --#HELPTAG      0
  --#STATE        OPERATIONAL
  ::=  1444359 

wfmMicroControllerInstallError TRAP-TYPE
  ENTERPRISE wfmTrapInfo
  VARIABLES {
    wfmTrapDetails,
    wfmTrapType
  }
  DESCRIPTION
  "Micro Controller: Install. Error."
  --#TYPE         "Micro Controller: Install. Error"
  --#SUMMARY      "%s"
  --#ARGUMENTS    { 1 }
  --#SEVERITY     MAJOR
  --#TIMEINDEX    1
  --#HELPTAG      0
  --#STATE        OPERATIONAL
  ::=  1444360 

wfmSoftPowerControlFailed TRAP-TYPE
  ENTERPRISE wfmTrapInfo
  VARIABLES {
    wfmTrapDetails,
    wfmTrapType
  }
  DESCRIPTION
  "Soft Power Control Failed."
  --#TYPE         "Soft Power Control Failed"
  --#SUMMARY      "%s"
  --#ARGUMENTS    { 1 }
  --#SEVERITY     INFORMATIONAL
  --#TIMEINDEX    1
  --#HELP         "Note: This is no error condition."
  --#HELPTAG      0
  --#STATE        OPERATIONAL
  ::=  1666816 

wfmThermalTripN2 TRAP-TYPE
  ENTERPRISE wfmTrapInfo
  VARIABLES {
    wfmTrapDetails,
    wfmTrapType
  }
  DESCRIPTION
  "Thermal trip"
  --#TYPE         "Thermal trip"
  --#SUMMARY      "%s"
  --#ARGUMENTS    { 1 }
  --#SEVERITY     CRITICAL
  --#TIMEINDEX    1
  --#HELPTAG      0
  --#STATE        OPERATIONAL
  ::=  1666817 

wfmlocalMonDeviceDisabled TRAP-TYPE
  ENTERPRISE wfmTrapInfo
  VARIABLES {
    wfmTrapDetails,
    wfmTrapType
  }
  DESCRIPTION
  "'local Mon.': Device Disabled."
  --#TYPE         "'local Mon.': Device Disabled"
  --#SUMMARY      "%s"
  --#ARGUMENTS    { 1 }
  --#SEVERITY     INFORMATIONAL
  --#TIMEINDEX    1
  --#HELP         "Note: This is no error condition."
  --#HELPTAG      0
  --#STATE        OPERATIONAL
  ::=  1706240 

wfmlocalMonDeviceEnabled TRAP-TYPE
  ENTERPRISE wfmTrapInfo
  VARIABLES {
    wfmTrapDetails,
    wfmTrapType
  }
  DESCRIPTION
  "'local Mon.': Device Enabled."
  --#TYPE         "'local Mon.': Device Enabled"
  --#SUMMARY      "%s"
  --#ARGUMENTS    { 1 }
  --#SEVERITY     INFORMATIONAL
  --#TIMEINDEX    1
  --#HELP         "Note: This is no error condition."
  --#HELPTAG      0
  --#STATE        OPERATIONAL
  ::=  1706241 

wfmCageSCSIBusType TRAP-TYPE
  ENTERPRISE wfmTrapInfo
  VARIABLES {
    wfmTrapDetails,
    wfmTrapType
  }
  DESCRIPTION
  "Cage SCSI bus type."
  --#TYPE         "Cage SCSI bus type"
  --#SUMMARY      "%s"
  --#ARGUMENTS    { 1 }
  --#SEVERITY     INFORMATIONAL
  --#TIMEINDEX    1
  --#HELP         "Note: This is no error condition."
  --#HELPTAG      0
  --#STATE        OPERATIONAL
  ::=  1770241 

wfmCableDisconnected TRAP-TYPE
  ENTERPRISE wfmTrapInfo
  VARIABLES {
    wfmTrapDetails,
    wfmTrapType
  }
  DESCRIPTION
  "Cable disconnected."
  --#TYPE         "Cable disconnected"
  --#SUMMARY      "%s"
  --#ARGUMENTS    { 1 }
  --#SEVERITY     INFORMATIONAL
  --#TIMEINDEX    1
  --#HELP         "Note: This is no error condition."
  --#HELPTAG      0
  --#STATE        OPERATIONAL
  ::=  1771520 

wfmCableConnected TRAP-TYPE
  ENTERPRISE wfmTrapInfo
  VARIABLES {
    wfmTrapDetails,
    wfmTrapType
  }
  DESCRIPTION
  "Cable connected."
  --#TYPE         "Cable connected"
  --#SUMMARY      "%s"
  --#ARGUMENTS    { 1 }
  --#SEVERITY     INFORMATIONAL
  --#TIMEINDEX    1
  --#HELP         "Note: This is no error condition."
  --#HELPTAG      0
  --#STATE        OPERATIONAL
  ::=  1771521 

wfmPCIInterconnectSlotRunning TRAP-TYPE
  ENTERPRISE wfmTrapInfo
  VARIABLES {
    wfmTrapDetails,
    wfmTrapType
  }
  DESCRIPTION
  "PCI Interconnect: Slot Running ."
  --#TYPE         "PCI Interconnect: Slot Running"
  --#SUMMARY      "%s"
  --#ARGUMENTS    { 1 }
  --#SEVERITY     INFORMATIONAL
  --#TIMEINDEX    1
  --#HELP         "Note: This is no error condition."
  --#HELPTAG      0
  --#STATE        OPERATIONAL
  ::=  1772032 

wfmPCIInterconnectSlotInTest TRAP-TYPE
  ENTERPRISE wfmTrapInfo
  VARIABLES {
    wfmTrapDetails,
    wfmTrapType
  }
  DESCRIPTION
  "PCI Interconnect: Slot In Test."
  --#TYPE         "PCI Interconnect: Slot In Test"
  --#SUMMARY      "%s"
  --#ARGUMENTS    { 1 }
  --#SEVERITY     INFORMATIONAL
  --#TIMEINDEX    1
  --#HELP         "Note: This is no error condition."
  --#HELPTAG      0
  --#STATE        OPERATIONAL
  ::=  1772033 

wfmPCIInterconnectSlotPowerOff TRAP-TYPE
  ENTERPRISE wfmTrapInfo
  VARIABLES {
    wfmTrapDetails,
    wfmTrapType
  }
  DESCRIPTION
  "PCI Interconnect: Slot Power Off."
  --#TYPE         "PCI Interconnect: Slot Power Off"
  --#SUMMARY      "%s"
  --#ARGUMENTS    { 1 }
  --#SEVERITY     INFORMATIONAL
  --#TIMEINDEX    1
  --#HELP         "Note: This is no error condition."
  --#HELPTAG      0
  --#STATE        OPERATIONAL
  ::=  1772034 

wfmPCIInterconnectSlotOnLine TRAP-TYPE
  ENTERPRISE wfmTrapInfo
  VARIABLES {
    wfmTrapDetails,
    wfmTrapType
  }
  DESCRIPTION
  "PCI Interconnect: Slot On Line."
  --#TYPE         "PCI Interconnect: Slot On Line"
  --#SUMMARY      "%s"
  --#ARGUMENTS    { 1 }
  --#SEVERITY     INFORMATIONAL
  --#TIMEINDEX    1
  --#HELP         "Note: This is no error condition."
  --#HELPTAG      0
  --#STATE        OPERATIONAL
  ::=  1772035 

wfmPCIInterconnectSlotOffLine TRAP-TYPE
  ENTERPRISE wfmTrapInfo
  VARIABLES {
    wfmTrapDetails,
    wfmTrapType
  }
  DESCRIPTION
  "PCI Interconnect: Slot Off Line."
  --#TYPE         "PCI Interconnect: Slot Off Line"
  --#SUMMARY      "%s"
  --#ARGUMENTS    { 1 }
  --#SEVERITY     INFORMATIONAL
  --#TIMEINDEX    1
  --#HELP         "Note: This is no error condition."
  --#HELPTAG      0
  --#STATE        OPERATIONAL
  ::=  1772036 

wfmPCIInterconnectSlotOffDuty TRAP-TYPE
  ENTERPRISE wfmTrapInfo
  VARIABLES {
    wfmTrapDetails,
    wfmTrapType
  }
  DESCRIPTION
  "PCI Interconnect: Slot Off Duty."
  --#TYPE         "PCI Interconnect: Slot Off Duty"
  --#SUMMARY      "%s"
  --#ARGUMENTS    { 1 }
  --#SEVERITY     INFORMATIONAL
  --#TIMEINDEX    1
  --#HELP         "Note: This is no error condition."
  --#HELPTAG      0
  --#STATE        OPERATIONAL
  ::=  1772037 

wfmPCIInterconnectSlotDegraded TRAP-TYPE
  ENTERPRISE wfmTrapInfo
  VARIABLES {
    wfmTrapDetails,
    wfmTrapType
  }
  DESCRIPTION
  "PCI Interconnect: Slot Degraded."
  --#TYPE         "PCI Interconnect: Slot Degraded"
  --#SUMMARY      "%s"
  --#ARGUMENTS    { 1 }
  --#SEVERITY     MAJOR
  --#TIMEINDEX    1
  --#HELPTAG      0
  --#STATE        OPERATIONAL
  ::=  1772038 

wfmPCIInterconnectSlotPowerSave TRAP-TYPE
  ENTERPRISE wfmTrapInfo
  VARIABLES {
    wfmTrapDetails,
    wfmTrapType
  }
  DESCRIPTION
  "PCI Interconnect: Slot Power Save."
  --#TYPE         "PCI Interconnect: Slot Power Save"
  --#SUMMARY      "%s"
  --#ARGUMENTS    { 1 }
  --#SEVERITY     INFORMATIONAL
  --#TIMEINDEX    1
  --#HELP         "Note: This is no error condition."
  --#HELPTAG      0
  --#STATE        OPERATIONAL
  ::=  1772039 

wfmPCIInterconnectSlotInstallError TRAP-TYPE
  ENTERPRISE wfmTrapInfo
  VARIABLES {
    wfmTrapDetails,
    wfmTrapType
  }
  DESCRIPTION
  "PCI Interconnect: Slot Install Error."
  --#TYPE         "PCI Interconnect: Slot Install Error"
  --#SUMMARY      "%s"
  --#ARGUMENTS    { 1 }
  --#SEVERITY     MAJOR
  --#TIMEINDEX    1
  --#HELPTAG      0
  --#STATE        OPERATIONAL
  ::=  1772040 

wfmTerminatorRemovedFromCage TRAP-TYPE
  ENTERPRISE wfmTrapInfo
  VARIABLES {
    wfmTrapDetails,
    wfmTrapType
  }
  DESCRIPTION
  "Terminator removed from cage."
  --#TYPE         "Terminator removed from cage"
  --#SUMMARY      "%s"
  --#ARGUMENTS    { 1 }
  --#SEVERITY     INFORMATIONAL
  --#TIMEINDEX    1
  --#HELP         "Note: This is no error condition."
  --#HELPTAG      0
  --#STATE        OPERATIONAL
  ::=  1837056 

wfmTerminatorAttachedToCage TRAP-TYPE
  ENTERPRISE wfmTrapInfo
  VARIABLES {
    wfmTrapDetails,
    wfmTrapType
  }
  DESCRIPTION
  "Terminator attached to cage."
  --#TYPE         "Terminator attached to cage"
  --#SUMMARY      "%s"
  --#ARGUMENTS    { 1 }
  --#SEVERITY     INFORMATIONAL
  --#TIMEINDEX    1
  --#HELP         "Note: This is no error condition."
  --#HELPTAG      0
  --#STATE        OPERATIONAL
  ::=  1837057 

wfmSystemRebootedByPowerUp TRAP-TYPE
  ENTERPRISE wfmTrapInfo
  VARIABLES {
    wfmTrapDetails,
    wfmTrapType
  }
  DESCRIPTION
  "System rebooted by PowerUp."
  --#TYPE         "System rebooted by PowerUp"
  --#SUMMARY      "%s"
  --#ARGUMENTS    { 1 }
  --#SEVERITY     INFORMATIONAL
  --#TIMEINDEX    1
  --#HELP         "Note: This is no error condition."
  --#HELPTAG      0
  --#STATE        OPERATIONAL
  ::=  1928960 

wfmSystemRebootedByHardReset TRAP-TYPE
  ENTERPRISE wfmTrapInfo
  VARIABLES {
    wfmTrapDetails,
    wfmTrapType
  }
  DESCRIPTION
  "System rebooted by Hard Reset."
  --#TYPE         "System rebooted by Hard Reset"
  --#SUMMARY      "%s"
  --#ARGUMENTS    { 1 }
  --#SEVERITY     INFORMATIONAL
  --#TIMEINDEX    1
  --#HELP         "Note: This is no error condition."
  --#HELPTAG      0
  --#STATE        OPERATIONAL
  ::=  1928961 

wfmSystemRebootedByWarmReset TRAP-TYPE
  ENTERPRISE wfmTrapInfo
  VARIABLES {
    wfmTrapDetails,
    wfmTrapType
  }
  DESCRIPTION
  "System rebooted by Warm Reset."
  --#TYPE         "System rebooted by Warm Reset"
  --#SUMMARY      "%s"
  --#ARGUMENTS    { 1 }
  --#SEVERITY     INFORMATIONAL
  --#TIMEINDEX    1
  --#HELP         "Note: This is no error condition."
  --#HELPTAG      0
  --#STATE        OPERATIONAL
  ::=  1928962 

wfmSystemRebootedToPXEBoot TRAP-TYPE
  ENTERPRISE wfmTrapInfo
  VARIABLES {
    wfmTrapDetails,
    wfmTrapType
  }
  DESCRIPTION
  "System rebooted to PXE Boot."
  --#TYPE         "System rebooted to PXE Boot"
  --#SUMMARY      "%s"
  --#ARGUMENTS    { 1 }
  --#SEVERITY     INFORMATIONAL
  --#TIMEINDEX    1
  --#HELP         "Note: This is no error condition."
  --#HELPTAG      0
  --#STATE        OPERATIONAL
  ::=  1928963 

wfmSystemRebootedToDiagnosticBoot TRAP-TYPE
  ENTERPRISE wfmTrapInfo
  VARIABLES {
    wfmTrapDetails,
    wfmTrapType
  }
  DESCRIPTION
  "System rebooted to Diagnostic Boot."
  --#TYPE         "System rebooted to Diagnostic Boot"
  --#SUMMARY      "%s"
  --#ARGUMENTS    { 1 }
  --#SEVERITY     INFORMATIONAL
  --#TIMEINDEX    1
  --#HELP         "Note: This is no error condition."
  --#HELPTAG      0
  --#STATE        OPERATIONAL
  ::=  1928964 

wfmOSRuntimeSoftwareInitiatedHardReset TRAP-TYPE
  ENTERPRISE wfmTrapInfo
  VARIABLES {
    wfmTrapDetails,
    wfmTrapType
  }
  DESCRIPTION
  "OS / runtime software initiated Hard Reset."
  --#TYPE         "OS / runtime software initiated Hard Reset"
  --#SUMMARY      "%s"
  --#ARGUMENTS    { 1 }
  --#SEVERITY     INFORMATIONAL
  --#TIMEINDEX    1
  --#HELP         "Note: This is no error condition."
  --#HELPTAG      0
  --#STATE        OPERATIONAL
  ::=  1928965 

wfmOSRuntimeSoftwareInitiatedSoftReset TRAP-TYPE
  ENTERPRISE wfmTrapInfo
  VARIABLES {
    wfmTrapDetails,
    wfmTrapType
  }
  DESCRIPTION
  "OS / runtime software initiated Soft Reset."
  --#TYPE         "OS / runtime software initiated Soft Reset"
  --#SUMMARY      "%s"
  --#ARGUMENTS    { 1 }
  --#SEVERITY     INFORMATIONAL
  --#TIMEINDEX    1
  --#HELP         "Note: This is no error condition."
  --#HELPTAG      0
  --#STATE        OPERATIONAL
  ::=  1928966 

wfmSystemRestart TRAP-TYPE
  ENTERPRISE wfmTrapInfo
  VARIABLES {
    wfmTrapDetails,
    wfmTrapType
  }
  DESCRIPTION
  "System Restart."
  --#TYPE         "System Restart"
  --#SUMMARY      "%s"
  --#ARGUMENTS    { 1 }
  --#SEVERITY     INFORMATIONAL
  --#TIMEINDEX    1
  --#HELP         "Note: This is no error condition."
  --#HELPTAG      0
  --#STATE        OPERATIONAL
  ::=  1928967 

wfmNoBootableMedia TRAP-TYPE
  ENTERPRISE wfmTrapInfo
  VARIABLES {
    wfmTrapDetails,
    wfmTrapType
  }
  DESCRIPTION
  "No bootable media."
  --#TYPE         "No bootable media"
  --#SUMMARY      "%s"
  --#ARGUMENTS    { 1 }
  --#SEVERITY     INFORMATIONAL
  --#TIMEINDEX    1
  --#HELP         "Note: This is no error condition."
  --#HELPTAG      0
  --#STATE        OPERATIONAL
  ::=  1994496 

wfmNonBootableDisketteLeftInDrive TRAP-TYPE
  ENTERPRISE wfmTrapInfo
  VARIABLES {
    wfmTrapDetails,
    wfmTrapType
  }
  DESCRIPTION
  "Non bootable diskette left in drive."
  --#TYPE         "Non bootable diskette left in drive"
  --#SUMMARY      "%s"
  --#ARGUMENTS    { 1 }
  --#SEVERITY     INFORMATIONAL
  --#TIMEINDEX    1
  --#HELP         "Note: This is no error condition."
  --#HELPTAG      0
  --#STATE        OPERATIONAL
  ::=  1994497 

wfmPXEServerNotFound TRAP-TYPE
  ENTERPRISE wfmTrapInfo
  VARIABLES {
    wfmTrapDetails,
    wfmTrapType
  }
  DESCRIPTION
  "PXE Server not found."
  --#TYPE         "PXE Server not found"
  --#SUMMARY      "%s"
  --#ARGUMENTS    { 1 }
  --#SEVERITY     INFORMATIONAL
  --#TIMEINDEX    1
  --#HELP         "Note: This is no error condition."
  --#HELPTAG      0
  --#STATE        OPERATIONAL
  ::=  1994498 

wfmInvalidBootSector TRAP-TYPE
  ENTERPRISE wfmTrapInfo
  VARIABLES {
    wfmTrapDetails,
    wfmTrapType
  }
  DESCRIPTION
  "Invalid boot sector."
  --#TYPE         "Invalid boot sector"
  --#SUMMARY      "%s"
  --#ARGUMENTS    { 1 }
  --#SEVERITY     INFORMATIONAL
  --#TIMEINDEX    1
  --#HELP         "Note: This is no error condition."
  --#HELPTAG      0
  --#STATE        OPERATIONAL
  ::=  1994499 

wfmTimeoutWaitingForUserSelectionOfBootSource TRAP-TYPE
  ENTERPRISE wfmTrapInfo
  VARIABLES {
    wfmTrapDetails,
    wfmTrapType
  }
  DESCRIPTION
  "Timeout waiting for user selection of boot source."
  --#TYPE         "Timeout waiting for user selection of boot source"
  --#SUMMARY      "%s"
  --#ARGUMENTS    { 1 }
  --#SEVERITY     INFORMATIONAL
  --#TIMEINDEX    1
  --#HELP         "Note: This is no error condition."
  --#HELPTAG      0
  --#STATE        OPERATIONAL
  ::=  1994500 

wfmABootCompleted TRAP-TYPE
  ENTERPRISE wfmTrapInfo
  VARIABLES {
    wfmTrapDetails,
    wfmTrapType
  }
  DESCRIPTION
  "A: Boot completed."
  --#TYPE         "A: Boot completed"
  --#SUMMARY      "%s"
  --#ARGUMENTS    { 1 }
  --#SEVERITY     INFORMATIONAL
  --#TIMEINDEX    1
  --#HELP         "Note: This is no error condition."
  --#HELPTAG      0
  --#STATE        OPERATIONAL
  ::=  2060032 

wfmCBootCompleted TRAP-TYPE
  ENTERPRISE wfmTrapInfo
  VARIABLES {
    wfmTrapDetails,
    wfmTrapType
  }
  DESCRIPTION
  "C: Boot completed."
  --#TYPE         "C: Boot completed"
  --#SUMMARY      "%s"
  --#ARGUMENTS    { 1 }
  --#SEVERITY     INFORMATIONAL
  --#TIMEINDEX    1
  --#HELP         "Note: This is no error condition."
  --#HELPTAG      0
  --#STATE        OPERATIONAL
  ::=  2060033 

wfmPXEBootCompleted TRAP-TYPE
  ENTERPRISE wfmTrapInfo
  VARIABLES {
    wfmTrapDetails,
    wfmTrapType
  }
  DESCRIPTION
  "PXE Boot completed."
  --#TYPE         "PXE Boot completed"
  --#SUMMARY      "%s"
  --#ARGUMENTS    { 1 }
  --#SEVERITY     INFORMATIONAL
  --#TIMEINDEX    1
  --#HELP         "Note: This is no error condition."
  --#HELPTAG      0
  --#STATE        OPERATIONAL
  ::=  2060034 

wfmDiagnosticBootCompleted TRAP-TYPE
  ENTERPRISE wfmTrapInfo
  VARIABLES {
    wfmTrapDetails,
    wfmTrapType
  }
  DESCRIPTION
  "Diagnostic Boot completed."
  --#TYPE         "Diagnostic Boot completed"
  --#SUMMARY      "%s"
  --#ARGUMENTS    { 1 }
  --#SEVERITY     INFORMATIONAL
  --#TIMEINDEX    1
  --#HELP         "Note: This is no error condition."
  --#HELPTAG      0
  --#STATE        OPERATIONAL
  ::=  2060035 

wfmCDROMBootCompleted TRAP-TYPE
  ENTERPRISE wfmTrapInfo
  VARIABLES {
    wfmTrapDetails,
    wfmTrapType
  }
  DESCRIPTION
  "CD-ROM Boot completed."
  --#TYPE         "CD-ROM Boot completed"
  --#SUMMARY      "%s"
  --#ARGUMENTS    { 1 }
  --#SEVERITY     INFORMATIONAL
  --#TIMEINDEX    1
  --#HELP         "Note: This is no error condition."
  --#HELPTAG      0
  --#STATE        OPERATIONAL
  ::=  2060036 

wfmROMBootCompleted TRAP-TYPE
  ENTERPRISE wfmTrapInfo
  VARIABLES {
    wfmTrapDetails,
    wfmTrapType
  }
  DESCRIPTION
  "ROM Boot completed."
  --#TYPE         "ROM Boot completed"
  --#SUMMARY      "%s"
  --#ARGUMENTS    { 1 }
  --#SEVERITY     INFORMATIONAL
  --#TIMEINDEX    1
  --#HELP         "Note: This is no error condition."
  --#HELPTAG      0
  --#STATE        OPERATIONAL
  ::=  2060037 

wfmBootCompletedBootDeviceNotSpecified TRAP-TYPE
  ENTERPRISE wfmTrapInfo
  VARIABLES {
    wfmTrapDetails,
    wfmTrapType
  }
  DESCRIPTION
  "Boot completed - boot device not specified."
  --#TYPE         "Boot completed - boot device not specified"
  --#SUMMARY      "%s"
  --#ARGUMENTS    { 1 }
  --#SEVERITY     INFORMATIONAL
  --#TIMEINDEX    1
  --#HELP         "Note: This is no error condition."
  --#HELPTAG      0
  --#STATE        OPERATIONAL
  ::=  2060038 

wfmStopDuringOSLoadInitialization TRAP-TYPE
  ENTERPRISE wfmTrapInfo
  VARIABLES {
    wfmTrapDetails,
    wfmTrapType
  }
  DESCRIPTION
  "Stop during OS load / initialization."
  --#TYPE         "Stop during OS load / initialization"
  --#SUMMARY      "%s"
  --#ARGUMENTS    { 1 }
  --#SEVERITY     MAJOR
  --#TIMEINDEX    1
  --#HELPTAG      0
  --#STATE        OPERATIONAL
  ::=  2125568 

wfmRuntimeStop TRAP-TYPE
  ENTERPRISE wfmTrapInfo
  VARIABLES {
    wfmTrapDetails,
    wfmTrapType
  }
  DESCRIPTION
  "Run-time Stop."
  --#TYPE         "Run-time Stop"
  --#SUMMARY      "%s"
  --#ARGUMENTS    { 1 }
  --#SEVERITY     MAJOR
  --#TIMEINDEX    1
  --#HELPTAG      0
  --#STATE        OPERATIONAL
  ::=  2125569 

wfmOSGracefulCriticalStop TRAP-TYPE
  ENTERPRISE wfmTrapInfo
  VARIABLES {
    wfmTrapDetails,
    wfmTrapType
  }
  DESCRIPTION
  "OS Graceful Critical Stop."
  --#TYPE         "OS Graceful Critical Stop"
  --#SUMMARY      "%s"
  --#ARGUMENTS    { 1 }
  --#SEVERITY     MAJOR
  --#TIMEINDEX    1
  --#HELPTAG      0
  --#STATE        OPERATIONAL
  ::=  2125570 

wfmOSGracefulShutdown TRAP-TYPE
  ENTERPRISE wfmTrapInfo
  VARIABLES {
    wfmTrapDetails,
    wfmTrapType
  }
  DESCRIPTION
  "OS Graceful Shutdown."
  --#TYPE         "OS Graceful Shutdown"
  --#SUMMARY      "%s"
  --#ARGUMENTS    { 1 }
  --#SEVERITY     INFORMATIONAL
  --#TIMEINDEX    1
  --#HELP         "Note: This is no error condition."
  --#HELPTAG      0
  --#STATE        OPERATIONAL
  ::=  2125571 

wfmSoftShutdownInitiatedByPEF TRAP-TYPE
  ENTERPRISE wfmTrapInfo
  VARIABLES {
    wfmTrapDetails,
    wfmTrapType
  }
  DESCRIPTION
  "Soft Shutdown initiated by PEF."
  --#TYPE         "Soft Shutdown initiated by PEF"
  --#SUMMARY      "%s"
  --#ARGUMENTS    { 1 }
  --#SEVERITY     INFORMATIONAL
  --#TIMEINDEX    1
  --#HELP         "Note: This is no error condition."
  --#HELPTAG      0
  --#STATE        OPERATIONAL
  ::=  2125572 

wfmAgentNotResponding TRAP-TYPE
  ENTERPRISE wfmTrapInfo
  VARIABLES {
    wfmTrapDetails,
    wfmTrapType
  }
  DESCRIPTION
  "Agent Not Responding."
  --#TYPE         "Agent Not Responding"
  --#SUMMARY      "%s"
  --#ARGUMENTS    { 1 }
  --#SEVERITY     INFORMATIONAL
  --#TIMEINDEX    1
  --#HELP         "Note: This is no error condition."
  --#HELPTAG      0
  --#STATE        OPERATIONAL
  ::=  2125573 

wfmPredictiveFailureAssertedOnSlotConnector TRAP-TYPE
  ENTERPRISE wfmTrapInfo
  VARIABLES {
    wfmTrapDetails,
    wfmTrapType
  }
  DESCRIPTION
  "Predictive failure asserted on slot / connector"
  --#TYPE         "Predictive failure asserted on slot / connector"
  --#SUMMARY      "%s"
  --#ARGUMENTS    { 1 }
  --#SEVERITY     MAJOR
  --#TIMEINDEX    1
  --#HELPTAG      0
  --#STATE        OPERATIONAL
  ::=  2163713 

wfmPCIHotPlugSlotFaultAsserted TRAP-TYPE
  ENTERPRISE wfmTrapInfo
  VARIABLES {
    wfmTrapDetails,
    wfmTrapType
  }
  DESCRIPTION
  "PCI Hot Plug Slot fault asserted."
  --#TYPE         "PCI Hot Plug Slot fault asserted"
  --#SUMMARY      "%s"
  --#ARGUMENTS    { 1 }
  --#SEVERITY     MAJOR
  --#TIMEINDEX    1
  --#HELPTAG      0
  --#STATE        OPERATIONAL
  ::=  2191104 

wfmPCIHotPlugSlotIdentifyAsserted TRAP-TYPE
  ENTERPRISE wfmTrapInfo
  VARIABLES {
    wfmTrapDetails,
    wfmTrapType
  }
  DESCRIPTION
  "PCI Hot Plug Slot identify asserted."
  --#TYPE         "PCI Hot Plug Slot identify asserted"
  --#SUMMARY      "%s"
  --#ARGUMENTS    { 1 }
  --#SEVERITY     INFORMATIONAL
  --#TIMEINDEX    1
  --#HELP         "Note: This is no error condition."
  --#HELPTAG      0
  --#STATE        OPERATIONAL
  ::=  2191105 

wfmPCIHotPlugSlotDeviceInstalled TRAP-TYPE
  ENTERPRISE wfmTrapInfo
  VARIABLES {
    wfmTrapDetails,
    wfmTrapType
  }
  DESCRIPTION
  "PCI Hot Plug Slot Device installed."
  --#TYPE         "PCI Hot Plug Slot Device installed"
  --#SUMMARY      "%s"
  --#ARGUMENTS    { 1 }
  --#SEVERITY     INFORMATIONAL
  --#TIMEINDEX    1
  --#HELP         "Note: This is no error condition."
  --#HELPTAG      0
  --#STATE        OPERATIONAL
  ::=  2191106 

wfmPCIHotPlugSlotReadyForDeviceInstallation TRAP-TYPE
  ENTERPRISE wfmTrapInfo
  VARIABLES {
    wfmTrapDetails,
    wfmTrapType
  }
  DESCRIPTION
  "PCI Hot Plug Slot ready for device installation."
  --#TYPE         "PCI Hot Plug Slot ready for device installation"
  --#SUMMARY      "%s"
  --#ARGUMENTS    { 1 }
  --#SEVERITY     INFORMATIONAL
  --#TIMEINDEX    1
  --#HELP         "Note: This is no error condition."
  --#HELPTAG      0
  --#STATE        OPERATIONAL
  ::=  2191107 

wfmPCIHotPlugSlotReadyForDeviceRemoval TRAP-TYPE
  ENTERPRISE wfmTrapInfo
  VARIABLES {
    wfmTrapDetails,
    wfmTrapType
  }
  DESCRIPTION
  "PCI Hot Plug Slot ready for device removal."
  --#TYPE         "PCI Hot Plug Slot ready for device removal"
  --#SUMMARY      "%s"
  --#ARGUMENTS    { 1 }
  --#SEVERITY     INFORMATIONAL
  --#TIMEINDEX    1
  --#HELP         "Note: This is no error condition."
  --#HELPTAG      0
  --#STATE        OPERATIONAL
  ::=  2191108 

wfmPCIHotPlugSlotPoweredOff TRAP-TYPE
  ENTERPRISE wfmTrapInfo
  VARIABLES {
    wfmTrapDetails,
    wfmTrapType
  }
  DESCRIPTION
  "PCI Hot Plug Slot powered off."
  --#TYPE         "PCI Hot Plug Slot powered off"
  --#SUMMARY      "%s"
  --#ARGUMENTS    { 1 }
  --#SEVERITY     INFORMATIONAL
  --#TIMEINDEX    1
  --#HELP         "Note: This is no error condition."
  --#HELPTAG      0
  --#STATE        OPERATIONAL
  ::=  2191109 

wfmPCIHotPlugSlotRemovalRequest TRAP-TYPE
  ENTERPRISE wfmTrapInfo
  VARIABLES {
    wfmTrapDetails,
    wfmTrapType
  }
  DESCRIPTION
  "PCI Hot Plug Slot removal request."
  --#TYPE         "PCI Hot Plug Slot removal request"
  --#SUMMARY      "%s"
  --#ARGUMENTS    { 1 }
  --#SEVERITY     INFORMATIONAL
  --#TIMEINDEX    1
  --#HELP         "Note: This is no error condition."
  --#HELPTAG      0
  --#STATE        OPERATIONAL
  ::=  2191110 

wfmPCIHotPlugSlotInterlockAssertedlatchNotClosed TRAP-TYPE
  ENTERPRISE wfmTrapInfo
  VARIABLES {
    wfmTrapDetails,
    wfmTrapType
  }
  DESCRIPTION
  "PCI Hot Plug Slot Interlock asserted (latch not closed)."
  --#TYPE         "PCI Hot Plug Slot Interlock asserted (latch not closed)"
  --#SUMMARY      "%s"
  --#ARGUMENTS    { 1 }
  --#SEVERITY     MAJOR
  --#TIMEINDEX    1
  --#HELPTAG      0
  --#STATE        OPERATIONAL
  ::=  2191111 

wfmPCIHotPlugSlotDisabled TRAP-TYPE
  ENTERPRISE wfmTrapInfo
  VARIABLES {
    wfmTrapDetails,
    wfmTrapType
  }
  DESCRIPTION
  "PCI Hot Plug Slot disabled."
  --#TYPE         "PCI Hot Plug Slot disabled"
  --#SUMMARY      "%s"
  --#ARGUMENTS    { 1 }
  --#SEVERITY     INFORMATIONAL
  --#TIMEINDEX    1
  --#HELP         "Note: This is no error condition."
  --#HELPTAG      0
  --#STATE        OPERATIONAL
  ::=  2191112 

wfmPCIHotPlugSlotHoldsSpareDevice TRAP-TYPE
  ENTERPRISE wfmTrapInfo
  VARIABLES {
    wfmTrapDetails,
    wfmTrapType
  }
  DESCRIPTION
  "PCI Hot Plug Slot holds spare device."
  --#TYPE         "PCI Hot Plug Slot holds spare device"
  --#SUMMARY      "%s"
  --#ARGUMENTS    { 1 }
  --#SEVERITY     INFORMATIONAL
  --#TIMEINDEX    1
  --#HELP         "Note: This is no error condition."
  --#HELPTAG      0
  --#STATE        OPERATIONAL
  ::=  2191113 

wfmPCIHotPlugSlotFaultDeasserted TRAP-TYPE
  ENTERPRISE wfmTrapInfo
  VARIABLES {
    wfmTrapDetails,
    wfmTrapType
  }
  DESCRIPTION
  "PCI Hot Plug Slot fault deasserted."
  --#TYPE         "PCI Hot Plug Slot fault deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2191232 

wfmPCIHotPlugSlotIdentifyDeasserted TRAP-TYPE
  ENTERPRISE wfmTrapInfo
  VARIABLES {
    wfmTrapDetails,
    wfmTrapType
  }
  DESCRIPTION
  "PCI Hot Plug Slot identify deasserted."
  --#TYPE         "PCI Hot Plug Slot identify deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2191233 

wfmPCIHotPlugSlotDeviceRemoved TRAP-TYPE
  ENTERPRISE wfmTrapInfo
  VARIABLES {
    wfmTrapDetails,
    wfmTrapType
  }
  DESCRIPTION
  "PCI Hot Plug Slot Device removed."
  --#TYPE         "PCI Hot Plug Slot Device removed"
  --#SUMMARY      "%s"
  --#ARGUMENTS    { 1 }
  --#SEVERITY     INFORMATIONAL
  --#TIMEINDEX    1
  --#HELP         "Note: This is no error condition."
  --#HELPTAG      0
  --#STATE        OPERATIONAL
  ::=  2191234 

wfmPCIHotPlugSlotPoweredOn TRAP-TYPE
  ENTERPRISE wfmTrapInfo
  VARIABLES {
    wfmTrapDetails,
    wfmTrapType
  }
  DESCRIPTION
  "PCI Hot Plug Slot powered on."
  --#TYPE         "PCI Hot Plug Slot powered on"
  --#SUMMARY      "%s"
  --#ARGUMENTS    { 1 }
  --#SEVERITY     INFORMATIONAL
  --#TIMEINDEX    1
  --#HELP         "Note: This is no error condition."
  --#HELPTAG      0
  --#STATE        OPERATIONAL
  ::=  2191237 

wfminterlockDeassertedlatchClosed TRAP-TYPE
  ENTERPRISE wfmTrapInfo
  VARIABLES {
    wfmTrapDetails,
    wfmTrapType
  }
  DESCRIPTION
  "interlock deasserted (latch closed)."
  --#TYPE         "interlock deasserted (latch closed)"
  --#SUMMARY      "%s"
  --#ARGUMENTS    { 1 }
  --#SEVERITY     INFORMATIONAL
  --#TIMEINDEX    1
  --#HELP         "Note: This is no error condition."
  --#HELPTAG      0
  --#STATE        OPERATIONAL
  ::=  2191239 

wfmPCIHotPlugSlotEnabled TRAP-TYPE
  ENTERPRISE wfmTrapInfo
  VARIABLES {
    wfmTrapDetails,
    wfmTrapType
  }
  DESCRIPTION
  "PCI Hot Plug Slot enabled."
  --#TYPE         "PCI Hot Plug Slot enabled"
  --#SUMMARY      "%s"
  --#ARGUMENTS    { 1 }
  --#SEVERITY     INFORMATIONAL
  --#TIMEINDEX    1
  --#HELP         "Note: This is no error condition."
  --#HELPTAG      0
  --#STATE        OPERATIONAL
  ::=  2191240 

wfmACPIPowerStateWorkingS0G0 TRAP-TYPE
  ENTERPRISE wfmTrapInfo
  VARIABLES {
    wfmTrapDetails,
    wfmTrapType
  }
  DESCRIPTION
  "ACPI Power State: working (S0/G0)."
  --#TYPE         "ACPI Power State: working (S0/G0)"
  --#SUMMARY      "%s"
  --#ARGUMENTS    { 1 }
  --#SEVERITY     INFORMATIONAL
  --#TIMEINDEX    1
  --#HELP         "Note: This is no error condition."
  --#HELPTAG      0
  --#STATE        OPERATIONAL
  ::=  2256640 

wfmACPIPowerStateSleepingS1 TRAP-TYPE
  ENTERPRISE wfmTrapInfo
  VARIABLES {
    wfmTrapDetails,
    wfmTrapType
  }
  DESCRIPTION
  "ACPI Power State: sleeping (S1)."
  --#TYPE         "ACPI Power State: sleeping (S1)"
  --#SUMMARY      "%s"
  --#ARGUMENTS    { 1 }
  --#SEVERITY     INFORMATIONAL
  --#TIMEINDEX    1
  --#HELP         "Note: This is no error condition."
  --#HELPTAG      0
  --#STATE        OPERATIONAL
  ::=  2256641 

wfmACPIPowerStateSleepingS2 TRAP-TYPE
  ENTERPRISE wfmTrapInfo
  VARIABLES {
    wfmTrapDetails,
    wfmTrapType
  }
  DESCRIPTION
  "ACPI Power State: sleeping (S2)."
  --#TYPE         "ACPI Power State: sleeping (S2)"
  --#SUMMARY      "%s"
  --#ARGUMENTS    { 1 }
  --#SEVERITY     INFORMATIONAL
  --#TIMEINDEX    1
  --#HELP         "Note: This is no error condition."
  --#HELPTAG      0
  --#STATE        OPERATIONAL
  ::=  2256642 

wfmACPIPowerStateSleepingS3 TRAP-TYPE
  ENTERPRISE wfmTrapInfo
  VARIABLES {
    wfmTrapDetails,
    wfmTrapType
  }
  DESCRIPTION
  "ACPI Power State: sleeping (S3)."
  --#TYPE         "ACPI Power State: sleeping (S3)"
  --#SUMMARY      "%s"
  --#ARGUMENTS    { 1 }
  --#SEVERITY     INFORMATIONAL
  --#TIMEINDEX    1
  --#HELP         "Note: This is no error condition."
  --#HELPTAG      0
  --#STATE        OPERATIONAL
  ::=  2256643 

wfmACPIPowerStateSleepingS4SuspendToDisk TRAP-TYPE
  ENTERPRISE wfmTrapInfo
  VARIABLES {
    wfmTrapDetails,
    wfmTrapType
  }
  DESCRIPTION
  "ACPI Power State: sleeping (S4 - Suspend to disk)."
  --#TYPE         "ACPI Power State: sleeping (S4 - Suspend to disk)"
  --#SUMMARY      "%s"
  --#ARGUMENTS    { 1 }
  --#SEVERITY     INFORMATIONAL
  --#TIMEINDEX    1
  --#HELP         "Note: This is no error condition."
  --#HELPTAG      0
  --#STATE        OPERATIONAL
  ::=  2256644 

wfmACPIPowerStateSleepingS5SoftOff TRAP-TYPE
  ENTERPRISE wfmTrapInfo
  VARIABLES {
    wfmTrapDetails,
    wfmTrapType
  }
  DESCRIPTION
  "ACPI Power State: sleeping (S5 - soft off)."
  --#TYPE         "ACPI Power State: sleeping (S5 - soft off)"
  --#SUMMARY      "%s"
  --#ARGUMENTS    { 1 }
  --#SEVERITY     INFORMATIONAL
  --#TIMEINDEX    1
  --#HELP         "Note: This is no error condition."
  --#HELPTAG      0
  --#STATE        OPERATIONAL
  ::=  2256645 

wfmACPIPowerStateSleepingS4S5 TRAP-TYPE
  ENTERPRISE wfmTrapInfo
  VARIABLES {
    wfmTrapDetails,
    wfmTrapType
  }
  DESCRIPTION
  "ACPI Power State: sleeping (S4/S5)."
  --#TYPE         "ACPI Power State: sleeping (S4/S5)"
  --#SUMMARY      "%s"
  --#ARGUMENTS    { 1 }
  --#SEVERITY     INFORMATIONAL
  --#TIMEINDEX    1
  --#HELP         "Note: This is no error condition."
  --#HELPTAG      0
  --#STATE        OPERATIONAL
  ::=  2256646 

wfmACPIPowerStateSleepingG7MechanicalOff TRAP-TYPE
  ENTERPRISE wfmTrapInfo
  VARIABLES {
    wfmTrapDetails,
    wfmTrapType
  }
  DESCRIPTION
  "ACPI Power State: sleeping (G7 - mechanical off)."
  --#TYPE         "ACPI Power State: sleeping (G7 - mechanical off)"
  --#SUMMARY      "%s"
  --#ARGUMENTS    { 1 }
  --#SEVERITY     INFORMATIONAL
  --#TIMEINDEX    1
  --#HELP         "Note: This is no error condition."
  --#HELPTAG      0
  --#STATE        OPERATIONAL
  ::=  2256647 

wfmACPIPowerStateSleepingS1S2S3 TRAP-TYPE
  ENTERPRISE wfmTrapInfo
  VARIABLES {
    wfmTrapDetails,
    wfmTrapType
  }
  DESCRIPTION
  "ACPI Power State: sleeping (S1/S2/S3)."
  --#TYPE         "ACPI Power State: sleeping (S1/S2/S3)"
  --#SUMMARY      "%s"
  --#ARGUMENTS    { 1 }
  --#SEVERITY     INFORMATIONAL
  --#TIMEINDEX    1
  --#HELP         "Note: This is no error condition."
  --#HELPTAG      0
  --#STATE        OPERATIONAL
  ::=  2256648 

wfmACPIPowerStateSleepingG1 TRAP-TYPE
  ENTERPRISE wfmTrapInfo
  VARIABLES {
    wfmTrapDetails,
    wfmTrapType
  }
  DESCRIPTION
  "ACPI Power State: sleeping (G1)."
  --#TYPE         "ACPI Power State: sleeping (G1)"
  --#SUMMARY      "%s"
  --#ARGUMENTS    { 1 }
  --#SEVERITY     INFORMATIONAL
  --#TIMEINDEX    1
  --#HELP         "Note: This is no error condition."
  --#HELPTAG      0
  --#STATE        OPERATIONAL
  ::=  2256649 

wfmACPIPowerStateSleepingS5ByOverrride TRAP-TYPE
  ENTERPRISE wfmTrapInfo
  VARIABLES {
    wfmTrapDetails,
    wfmTrapType
  }
  DESCRIPTION
  "ACPI Power State: sleeping (S5 - by overrride)."
  --#TYPE         "ACPI Power State: sleeping (S5 - by overrride)"
  --#SUMMARY      "%s"
  --#ARGUMENTS    { 1 }
  --#SEVERITY     INFORMATIONAL
  --#TIMEINDEX    1
  --#HELP         "Note: This is no error condition."
  --#HELPTAG      0
  --#STATE        OPERATIONAL
  ::=  2256650 

wfmACPIPowerStateLegacyONState TRAP-TYPE
  ENTERPRISE wfmTrapInfo
  VARIABLES {
    wfmTrapDetails,
    wfmTrapType
  }
  DESCRIPTION
  "ACPI Power State: Legacy ON State."
  --#TYPE         "ACPI Power State: Legacy ON State"
  --#SUMMARY      "%s"
  --#ARGUMENTS    { 1 }
  --#SEVERITY     INFORMATIONAL
  --#TIMEINDEX    1
  --#HELP         "Note: This is no error condition."
  --#HELPTAG      0
  --#STATE        OPERATIONAL
  ::=  2256651 

wfmACPIPowerStateLegacyOFFState TRAP-TYPE
  ENTERPRISE wfmTrapInfo
  VARIABLES {
    wfmTrapDetails,
    wfmTrapType
  }
  DESCRIPTION
  "ACPI Power State: Legacy OFF State."
  --#TYPE         "ACPI Power State: Legacy OFF State"
  --#SUMMARY      "%s"
  --#ARGUMENTS    { 1 }
  --#SEVERITY     INFORMATIONAL
  --#TIMEINDEX    1
  --#HELP         "Note: This is no error condition."
  --#HELPTAG      0
  --#STATE        OPERATIONAL
  ::=  2256652 

wfmACPIPowerStateInvalid TRAP-TYPE
  ENTERPRISE wfmTrapInfo
  VARIABLES {
    wfmTrapDetails,
    wfmTrapType
  }
  DESCRIPTION
  "ACPI Power State: invalid."
  --#TYPE         "ACPI Power State: invalid"
  --#SUMMARY      "%s"
  --#ARGUMENTS    { 1 }
  --#SEVERITY     INFORMATIONAL
  --#TIMEINDEX    1
  --#HELP         "Note: This is no error condition."
  --#HELPTAG      0
  --#STATE        OPERATIONAL
  ::=  2256653 

wfmACPIPowerStateUnknown TRAP-TYPE
  ENTERPRISE wfmTrapInfo
  VARIABLES {
    wfmTrapDetails,
    wfmTrapType
  }
  DESCRIPTION
  "ACPI Power State: unknown."
  --#TYPE         "ACPI Power State: unknown"
  --#SUMMARY      "%s"
  --#ARGUMENTS    { 1 }
  --#SEVERITY     INFORMATIONAL
  --#TIMEINDEX    1
  --#HELP         "Note: This is no error condition."
  --#HELPTAG      0
  --#STATE        OPERATIONAL
  ::=  2256654 

wfmWatchdogTimerExpired TRAP-TYPE
  ENTERPRISE wfmTrapInfo
  VARIABLES {
    wfmTrapDetails,
    wfmTrapType
  }
  DESCRIPTION
  "Watchdog: Timer Expired."
  --#TYPE         "Watchdog: Timer Expired"
  --#SUMMARY      "%s"
  --#ARGUMENTS    { 1 }
  --#SEVERITY     CRITICAL
  --#TIMEINDEX    1
  --#HELPTAG      0
  --#STATE        OPERATIONAL
  ::=  2322176 

wfmWatchdogHardReset TRAP-TYPE
  ENTERPRISE wfmTrapInfo
  VARIABLES {
    wfmTrapDetails,
    wfmTrapType
  }
  DESCRIPTION
  "Watchdog: Hard Reset."
  --#TYPE         "Watchdog: Hard Reset"
  --#SUMMARY      "%s"
  --#ARGUMENTS    { 1 }
  --#SEVERITY     CRITICAL
  --#TIMEINDEX    1
  --#HELPTAG      0
  --#STATE        OPERATIONAL
  ::=  2322177 

wfmWatchdogPowerDown TRAP-TYPE
  ENTERPRISE wfmTrapInfo
  VARIABLES {
    wfmTrapDetails,
    wfmTrapType
  }
  DESCRIPTION
  "Watchdog: Power Down."
  --#TYPE         "Watchdog: Power Down"
  --#SUMMARY      "%s"
  --#ARGUMENTS    { 1 }
  --#SEVERITY     CRITICAL
  --#TIMEINDEX    1
  --#HELPTAG      0
  --#STATE        OPERATIONAL
  ::=  2322178 

wfmWatchdogPowerCycle TRAP-TYPE
  ENTERPRISE wfmTrapInfo
  VARIABLES {
    wfmTrapDetails,
    wfmTrapType
  }
  DESCRIPTION
  "Watchdog: Power Cycle."
  --#TYPE         "Watchdog: Power Cycle"
  --#SUMMARY      "%s"
  --#ARGUMENTS    { 1 }
  --#SEVERITY     CRITICAL
  --#TIMEINDEX    1
  --#HELPTAG      0
  --#STATE        OPERATIONAL
  ::=  2322179 

wfmWatchdogHardwareWatchdogExpired TRAP-TYPE
  ENTERPRISE wfmTrapInfo
  VARIABLES {
    wfmTrapDetails,
    wfmTrapType
  }
  DESCRIPTION
  "Watchdog: Hardware Watchdog expired."
  --#TYPE         "Watchdog: Hardware Watchdog expired"
  --#SUMMARY      "%s"
  --#ARGUMENTS    { 1 }
  --#SEVERITY     CRITICAL
  --#TIMEINDEX    1
  --#HELPTAG      0
  --#STATE        OPERATIONAL
  ::=  2322180 

wfmWatchdogTimerInterrupt TRAP-TYPE
  ENTERPRISE wfmTrapInfo
  VARIABLES {
    wfmTrapDetails,
    wfmTrapType
  }
  DESCRIPTION
  "Watchdog: Timer Interrupt."
  --#TYPE         "Watchdog: Timer Interrupt"
  --#SUMMARY      "%s"
  --#ARGUMENTS    { 1 }
  --#SEVERITY     CRITICAL
  --#TIMEINDEX    1
  --#HELPTAG      0
  --#STATE        OPERATIONAL
  ::=  2322184 

wfmEntityPresentaddeddisabled TRAP-TYPE
  ENTERPRISE wfmTrapInfo
  VARIABLES {
    wfmTrapDetails,
    wfmTrapType
  }
  DESCRIPTION
  "Entity present/added."
  --#TYPE         "Entity present/added (disabled)"
  --#SUMMARY      "%s"
  --#ARGUMENTS    { 1 }
  --#SEVERITY     INFORMATIONAL
  --#TIMEINDEX    1
  --#HELP         "Note: This is no error condition."
  --#HELPTAG      0
  --#STATE        OPERATIONAL
  ::=  2453248 

wfmEntityAbsentremoveddisabled TRAP-TYPE
  ENTERPRISE wfmTrapInfo
  VARIABLES {
    wfmTrapDetails,
    wfmTrapType
  }
  DESCRIPTION
  "Entity absent/removed."
  --#TYPE         "Entity absent/removed (disabled)"
  --#SUMMARY      "%s"
  --#ARGUMENTS    { 1 }
  --#SEVERITY     INFORMATIONAL
  --#TIMEINDEX    1
  --#HELP         "Note: This is no error condition."
  --#HELPTAG      0
  --#STATE        OPERATIONAL
  ::=  2453249 

wfmEntityDisabled TRAP-TYPE
  ENTERPRISE wfmTrapInfo
  VARIABLES {
    wfmTrapDetails,
    wfmTrapType
  }
  DESCRIPTION
  "Entity disabled."
  --#TYPE         "Entity disabled"
  --#SUMMARY      "%s"
  --#ARGUMENTS    { 1 }
  --#SEVERITY     INFORMATIONAL
  --#TIMEINDEX    1
  --#HELP         "Note: This is no error condition."
  --#HELPTAG      0
  --#STATE        OPERATIONAL
  ::=  2453250 

wfmEntityAbsentremovedenabled TRAP-TYPE
  ENTERPRISE wfmTrapInfo
  VARIABLES {
    wfmTrapDetails,
    wfmTrapType
  }
  DESCRIPTION
  "Entity absent/removed."
  --#TYPE         "Entity absent/removed (enabled)"
  --#SUMMARY      "%s"
  --#ARGUMENTS    { 1 }
  --#SEVERITY     INFORMATIONAL
  --#TIMEINDEX    1
  --#HELP         "Note: This is no error condition."
  --#HELPTAG      0
  --#STATE        OPERATIONAL
  ::=  2453376 

wfmEntityPresentaddedenabled TRAP-TYPE
  ENTERPRISE wfmTrapInfo
  VARIABLES {
    wfmTrapDetails,
    wfmTrapType
  }
  DESCRIPTION
  "Entity present/added."
  --#TYPE         "Entity present/added (enabled)"
  --#SUMMARY      "%s"
  --#ARGUMENTS    { 1 }
  --#SEVERITY     INFORMATIONAL
  --#TIMEINDEX    1
  --#HELP         "Note: This is no error condition."
  --#HELPTAG      0
  --#STATE        OPERATIONAL
  ::=  2453377 

wfmEntityEnabled TRAP-TYPE
  ENTERPRISE wfmTrapInfo
  VARIABLES {
    wfmTrapDetails,
    wfmTrapType
  }
  DESCRIPTION
  "Entity enabled."
  --#TYPE         "Entity enabled"
  --#SUMMARY      "%s"
  --#ARGUMENTS    { 1 }
  --#SEVERITY     INFORMATIONAL
  --#TIMEINDEX    1
  --#HELP         "Note: This is no error condition."
  --#HELPTAG      0
  --#STATE        OPERATIONAL
  ::=  2453378 

wfmMonitoringBelowWarningLevelLNCGL TRAP-TYPE
  ENTERPRISE wfmTrapInfo
  VARIABLES {
    wfmTrapDetails,
    wfmTrapType
  }
  DESCRIPTION
  "Monitoring below warning level  (lower non critical going low)."
  --#TYPE         "Monitoring below warning level (LNC_GL)"
  --#SUMMARY      "%s"
  --#ARGUMENTS    { 1 }
  --#SEVERITY     MAJOR
  --#TIMEINDEX    1
  --#HELPTAG      0
  --#STATE        OPERATIONAL
  ::=  2490624 

wfmMonitoringOKLNCGH TRAP-TYPE
  ENTERPRISE wfmTrapInfo
  VARIABLES {
    wfmTrapDetails,
    wfmTrapType
  }
  DESCRIPTION
  "Monitoring OK (lower non critical going high)."
  --#TYPE         "Monitoring OK (LNC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  2490625 

wfmMonitoringBelowCriticalLevelLCGL TRAP-TYPE
  ENTERPRISE wfmTrapInfo
  VARIABLES {
    wfmTrapDetails,
    wfmTrapType
  }
  DESCRIPTION
  "Monitoring below critical level   (lower critical going low)."
  --#TYPE         "Monitoring below critical level (LC_GL)"
  --#SUMMARY      "%s"
  --#ARGUMENTS    { 1 }
  --#SEVERITY     CRITICAL
  --#TIMEINDEX    1
  --#HELPTAG      0
  --#STATE        OPERATIONAL
  ::=  2490626 

wfmMonitoringBelowWarningLevelLCGH TRAP-TYPE
  ENTERPRISE wfmTrapInfo
  VARIABLES {
    wfmTrapDetails,
    wfmTrapType
  }
  DESCRIPTION
  "Monitoring below warning level   (lower critical going high)."
  --#TYPE         "Monitoring below warning level (LC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  2490627 

wfmMonitoringBelowDamageLevelLNRGL TRAP-TYPE
  ENTERPRISE wfmTrapInfo
  VARIABLES {
    wfmTrapDetails,
    wfmTrapType
  }
  DESCRIPTION
  "Monitoring below damage level (lower non recover going low)."
  --#TYPE         "Monitoring below damage level (LNR_GL)"
  --#SUMMARY      "%s"
  --#ARGUMENTS    { 1 }
  --#SEVERITY     CRITICAL
  --#TIMEINDEX    1
  --#HELPTAG      0
  --#STATE        OPERATIONAL
  ::=  2490628 

wfmMonitoringBelowCriticalLevelLNRGH TRAP-TYPE
  ENTERPRISE wfmTrapInfo
  VARIABLES {
    wfmTrapDetails,
    wfmTrapType
  }
  DESCRIPTION
  "Monitoring below critical level  (lower non recover going high)."
  --#TYPE         "Monitoring below critical level (LNR_GH)"
  --#SUMMARY      "%s"
  --#ARGUMENTS    { 1 }
  --#SEVERITY     CRITICAL
  --#TIMEINDEX    1
  --#HELPTAG      0
  --#STATE        OPERATIONAL
  ::=  2490629 

wfmMonitoringOKUNCGL TRAP-TYPE
  ENTERPRISE wfmTrapInfo
  VARIABLES {
    wfmTrapDetails,
    wfmTrapType
  }
  DESCRIPTION
  "Monitoring OK (upper non critical going low)."
  --#TYPE         "Monitoring OK (UNC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  2490630 

wfmMonitoringAboveWarningLevelUNCGH TRAP-TYPE
  ENTERPRISE wfmTrapInfo
  VARIABLES {
    wfmTrapDetails,
    wfmTrapType
  }
  DESCRIPTION
  "Monitoring above warning level   (upper non critical going high)."
  --#TYPE         "Monitoring above warning level (UNC_GH)"
  --#SUMMARY      "%s"
  --#ARGUMENTS    { 1 }
  --#SEVERITY     MAJOR
  --#TIMEINDEX    1
  --#HELPTAG      0
  --#STATE        OPERATIONAL
  ::=  2490631 

wfmMonitoringAboveWarningLevelUCGL TRAP-TYPE
  ENTERPRISE wfmTrapInfo
  VARIABLES {
    wfmTrapDetails,
    wfmTrapType
  }
  DESCRIPTION
  "Monitoring above warning level   (upper critical going low)."
  --#TYPE         "Monitoring above warning level (UC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  2490632 

wfmMonitoringAboveCriticalLevelUCGH TRAP-TYPE
  ENTERPRISE wfmTrapInfo
  VARIABLES {
    wfmTrapDetails,
    wfmTrapType
  }
  DESCRIPTION
  "Monitoring above critical level   (upper critical going high)."
  --#TYPE         "Monitoring above critical level (UC_GH)"
  --#SUMMARY      "%s"
  --#ARGUMENTS    { 1 }
  --#SEVERITY     CRITICAL
  --#TIMEINDEX    1
  --#HELPTAG      0
  --#STATE        OPERATIONAL
  ::=  2490633 

wfmMonitoringAboveCriticalLevelUNRGL TRAP-TYPE
  ENTERPRISE wfmTrapInfo
  VARIABLES {
    wfmTrapDetails,
    wfmTrapType
  }
  DESCRIPTION
  "Monitoring above critical level   (upper non recover going low)."
  --#TYPE         "Monitoring above critical level (UNR_GL)"
  --#SUMMARY      "%s"
  --#ARGUMENTS    { 1 }
  --#SEVERITY     CRITICAL
  --#TIMEINDEX    1
  --#HELPTAG      0
  --#STATE        OPERATIONAL
  ::=  2490634 

wfmMonitoringAboveDamageLevelUNRGH TRAP-TYPE
  ENTERPRISE wfmTrapInfo
  VARIABLES {
    wfmTrapDetails,
    wfmTrapType
  }
  DESCRIPTION
  "Monitoring above damage level   (upper non recover going high)."
  --#TYPE         "Monitoring above damage level (UNR_GH)"
  --#SUMMARY      "%s"
  --#ARGUMENTS    { 1 }
  --#SEVERITY     CRITICAL
  --#TIMEINDEX    1
  --#HELPTAG      0
  --#STATE        OPERATIONAL
  ::=  2490635 

wfmMonitoringOKLNCGL TRAP-TYPE
  ENTERPRISE wfmTrapInfo
  VARIABLES {
    wfmTrapDetails,
    wfmTrapType
  }
  DESCRIPTION
  "Monitoring OK (lower non critical going low de-asserted)."
  --#TYPE         "Monitoring OK (LNC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  2490752 

wfmMonitoringBelowWarningLevelLNCGH TRAP-TYPE
  ENTERPRISE wfmTrapInfo
  VARIABLES {
    wfmTrapDetails,
    wfmTrapType
  }
  DESCRIPTION
  "Monitoring below warning level  (lower non critical going high de-asserted)."
  --#TYPE         "Monitoring below warning level (LNC_GHD)"
  --#SUMMARY      "%s"
  --#ARGUMENTS    { 1 }
  --#SEVERITY     MAJOR
  --#TIMEINDEX    1
  --#HELPTAG      0
  --#STATE        OPERATIONAL
  ::=  2490753 

wfmMonitoringBelowWarningLevelLCGL TRAP-TYPE
  ENTERPRISE wfmTrapInfo
  VARIABLES {
    wfmTrapDetails,
    wfmTrapType
  }
  DESCRIPTION
  "Monitoring below warning level   (lower critical going low de-asserted)."
  --#TYPE         "Monitoring below warning level (LC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  2490754 

wfmMonitoringBelowCriticalLevelLCGH TRAP-TYPE
  ENTERPRISE wfmTrapInfo
  VARIABLES {
    wfmTrapDetails,
    wfmTrapType
  }
  DESCRIPTION
  "Monitoring below critical level  (lower critical going high de-asserted)."
  --#TYPE         "Monitoring below critical level (LC_GHD)"
  --#SUMMARY      "%s"
  --#ARGUMENTS    { 1 }
  --#SEVERITY     CRITICAL
  --#TIMEINDEX    1
  --#HELPTAG      0
  --#STATE        OPERATIONAL
  ::=  2490755 

wfmMonitoringBelowCriticalLevelLNRGL TRAP-TYPE
  ENTERPRISE wfmTrapInfo
  VARIABLES {
    wfmTrapDetails,
    wfmTrapType
  }
  DESCRIPTION
  "Monitoring below critical level  (lower non recover going low de-asserted)."
  --#TYPE         "Monitoring below critical level (LNR_GLD)"
  --#SUMMARY      "%s"
  --#ARGUMENTS    { 1 }
  --#SEVERITY     CRITICAL
  --#TIMEINDEX    1
  --#HELPTAG      0
  --#STATE        OPERATIONAL
  ::=  2490756 

wfmMonitoringBelowDamageLevelLNRGH TRAP-TYPE
  ENTERPRISE wfmTrapInfo
  VARIABLES {
    wfmTrapDetails,
    wfmTrapType
  }
  DESCRIPTION
  "Monitoring below damage level  (lower non recover going high de-asserted)."
  --#TYPE         "Monitoring below damage level (LNR_GHD)"
  --#SUMMARY      "%s"
  --#ARGUMENTS    { 1 }
  --#SEVERITY     CRITICAL
  --#TIMEINDEX    1
  --#HELPTAG      0
  --#STATE        OPERATIONAL
  ::=  2490757 

wfmMonitoringAboveWarningLevelUNCGL TRAP-TYPE
  ENTERPRISE wfmTrapInfo
  VARIABLES {
    wfmTrapDetails,
    wfmTrapType
  }
  DESCRIPTION
  "Monitoring above warning level  (upper non critical going low de-asserted)."
  --#TYPE         "Monitoring above warning level (UNC_GLD)"
  --#SUMMARY      "%s"
  --#ARGUMENTS    { 1 }
  --#SEVERITY     MAJOR
  --#TIMEINDEX    1
  --#HELPTAG      0
  --#STATE        OPERATIONAL
  ::=  2490758 

wfmMonitoringOKUNCGH TRAP-TYPE
  ENTERPRISE wfmTrapInfo
  VARIABLES {
    wfmTrapDetails,
    wfmTrapType
  }
  DESCRIPTION
  "Monitoring OK (upper non critical going high de-asserted)."
  --#TYPE         "Monitoring OK (UNC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  2490759 

wfmMonitoringAboveCriticalLevelUCGL TRAP-TYPE
  ENTERPRISE wfmTrapInfo
  VARIABLES {
    wfmTrapDetails,
    wfmTrapType
  }
  DESCRIPTION
  "Monitoring above critical level   (upper critical going low de-asserted)."
  --#TYPE         "Monitoring above critical level (UC_GLD)"
  --#SUMMARY      "%s"
  --#ARGUMENTS    { 1 }
  --#SEVERITY     CRITICAL
  --#TIMEINDEX    1
  --#HELPTAG      0
  --#STATE        OPERATIONAL
  ::=  2490760 

wfmMonitoringAboveWarningLevelUCGH TRAP-TYPE
  ENTERPRISE wfmTrapInfo
  VARIABLES {
    wfmTrapDetails,
    wfmTrapType
  }
  DESCRIPTION
  "Monitoring above warning level   (upper critical going high de-asserted)."
  --#TYPE         "Monitoring above warning level (UC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  2490761 

wfmMonitoringAboveDamageLevelUNRGL TRAP-TYPE
  ENTERPRISE wfmTrapInfo
  VARIABLES {
    wfmTrapDetails,
    wfmTrapType
  }
  DESCRIPTION
  "Monitoring above damage level  (upper non recover going low de-asserted)."
  --#TYPE         "Monitoring above damage level (UNR_GLD)"
  --#SUMMARY      "%s"
  --#ARGUMENTS    { 1 }
  --#SEVERITY     CRITICAL
  --#TIMEINDEX    1
  --#HELPTAG      0
  --#STATE        OPERATIONAL
  ::=  2490762 

wfmMonitoringAboveCriticalLevelUNRGH TRAP-TYPE
  ENTERPRISE wfmTrapInfo
  VARIABLES {
    wfmTrapDetails,
    wfmTrapType
  }
  DESCRIPTION
  "Monitoring above critical level   (upper non recover going high de-asserted)."
  --#TYPE         "Monitoring above critical level (UNR_GHD)"
  --#SUMMARY      "%s"
  --#ARGUMENTS    { 1 }
  --#SEVERITY     CRITICAL
  --#TIMEINDEX    1
  --#HELPTAG      0
  --#STATE        OPERATIONAL
  ::=  2490763 

wfmMonitoringOKassert TRAP-TYPE
  ENTERPRISE wfmTrapInfo
  VARIABLES {
    wfmTrapDetails,
    wfmTrapType
  }
  DESCRIPTION
  "Monitoring OK (digital assert sensor)."
  --#TYPE         "Monitoring OK (assert)"
  --#SUMMARY      "%s"
  --#ARGUMENTS    { 1 }
  --#SEVERITY     INFORMATIONAL
  --#TIMEINDEX    1
  --#HELP         "Note: This is no error condition."
  --#HELPTAG      0
  --#STATE        OPERATIONAL
  ::=  2491136 

wfmMonitoringFailedassert TRAP-TYPE
  ENTERPRISE wfmTrapInfo
  VARIABLES {
    wfmTrapDetails,
    wfmTrapType
  }
  DESCRIPTION
  "Monitoring Failed (digital assert sensor)."
  --#TYPE         "Monitoring Failed (assert)"
  --#SUMMARY      "%s"
  --#ARGUMENTS    { 1 }
  --#SEVERITY     CRITICAL
  --#TIMEINDEX    1
  --#HELPTAG      0
  --#STATE        OPERATIONAL
  ::=  2491137 

wfmMonitoringOKpredictive TRAP-TYPE
  ENTERPRISE wfmTrapInfo
  VARIABLES {
    wfmTrapDetails,
    wfmTrapType
  }
  DESCRIPTION
  "Monitoring OK (digital predictive sensor)."
  --#TYPE         "Monitoring OK (predictive)"
  --#SUMMARY      "%s"
  --#ARGUMENTS    { 1 }
  --#SEVERITY     INFORMATIONAL
  --#TIMEINDEX    1
  --#HELP         "Note: This is no error condition."
  --#HELPTAG      0
  --#STATE        OPERATIONAL
  ::=  2491392 

wfmMonitoringFailedpredictive TRAP-TYPE
  ENTERPRISE wfmTrapInfo
  VARIABLES {
    wfmTrapDetails,
    wfmTrapType
  }
  DESCRIPTION
  "Monitoring Failed (digital predictive sensor)."
  --#TYPE         "Monitoring Failed (predictive)"
  --#SUMMARY      "%s"
  --#ARGUMENTS    { 1 }
  --#SEVERITY     MAJOR
  --#TIMEINDEX    1
  --#HELPTAG      0
  --#STATE        OPERATIONAL
  ::=  2491393 

wfmMonitoringWithinLimit TRAP-TYPE
  ENTERPRISE wfmTrapInfo
  VARIABLES {
    wfmTrapDetails,
    wfmTrapType
  }
  DESCRIPTION
  "Monitoring within limit."
  --#TYPE         "Monitoring within limit"
  --#SUMMARY      "%s"
  --#ARGUMENTS    { 1 }
  --#SEVERITY     CRITICAL
  --#TIMEINDEX    1
  --#HELPTAG      0
  --#STATE        OPERATIONAL
  ::=  2491648 

wfmMonitoringLimitExceeded TRAP-TYPE
  ENTERPRISE wfmTrapInfo
  VARIABLES {
    wfmTrapDetails,
    wfmTrapType
  }
  DESCRIPTION
  "Monitoring limit exceeded."
  --#TYPE         "Monitoring limit exceeded"
  --#SUMMARY      "%s"
  --#ARGUMENTS    { 1 }
  --#SEVERITY     CRITICAL
  --#TIMEINDEX    1
  --#HELPTAG      0
  --#STATE        OPERATIONAL
  ::=  2491649 

wfmMonitoringPerformanceOK TRAP-TYPE
  ENTERPRISE wfmTrapInfo
  VARIABLES {
    wfmTrapDetails,
    wfmTrapType
  }
  DESCRIPTION
  "Monitoring performance OK."
  --#TYPE         "Monitoring performance OK"
  --#SUMMARY      "%s"
  --#ARGUMENTS    { 1 }
  --#SEVERITY     INFORMATIONAL
  --#TIMEINDEX    1
  --#HELP         "Note: This is no error condition."
  --#HELPTAG      0
  --#STATE        OPERATIONAL
  ::=  2491904 

wfmMonitoringPerformanceLags TRAP-TYPE
  ENTERPRISE wfmTrapInfo
  VARIABLES {
    wfmTrapDetails,
    wfmTrapType
  }
  DESCRIPTION
  "Monitoring performance lags."
  --#TYPE         "Monitoring performance lags"
  --#SUMMARY      "%s"
  --#ARGUMENTS    { 1 }
  --#SEVERITY     CRITICAL
  --#TIMEINDEX    1
  --#HELPTAG      0
  --#STATE        OPERATIONAL
  ::=  2491905 

wfmMonitoringRemoved TRAP-TYPE
  ENTERPRISE wfmTrapInfo
  VARIABLES {
    wfmTrapDetails,
    wfmTrapType
  }
  DESCRIPTION
  "Monitoring removed."
  --#TYPE         "Monitoring removed"
  --#SUMMARY      "%s"
  --#ARGUMENTS    { 1 }
  --#SEVERITY     INFORMATIONAL
  --#TIMEINDEX    1
  --#HELP         "Note: This is no error condition."
  --#HELPTAG      0
  --#STATE        OPERATIONAL
  ::=  2492416 

wfmMonitoringRestoredreplaced TRAP-TYPE
  ENTERPRISE wfmTrapInfo
  VARIABLES {
    wfmTrapDetails,
    wfmTrapType
  }
  DESCRIPTION
  "Monitoring restored/replaced."
  --#TYPE         "Monitoring restored/replaced"
  --#SUMMARY      "%s"
  --#ARGUMENTS    { 1 }
  --#SEVERITY     INFORMATIONAL
  --#TIMEINDEX    1
  --#HELP         "Note: This is no error condition."
  --#HELPTAG      0
  --#STATE        OPERATIONAL
  ::=  2492417 

wfmMonitoringDisabled TRAP-TYPE
  ENTERPRISE wfmTrapInfo
  VARIABLES {
    wfmTrapDetails,
    wfmTrapType
  }
  DESCRIPTION
  "Monitoring disabled."
  --#TYPE         "Monitoring disabled"
  --#SUMMARY      "%s"
  --#ARGUMENTS    { 1 }
  --#SEVERITY     INFORMATIONAL
  --#TIMEINDEX    1
  --#HELP         "Note: This is no error condition."
  --#HELPTAG      0
  --#STATE        OPERATIONAL
  ::=  2492672 

wfmMonitoringEnabled TRAP-TYPE
  ENTERPRISE wfmTrapInfo
  VARIABLES {
    wfmTrapDetails,
    wfmTrapType
  }
  DESCRIPTION
  "Monitoring enabled."
  --#TYPE         "Monitoring enabled"
  --#SUMMARY      "%s"
  --#ARGUMENTS    { 1 }
  --#SEVERITY     INFORMATIONAL
  --#TIMEINDEX    1
  --#HELP         "Note: This is no error condition."
  --#HELPTAG      0
  --#STATE        OPERATIONAL
  ::=  2492673 

wfmLANHeartbeatLost TRAP-TYPE
  ENTERPRISE wfmTrapInfo
  VARIABLES {
    wfmTrapDetails,
    wfmTrapType
  }
  DESCRIPTION
  "LAN Heartbeat lost."
  --#TYPE         "LAN Heartbeat lost"
  --#SUMMARY      "%s"
  --#ARGUMENTS    { 1 }
  --#SEVERITY     INFORMATIONAL
  --#TIMEINDEX    1
  --#HELP         "Note: This is no error condition."
  --#HELPTAG      0
  --#STATE        OPERATIONAL
  ::=  2584320 

wfmLANHeartbeat TRAP-TYPE
  ENTERPRISE wfmTrapInfo
  VARIABLES {
    wfmTrapDetails,
    wfmTrapType
  }
  DESCRIPTION
  "LAN Heartbeat."
  --#TYPE         "LAN Heartbeat"
  --#SUMMARY      "%s"
  --#ARGUMENTS    { 1 }
  --#SEVERITY     INFORMATIONAL
  --#TIMEINDEX    1
  --#HELP         "Note: This is no error condition."
  --#HELPTAG      0
  --#STATE        OPERATIONAL
  ::=  2584321 

wfmSensorAccessDegraded TRAP-TYPE
  ENTERPRISE wfmTrapInfo
  VARIABLES {
    wfmTrapDetails,
    wfmTrapType
  }
  DESCRIPTION
  "Sensor access degraded."
  --#TYPE         "Sensor access degraded"
  --#SUMMARY      "%s"
  --#ARGUMENTS    { 1 }
  --#SEVERITY     MINOR
  --#TIMEINDEX    1
  --#HELPTAG      0
  --#STATE        OPERATIONAL
  ::=  2649856 

wfmControllerAccessDegradedOrUnavailable TRAP-TYPE
  ENTERPRISE wfmTrapInfo
  VARIABLES {
    wfmTrapDetails,
    wfmTrapType
  }
  DESCRIPTION
  "Controller access degraded or unavailable."
  --#TYPE         "Controller access degraded or unavailable"
  --#SUMMARY      "%s"
  --#ARGUMENTS    { 1 }
  --#SEVERITY     MINOR
  --#TIMEINDEX    1
  --#HELPTAG      0
  --#STATE        OPERATIONAL
  ::=  2649857 

wfmManagementControllerOffline TRAP-TYPE
  ENTERPRISE wfmTrapInfo
  VARIABLES {
    wfmTrapDetails,
    wfmTrapType
  }
  DESCRIPTION
  "Management Controller off-line."
  --#TYPE         "Management Controller off-line"
  --#SUMMARY      "%s"
  --#ARGUMENTS    { 1 }
  --#SEVERITY     MAJOR
  --#TIMEINDEX    1
  --#HELPTAG      0
  --#STATE        OPERATIONAL
  ::=  2649858 

wfmManagementControllerUnavailable TRAP-TYPE
  ENTERPRISE wfmTrapInfo
  VARIABLES {
    wfmTrapDetails,
    wfmTrapType
  }
  DESCRIPTION
  "Management Controller unavailable."
  --#TYPE         "Management Controller unavailable"
  --#SUMMARY      "%s"
  --#ARGUMENTS    { 1 }
  --#SEVERITY     CRITICAL
  --#TIMEINDEX    1
  --#HELPTAG      0
  --#STATE        OPERATIONAL
  ::=  2649859 

wfmSensorFailure TRAP-TYPE
  ENTERPRISE wfmTrapInfo
  VARIABLES {
    wfmTrapDetails,
    wfmTrapType
  }
  DESCRIPTION
  "Sensor Failure."
  --#TYPE         "Sensor Failure"
  --#SUMMARY      "%s"
  --#ARGUMENTS    { 1 }
  --#SEVERITY     MINOR
  --#TIMEINDEX    1
  --#HELPTAG      0
  --#STATE        OPERATIONAL
  ::=  2649860 

wfmFRUFailure TRAP-TYPE
  ENTERPRISE wfmTrapInfo
  VARIABLES {
    wfmTrapDetails,
    wfmTrapType
  }
  DESCRIPTION
  "FRU Failure."
  --#TYPE         "FRU Failure"
  --#SUMMARY      "%s"
  --#ARGUMENTS    { 1 }
  --#SEVERITY     MINOR
  --#TIMEINDEX    1
  --#HELPTAG      0
  --#STATE        OPERATIONAL
  ::=  2649861 

wfmManagementControllerAccessOk TRAP-TYPE
  ENTERPRISE wfmTrapInfo
  VARIABLES {
    wfmTrapDetails,
    wfmTrapType
  }
  DESCRIPTION
  "Management Controller access ok"
  --#TYPE         "Management Controller access ok"
  --#SUMMARY      "%s"
  --#ARGUMENTS    { 1 }
  --#SEVERITY     INFORMATIONAL
  --#TIMEINDEX    1
  --#HELP         "Note: This is no error condition."
  --#HELPTAG      0
  --#STATE        OPERATIONAL
  ::=  2649985 

wfmManagementControllerOnline TRAP-TYPE
  ENTERPRISE wfmTrapInfo
  VARIABLES {
    wfmTrapDetails,
    wfmTrapType
  }
  DESCRIPTION
  "Management Controller on-line"
  --#TYPE         "Management Controller on-line"
  --#SUMMARY      "%s"
  --#ARGUMENTS    { 1 }
  --#SEVERITY     INFORMATIONAL
  --#TIMEINDEX    1
  --#HELP         "Note: This is no error condition."
  --#HELPTAG      0
  --#STATE        OPERATIONAL
  ::=  2649986 

wfmManagementEngineFailureOnSensorAssertedN1 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651648 

wfmManagementEngineFailureOnSensorAssertedN2 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651649 

wfmManagementEngineFailureOnSensorAssertedN3 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651650 

wfmManagementEngineFailureOnSensorAssertedN4 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651651 

wfmManagementEngineFailureOnSensorAssertedN5 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651652 

wfmManagementEngineFailureOnSensorAssertedN6 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651653 

wfmManagementEngineFailureOnSensorAssertedN7 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651654 

wfmManagementEngineFailureOnSensorAssertedN8 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651655 

wfmManagementEngineFailureOnSensorAssertedN9 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651656 

wfmManagementEngineFailureOnSensorAssertedN10 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651657 

wfmManagementEngineFailureOnSensorAssertedN11 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651658 

wfmManagementEngineFailureOnSensorAssertedN12 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651659 

wfmManagementEngineFailureOnSensorAssertedN13 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651660 

wfmManagementEngineFailureOnSensorAssertedN14 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651661 

wfmManagementEngineFailureOnSensorAssertedN15 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651662 

wfmManagementEngineFailureOnSensorAssertedN16 TRAP-TYPE
  ENTERPRISE wfmTrapInfo
  VARIABLES {
    wfmTrapDetails,
    wfmTrapType
  }
  DESCRIPTION
  "Management Engine: Failure on sensor asserted"
  --#TYPE         "Management Engine: Failure on sensor asserted"
  --#SUMMARY      "%s"
  --#ARGUMENTS    { 1 }
  --#SEVERITY     MAJOR
  --#TIMEINDEX    1
  --#HELPTAG      0
  --#STATE        OPERATIONAL
  ::=  2651663 

wfmManagementEngineFailureOnSensorDeassertedN1 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651776 

wfmManagementEngineFailureOnSensorDeassertedN2 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651777 

wfmManagementEngineFailureOnSensorDeassertedN3 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651778 

wfmManagementEngineFailureOnSensorDeassertedN4 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651779 

wfmManagementEngineFailureOnSensorDeassertedN5 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651780 

wfmManagementEngineFailureOnSensorDeassertedN6 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651781 

wfmManagementEngineFailureOnSensorDeassertedN7 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651782 

wfmManagementEngineFailureOnSensorDeassertedN8 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651783 

wfmManagementEngineFailureOnSensorDeassertedN9 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651784 

wfmManagementEngineFailureOnSensorDeassertedN10 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651785 

wfmManagementEngineFailureOnSensorDeassertedN11 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651786 

wfmManagementEngineFailureOnSensorDeassertedN12 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651787 

wfmManagementEngineFailureOnSensorDeassertedN13 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651788 

wfmManagementEngineFailureOnSensorDeassertedN14 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651789 

wfmManagementEngineFailureOnSensorDeassertedN15 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651790 

wfmManagementEngineFailureOnSensorDeassertedN16 TRAP-TYPE
  ENTERPRISE wfmTrapInfo
  VARIABLES {
    wfmTrapDetails,
    wfmTrapType
  }
  DESCRIPTION
  "Management Engine: Failure on sensor deasserted"
  --#TYPE         "Management Engine: Failure on sensor deasserted"
  --#SUMMARY      "%s"
  --#ARGUMENTS    { 1 }
  --#SEVERITY     INFORMATIONAL
  --#TIMEINDEX    1
  --#HELP         "Note: This is no error condition."
  --#HELPTAG      0
  --#STATE        OPERATIONAL
  ::=  2651791 

wfmBatteryLowpredictiveFailure TRAP-TYPE
  ENTERPRISE wfmTrapInfo
  VARIABLES {
    wfmTrapDetails,
    wfmTrapType
  }
  DESCRIPTION
  "Battery low (predictive failure)."
  --#TYPE         "Battery low (predictive failure)"
  --#SUMMARY      "%s"
  --#ARGUMENTS    { 1 }
  --#SEVERITY     MINOR
  --#TIMEINDEX    1
  --#HELPTAG      0
  --#STATE        OPERATIONAL
  ::=  2715392 

wfmBatteryFailed TRAP-TYPE
  ENTERPRISE wfmTrapInfo
  VARIABLES {
    wfmTrapDetails,
    wfmTrapType
  }
  DESCRIPTION
  "Battery failed."
  --#TYPE         "Battery failed"
  --#SUMMARY      "%s"
  --#ARGUMENTS    { 1 }
  --#SEVERITY     MAJOR
  --#TIMEINDEX    1
  --#HELPTAG      0
  --#STATE        OPERATIONAL
  ::=  2715393 

wfmBatteryPresenceDetected TRAP-TYPE
  ENTERPRISE wfmTrapInfo
  VARIABLES {
    wfmTrapDetails,
    wfmTrapType
  }
  DESCRIPTION
  "Battery presence detected."
  --#TYPE         "Battery presence detected"
  --#SUMMARY      "%s"
  --#ARGUMENTS    { 1 }
  --#SEVERITY     INFORMATIONAL
  --#TIMEINDEX    1
  --#HELP         "Note: This is no error condition."
  --#HELPTAG      0
  --#STATE        OPERATIONAL
  ::=  2715394 

wfmBBUOnRAIDCtrlOnline TRAP-TYPE
  ENTERPRISE wfmTrapInfo
  VARIABLES {
    wfmTrapDetails,
    wfmTrapType
  }
  DESCRIPTION
  "BBU on RAID Ctrl. online."
  --#TYPE         "BBU on RAID Ctrl. online"
  --#SUMMARY      "%s"
  --#ARGUMENTS    { 1 }
  --#SEVERITY     INFORMATIONAL
  --#TIMEINDEX    1
  --#HELP         "Note: This is no error condition."
  --#HELPTAG      0
  --#STATE        OPERATIONAL
  ::=  2719488 

wfmBBUOnRAIDCtrlOnBattery TRAP-TYPE
  ENTERPRISE wfmTrapInfo
  VARIABLES {
    wfmTrapDetails,
    wfmTrapType
  }
  DESCRIPTION
  "BBU on RAID Ctrl. on battery."
  --#TYPE         "BBU on RAID Ctrl. on battery"
  --#SUMMARY      "%s"
  --#ARGUMENTS    { 1 }
  --#SEVERITY     MINOR
  --#TIMEINDEX    1
  --#HELPTAG      0
  --#STATE        OPERATIONAL
  ::=  2719489 

wfmBBUOnRAIDCtrlBatteryLow TRAP-TYPE
  ENTERPRISE wfmTrapInfo
  VARIABLES {
    wfmTrapDetails,
    wfmTrapType
  }
  DESCRIPTION
  "BBU on RAID Ctrl. battery low."
  --#TYPE         "BBU on RAID Ctrl. battery low"
  --#SUMMARY      "%s"
  --#ARGUMENTS    { 1 }
  --#SEVERITY     MAJOR
  --#TIMEINDEX    1
  --#HELPTAG      0
  --#STATE        OPERATIONAL
  ::=  2719490 

wfmBBUOnRAIDCtrlCharging TRAP-TYPE
  ENTERPRISE wfmTrapInfo
  VARIABLES {
    wfmTrapDetails,
    wfmTrapType
  }
  DESCRIPTION
  "BBU on RAID Ctrl. charging."
  --#TYPE         "BBU on RAID Ctrl. charging"
  --#SUMMARY      "%s"
  --#ARGUMENTS    { 1 }
  --#SEVERITY     INFORMATIONAL
  --#TIMEINDEX    1
  --#HELP         "Note: This is no error condition."
  --#HELPTAG      0
  --#STATE        OPERATIONAL
  ::=  2719491 

wfmBBUOnRAIDCtrlDischarging TRAP-TYPE
  ENTERPRISE wfmTrapInfo
  VARIABLES {
    wfmTrapDetails,
    wfmTrapType
  }
  DESCRIPTION
  "BBU on RAID Ctrl. discharging."
  --#TYPE         "BBU on RAID Ctrl. discharging"
  --#SUMMARY      "%s"
  --#ARGUMENTS    { 1 }
  --#SEVERITY     INFORMATIONAL
  --#TIMEINDEX    1
  --#HELP         "Note: This is no error condition."
  --#HELPTAG      0
  --#STATE        OPERATIONAL
  ::=  2719492 

wfmBBUOnRAIDCtrlFailed TRAP-TYPE
  ENTERPRISE wfmTrapInfo
  VARIABLES {
    wfmTrapDetails,
    wfmTrapType
  }
  DESCRIPTION
  "BBU on RAID Ctrl. failed."
  --#TYPE         "BBU on RAID Ctrl. failed"
  --#SUMMARY      "%s"
  --#ARGUMENTS    { 1 }
  --#SEVERITY     CRITICAL
  --#TIMEINDEX    1
  --#HELPTAG      0
  --#STATE        OPERATIONAL
  ::=  2719493 

wfmBBUOnRAIDCtrlRelearnRequired TRAP-TYPE
  ENTERPRISE wfmTrapInfo
  VARIABLES {
    wfmTrapDetails,
    wfmTrapType
  }
  DESCRIPTION
  "BBU on RAID Ctrl. relearn required."
  --#TYPE         "BBU on RAID Ctrl. relearn required"
  --#SUMMARY      "%s"
  --#ARGUMENTS    { 1 }
  --#SEVERITY     INFORMATIONAL
  --#TIMEINDEX    1
  --#HELP         "Note: This is no error condition."
  --#HELPTAG      0
  --#STATE        OPERATIONAL
  ::=  2719494 

wfmSESSIONActivated TRAP-TYPE
  ENTERPRISE wfmTrapInfo
  VARIABLES {
    wfmTrapDetails,
    wfmTrapType
  }
  DESCRIPTION
  "SESSION activated."
  --#TYPE         "SESSION activated"
  --#SUMMARY      "%s"
  --#ARGUMENTS    { 1 }
  --#SEVERITY     INFORMATIONAL
  --#TIMEINDEX    1
  --#HELP         "Note: This is no error condition."
  --#HELPTAG      0
  --#STATE        OPERATIONAL
  ::=  2780928 

wfmSESSIONDeactivated TRAP-TYPE
  ENTERPRISE wfmTrapInfo
  VARIABLES {
    wfmTrapDetails,
    wfmTrapType
  }
  DESCRIPTION
  "SESSION De-activated."
  --#TYPE         "SESSION De-activated"
  --#SUMMARY      "%s"
  --#ARGUMENTS    { 1 }
  --#SEVERITY     INFORMATIONAL
  --#TIMEINDEX    1
  --#HELP         "Note: This is no error condition."
  --#HELPTAG      0
  --#STATE        OPERATIONAL
  ::=  2780929 

wfmHWChangeDetected TRAP-TYPE
  ENTERPRISE wfmTrapInfo
  VARIABLES {
    wfmTrapDetails,
    wfmTrapType
  }
  DESCRIPTION
  "HW change detected."
  --#TYPE         "HW change detected"
  --#SUMMARY      "%s"
  --#ARGUMENTS    { 1 }
  --#SEVERITY     INFORMATIONAL
  --#TIMEINDEX    1
  --#HELP         "Note: This is no error condition."
  --#HELPTAG      0
  --#STATE        OPERATIONAL
  ::=  2846464 

wfmFWOrSWChangeDetected TRAP-TYPE
  ENTERPRISE wfmTrapInfo
  VARIABLES {
    wfmTrapDetails,
    wfmTrapType
  }
  DESCRIPTION
  "FW or SW change detected."
  --#TYPE         "FW or SW change detected"
  --#SUMMARY      "%s"
  --#ARGUMENTS    { 1 }
  --#SEVERITY     INFORMATIONAL
  --#TIMEINDEX    1
  --#HELP         "Note: This is no error condition."
  --#HELPTAG      0
  --#STATE        OPERATIONAL
  ::=  2846465 

wfmHWIncompatibilityDetected TRAP-TYPE
  ENTERPRISE wfmTrapInfo
  VARIABLES {
    wfmTrapDetails,
    wfmTrapType
  }
  DESCRIPTION
  "HW incompatibility detected."
  --#TYPE         "HW incompatibility detected"
  --#SUMMARY      "%s"
  --#ARGUMENTS    { 1 }
  --#SEVERITY     INFORMATIONAL
  --#TIMEINDEX    1
  --#HELP         "Note: This is no error condition."
  --#HELPTAG      0
  --#STATE        OPERATIONAL
  ::=  2846466 

wfmFWOrSWIncompatibilityDetected TRAP-TYPE
  ENTERPRISE wfmTrapInfo
  VARIABLES {
    wfmTrapDetails,
    wfmTrapType
  }
  DESCRIPTION
  "FW or SW incompatibility detected."
  --#TYPE         "FW or SW incompatibility detected"
  --#SUMMARY      "%s"
  --#ARGUMENTS    { 1 }
  --#SEVERITY     INFORMATIONAL
  --#TIMEINDEX    1
  --#HELP         "Note: This is no error condition."
  --#HELPTAG      0
  --#STATE        OPERATIONAL
  ::=  2846467 

wfmInvalidunsupportedHWVersionDetected TRAP-TYPE
  ENTERPRISE wfmTrapInfo
  VARIABLES {
    wfmTrapDetails,
    wfmTrapType
  }
  DESCRIPTION
  "Invalid/unsupported HW version detected."
  --#TYPE         "Invalid/unsupported HW version detected"
  --#SUMMARY      "%s"
  --#ARGUMENTS    { 1 }
  --#SEVERITY     INFORMATIONAL
  --#TIMEINDEX    1
  --#HELP         "Note: This is no error condition."
  --#HELPTAG      0
  --#STATE        OPERATIONAL
  ::=  2846468 

wfmInvalidunsupportedFWOrSWVersionDetected TRAP-TYPE
  ENTERPRISE wfmTrapInfo
  VARIABLES {
    wfmTrapDetails,
    wfmTrapType
  }
  DESCRIPTION
  "Invalid/unsupported FW or SW version detected."
  --#TYPE         "Invalid/unsupported FW or SW version detected"
  --#SUMMARY      "%s"
  --#ARGUMENTS    { 1 }
  --#SEVERITY     INFORMATIONAL
  --#TIMEINDEX    1
  --#HELP         "Note: This is no error condition."
  --#HELPTAG      0
  --#STATE        OPERATIONAL
  ::=  2846469 

wfmHWChangeSuccessful TRAP-TYPE
  ENTERPRISE wfmTrapInfo
  VARIABLES {
    wfmTrapDetails,
    wfmTrapType
  }
  DESCRIPTION
  "HW change successful."
  --#TYPE         "HW change successful"
  --#SUMMARY      "%s"
  --#ARGUMENTS    { 1 }
  --#SEVERITY     INFORMATIONAL
  --#TIMEINDEX    1
  --#HELP         "Note: This is no error condition."
  --#HELPTAG      0
  --#STATE        OPERATIONAL
  ::=  2846470 

wfmFWOrSWChangeSuccessful TRAP-TYPE
  ENTERPRISE wfmTrapInfo
  VARIABLES {
    wfmTrapDetails,
    wfmTrapType
  }
  DESCRIPTION
  "FW or SW change successful."
  --#TYPE         "FW or SW change successful"
  --#SUMMARY      "%s"
  --#ARGUMENTS    { 1 }
  --#SEVERITY     INFORMATIONAL
  --#TIMEINDEX    1
  --#HELP         "Note: This is no error condition."
  --#HELPTAG      0
  --#STATE        OPERATIONAL
  ::=  2846471 

wfmHWChangeFailed TRAP-TYPE
  ENTERPRISE wfmTrapInfo
  VARIABLES {
    wfmTrapDetails,
    wfmTrapType
  }
  DESCRIPTION
  "HW change failed."
  --#TYPE         "HW change failed"
  --#SUMMARY      "%s"
  --#ARGUMENTS    { 1 }
  --#SEVERITY     INFORMATIONAL
  --#TIMEINDEX    1
  --#HELP         "Note: This is no error condition."
  --#HELPTAG      0
  --#STATE        OPERATIONAL
  ::=  2846598 

wfmFWOrSWChangeFailed TRAP-TYPE
  ENTERPRISE wfmTrapInfo
  VARIABLES {
    wfmTrapDetails,
    wfmTrapType
  }
  DESCRIPTION
  "FW or SW change failed."
  --#TYPE         "FW or SW change failed"
  --#SUMMARY      "%s"
  --#ARGUMENTS    { 1 }
  --#SEVERITY     INFORMATIONAL
  --#TIMEINDEX    1
  --#HELP         "Note: This is no error condition."
  --#HELPTAG      0
  --#STATE        OPERATIONAL
  ::=  2846599 

wfmIDPROMFRUActive TRAP-TYPE
  ENTERPRISE wfmTrapInfo
  VARIABLES {
    wfmTrapDetails,
    wfmTrapType
  }
  DESCRIPTION
  "ID PROM (FRU) active"
  --#TYPE         "ID PROM (FRU) active"
  --#SUMMARY      "%s"
  --#ARGUMENTS    { 1 }
  --#SEVERITY     INFORMATIONAL
  --#TIMEINDEX    1
  --#HELP         "Note: This is no error condition."
  --#HELPTAG      0
  --#STATE        OPERATIONAL
  ::=  2912004 

wfmIDPROMFRUConnectionLost TRAP-TYPE
  ENTERPRISE wfmTrapInfo
  VARIABLES {
    wfmTrapDetails,
    wfmTrapType
  }
  DESCRIPTION
  "ID PROM (FRU) connection lost"
  --#TYPE         "ID PROM (FRU) connection lost"
  --#SUMMARY      "%s"
  --#ARGUMENTS    { 1 }
  --#SEVERITY     MAJOR
  --#TIMEINDEX    1
  --#HELPTAG      0
  --#STATE        OPERATIONAL
  ::=  2912007 

wfmI2CErrorsBelowWarningLevelLNCGL TRAP-TYPE
  ENTERPRISE wfmTrapInfo
  VARIABLES {
    wfmTrapDetails,
    wfmTrapType
  }
  DESCRIPTION
  "I2C Errors below warning level  (lower non critical going low)."
  --#TYPE         "I2C Errors below warning level (LNC_GL)"
  --#SUMMARY      "%s"
  --#ARGUMENTS    { 1 }
  --#SEVERITY     MAJOR
  --#TIMEINDEX    1
  --#HELPTAG      0
  --#STATE        OPERATIONAL
  ::=  12583168 

wfmI2CErrorsOKLNCGH TRAP-TYPE
  ENTERPRISE wfmTrapInfo
  VARIABLES {
    wfmTrapDetails,
    wfmTrapType
  }
  DESCRIPTION
  "I2C Errors OK (lower non critical going high)."
  --#TYPE         "I2C Errors OK (LNC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  12583169 

wfmI2CErrorsBelowCriticalLevelLCGL TRAP-TYPE
  ENTERPRISE wfmTrapInfo
  VARIABLES {
    wfmTrapDetails,
    wfmTrapType
  }
  DESCRIPTION
  "I2C Errors below critical level	 (lower critical going low)."
  --#TYPE         "I2C Errors below critical level	 (LC_GL)"
  --#SUMMARY      "%s"
  --#ARGUMENTS    { 1 }
  --#SEVERITY     CRITICAL
  --#TIMEINDEX    1
  --#HELPTAG      0
  --#STATE        OPERATIONAL
  ::=  12583170 

wfmI2CErrorsBelowWarningLevelLCGH TRAP-TYPE
  ENTERPRISE wfmTrapInfo
  VARIABLES {
    wfmTrapDetails,
    wfmTrapType
  }
  DESCRIPTION
  "I2C Errors below warning level   (lower critical going high)."
  --#TYPE         "I2C Errors below warning level (LC_GH)"
  --#SUMMARY      "%s"
  --#ARGUMENTS    { 1 }
  --#SEVERITY     INFORMATIONAL
  --#TIMEINDEX    1
  --#HELP         "Note: This is no error condition."
  --#HELPTAG      0
  --#STATE        OPERATIONAL
  ::=  12583171 

wfmI2CErrorsBelowDamageLevelLNRGL TRAP-TYPE
  ENTERPRISE wfmTrapInfo
  VARIABLES {
    wfmTrapDetails,
    wfmTrapType
  }
  DESCRIPTION
  "I2C Errors below damage level (lower non recover going low)."
  --#TYPE         "I2C Errors below damage level (LNR_GL)"
  --#SUMMARY      "%s"
  --#ARGUMENTS    { 1 }
  --#SEVERITY     CRITICAL
  --#TIMEINDEX    1
  --#HELPTAG      0
  --#STATE        OPERATIONAL
  ::=  12583172 

wfmI2CErrorsBelowCriticalLevelLNRGH TRAP-TYPE
  ENTERPRISE wfmTrapInfo
  VARIABLES {
    wfmTrapDetails,
    wfmTrapType
  }
  DESCRIPTION
  "I2C Errors below critical level  (lower non recover going high)."
  --#TYPE         "I2C Errors below critical level (LNR_GH)"
  --#SUMMARY      "%s"
  --#ARGUMENTS    { 1 }
  --#SEVERITY     CRITICAL
  --#TIMEINDEX    1
  --#HELPTAG      0
  --#STATE        OPERATIONAL
  ::=  12583173 

wfmI2CErrorsOKUNCGL TRAP-TYPE
  ENTERPRISE wfmTrapInfo
  VARIABLES {
    wfmTrapDetails,
    wfmTrapType
  }
  DESCRIPTION
  "I2C Errors OK (upper non critical going low)."
  --#TYPE         "I2C Errors OK (UNC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  12583174 

wfmI2CErrorsAboveWarningLevelUNCGH TRAP-TYPE
  ENTERPRISE wfmTrapInfo
  VARIABLES {
    wfmTrapDetails,
    wfmTrapType
  }
  DESCRIPTION
  "I2C Errors above warning level   (upper non critical going high)."
  --#TYPE         "I2C Errors above warning level (UNC_GH)"
  --#SUMMARY      "%s"
  --#ARGUMENTS    { 1 }
  --#SEVERITY     MAJOR
  --#TIMEINDEX    1
  --#HELPTAG      0
  --#STATE        OPERATIONAL
  ::=  12583175 

wfmI2CErrorsAboveWarningLevelUCGL TRAP-TYPE
  ENTERPRISE wfmTrapInfo
  VARIABLES {
    wfmTrapDetails,
    wfmTrapType
  }
  DESCRIPTION
  "I2C Errors above warning level   (upper critical going low)."
  --#TYPE         "I2C Errors above warning level (UC_GL)"
  --#SUMMARY      "%s"
  --#ARGUMENTS    { 1 }
  --#SEVERITY     INFORMATIONAL
  --#TIMEINDEX    1
  --#HELP         "Note: This is no error condition."
  --#HELPTAG      0
  --#STATE        OPERATIONAL
  ::=  12583176 

wfmI2CErrorsAboveCriticalLevelUCGH TRAP-TYPE
  ENTERPRISE wfmTrapInfo
  VARIABLES {
    wfmTrapDetails,
    wfmTrapType
  }
  DESCRIPTION
  "I2C Errors above critical level	 (upper critical going high)."
  --#TYPE         "I2C Errors above critical level	 (UC_GH)"
  --#SUMMARY      "%s"
  --#ARGUMENTS    { 1 }
  --#SEVERITY     CRITICAL
  --#TIMEINDEX    1
  --#HELPTAG      0
  --#STATE        OPERATIONAL
  ::=  12583177 

wfmI2CErrorsAboveCriticalLevelUNRGL TRAP-TYPE
  ENTERPRISE wfmTrapInfo
  VARIABLES {
    wfmTrapDetails,
    wfmTrapType
  }
  DESCRIPTION
  "I2C Errors above critical level	 (upper non recover going low)."
  --#TYPE         "I2C Errors above critical level	 (UNR_GL)"
  --#SUMMARY      "%s"
  --#ARGUMENTS    { 1 }
  --#SEVERITY     CRITICAL
  --#TIMEINDEX    1
  --#HELPTAG      0
  --#STATE        OPERATIONAL
  ::=  12583178 

wfmI2CErrorsAboveDamageLevelUNRGH TRAP-TYPE
  ENTERPRISE wfmTrapInfo
  VARIABLES {
    wfmTrapDetails,
    wfmTrapType
  }
  DESCRIPTION
  "I2C Errors above damage level   (upper non recover going high)."
  --#TYPE         "I2C Errors above damage level (UNR_GH)"
  --#SUMMARY      "%s"
  --#ARGUMENTS    { 1 }
  --#SEVERITY     CRITICAL
  --#TIMEINDEX    1
  --#HELPTAG      0
  --#STATE        OPERATIONAL
  ::=  12583179 

wfmI2CErrorsOKLNCGL TRAP-TYPE
  ENTERPRISE wfmTrapInfo
  VARIABLES {
    wfmTrapDetails,
    wfmTrapType
  }
  DESCRIPTION
  "I2C Errors OK (lower non critical going low de-asserted)."
  --#TYPE         "I2C Errors OK (LNC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  12583296 

wfmI2CErrorsBelowWarningLevelLNCGH TRAP-TYPE
  ENTERPRISE wfmTrapInfo
  VARIABLES {
    wfmTrapDetails,
    wfmTrapType
  }
  DESCRIPTION
  "I2C Errors below warning level  (lower non critical going high de-asserted)."
  --#TYPE         "I2C Errors below warning level (LNC_GHD)"
  --#SUMMARY      "%s"
  --#ARGUMENTS    { 1 }
  --#SEVERITY     MAJOR
  --#TIMEINDEX    1
  --#HELPTAG      0
  --#STATE        OPERATIONAL
  ::=  12583297 

wfmI2CErrorsBelowWarningLevelLCGL TRAP-TYPE
  ENTERPRISE wfmTrapInfo
  VARIABLES {
    wfmTrapDetails,
    wfmTrapType
  }
  DESCRIPTION
  "I2C Errors below warning level   (lower critical going low de-asserted)."
  --#TYPE         "I2C Errors below warning level (LC_GLD)"
  --#SUMMARY      "%s"
  --#ARGUMENTS    { 1 }
  --#SEVERITY     INFORMATIONAL
  --#TIMEINDEX    1
  --#HELP         "Note: This is no error condition."
  --#HELPTAG      0
  --#STATE        OPERATIONAL
  ::=  12583298 

wfmI2CErrorsBelowCriticalLevelLCGH TRAP-TYPE
  ENTERPRISE wfmTrapInfo
  VARIABLES {
    wfmTrapDetails,
    wfmTrapType
  }
  DESCRIPTION
  "I2C Errors below critical level  (lower critical going high de-asserted)."
  --#TYPE         "I2C Errors below critical level (LC_GHD)"
  --#SUMMARY      "%s"
  --#ARGUMENTS    { 1 }
  --#SEVERITY     CRITICAL
  --#TIMEINDEX    1
  --#HELPTAG      0
  --#STATE        OPERATIONAL
  ::=  12583299 

wfmI2CErrorsBelowCriticalLevelLNRGL TRAP-TYPE
  ENTERPRISE wfmTrapInfo
  VARIABLES {
    wfmTrapDetails,
    wfmTrapType
  }
  DESCRIPTION
  "I2C Errors below critical level  (lower non recover going low de-asserted)."
  --#TYPE         "I2C Errors below critical level (LNR_GLD)"
  --#SUMMARY      "%s"
  --#ARGUMENTS    { 1 }
  --#SEVERITY     CRITICAL
  --#TIMEINDEX    1
  --#HELPTAG      0
  --#STATE        OPERATIONAL
  ::=  12583300 

wfmI2CErrorsBelowDamageLevelLNRGH TRAP-TYPE
  ENTERPRISE wfmTrapInfo
  VARIABLES {
    wfmTrapDetails,
    wfmTrapType
  }
  DESCRIPTION
  "I2C Errors below damage level  (lower non recover going high de-asserted)."
  --#TYPE         "I2C Errors below damage level (LNR_GHD)"
  --#SUMMARY      "%s"
  --#ARGUMENTS    { 1 }
  --#SEVERITY     CRITICAL
  --#TIMEINDEX    1
  --#HELPTAG      0
  --#STATE        OPERATIONAL
  ::=  12583301 

wfmI2CErrorsAboveWarningLevelUNCGL TRAP-TYPE
  ENTERPRISE wfmTrapInfo
  VARIABLES {
    wfmTrapDetails,
    wfmTrapType
  }
  DESCRIPTION
  "I2C Errors above warning level  (upper non critical going low de-asserted)."
  --#TYPE         "I2C Errors above warning level (UNC_GLD)"
  --#SUMMARY      "%s"
  --#ARGUMENTS    { 1 }
  --#SEVERITY     MAJOR
  --#TIMEINDEX    1
  --#HELPTAG      0
  --#STATE        OPERATIONAL
  ::=  12583302 

wfmI2CErrorsOKUNCGH TRAP-TYPE
  ENTERPRISE wfmTrapInfo
  VARIABLES {
    wfmTrapDetails,
    wfmTrapType
  }
  DESCRIPTION
  "I2C Errors OK (upper non critical going high de-asserted)."
  --#TYPE         "I2C Errors OK (UNC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  12583303 

wfmI2CErrorsAboveCriticalLevelUCGL TRAP-TYPE
  ENTERPRISE wfmTrapInfo
  VARIABLES {
    wfmTrapDetails,
    wfmTrapType
  }
  DESCRIPTION
  "I2C Errors above critical level	 (upper critical going low de-asserted)."
  --#TYPE         "I2C Errors above critical level	 (UC_GLD)"
  --#SUMMARY      "%s"
  --#ARGUMENTS    { 1 }
  --#SEVERITY     CRITICAL
  --#TIMEINDEX    1
  --#HELPTAG      0
  --#STATE        OPERATIONAL
  ::=  12583304 

wfmI2CErrorsAboveWarningLevelUCGH TRAP-TYPE
  ENTERPRISE wfmTrapInfo
  VARIABLES {
    wfmTrapDetails,
    wfmTrapType
  }
  DESCRIPTION
  "I2C Errors above warning level   (upper critical going high de-asserted)."
  --#TYPE         "I2C Errors above warning level (UC_GHD)"
  --#SUMMARY      "%s"
  --#ARGUMENTS    { 1 }
  --#SEVERITY     INFORMATIONAL
  --#TIMEINDEX    1
  --#HELP         "Note: This is no error condition."
  --#HELPTAG      0
  --#STATE        OPERATIONAL
  ::=  12583305 

wfmI2CErrorsAboveDamageLevelUNRGL TRAP-TYPE
  ENTERPRISE wfmTrapInfo
  VARIABLES {
    wfmTrapDetails,
    wfmTrapType
  }
  DESCRIPTION
  "I2C Errors above damage level  (upper non recover going low de-asserted)."
  --#TYPE         "I2C Errors above damage level (UNR_GLD)"
  --#SUMMARY      "%s"
  --#ARGUMENTS    { 1 }
  --#SEVERITY     CRITICAL
  --#TIMEINDEX    1
  --#HELPTAG      0
  --#STATE        OPERATIONAL
  ::=  12583306 

wfmI2CErrorsAboveCriticalLevelUNRGH TRAP-TYPE
  ENTERPRISE wfmTrapInfo
  VARIABLES {
    wfmTrapDetails,
    wfmTrapType
  }
  DESCRIPTION
  "I2C Errors above critical level	 (upper non recover going high de-asserted)."
  --#TYPE         "I2C Errors above critical level	 (UNR_GHD)"
  --#SUMMARY      "%s"
  --#ARGUMENTS    { 1 }
  --#SEVERITY     CRITICAL
  --#TIMEINDEX    1
  --#HELPTAG      0
  --#STATE        OPERATIONAL
  ::=  12583307 

wfmI2CBusError TRAP-TYPE
  ENTERPRISE wfmTrapInfo
  VARIABLES {
    wfmTrapDetails,
    wfmTrapType
  }
  DESCRIPTION
  "I2C Bus Error."
  --#TYPE         "I2C Bus Error"
  --#SUMMARY      "%s"
  --#ARGUMENTS    { 1 }
  --#SEVERITY     MAJOR
  --#TIMEINDEX    1
  --#HELPTAG      0
  --#STATE        OPERATIONAL
  ::=  12611328 

wfmI2CBusOK TRAP-TYPE
  ENTERPRISE wfmTrapInfo
  VARIABLES {
    wfmTrapDetails,
    wfmTrapType
  }
  DESCRIPTION
  "I2C Bus OK."
  --#TYPE         "I2C Bus OK"
  --#SUMMARY      "%s"
  --#ARGUMENTS    { 1 }
  --#SEVERITY     INFORMATIONAL
  --#TIMEINDEX    1
  --#HELP         "Note: This is no error condition."
  --#HELPTAG      0
  --#STATE        OPERATIONAL
  ::=  12611329 

wfmI2CBusDisabled TRAP-TYPE
  ENTERPRISE wfmTrapInfo
  VARIABLES {
    wfmTrapDetails,
    wfmTrapType
  }
  DESCRIPTION
  "I2C Bus Disabled."
  --#TYPE         "I2C Bus Disabled"
  --#SUMMARY      "%s"
  --#ARGUMENTS    { 1 }
  --#SEVERITY     INFORMATIONAL
  --#TIMEINDEX    1
  --#HELP         "Note: This is no error condition."
  --#HELPTAG      0
  --#STATE        OPERATIONAL
  ::=  12611330 

wfmI2CBusFailed TRAP-TYPE
  ENTERPRISE wfmTrapInfo
  VARIABLES {
    wfmTrapDetails,
    wfmTrapType
  }
  DESCRIPTION
  "I2C Bus Failed."
  --#TYPE         "I2C Bus Failed"
  --#SUMMARY      "%s"
  --#ARGUMENTS    { 1 }
  --#SEVERITY     MAJOR
  --#TIMEINDEX    1
  --#HELPTAG      0
  --#STATE        OPERATIONAL
  ::=  12611331 

wfmBladeI2CBusError TRAP-TYPE
  ENTERPRISE wfmTrapInfo
  VARIABLES {
    wfmTrapDetails,
    wfmTrapType
  }
  DESCRIPTION
  "Blade I2C Bus Error."
  --#TYPE         "Blade I2C Bus Error"
  --#SUMMARY      "%s"
  --#ARGUMENTS    { 1 }
  --#SEVERITY     MAJOR
  --#TIMEINDEX    1
  --#HELPTAG      0
  --#STATE        OPERATIONAL
  ::=  12611584 

wfmOEMEventlogEntryC1StateDeAsserted TRAP-TYPE
  ENTERPRISE wfmTrapInfo
  VARIABLES {
    wfmTrapDetails,
    wfmTrapType
  }
  DESCRIPTION
  "OEM Eventlog Entry (C1): State DeAsserted ."
  --#TYPE         "OEM Eventlog Entry (C1): State DeAsserted"
  --#SUMMARY      "%s"
  --#ARGUMENTS    { 1 }
  --#SEVERITY     INFORMATIONAL
  --#TIMEINDEX    1
  --#HELP         "Note: This is no error condition."
  --#HELPTAG      0
  --#STATE        OPERATIONAL
  ::=  12649216 

wfmOEMEventlogEntryC1StateAsserted TRAP-TYPE
  ENTERPRISE wfmTrapInfo
  VARIABLES {
    wfmTrapDetails,
    wfmTrapType
  }
  DESCRIPTION
  "OEM Eventlog Entry (C1): State Asserted   ."
  --#TYPE         "OEM Eventlog Entry (C1): State Asserted"
  --#SUMMARY      "%s"
  --#ARGUMENTS    { 1 }
  --#SEVERITY     INFORMATIONAL
  --#TIMEINDEX    1
  --#HELP         "Note: This is no error condition."
  --#HELPTAG      0
  --#STATE        OPERATIONAL
  ::=  12649217 

wfmOEMEventlogEntryC1 TRAP-TYPE
  ENTERPRISE wfmTrapInfo
  VARIABLES {
    wfmTrapDetails,
    wfmTrapType
  }
  DESCRIPTION
  "OEM Eventlog Entry (C1):."
  --#TYPE         "OEM Eventlog Entry (C1)"
  --#SUMMARY      "%s"
  --#ARGUMENTS    { 1 }
  --#SEVERITY     INFORMATIONAL
  --#TIMEINDEX    1
  --#HELP         "Note: This is no error condition."
  --#HELPTAG      0
  --#STATE        OPERATIONAL
  ::=  12676864 

wfmOEMEventlogEntryC2 TRAP-TYPE
  ENTERPRISE wfmTrapInfo
  VARIABLES {
    wfmTrapDetails,
    wfmTrapType
  }
  DESCRIPTION
  "OEM Eventlog Entry (C2):."
  --#TYPE         "OEM Eventlog Entry (C2)"
  --#SUMMARY      "%s"
  --#ARGUMENTS    { 1 }
  --#SEVERITY     INFORMATIONAL
  --#TIMEINDEX    1
  --#HELP         "Note: This is no error condition."
  --#HELPTAG      0
  --#STATE        OPERATIONAL
  ::=  12742400 

wfmOEMEventlogEntryC3StateDeAsserted TRAP-TYPE
  ENTERPRISE wfmTrapInfo
  VARIABLES {
    wfmTrapDetails,
    wfmTrapType
  }
  DESCRIPTION
  "OEM Eventlog Entry (C3): State DeAsserted ."
  --#TYPE         "OEM Eventlog Entry (C3): State DeAsserted"
  --#SUMMARY      "%s"
  --#ARGUMENTS    { 1 }
  --#SEVERITY     INFORMATIONAL
  --#TIMEINDEX    1
  --#HELP         "Note: This is no error condition."
  --#HELPTAG      0
  --#STATE        OPERATIONAL
  ::=  12780288 

wfmOEMEventlogEntryC3StateAsserted TRAP-TYPE
  ENTERPRISE wfmTrapInfo
  VARIABLES {
    wfmTrapDetails,
    wfmTrapType
  }
  DESCRIPTION
  "OEM Eventlog Entry (C3): State Asserted   ."
  --#TYPE         "OEM Eventlog Entry (C3): State Asserted"
  --#SUMMARY      "%s"
  --#ARGUMENTS    { 1 }
  --#SEVERITY     INFORMATIONAL
  --#TIMEINDEX    1
  --#HELP         "Note: This is no error condition."
  --#HELPTAG      0
  --#STATE        OPERATIONAL
  ::=  12780289 

wfmOEMEventlogEntryC3 TRAP-TYPE
  ENTERPRISE wfmTrapInfo
  VARIABLES {
    wfmTrapDetails,
    wfmTrapType
  }
  DESCRIPTION
  "OEM Eventlog Entry (C3):."
  --#TYPE         "OEM Eventlog Entry (C3)"
  --#SUMMARY      "%s"
  --#ARGUMENTS    { 1 }
  --#SEVERITY     INFORMATIONAL
  --#TIMEINDEX    1
  --#HELP         "Note: This is no error condition."
  --#HELPTAG      0
  --#STATE        OPERATIONAL
  ::=  12807936 

wfmOEMEventlogEntryC4 TRAP-TYPE
  ENTERPRISE wfmTrapInfo
  VARIABLES {
    wfmTrapDetails,
    wfmTrapType
  }
  DESCRIPTION
  "OEM Eventlog Entry (C4):."
  --#TYPE         "OEM Eventlog Entry (C4)"
  --#SUMMARY      "%s"
  --#ARGUMENTS    { 1 }
  --#SEVERITY     INFORMATIONAL
  --#TIMEINDEX    1
  --#HELP         "Note: This is no error condition."
  --#HELPTAG      0
  --#STATE        OPERATIONAL
  ::=  12873472 

wfmOEMEventlogEntryC5 TRAP-TYPE
  ENTERPRISE wfmTrapInfo
  VARIABLES {
    wfmTrapDetails,
    wfmTrapType
  }
  DESCRIPTION
  "OEM Eventlog Entry (C5):."
  --#TYPE         "OEM Eventlog Entry (C5)"
  --#SUMMARY      "%s"
  --#ARGUMENTS    { 1 }
  --#SEVERITY     INFORMATIONAL
  --#TIMEINDEX    1
  --#HELP         "Note: This is no error condition."
  --#HELPTAG      0
  --#STATE        OPERATIONAL
  ::=  12939008 

wfmOEMEventlogEntryC6 TRAP-TYPE
  ENTERPRISE wfmTrapInfo
  VARIABLES {
    wfmTrapDetails,
    wfmTrapType
  }
  DESCRIPTION
  "OEM Eventlog Entry (C6):."
  --#TYPE         "OEM Eventlog Entry (C6)"
  --#SUMMARY      "%s"
  --#ARGUMENTS    { 1 }
  --#SEVERITY     INFORMATIONAL
  --#TIMEINDEX    1
  --#HELP         "Note: This is no error condition."
  --#HELPTAG      0
  --#STATE        OPERATIONAL
  ::=  13004544 

wfmOEMEventlogEntryC7 TRAP-TYPE
  ENTERPRISE wfmTrapInfo
  VARIABLES {
    wfmTrapDetails,
    wfmTrapType
  }
  DESCRIPTION
  "OEM Eventlog Entry (C7):."
  --#TYPE         "OEM Eventlog Entry (C7)"
  --#SUMMARY      "%s"
  --#ARGUMENTS    { 1 }
  --#SEVERITY     INFORMATIONAL
  --#TIMEINDEX    1
  --#HELP         "Note: This is no error condition."
  --#HELPTAG      0
  --#STATE        OPERATIONAL
  ::=  13070080 

wfmConsecutiveIllegalRemoteManagementLogins TRAP-TYPE
  ENTERPRISE wfmTrapInfo
  VARIABLES {
    wfmTrapDetails,
    wfmTrapType
  }
  DESCRIPTION
  "Consecutive illegal remote management logins."
  --#TYPE         "Consecutive illegal remote management logins"
  --#SUMMARY      "%s"
  --#ARGUMENTS    { 1 }
  --#SEVERITY     MAJOR
  --#TIMEINDEX    1
  --#HELPTAG      0
  --#STATE        OPERATIONAL
  ::=  13135616 

wfmRemoteManagementUserLogin TRAP-TYPE
  ENTERPRISE wfmTrapInfo
  VARIABLES {
    wfmTrapDetails,
    wfmTrapType
  }
  DESCRIPTION
  "Remote management user login."
  --#TYPE         "Remote management user login"
  --#SUMMARY      "%s"
  --#ARGUMENTS    { 1 }
  --#SEVERITY     INFORMATIONAL
  --#TIMEINDEX    1
  --#HELP         "Note: This is no error condition."
  --#HELPTAG      0
  --#STATE        OPERATIONAL
  ::=  13135617 

wfmRemoteManagementUserLogout TRAP-TYPE
  ENTERPRISE wfmTrapInfo
  VARIABLES {
    wfmTrapDetails,
    wfmTrapType
  }
  DESCRIPTION
  "Remote management user logout."
  --#TYPE         "Remote management user logout"
  --#SUMMARY      "%s"
  --#ARGUMENTS    { 1 }
  --#SEVERITY     INFORMATIONAL
  --#TIMEINDEX    1
  --#HELP         "Note: This is no error condition."
  --#HELPTAG      0
  --#STATE        OPERATIONAL
  ::=  13135618 

wfmRemoteManagementUserAutologout TRAP-TYPE
  ENTERPRISE wfmTrapInfo
  VARIABLES {
    wfmTrapDetails,
    wfmTrapType
  }
  DESCRIPTION
  "Remote management user auto-logout."
  --#TYPE         "Remote management user auto-logout"
  --#SUMMARY      "%s"
  --#ARGUMENTS    { 1 }
  --#SEVERITY     INFORMATIONAL
  --#TIMEINDEX    1
  --#HELP         "Note: This is no error condition."
  --#HELPTAG      0
  --#STATE        OPERATIONAL
  ::=  13135619 

wfmRemoteManagementUserConnectionLost TRAP-TYPE
  ENTERPRISE wfmTrapInfo
  VARIABLES {
    wfmTrapDetails,
    wfmTrapType
  }
  DESCRIPTION
  "Remote management user connection lost."
  --#TYPE         "Remote management user connection lost"
  --#SUMMARY      "%s"
  --#ARGUMENTS    { 1 }
  --#SEVERITY     INFORMATIONAL
  --#TIMEINDEX    1
  --#HELP         "Note: This is no error condition."
  --#HELPTAG      0
  --#STATE        OPERATIONAL
  ::=  13135620 

wfmRemoteManagementUserDialbackFailed TRAP-TYPE
  ENTERPRISE wfmTrapInfo
  VARIABLES {
    wfmTrapDetails,
    wfmTrapType
  }
  DESCRIPTION
  "Remote management user dialback failed."
  --#TYPE         "Remote management user dialback failed"
  --#SUMMARY      "%s"
  --#ARGUMENTS    { 1 }
  --#SEVERITY     INFORMATIONAL
  --#TIMEINDEX    1
  --#HELP         "Note: This is no error condition."
  --#HELPTAG      0
  --#STATE        OPERATIONAL
  ::=  13135621 

wfmRemoteManagementUserLoginFailed TRAP-TYPE
  ENTERPRISE wfmTrapInfo
  VARIABLES {
    wfmTrapDetails,
    wfmTrapType
  }
  DESCRIPTION
  "Remote management user login failed."
  --#TYPE         "Remote management user login failed"
  --#SUMMARY      "%s"
  --#ARGUMENTS    { 1 }
  --#SEVERITY     MINOR
  --#TIMEINDEX    1
  --#HELPTAG      0
  --#STATE        OPERATIONAL
  ::=  13135622 

wfmRemoteManagementUserPublicKeyLoginFailed TRAP-TYPE
  ENTERPRISE wfmTrapInfo
  VARIABLES {
    wfmTrapDetails,
    wfmTrapType
  }
  DESCRIPTION
  "Remote management user Public Key login failed."
  --#TYPE         "Remote management user Public Key login failed"
  --#SUMMARY      "%s"
  --#ARGUMENTS    { 1 }
  --#SEVERITY     MINOR
  --#TIMEINDEX    1
  --#HELPTAG      0
  --#STATE        OPERATIONAL
  ::=  13135623 

wfmCLITelnetConsecutiveIllegalLogins TRAP-TYPE
  ENTERPRISE wfmTrapInfo
  VARIABLES {
    wfmTrapDetails,
    wfmTrapType
  }
  DESCRIPTION
  "CLI/Telnet consecutive illegal logins."
  --#TYPE         "CLI/Telnet consecutive illegal logins"
  --#SUMMARY      "%s"
  --#ARGUMENTS    { 1 }
  --#SEVERITY     MAJOR
  --#TIMEINDEX    1
  --#HELPTAG      0
  --#STATE        OPERATIONAL
  ::=  13135624 

wfmCLITelnetUserLogin TRAP-TYPE
  ENTERPRISE wfmTrapInfo
  VARIABLES {
    wfmTrapDetails,
    wfmTrapType
  }
  DESCRIPTION
  "CLI/Telnet user login."
  --#TYPE         "CLI/Telnet user login"
  --#SUMMARY      "%s"
  --#ARGUMENTS    { 1 }
  --#SEVERITY     INFORMATIONAL
  --#TIMEINDEX    1
  --#HELP         "Note: This is no error condition."
  --#HELPTAG      0
  --#STATE        OPERATIONAL
  ::=  13135625 

wfmCLITelnetUserLogout TRAP-TYPE
  ENTERPRISE wfmTrapInfo
  VARIABLES {
    wfmTrapDetails,
    wfmTrapType
  }
  DESCRIPTION
  "CLI/Telnet user logout."
  --#TYPE         "CLI/Telnet user logout"
  --#SUMMARY      "%s"
  --#ARGUMENTS    { 1 }
  --#SEVERITY     INFORMATIONAL
  --#TIMEINDEX    1
  --#HELP         "Note: This is no error condition."
  --#HELPTAG      0
  --#STATE        OPERATIONAL
  ::=  13135626 

wfmCLITelnetUserAutologout TRAP-TYPE
  ENTERPRISE wfmTrapInfo
  VARIABLES {
    wfmTrapDetails,
    wfmTrapType
  }
  DESCRIPTION
  "CLI/Telnet user auto-logout."
  --#TYPE         "CLI/Telnet user auto-logout"
  --#SUMMARY      "%s"
  --#ARGUMENTS    { 1 }
  --#SEVERITY     INFORMATIONAL
  --#TIMEINDEX    1
  --#HELP         "Note: This is no error condition."
  --#HELPTAG      0
  --#STATE        OPERATIONAL
  ::=  13135627 

wfmCLITelnetUserConnectionLost TRAP-TYPE
  ENTERPRISE wfmTrapInfo
  VARIABLES {
    wfmTrapDetails,
    wfmTrapType
  }
  DESCRIPTION
  "CLI/Telnet user connection lost."
  --#TYPE         "CLI/Telnet user connection lost"
  --#SUMMARY      "%s"
  --#ARGUMENTS    { 1 }
  --#SEVERITY     INFORMATIONAL
  --#TIMEINDEX    1
  --#HELP         "Note: This is no error condition."
  --#HELPTAG      0
  --#STATE        OPERATIONAL
  ::=  13135628 

wfmCLITelnetUserDialbackFailed TRAP-TYPE
  ENTERPRISE wfmTrapInfo
  VARIABLES {
    wfmTrapDetails,
    wfmTrapType
  }
  DESCRIPTION
  "CLI/Telnet user dialback failed."
  --#TYPE         "CLI/Telnet user dialback failed"
  --#SUMMARY      "%s"
  --#ARGUMENTS    { 1 }
  --#SEVERITY     INFORMATIONAL
  --#TIMEINDEX    1
  --#HELP         "Note: This is no error condition."
  --#HELPTAG      0
  --#STATE        OPERATIONAL
  ::=  13135629 

wfmCLITelnetUserLoginFailed TRAP-TYPE
  ENTERPRISE wfmTrapInfo
  VARIABLES {
    wfmTrapDetails,
    wfmTrapType
  }
  DESCRIPTION
  "CLI/Telnet user login failed."
  --#TYPE         "CLI/Telnet user login failed"
  --#SUMMARY      "%s"
  --#ARGUMENTS    { 1 }
  --#SEVERITY     MINOR
  --#TIMEINDEX    1
  --#HELPTAG      0
  --#STATE        OPERATIONAL
  ::=  13135630 

wfmCLISSHPublicKeyLoginFailed TRAP-TYPE
  ENTERPRISE wfmTrapInfo
  VARIABLES {
    wfmTrapDetails,
    wfmTrapType
  }
  DESCRIPTION
  "CLI/SSH Public Key login failed."
  --#TYPE         "CLI/SSH Public Key login failed"
  --#SUMMARY      "%s"
  --#ARGUMENTS    { 1 }
  --#SEVERITY     MINOR
  --#TIMEINDEX    1
  --#HELPTAG      0
  --#STATE        OPERATIONAL
  ::=  13135631 

wfmAVRSessionStarted TRAP-TYPE
  ENTERPRISE wfmTrapInfo
  VARIABLES {
    wfmTrapDetails,
    wfmTrapType
  }
  DESCRIPTION
  "AVR Session started."
  --#TYPE         "AVR Session started"
  --#SUMMARY      "%s"
  --#ARGUMENTS    { 1 }
  --#SEVERITY     INFORMATIONAL
  --#TIMEINDEX    1
  --#HELP         "Note: This is no error condition."
  --#HELPTAG      0
  --#STATE        OPERATIONAL
  ::=  13135632 

wfmAVRSessionFinished TRAP-TYPE
  ENTERPRISE wfmTrapInfo
  VARIABLES {
    wfmTrapDetails,
    wfmTrapType
  }
  DESCRIPTION
  "AVR Session finished."
  --#TYPE         "AVR Session finished"
  --#SUMMARY      "%s"
  --#ARGUMENTS    { 1 }
  --#SEVERITY     INFORMATIONAL
  --#TIMEINDEX    1
  --#HELP         "Note: This is no error condition."
  --#HELPTAG      0
  --#STATE        OPERATIONAL
  ::=  13135633 

wfmAVRSessionFailedToAuthenticate TRAP-TYPE
  ENTERPRISE wfmTrapInfo
  VARIABLES {
    wfmTrapDetails,
    wfmTrapType
  }
  DESCRIPTION
  "AVR Session failed to authenticate."
  --#TYPE         "AVR Session failed to authenticate"
  --#SUMMARY      "%s"
  --#ARGUMENTS    { 1 }
  --#SEVERITY     MINOR
  --#TIMEINDEX    1
  --#HELPTAG      0
  --#STATE        OPERATIONAL
  ::=  13135634 

wfmAVRSessionWithNoPermission TRAP-TYPE
  ENTERPRISE wfmTrapInfo
  VARIABLES {
    wfmTrapDetails,
    wfmTrapType
  }
  DESCRIPTION
  "AVR Session with no permission."
  --#TYPE         "AVR Session with no permission"
  --#SUMMARY      "%s"
  --#ARGUMENTS    { 1 }
  --#SEVERITY     MINOR
  --#TIMEINDEX    1
  --#HELPTAG      0
  --#STATE        OPERATIONAL
  ::=  13135635 

wfmIRMCBrowserConsecutiveIllegalLogins TRAP-TYPE
  ENTERPRISE wfmTrapInfo
  VARIABLES {
    wfmTrapDetails,
    wfmTrapType
  }
  DESCRIPTION
  "iRMC Browser consecutive illegal logins"
  --#TYPE         "iRMC Browser consecutive illegal logins"
  --#SUMMARY      "%s"
  --#ARGUMENTS    { 1 }
  --#SEVERITY     MAJOR
  --#TIMEINDEX    1
  --#HELPTAG      0
  --#STATE        OPERATIONAL
  ::=  13135872 

wfmIRMCBrowserLogin TRAP-TYPE
  ENTERPRISE wfmTrapInfo
  VARIABLES {
    wfmTrapDetails,
    wfmTrapType
  }
  DESCRIPTION
  "iRMC Browser login"
  --#TYPE         "iRMC Browser login"
  --#SUMMARY      "%s"
  --#ARGUMENTS    { 1 }
  --#SEVERITY     INFORMATIONAL
  --#TIMEINDEX    1
  --#HELP         "Note: This is no error condition."
  --#HELPTAG      0
  --#STATE        OPERATIONAL
  ::=  13135873 

wfmIRMCBrowserLogout TRAP-TYPE
  ENTERPRISE wfmTrapInfo
  VARIABLES {
    wfmTrapDetails,
    wfmTrapType
  }
  DESCRIPTION
  "iRMC Browser logout"
  --#TYPE         "iRMC Browser logout"
  --#SUMMARY      "%s"
  --#ARGUMENTS    { 1 }
  --#SEVERITY     INFORMATIONAL
  --#TIMEINDEX    1
  --#HELP         "Note: This is no error condition."
  --#HELPTAG      0
  --#STATE        OPERATIONAL
  ::=  13135874 

wfmIRMCBrowserAutologout TRAP-TYPE
  ENTERPRISE wfmTrapInfo
  VARIABLES {
    wfmTrapDetails,
    wfmTrapType
  }
  DESCRIPTION
  "iRMC Browser auto-logout"
  --#TYPE         "iRMC Browser auto-logout"
  --#SUMMARY      "%s"
  --#ARGUMENTS    { 1 }
  --#SEVERITY     INFORMATIONAL
  --#TIMEINDEX    1
  --#HELP         "Note: This is no error condition."
  --#HELPTAG      0
  --#STATE        OPERATIONAL
  ::=  13135875 

wfmIRMCBrowserConnectionLostFailed TRAP-TYPE
  ENTERPRISE wfmTrapInfo
  VARIABLES {
    wfmTrapDetails,
    wfmTrapType
  }
  DESCRIPTION
  "iRMC Browser connection lost failed"
  --#TYPE         "iRMC Browser connection lost failed"
  --#SUMMARY      "%s"
  --#ARGUMENTS    { 1 }
  --#SEVERITY     INFORMATIONAL
  --#TIMEINDEX    1
  --#HELP         "Note: This is no error condition."
  --#HELPTAG      0
  --#STATE        OPERATIONAL
  ::=  13135876 

wfmIRMCBrowserDialbackFailed TRAP-TYPE
  ENTERPRISE wfmTrapInfo
  VARIABLES {
    wfmTrapDetails,
    wfmTrapType
  }
  DESCRIPTION
  "iRMC Browser dialback failed"
  --#TYPE         "iRMC Browser dialback failed"
  --#SUMMARY      "%s"
  --#ARGUMENTS    { 1 }
  --#SEVERITY     INFORMATIONAL
  --#TIMEINDEX    1
  --#HELP         "Note: This is no error condition."
  --#HELPTAG      0
  --#STATE        OPERATIONAL
  ::=  13135877 

wfmIRMCBrowserLoginFailed TRAP-TYPE
  ENTERPRISE wfmTrapInfo
  VARIABLES {
    wfmTrapDetails,
    wfmTrapType
  }
  DESCRIPTION
  "iRMC Browser login failed"
  --#TYPE         "iRMC Browser login failed"
  --#SUMMARY      "%s"
  --#ARGUMENTS    { 1 }
  --#SEVERITY     MINOR
  --#TIMEINDEX    1
  --#HELPTAG      0
  --#STATE        OPERATIONAL
  ::=  13135878 

wfmIRMCBrowserPublicKeyLoginFailed TRAP-TYPE
  ENTERPRISE wfmTrapInfo
  VARIABLES {
    wfmTrapDetails,
    wfmTrapType
  }
  DESCRIPTION
  "iRMC Browser Public Key login failed"
  --#TYPE         "iRMC Browser Public Key login failed"
  --#SUMMARY      "%s"
  --#ARGUMENTS    { 1 }
  --#SEVERITY     MINOR
  --#TIMEINDEX    1
  --#HELPTAG      0
  --#STATE        OPERATIONAL
  ::=  13135879 

wfmIRMCCLITelnetConsecutiveIllegalLogins TRAP-TYPE
  ENTERPRISE wfmTrapInfo
  VARIABLES {
    wfmTrapDetails,
    wfmTrapType
  }
  DESCRIPTION
  "iRMC CLI/Telnet consecutive illegal logins"
  --#TYPE         "iRMC CLI/Telnet consecutive illegal logins"
  --#SUMMARY      "%s"
  --#ARGUMENTS    { 1 }
  --#SEVERITY     MAJOR
  --#TIMEINDEX    1
  --#HELPTAG      0
  --#STATE        OPERATIONAL
  ::=  13136128 

wfmIRMCCLITelnetLogin TRAP-TYPE
  ENTERPRISE wfmTrapInfo
  VARIABLES {
    wfmTrapDetails,
    wfmTrapType
  }
  DESCRIPTION
  "iRMC CLI/Telnet login"
  --#TYPE         "iRMC CLI/Telnet login"
  --#SUMMARY      "%s"
  --#ARGUMENTS    { 1 }
  --#SEVERITY     INFORMATIONAL
  --#TIMEINDEX    1
  --#HELP         "Note: This is no error condition."
  --#HELPTAG      0
  --#STATE        OPERATIONAL
  ::=  13136129 

wfmIRMCCLITelnetLogout TRAP-TYPE
  ENTERPRISE wfmTrapInfo
  VARIABLES {
    wfmTrapDetails,
    wfmTrapType
  }
  DESCRIPTION
  "iRMC CLI/Telnet logout"
  --#TYPE         "iRMC CLI/Telnet logout"
  --#SUMMARY      "%s"
  --#ARGUMENTS    { 1 }
  --#SEVERITY     INFORMATIONAL
  --#TIMEINDEX    1
  --#HELP         "Note: This is no error condition."
  --#HELPTAG      0
  --#STATE        OPERATIONAL
  ::=  13136130 

wfmIRMCCLITelnetAutologout TRAP-TYPE
  ENTERPRISE wfmTrapInfo
  VARIABLES {
    wfmTrapDetails,
    wfmTrapType
  }
  DESCRIPTION
  "iRMC CLI/Telnet auto-logout"
  --#TYPE         "iRMC CLI/Telnet auto-logout"
  --#SUMMARY      "%s"
  --#ARGUMENTS    { 1 }
  --#SEVERITY     INFORMATIONAL
  --#TIMEINDEX    1
  --#HELP         "Note: This is no error condition."
  --#HELPTAG      0
  --#STATE        OPERATIONAL
  ::=  13136131 

wfmIRMCCLITelnetConnectionLost TRAP-TYPE
  ENTERPRISE wfmTrapInfo
  VARIABLES {
    wfmTrapDetails,
    wfmTrapType
  }
  DESCRIPTION
  "iRMC CLI/Telnet connection lost"
  --#TYPE         "iRMC CLI/Telnet connection lost"
  --#SUMMARY      "%s"
  --#ARGUMENTS    { 1 }
  --#SEVERITY     INFORMATIONAL
  --#TIMEINDEX    1
  --#HELP         "Note: This is no error condition."
  --#HELPTAG      0
  --#STATE        OPERATIONAL
  ::=  13136132 

wfmIRMCCLITelnetDialbackFailed TRAP-TYPE
  ENTERPRISE wfmTrapInfo
  VARIABLES {
    wfmTrapDetails,
    wfmTrapType
  }
  DESCRIPTION
  "iRMC CLI/Telnet dialback failed"
  --#TYPE         "iRMC CLI/Telnet dialback failed"
  --#SUMMARY      "%s"
  --#ARGUMENTS    { 1 }
  --#SEVERITY     INFORMATIONAL
  --#TIMEINDEX    1
  --#HELP         "Note: This is no error condition."
  --#HELPTAG      0
  --#STATE        OPERATIONAL
  ::=  13136133 

wfmIRMCCLITelnetLoginFailed TRAP-TYPE
  ENTERPRISE wfmTrapInfo
  VARIABLES {
    wfmTrapDetails,
    wfmTrapType
  }
  DESCRIPTION
  "iRMC CLI/Telnet login failed"
  --#TYPE         "iRMC CLI/Telnet login failed"
  --#SUMMARY      "%s"
  --#ARGUMENTS    { 1 }
  --#SEVERITY     MINOR
  --#TIMEINDEX    1
  --#HELPTAG      0
  --#STATE        OPERATIONAL
  ::=  13136134 

wfmIRMCCLITelnetPublicKeyLoginFailed TRAP-TYPE
  ENTERPRISE wfmTrapInfo
  VARIABLES {
    wfmTrapDetails,
    wfmTrapType
  }
  DESCRIPTION
  "iRMC CLI/Telnet Public Key login failed"
  --#TYPE         "iRMC CLI/Telnet Public Key login failed"
  --#SUMMARY      "%s"
  --#ARGUMENTS    { 1 }
  --#SEVERITY     MINOR
  --#TIMEINDEX    1
  --#HELPTAG      0
  --#STATE        OPERATIONAL
  ::=  13136135 

wfmIRMCAdvancedVideoRedirectionAVRSessionStarted TRAP-TYPE
  ENTERPRISE wfmTrapInfo
  VARIABLES {
    wfmTrapDetails,
    wfmTrapType
  }
  DESCRIPTION
  "iRMC Advanced Video Redirection (AVR) Session started"
  --#TYPE         "iRMC Advanced Video Redirection (AVR) Session started"
  --#SUMMARY      "%s"
  --#ARGUMENTS    { 1 }
  --#SEVERITY     INFORMATIONAL
  --#TIMEINDEX    1
  --#HELP         "Note: This is no error condition."
  --#HELPTAG      0
  --#STATE        OPERATIONAL
  ::=  13139712 

wfmIRMCAdvancedVideoRedirectionAVRSessionFinished TRAP-TYPE
  ENTERPRISE wfmTrapInfo
  VARIABLES {
    wfmTrapDetails,
    wfmTrapType
  }
  DESCRIPTION
  "iRMC Advanced Video Redirection (AVR) Session finished"
  --#TYPE         "iRMC Advanced Video Redirection (AVR) Session finished"
  --#SUMMARY      "%s"
  --#ARGUMENTS    { 1 }
  --#SEVERITY     INFORMATIONAL
  --#TIMEINDEX    1
  --#HELP         "Note: This is no error condition."
  --#HELPTAG      0
  --#STATE        OPERATIONAL
  ::=  13139713 

wfmIRMCAdvancedVideoRedirectionAVRFailedToAuthenticate TRAP-TYPE
  ENTERPRISE wfmTrapInfo
  VARIABLES {
    wfmTrapDetails,
    wfmTrapType
  }
  DESCRIPTION
  "iRMC Advanced Video Redirection (AVR) failed to authenticate"
  --#TYPE         "iRMC Advanced Video Redirection (AVR) failed to authenticate"
  --#SUMMARY      "%s"
  --#ARGUMENTS    { 1 }
  --#SEVERITY     MINOR
  --#TIMEINDEX    1
  --#HELPTAG      0
  --#STATE        OPERATIONAL
  ::=  13139714 

wfmIRMCAdvancedVideoRedirectionAVRWithNoPermission TRAP-TYPE
  ENTERPRISE wfmTrapInfo
  VARIABLES {
    wfmTrapDetails,
    wfmTrapType
  }
  DESCRIPTION
  "iRMC Advanced Video Redirection (AVR) with no permission"
  --#TYPE         "iRMC Advanced Video Redirection (AVR) with no permission"
  --#SUMMARY      "%s"
  --#ARGUMENTS    { 1 }
  --#SEVERITY     MINOR
  --#TIMEINDEX    1
  --#HELPTAG      0
  --#STATE        OPERATIONAL
  ::=  13139715 

wfmRemoteinitiatedCtrlAltDel TRAP-TYPE
  ENTERPRISE wfmTrapInfo
  VARIABLES {
    wfmTrapDetails,
    wfmTrapType
  }
  DESCRIPTION
  "Remote-initiated <Ctrl-Alt-Del>."
  --#TYPE         "Remote-initiated <Ctrl-Alt-Del>"
  --#SUMMARY      "%s"
  --#ARGUMENTS    { 1 }
  --#SEVERITY     INFORMATIONAL
  --#TIMEINDEX    1
  --#HELP         "Note: This is no error condition."
  --#HELPTAG      0
  --#STATE        OPERATIONAL
  ::=  13201152 

wfmRemoteinitiatedReset TRAP-TYPE
  ENTERPRISE wfmTrapInfo
  VARIABLES {
    wfmTrapDetails,
    wfmTrapType
  }
  DESCRIPTION
  "Remote-initiated reset."
  --#TYPE         "Remote-initiated reset"
  --#SUMMARY      "%s"
  --#ARGUMENTS    { 1 }
  --#SEVERITY     INFORMATIONAL
  --#TIMEINDEX    1
  --#HELP         "Note: This is no error condition."
  --#HELPTAG      0
  --#STATE        OPERATIONAL
  ::=  13201153 

wfmRemoteinitiatedPowerCycle TRAP-TYPE
  ENTERPRISE wfmTrapInfo
  VARIABLES {
    wfmTrapDetails,
    wfmTrapType
  }
  DESCRIPTION
  "Remote-initiated power cycle."
  --#TYPE         "Remote-initiated power cycle"
  --#SUMMARY      "%s"
  --#ARGUMENTS    { 1 }
  --#SEVERITY     INFORMATIONAL
  --#TIMEINDEX    1
  --#HELP         "Note: This is no error condition."
  --#HELPTAG      0
  --#STATE        OPERATIONAL
  ::=  13201154 

wfmRemoteinitiatedPowerDown TRAP-TYPE
  ENTERPRISE wfmTrapInfo
  VARIABLES {
    wfmTrapDetails,
    wfmTrapType
  }
  DESCRIPTION
  "Remote-initiated power down."
  --#TYPE         "Remote-initiated power down"
  --#SUMMARY      "%s"
  --#ARGUMENTS    { 1 }
  --#SEVERITY     INFORMATIONAL
  --#TIMEINDEX    1
  --#HELP         "Note: This is no error condition."
  --#HELPTAG      0
  --#STATE        OPERATIONAL
  ::=  13201155 

wfmRemoteinitiatedPowerUp TRAP-TYPE
  ENTERPRISE wfmTrapInfo
  VARIABLES {
    wfmTrapDetails,
    wfmTrapType
  }
  DESCRIPTION
  "Remote-initiated power up."
  --#TYPE         "Remote-initiated power up"
  --#SUMMARY      "%s"
  --#ARGUMENTS    { 1 }
  --#SEVERITY     INFORMATIONAL
  --#TIMEINDEX    1
  --#HELP         "Note: This is no error condition."
  --#HELPTAG      0
  --#STATE        OPERATIONAL
  ::=  13201156 

wfmAutomaticPowerShutdownDueToCriticalCondition TRAP-TYPE
  ENTERPRISE wfmTrapInfo
  VARIABLES {
    wfmTrapDetails,
    wfmTrapType
  }
  DESCRIPTION
  "Automatic power shutdown due to critical condition."
  --#TYPE         "Automatic power shutdown due to critical condition"
  --#SUMMARY      "%s"
  --#ARGUMENTS    { 1 }
  --#SEVERITY     INFORMATIONAL
  --#TIMEINDEX    1
  --#HELP         "Note: This is no error condition."
  --#HELPTAG      0
  --#STATE        OPERATIONAL
  ::=  13201157 

wfmFrontPanelPowerDown TRAP-TYPE
  ENTERPRISE wfmTrapInfo
  VARIABLES {
    wfmTrapDetails,
    wfmTrapType
  }
  DESCRIPTION
  "Front panel power down."
  --#TYPE         "Front panel power down"
  --#SUMMARY      "%s"
  --#ARGUMENTS    { 1 }
  --#SEVERITY     INFORMATIONAL
  --#TIMEINDEX    1
  --#HELP         "Note: This is no error condition."
  --#HELPTAG      0
  --#STATE        OPERATIONAL
  ::=  13201158 

wfmAutomaticGracefulShutdown TRAP-TYPE
  ENTERPRISE wfmTrapInfo
  VARIABLES {
    wfmTrapDetails,
    wfmTrapType
  }
  DESCRIPTION
  "Automatic graceful shutdown."
  --#TYPE         "Automatic graceful shutdown"
  --#SUMMARY      "%s"
  --#ARGUMENTS    { 1 }
  --#SEVERITY     INFORMATIONAL
  --#TIMEINDEX    1
  --#HELP         "Note: This is no error condition."
  --#HELPTAG      0
  --#STATE        OPERATIONAL
  ::=  13201159 

wfmRemoteinitiatedGracefulShutdown TRAP-TYPE
  ENTERPRISE wfmTrapInfo
  VARIABLES {
    wfmTrapDetails,
    wfmTrapType
  }
  DESCRIPTION
  "Remote-initiated graceful shutdown."
  --#TYPE         "Remote-initiated graceful shutdown"
  --#SUMMARY      "%s"
  --#ARGUMENTS    { 1 }
  --#SEVERITY     INFORMATIONAL
  --#TIMEINDEX    1
  --#HELP         "Note: This is no error condition."
  --#HELPTAG      0
  --#STATE        OPERATIONAL
  ::=  13201160 

wfmRemoteinitiatedNMI TRAP-TYPE
  ENTERPRISE wfmTrapInfo
  VARIABLES {
    wfmTrapDetails,
    wfmTrapType
  }
  DESCRIPTION
  "Remote-initiated NMI."
  --#TYPE         "Remote-initiated NMI"
  --#SUMMARY      "%s"
  --#ARGUMENTS    { 1 }
  --#SEVERITY     INFORMATIONAL
  --#TIMEINDEX    1
  --#HELP         "Note: This is no error condition."
  --#HELPTAG      0
  --#STATE        OPERATIONAL
  ::=  13201161 

wfmRemoteinitiatedGracefullShutdown TRAP-TYPE
  ENTERPRISE wfmTrapInfo
  VARIABLES {
    wfmTrapDetails,
    wfmTrapType
  }
  DESCRIPTION
  "Remote-initiated gracefull Shutdown."
  --#TYPE         "Remote-initiated gracefull Shutdown"
  --#SUMMARY      "%s"
  --#ARGUMENTS    { 1 }
  --#SEVERITY     INFORMATIONAL
  --#TIMEINDEX    1
  --#HELP         "Note: This is no error condition."
  --#HELPTAG      0
  --#STATE        OPERATIONAL
  ::=  13201162 

wfmRemoteinitiatedGracefullReboot TRAP-TYPE
  ENTERPRISE wfmTrapInfo
  VARIABLES {
    wfmTrapDetails,
    wfmTrapType
  }
  DESCRIPTION
  "Remote-initiated gracefull Reboot."
  --#TYPE         "Remote-initiated gracefull Reboot"
  --#SUMMARY      "%s"
  --#ARGUMENTS    { 1 }
  --#SEVERITY     INFORMATIONAL
  --#TIMEINDEX    1
  --#HELP         "Note: This is no error condition."
  --#HELPTAG      0
  --#STATE        OPERATIONAL
  ::=  13201163 

wfmPAGINGReserved TRAP-TYPE
  ENTERPRISE wfmTrapInfo
  VARIABLES {
    wfmTrapDetails,
    wfmTrapType
  }
  DESCRIPTION
  "PAGING: reserved"
  --#TYPE         "PAGING: reserved"
  --#SUMMARY      "%s"
  --#ARGUMENTS    { 1 }
  --#SEVERITY     INFORMATIONAL
  --#TIMEINDEX    1
  --#HELP         "Note: This is no error condition."
  --#HELPTAG      0
  --#STATE        OPERATIONAL
  ::=  13266688 

wfmRemoteManagementUserPageModemError TRAP-TYPE
  ENTERPRISE wfmTrapInfo
  VARIABLES {
    wfmTrapDetails,
    wfmTrapType
  }
  DESCRIPTION
  "Remote management user page: Modem error."
  --#TYPE         "Remote management user page: Modem error"
  --#SUMMARY      "%s"
  --#ARGUMENTS    { 1 }
  --#SEVERITY     MAJOR
  --#TIMEINDEX    1
  --#HELPTAG      0
  --#STATE        OPERATIONAL
  ::=  13266689 

wfmRemoteManagementUserPageNoConnection TRAP-TYPE
  ENTERPRISE wfmTrapInfo
  VARIABLES {
    wfmTrapDetails,
    wfmTrapType
  }
  DESCRIPTION
  "Remote management user page: No connection."
  --#TYPE         "Remote management user page: No connection"
  --#SUMMARY      "%s"
  --#ARGUMENTS    { 1 }
  --#SEVERITY     INFORMATIONAL
  --#TIMEINDEX    1
  --#HELP         "Note: This is no error condition."
  --#HELPTAG      0
  --#STATE        OPERATIONAL
  ::=  13266690 

wfmRemoteManagementUserTAPPageNoIDPrompt TRAP-TYPE
  ENTERPRISE wfmTrapInfo
  VARIABLES {
    wfmTrapDetails,
    wfmTrapType
  }
  DESCRIPTION
  "Remote management user TAP page: No ID= prompt."
  --#TYPE         "Remote management user TAP page: No ID= prompt"
  --#SUMMARY      "%s"
  --#ARGUMENTS    { 1 }
  --#SEVERITY     INFORMATIONAL
  --#TIMEINDEX    1
  --#HELP         "Note: This is no error condition."
  --#HELPTAG      0
  --#STATE        OPERATIONAL
  ::=  13266691 

wfmRemoteManagementUserTAPPageNoMessageGoahead TRAP-TYPE
  ENTERPRISE wfmTrapInfo
  VARIABLES {
    wfmTrapDetails,
    wfmTrapType
  }
  DESCRIPTION
  "Remote management user TAP page: No message go-ahead."
  --#TYPE         "Remote management user TAP page: No message go-ahead"
  --#SUMMARY      "%s"
  --#ARGUMENTS    { 1 }
  --#SEVERITY     INFORMATIONAL
  --#TIMEINDEX    1
  --#HELP         "Note: This is no error condition."
  --#HELPTAG      0
  --#STATE        OPERATIONAL
  ::=  13266692 

wfmRemoteManagementUserTAPPageMessageNotAccepted TRAP-TYPE
  ENTERPRISE wfmTrapInfo
  VARIABLES {
    wfmTrapDetails,
    wfmTrapType
  }
  DESCRIPTION
  "Remote management user TAP page: Message not accepted."
  --#TYPE         "Remote management user TAP page: Message not accepted"
  --#SUMMARY      "%s"
  --#ARGUMENTS    { 1 }
  --#SEVERITY     INFORMATIONAL
  --#TIMEINDEX    1
  --#HELP         "Note: This is no error condition."
  --#HELPTAG      0
  --#STATE        OPERATIONAL
  ::=  13266693 

wfmRemoteManagementUserEmailNotificationFailed TRAP-TYPE
  ENTERPRISE wfmTrapInfo
  VARIABLES {
    wfmTrapDetails,
    wfmTrapType
  }
  DESCRIPTION
  "Remote management user Email notification failed."
  --#TYPE         "Remote management user Email notification failed"
  --#SUMMARY      "%s"
  --#ARGUMENTS    { 1 }
  --#SEVERITY     INFORMATIONAL
  --#TIMEINDEX    1
  --#HELP         "Note: This is no error condition."
  --#HELPTAG      0
  --#STATE        OPERATIONAL
  ::=  13266694 

wfmRemoteCtrlCardMemoryDiagStarted TRAP-TYPE
  ENTERPRISE wfmTrapInfo
  VARIABLES {
    wfmTrapDetails,
    wfmTrapType
  }
  DESCRIPTION
  "Remote Ctrl. Card Memory diag. started."
  --#TYPE         "Remote Ctrl. Card Memory diag. started"
  --#SUMMARY      "%s"
  --#ARGUMENTS    { 1 }
  --#SEVERITY     INFORMATIONAL
  --#TIMEINDEX    1
  --#HELP         "Note: This is no error condition."
  --#HELPTAG      0
  --#STATE        OPERATIONAL
  ::=  13332224 

wfmRemoteCtrlCardMemoryDiagStoppedOK TRAP-TYPE
  ENTERPRISE wfmTrapInfo
  VARIABLES {
    wfmTrapDetails,
    wfmTrapType
  }
  DESCRIPTION
  "Remote Ctrl. Card Memory diag. stopped OK."
  --#TYPE         "Remote Ctrl. Card Memory diag. stopped OK"
  --#SUMMARY      "%s"
  --#ARGUMENTS    { 1 }
  --#SEVERITY     INFORMATIONAL
  --#TIMEINDEX    1
  --#HELP         "Note: This is no error condition."
  --#HELPTAG      0
  --#STATE        OPERATIONAL
  ::=  13332225 

wfmRemoteCtrlCardMemoryDiagStoppedByUser TRAP-TYPE
  ENTERPRISE wfmTrapInfo
  VARIABLES {
    wfmTrapDetails,
    wfmTrapType
  }
  DESCRIPTION
  "Remote Ctrl. Card Memory diag. stopped by user."
  --#TYPE         "Remote Ctrl. Card Memory diag. stopped by user"
  --#SUMMARY      "%s"
  --#ARGUMENTS    { 1 }
  --#SEVERITY     INFORMATIONAL
  --#TIMEINDEX    1
  --#HELP         "Note: This is no error condition."
  --#HELPTAG      0
  --#STATE        OPERATIONAL
  ::=  13332226 

wfmRemoteCtrlCardMemoryDiagStoppedWithError TRAP-TYPE
  ENTERPRISE wfmTrapInfo
  VARIABLES {
    wfmTrapDetails,
    wfmTrapType
  }
  DESCRIPTION
  "Remote Ctrl. Card Memory diag. stopped with Error."
  --#TYPE         "Remote Ctrl. Card Memory diag. stopped with Error"
  --#SUMMARY      "%s"
  --#ARGUMENTS    { 1 }
  --#SEVERITY     INFORMATIONAL
  --#TIMEINDEX    1
  --#HELP         "Note: This is no error condition."
  --#HELPTAG      0
  --#STATE        OPERATIONAL
  ::=  13332227 

wfmVSPDiagnosticError TRAP-TYPE
  ENTERPRISE wfmTrapInfo
  VARIABLES {
    wfmTrapDetails,
    wfmTrapType
  }
  DESCRIPTION
  "VSP' diagnostic error"
  --#TYPE         "VSP diagnostic error"
  --#SUMMARY      "%s"
  --#ARGUMENTS    { 1 }
  --#SEVERITY     CRITICAL
  --#TIMEINDEX    1
  --#HELPTAG      0
  --#STATE        OPERATIONAL
  ::=  13332228 

wfmPECIDiagnosticError TRAP-TYPE
  ENTERPRISE wfmTrapInfo
  VARIABLES {
    wfmTrapDetails,
    wfmTrapType
  }
  DESCRIPTION
  "PECI' diagnostic error"
  --#TYPE         "PECI diagnostic error"
  --#SUMMARY      "%s"
  --#ARGUMENTS    { 1 }
  --#SEVERITY     CRITICAL
  --#TIMEINDEX    1
  --#HELPTAG      0
  --#STATE        OPERATIONAL
  ::=  13332229 

wfmSPIDiagnosticError TRAP-TYPE
  ENTERPRISE wfmTrapInfo
  VARIABLES {
    wfmTrapDetails,
    wfmTrapType
  }
  DESCRIPTION
  "SPI' diagnostic error"
  --#TYPE         "SPI diagnostic error"
  --#SUMMARY      "%s"
  --#ARGUMENTS    { 1 }
  --#SEVERITY     CRITICAL
  --#TIMEINDEX    1
  --#HELPTAG      0
  --#STATE        OPERATIONAL
  ::=  13332230 

wfmFirmwareStackCheckError TRAP-TYPE
  ENTERPRISE wfmTrapInfo
  VARIABLES {
    wfmTrapDetails,
    wfmTrapType
  }
  DESCRIPTION
  "Firmware stack check error"
  --#TYPE         "Firmware stack check error"
  --#SUMMARY      "%s"
  --#ARGUMENTS    { 1 }
  --#SEVERITY     CRITICAL
  --#TIMEINDEX    1
  --#HELPTAG      0
  --#STATE        OPERATIONAL
  ::=  13332231 

wfmBMCMemoryUncorrectableError TRAP-TYPE
  ENTERPRISE wfmTrapInfo
  VARIABLES {
    wfmTrapDetails,
    wfmTrapType
  }
  DESCRIPTION
  "BMC Memory Uncorrectable error"
  --#TYPE         "BMC Memory Uncorrectable error"
  --#SUMMARY      "%s"
  --#ARGUMENTS    { 1 }
  --#SEVERITY     CRITICAL
  --#TIMEINDEX    1
  --#HELPTAG      0
  --#STATE        OPERATIONAL
  ::=  13332232 

wfmBMCMemoryCorrectableErrorLoggingLimitReached TRAP-TYPE
  ENTERPRISE wfmTrapInfo
  VARIABLES {
    wfmTrapDetails,
    wfmTrapType
  }
  DESCRIPTION
  "BMC Memory Correctable error logging limit reached"
  --#TYPE         "BMC Memory Correctable error logging limit reached"
  --#SUMMARY      "%s"
  --#ARGUMENTS    { 1 }
  --#SEVERITY     MAJOR
  --#TIMEINDEX    1
  --#HELPTAG      0
  --#STATE        OPERATIONAL
  ::=  13332233 

wfmRemoteCtrlCardStarted TRAP-TYPE
  ENTERPRISE wfmTrapInfo
  VARIABLES {
    wfmTrapDetails,
    wfmTrapType
  }
  DESCRIPTION
  "Remote Ctrl. Card Started."
  --#TYPE         "Remote Ctrl. Card Started"
  --#SUMMARY      "%s"
  --#ARGUMENTS    { 1 }
  --#SEVERITY     INFORMATIONAL
  --#TIMEINDEX    1
  --#HELP         "Note: This is no error condition."
  --#HELPTAG      0
  --#STATE        OPERATIONAL
  ::=  13397760 

wfmRemoteCtrlCardInternalError TRAP-TYPE
  ENTERPRISE wfmTrapInfo
  VARIABLES {
    wfmTrapDetails,
    wfmTrapType
  }
  DESCRIPTION
  "Remote Ctrl. Card Internal error."
  --#TYPE         "Remote Ctrl. Card Internal error"
  --#SUMMARY      "%s"
  --#ARGUMENTS    { 1 }
  --#SEVERITY     INFORMATIONAL
  --#TIMEINDEX    1
  --#HELP         "Note: This is no error condition."
  --#HELPTAG      0
  --#STATE        OPERATIONAL
  ::=  13397761 

wfmRemoteCtrlCardFirmwareUpdated TRAP-TYPE
  ENTERPRISE wfmTrapInfo
  VARIABLES {
    wfmTrapDetails,
    wfmTrapType
  }
  DESCRIPTION
  "Remote Ctrl. Card Firmware updated."
  --#TYPE         "Remote Ctrl. Card Firmware updated"
  --#SUMMARY      "%s"
  --#ARGUMENTS    { 1 }
  --#SEVERITY     INFORMATIONAL
  --#TIMEINDEX    1
  --#HELP         "Note: This is no error condition."
  --#HELPTAG      0
  --#STATE        OPERATIONAL
  ::=  13397762 

wfmRemoteCtrlCardBatteryLow TRAP-TYPE
  ENTERPRISE wfmTrapInfo
  VARIABLES {
    wfmTrapDetails,
    wfmTrapType
  }
  DESCRIPTION
  "Remote Ctrl. Card Battery low."
  --#TYPE         "Remote Ctrl. Card Battery low"
  --#SUMMARY      "%s"
  --#ARGUMENTS    { 1 }
  --#SEVERITY     INFORMATIONAL
  --#TIMEINDEX    1
  --#HELP         "Note: This is no error condition."
  --#HELPTAG      0
  --#STATE        OPERATIONAL
  ::=  13397763 

wfmRemoteCtrlCardBatteryDisconnected TRAP-TYPE
  ENTERPRISE wfmTrapInfo
  VARIABLES {
    wfmTrapDetails,
    wfmTrapType
  }
  DESCRIPTION
  "Remote Ctrl. Card Battery disconnected."
  --#TYPE         "Remote Ctrl. Card Battery disconnected"
  --#SUMMARY      "%s"
  --#ARGUMENTS    { 1 }
  --#SEVERITY     INFORMATIONAL
  --#TIMEINDEX    1
  --#HELP         "Note: This is no error condition."
  --#HELPTAG      0
  --#STATE        OPERATIONAL
  ::=  13397764 

wfmRemoteCtrlCardConfigSetToDefault TRAP-TYPE
  ENTERPRISE wfmTrapInfo
  VARIABLES {
    wfmTrapDetails,
    wfmTrapType
  }
  DESCRIPTION
  "Remote Ctrl. Card Config set to default."
  --#TYPE         "Remote Ctrl. Card Config set to default"
  --#SUMMARY      "%s"
  --#ARGUMENTS    { 1 }
  --#SEVERITY     INFORMATIONAL
  --#TIMEINDEX    1
  --#HELP         "Note: This is no error condition."
  --#HELPTAG      0
  --#STATE        OPERATIONAL
  ::=  13397765 

wfmRemoteCtrlCardIPAddressChanged TRAP-TYPE
  ENTERPRISE wfmTrapInfo
  VARIABLES {
    wfmTrapDetails,
    wfmTrapType
  }
  DESCRIPTION
  "Remote Ctrl. Card IP Address Changed."
  --#TYPE         "Remote Ctrl. Card IP Address Changed"
  --#SUMMARY      "%s"
  --#ARGUMENTS    { 1 }
  --#SEVERITY     INFORMATIONAL
  --#TIMEINDEX    1
  --#HELP         "Note: This is no error condition."
  --#HELPTAG      0
  --#STATE        OPERATIONAL
  ::=  13397766 

wfmRemoteCtrlCardBatteryDefective TRAP-TYPE
  ENTERPRISE wfmTrapInfo
  VARIABLES {
    wfmTrapDetails,
    wfmTrapType
  }
  DESCRIPTION
  "Remote Ctrl. Card Battery Defective."
  --#TYPE         "Remote Ctrl. Card Battery Defective"
  --#SUMMARY      "%s"
  --#ARGUMENTS    { 1 }
  --#SEVERITY     INFORMATIONAL
  --#TIMEINDEX    1
  --#HELP         "Note: This is no error condition."
  --#HELPTAG      0
  --#STATE        OPERATIONAL
  ::=  13397767 

wfmRemoteCtrlCardBatteryTooOld TRAP-TYPE
  ENTERPRISE wfmTrapInfo
  VARIABLES {
    wfmTrapDetails,
    wfmTrapType
  }
  DESCRIPTION
  "Remote Ctrl. Card Battery Too Old."
  --#TYPE         "Remote Ctrl. Card Battery Too Old"
  --#SUMMARY      "%s"
  --#ARGUMENTS    { 1 }
  --#SEVERITY     INFORMATIONAL
  --#TIMEINDEX    1
  --#HELP         "Note: This is no error condition."
  --#HELPTAG      0
  --#STATE        OPERATIONAL
  ::=  13397768 

wfmRemoteCtrlCardCertificateExpiresInDays TRAP-TYPE
  ENTERPRISE wfmTrapInfo
  VARIABLES {
    wfmTrapDetails,
    wfmTrapType
  }
  DESCRIPTION
  "Remote Ctrl. Card Certificate Expires in Days."
  --#TYPE         "Remote Ctrl. Card Certificate Expires in Days"
  --#SUMMARY      "%s"
  --#ARGUMENTS    { 1 }
  --#SEVERITY     INFORMATIONAL
  --#TIMEINDEX    1
  --#HELP         "Note: This is no error condition."
  --#HELPTAG      0
  --#STATE        OPERATIONAL
  ::=  13397769 

wfmFrontLANConnected TRAP-TYPE
  ENTERPRISE wfmTrapInfo
  VARIABLES {
    wfmTrapDetails,
    wfmTrapType
  }
  DESCRIPTION
  "Front LAN connected."
  --#TYPE         "Front LAN connected"
  --#SUMMARY      "%s"
  --#ARGUMENTS    { 1 }
  --#SEVERITY     INFORMATIONAL
  --#TIMEINDEX    1
  --#HELP         "Note: This is no error condition."
  --#HELPTAG      0
  --#STATE        OPERATIONAL
  ::=  13397770 

wfmSSLCertificatekeyMismatchUsingDefaultsInstead TRAP-TYPE
  ENTERPRISE wfmTrapInfo
  VARIABLES {
    wfmTrapDetails,
    wfmTrapType
  }
  DESCRIPTION
  "SSL certificate/key mismatch - using defaults instead."
  --#TYPE         "SSL certificate/key mismatch - using defaults instead"
  --#SUMMARY      "%s"
  --#ARGUMENTS    { 1 }
  --#SEVERITY     MINOR
  --#TIMEINDEX    1
  --#HELPTAG      0
  --#STATE        OPERATIONAL
  ::=  13397771 

wfmServerManagementLANSwitchedAutomatically TRAP-TYPE
  ENTERPRISE wfmTrapInfo
  VARIABLES {
    wfmTrapDetails,
    wfmTrapType
  }
  DESCRIPTION
  "Server Management LAN switched automatically"
  --#TYPE         "Server Management LAN switched automatically"
  --#SUMMARY      "%s"
  --#ARGUMENTS    { 1 }
  --#SEVERITY     MINOR
  --#TIMEINDEX    1
  --#HELPTAG      0
  --#STATE        OPERATIONAL
  ::=  13397772 

wfmServerManagementLANSwitchedManually TRAP-TYPE
  ENTERPRISE wfmTrapInfo
  VARIABLES {
    wfmTrapDetails,
    wfmTrapType
  }
  DESCRIPTION
  "Server Management LAN switched manually"
  --#TYPE         "Server Management LAN switched manually"
  --#SUMMARY      "%s"
  --#ARGUMENTS    { 1 }
  --#SEVERITY     INFORMATIONAL
  --#TIMEINDEX    1
  --#HELP         "Note: This is no error condition."
  --#HELPTAG      0
  --#STATE        OPERATIONAL
  ::=  13397773 

wfmFrontLANDisconnected TRAP-TYPE
  ENTERPRISE wfmTrapInfo
  VARIABLES {
    wfmTrapDetails,
    wfmTrapType
  }
  DESCRIPTION
  "Front LAN disconnected."
  --#TYPE         "Front LAN disconnected"
  --#SUMMARY      "%s"
  --#ARGUMENTS    { 1 }
  --#SEVERITY     INFORMATIONAL
  --#TIMEINDEX    1
  --#HELP         "Note: This is no error condition."
  --#HELPTAG      0
  --#STATE        OPERATIONAL
  ::=  13397898 

wfmManagementEngineInfoN1 TRAP-TYPE
  ENTERPRISE wfmTrapInfo
  VARIABLES {
    wfmTrapDetails,
    wfmTrapType
  }
  DESCRIPTION
  "Management Engine: Info"
  --#TYPE         "Management Engine: Info"
  --#SUMMARY      "%s"
  --#ARGUMENTS    { 1 }
  --#SEVERITY     INFORMATIONAL
  --#TIMEINDEX    1
  --#HELP         "Note: This is no error condition."
  --#HELPTAG      0
  --#STATE        OPERATIONAL
  ::=  14419712 

wfmManagementEngineWarning TRAP-TYPE
  ENTERPRISE wfmTrapInfo
  VARIABLES {
    wfmTrapDetails,
    wfmTrapType
  }
  DESCRIPTION
  "Management Engine: Warning"
  --#TYPE         "Management Engine: Warning"
  --#SUMMARY      "%s"
  --#ARGUMENTS    { 1 }
  --#SEVERITY     MINOR
  --#TIMEINDEX    1
  --#HELPTAG      0
  --#STATE        OPERATIONAL
  ::=  14419713 

wfmManagementEngineError TRAP-TYPE
  ENTERPRISE wfmTrapInfo
  VARIABLES {
    wfmTrapDetails,
    wfmTrapType
  }
  DESCRIPTION
  "Management Engine: Error"
  --#TYPE         "Management Engine: Error"
  --#SUMMARY      "%s"
  --#ARGUMENTS    { 1 }
  --#SEVERITY     MAJOR
  --#TIMEINDEX    1
  --#HELPTAG      0
  --#STATE        OPERATIONAL
  ::=  14419714 

wfmManagementEngineFatalError TRAP-TYPE
  ENTERPRISE wfmTrapInfo
  VARIABLES {
    wfmTrapDetails,
    wfmTrapType
  }
  DESCRIPTION
  "Management Engine: Fatal error"
  --#TYPE         "Management Engine: Fatal error"
  --#SUMMARY      "%s"
  --#ARGUMENTS    { 1 }
  --#SEVERITY     CRITICAL
  --#TIMEINDEX    1
  --#HELPTAG      0
  --#STATE        OPERATIONAL
  ::=  14419718 

wfmManagementEngineInfoN2 TRAP-TYPE
  ENTERPRISE wfmTrapInfo
  VARIABLES {
    wfmTrapDetails,
    wfmTrapType
  }
  DESCRIPTION
  "Management Engine: Info"
  --#TYPE         "Management Engine: Info"
  --#SUMMARY      "%s"
  --#ARGUMENTS    { 1 }
  --#SEVERITY     INFORMATIONAL
  --#TIMEINDEX    1
  --#HELP         "Note: This is no error condition."
  --#HELPTAG      0
  --#STATE        OPERATIONAL
  ::=  14419719 

wfmManagementEngineInfoN3 TRAP-TYPE
  ENTERPRISE wfmTrapInfo
  VARIABLES {
    wfmTrapDetails,
    wfmTrapType
  }
  DESCRIPTION
  "Management Engine: Info"
  --#TYPE         "Management Engine: Info"
  --#SUMMARY      "%s"
  --#ARGUMENTS    { 1 }
  --#SEVERITY     INFORMATIONAL
  --#TIMEINDEX    1
  --#HELP         "Note: This is no error condition."
  --#HELPTAG      0
  --#STATE        OPERATIONAL
  ::=  14419720 

wfmNodeManagerPolicyCorrectionTimeExceededForPolicyID TRAP-TYPE
  ENTERPRISE wfmTrapInfo
  VARIABLES {
    wfmTrapDetails,
    wfmTrapType
  }
  DESCRIPTION
  "Node Manager: Policy correction time exceeded for policy ID."
  --#TYPE         "Node Manager: Policy correction time exceeded for policy ID"
  --#SUMMARY      "%s"
  --#ARGUMENTS    { 1 }
  --#SEVERITY     MINOR
  --#TIMEINDEX    1
  --#HELPTAG      0
  --#STATE        OPERATIONAL
  ::=  14447112 

wfmNodeManagerPolicyCorrectionTimeOKForPolicyID TRAP-TYPE
  ENTERPRISE wfmTrapInfo
  VARIABLES {
    wfmTrapDetails,
    wfmTrapType
  }
  DESCRIPTION
  "Node Manager: Policy correction time OK for policy ID."
  --#TYPE         "Node Manager: Policy correction time OK for policy ID"
  --#SUMMARY      "%s"
  --#ARGUMENTS    { 1 }
  --#SEVERITY     INFORMATIONAL
  --#TIMEINDEX    1
  --#HELP         "Note: This is no error condition."
  --#HELPTAG      0
  --#STATE        OPERATIONAL
  ::=  14447240 

wfmNodeManagerPlatformShutdownInitiatedByNMPolicyID TRAP-TYPE
  ENTERPRISE wfmTrapInfo
  VARIABLES {
    wfmTrapDetails,
    wfmTrapType
  }
  DESCRIPTION
  "Node Manager: Platform shutdown initiated by NM policy ID."
  --#TYPE         "Node Manager: Platform shutdown initiated by NM policy ID"
  --#SUMMARY      "%s"
  --#ARGUMENTS    { 1 }
  --#SEVERITY     MINOR
  --#TIMEINDEX    1
  --#HELPTAG      0
  --#STATE        OPERATIONAL
  ::=  14447362 

wfmNodeManagerCapabilitiesChangeEventNoneAvailable TRAP-TYPE
  ENTERPRISE wfmTrapInfo
  VARIABLES {
    wfmTrapDetails,
    wfmTrapType
  }
  DESCRIPTION
  "Node Manager Capabilities change event: None available"
  --#TYPE         "Node Manager Capabilities change event: None available"
  --#SUMMARY      "%s"
  --#ARGUMENTS    { 1 }
  --#SEVERITY     INFORMATIONAL
  --#TIMEINDEX    1
  --#HELP         "Note: This is no error condition."
  --#HELPTAG      0
  --#STATE        OPERATIONAL
  ::=  14447616 

wfmNodeManagerCapabilitiesChangeEventPoliciesAvailable TRAP-TYPE
  ENTERPRISE wfmTrapInfo
  VARIABLES {
    wfmTrapDetails,
    wfmTrapType
  }
  DESCRIPTION
  "Node Manager Capabilities change event: Policies available"
  --#TYPE         "Node Manager Capabilities change event: Policies available"
  --#SUMMARY      "%s"
  --#ARGUMENTS    { 1 }
  --#SEVERITY     INFORMATIONAL
  --#TIMEINDEX    1
  --#HELP         "Note: This is no error condition."
  --#HELPTAG      0
  --#STATE        OPERATIONAL
  ::=  14447617 

wfmNodeManagerCapabilitiesChangeEventMonitoringAvailable TRAP-TYPE
  ENTERPRISE wfmTrapInfo
  VARIABLES {
    wfmTrapDetails,
    wfmTrapType
  }
  DESCRIPTION
  "Node Manager Capabilities change event: Monitoring available"
  --#TYPE         "Node Manager Capabilities change event: Monitoring available"
  --#SUMMARY      "%s"
  --#ARGUMENTS    { 1 }
  --#SEVERITY     INFORMATIONAL
  --#TIMEINDEX    1
  --#HELP         "Note: This is no error condition."
  --#HELPTAG      0
  --#STATE        OPERATIONAL
  ::=  14447618 

wfmNodeManagerCapabilitiesChangeEventPoliciesMonitoringAvailab TRAP-TYPE
  ENTERPRISE wfmTrapInfo
  VARIABLES {
    wfmTrapDetails,
    wfmTrapType
  }
  DESCRIPTION
  "Node Manager Capabilities change event: Policies, Monitoring available"
  --#TYPE         "Node Manager Capabilities change event: Policies, Monitoring available"
  --#SUMMARY      "%s"
  --#ARGUMENTS    { 1 }
  --#SEVERITY     INFORMATIONAL
  --#TIMEINDEX    1
  --#HELP         "Note: This is no error condition."
  --#HELPTAG      0
  --#STATE        OPERATIONAL
  ::=  14447619 

wfmNodeManagerCapabilitiesChangeEventPwrLimitingAvailable TRAP-TYPE
  ENTERPRISE wfmTrapInfo
  VARIABLES {
    wfmTrapDetails,
    wfmTrapType
  }
  DESCRIPTION
  "Node Manager Capabilities change event: Pwr limiting available"
  --#TYPE         "Node Manager Capabilities change event: Pwr limiting available"
  --#SUMMARY      "%s"
  --#ARGUMENTS    { 1 }
  --#SEVERITY     INFORMATIONAL
  --#TIMEINDEX    1
  --#HELP         "Note: This is no error condition."
  --#HELPTAG      0
  --#STATE        OPERATIONAL
  ::=  14447620 

wfmNodeManagerCapabilitiesChangeEventPoliciesPwrLimitingAvaila TRAP-TYPE
  ENTERPRISE wfmTrapInfo
  VARIABLES {
    wfmTrapDetails,
    wfmTrapType
  }
  DESCRIPTION
  "Node Manager Capabilities change event: Policies, Pwr limiting available"
  --#TYPE         "Node Manager Capabilities change event: Policies, Pwr limiting available"
  --#SUMMARY      "%s"
  --#ARGUMENTS    { 1 }
  --#SEVERITY     INFORMATIONAL
  --#TIMEINDEX    1
  --#HELP         "Note: This is no error condition."
  --#HELPTAG      0
  --#STATE        OPERATIONAL
  ::=  14447621 

wfmNodeManagerCapabilitiesChangeEventMonitoringPwrLimitingAvai TRAP-TYPE
  ENTERPRISE wfmTrapInfo
  VARIABLES {
    wfmTrapDetails,
    wfmTrapType
  }
  DESCRIPTION
  "Node Manager Capabilities change event: Monitoring, Pwr limiting  available"
  --#TYPE         "Node Manager Capabilities change event: Monitoring, Pwr limiting available"
  --#SUMMARY      "%s"
  --#ARGUMENTS    { 1 }
  --#SEVERITY     INFORMATIONAL
  --#TIMEINDEX    1
  --#HELP         "Note: This is no error condition."
  --#HELPTAG      0
  --#STATE        OPERATIONAL
  ::=  14447622 

wfmNodeManagerCapabilitiesChangeEventPoliciesMonitoringPwrLimi TRAP-TYPE
  ENTERPRISE wfmTrapInfo
  VARIABLES {
    wfmTrapDetails,
    wfmTrapType
  }
  DESCRIPTION
  "Node Manager Capabilities change event: Policies, Monitoring, Pwr limiting available"
  --#TYPE         "Node Manager Capabilities change event: Policies, Monitoring, Pwr limiting available"
  --#SUMMARY      "%s"
  --#ARGUMENTS    { 1 }
  --#SEVERITY     INFORMATIONAL
  --#TIMEINDEX    1
  --#HELP         "Note: This is no error condition."
  --#HELPTAG      0
  --#STATE        OPERATIONAL
  ::=  14447623 

wfmNodeManagerCapabilitiesChangeDessartEventNoneAvailable TRAP-TYPE
  ENTERPRISE wfmTrapInfo
  VARIABLES {
    wfmTrapDetails,
    wfmTrapType
  }
  DESCRIPTION
  "Node Manager Capabilities change dessart event: None available"
  --#TYPE         "Node Manager Capabilities change dessart event: None available"
  --#SUMMARY      "%s"
  --#ARGUMENTS    { 1 }
  --#SEVERITY     INFORMATIONAL
  --#TIMEINDEX    1
  --#HELP         "Note: This is no error condition."
  --#HELPTAG      0
  --#STATE        OPERATIONAL
  ::=  14447744 

wfmNodeManagerCapabilitiesChangeDessartEventPoliciesAvailable TRAP-TYPE
  ENTERPRISE wfmTrapInfo
  VARIABLES {
    wfmTrapDetails,
    wfmTrapType
  }
  DESCRIPTION
  "Node Manager Capabilities change dessart event: Policies available"
  --#TYPE         "Node Manager Capabilities change dessart event: Policies available"
  --#SUMMARY      "%s"
  --#ARGUMENTS    { 1 }
  --#SEVERITY     INFORMATIONAL
  --#TIMEINDEX    1
  --#HELP         "Note: This is no error condition."
  --#HELPTAG      0
  --#STATE        OPERATIONAL
  ::=  14447745 

wfmNodeManagerCapabilitiesChangeDessartEventMonitoringAvailabl TRAP-TYPE
  ENTERPRISE wfmTrapInfo
  VARIABLES {
    wfmTrapDetails,
    wfmTrapType
  }
  DESCRIPTION
  "Node Manager Capabilities change dessart event: Monitoring available"
  --#TYPE         "Node Manager Capabilities change dessart event: Monitoring available"
  --#SUMMARY      "%s"
  --#ARGUMENTS    { 1 }
  --#SEVERITY     INFORMATIONAL
  --#TIMEINDEX    1
  --#HELP         "Note: This is no error condition."
  --#HELPTAG      0
  --#STATE        OPERATIONAL
  ::=  14447746 

wfmNodeManagerCapabilitiesChangeDessartEventPoliciesMonitoringN1 TRAP-TYPE
  ENTERPRISE wfmTrapInfo
  VARIABLES {
    wfmTrapDetails,
    wfmTrapType
  }
  DESCRIPTION
  "Node Manager Capabilities change dessart event: Policies, Monitoring available"
  --#TYPE         "Node Manager Capabilities change dessart event: Policies, Monitoring available"
  --#SUMMARY      "%s"
  --#ARGUMENTS    { 1 }
  --#SEVERITY     INFORMATIONAL
  --#TIMEINDEX    1
  --#HELP         "Note: This is no error condition."
  --#HELPTAG      0
  --#STATE        OPERATIONAL
  ::=  14447747 

wfmNodeManagerCapabilitiesChangeDessartEventPwrLimitingAvailab TRAP-TYPE
  ENTERPRISE wfmTrapInfo
  VARIABLES {
    wfmTrapDetails,
    wfmTrapType
  }
  DESCRIPTION
  "Node Manager Capabilities change dessart event: Pwr limiting available"
  --#TYPE         "Node Manager Capabilities change dessart event: Pwr limiting available"
  --#SUMMARY      "%s"
  --#ARGUMENTS    { 1 }
  --#SEVERITY     INFORMATIONAL
  --#TIMEINDEX    1
  --#HELP         "Note: This is no error condition."
  --#HELPTAG      0
  --#STATE        OPERATIONAL
  ::=  14447748 

wfmNodeManagerCapabilitiesChangeDessartEventPoliciesPwrLimitin TRAP-TYPE
  ENTERPRISE wfmTrapInfo
  VARIABLES {
    wfmTrapDetails,
    wfmTrapType
  }
  DESCRIPTION
  "Node Manager Capabilities change dessart event: Policies, Pwr limiting available"
  --#TYPE         "Node Manager Capabilities change dessart event: Policies, Pwr limiting available"
  --#SUMMARY      "%s"
  --#ARGUMENTS    { 1 }
  --#SEVERITY     INFORMATIONAL
  --#TIMEINDEX    1
  --#HELP         "Note: This is no error condition."
  --#HELPTAG      0
  --#STATE        OPERATIONAL
  ::=  14447749 

wfmNodeManagerCapabilitiesChangeDessartEventMonitoringPwrLimit TRAP-TYPE
  ENTERPRISE wfmTrapInfo
  VARIABLES {
    wfmTrapDetails,
    wfmTrapType
  }
  DESCRIPTION
  "Node Manager Capabilities change dessart event: Monitoring, Pwr limiting  available"
  --#TYPE         "Node Manager Capabilities change dessart event: Monitoring, Pwr limiting available"
  --#SUMMARY      "%s"
  --#ARGUMENTS    { 1 }
  --#SEVERITY     INFORMATIONAL
  --#TIMEINDEX    1
  --#HELP         "Note: This is no error condition."
  --#HELPTAG      0
  --#STATE        OPERATIONAL
  ::=  14447750 

wfmNodeManagerCapabilitiesChangeDessartEventPoliciesMonitoringN2 TRAP-TYPE
  ENTERPRISE wfmTrapInfo
  VARIABLES {
    wfmTrapDetails,
    wfmTrapType
  }
  DESCRIPTION
  "Node Manager Capabilities change dessart event: Policies, Monitoring, Pwr limiting available"
  --#TYPE         "Node Manager Capabilities change dessart event: Policies, Monitoring, Pwr limiting available"
  --#SUMMARY      "%s"
  --#ARGUMENTS    { 1 }
  --#SEVERITY     INFORMATIONAL
  --#TIMEINDEX    1
  --#HELP         "Note: This is no error condition."
  --#HELPTAG      0
  --#STATE        OPERATIONAL
  ::=  14447751 

wfmNodeManagerPersistentStorageIntegrityErrorFlashFileSystemEr TRAP-TYPE
  ENTERPRISE wfmTrapInfo
  VARIABLES {
    wfmTrapDetails,
    wfmTrapType
  }
  DESCRIPTION
  "Node Manager: Persistent storage integrity error. Flash file system error detected.."
  --#TYPE         "Node Manager: Persistent storage integrity error. Flash file system error detected."
  --#SUMMARY      "%s"
  --#ARGUMENTS    { 1 }
  --#SEVERITY     MAJOR
  --#TIMEINDEX    1
  --#HELPTAG      0
  --#STATE        OPERATIONAL
  ::=  14447872 

wfmSystemPowerConsumptionWithinLimit TRAP-TYPE
  ENTERPRISE wfmTrapInfo
  VARIABLES {
    wfmTrapDetails,
    wfmTrapType
  }
  DESCRIPTION
  "System Power Consumption within Limit."
  --#TYPE         "System Power Consumption within Limit"
  --#SUMMARY      "%s"
  --#ARGUMENTS    { 1 }
  --#SEVERITY     INFORMATIONAL
  --#TIMEINDEX    1
  --#HELP         "Note: This is no error condition."
  --#HELPTAG      0
  --#STATE        OPERATIONAL
  ::=  14511872 

wfmSystemPowerConsumptionAboveWarningLevel TRAP-TYPE
  ENTERPRISE wfmTrapInfo
  VARIABLES {
    wfmTrapDetails,
    wfmTrapType
  }
  DESCRIPTION
  "System Power Consumption above Warning Level."
  --#TYPE         "System Power Consumption above Warning Level"
  --#SUMMARY      "%s"
  --#ARGUMENTS    { 1 }
  --#SEVERITY     MAJOR
  --#TIMEINDEX    1
  --#HELPTAG      0
  --#STATE        OPERATIONAL
  ::=  14511873 

wfmSystemPowerConsumptionAboveCriticalLevel TRAP-TYPE
  ENTERPRISE wfmTrapInfo
  VARIABLES {
    wfmTrapDetails,
    wfmTrapType
  }
  DESCRIPTION
  "System Power Consumption above Critical Level."
  --#TYPE         "System Power Consumption above Critical Level"
  --#SUMMARY      "%s"
  --#ARGUMENTS    { 1 }
  --#SEVERITY     CRITICAL
  --#TIMEINDEX    1
  --#HELPTAG      0
  --#STATE        OPERATIONAL
  ::=  14511874 

wfmSystemPowerConsumptionLimitingDisabled TRAP-TYPE
  ENTERPRISE wfmTrapInfo
  VARIABLES {
    wfmTrapDetails,
    wfmTrapType
  }
  DESCRIPTION
  "System Power Consumption limiting disabled."
  --#TYPE         "System Power Consumption limiting disabled"
  --#SUMMARY      "%s"
  --#ARGUMENTS    { 1 }
  --#SEVERITY     INFORMATIONAL
  --#TIMEINDEX    1
  --#HELP         "Note: This is no error condition."
  --#HELPTAG      0
  --#STATE        OPERATIONAL
  ::=  14511875 

wfmMemoryModuleError TRAP-TYPE
  ENTERPRISE wfmTrapInfo
  VARIABLES {
    wfmTrapDetails,
    wfmTrapType
  }
  DESCRIPTION
  "Memory module error."
  --#TYPE         "Memory module error"
  --#SUMMARY      "%s"
  --#ARGUMENTS    { 1 }
  --#SEVERITY     CRITICAL
  --#TIMEINDEX    1
  --#HELPTAG      0
  --#STATE        OPERATIONAL
  ::=  14577411 

wfmMemoryModuleFailed TRAP-TYPE
  ENTERPRISE wfmTrapInfo
  VARIABLES {
    wfmTrapDetails,
    wfmTrapType
  }
  DESCRIPTION
  "Memory module failed."
  --#TYPE         "Memory module failed"
  --#SUMMARY      "%s"
  --#ARGUMENTS    { 1 }
  --#SEVERITY     CRITICAL
  --#TIMEINDEX    1
  --#HELPTAG      0
  --#STATE        OPERATIONAL
  ::=  14577412 

wfmMemoryModulePrefailure TRAP-TYPE
  ENTERPRISE wfmTrapInfo
  VARIABLES {
    wfmTrapDetails,
    wfmTrapType
  }
  DESCRIPTION
  "Memory module prefailure."
  --#TYPE         "Memory module prefailure"
  --#SUMMARY      "%s"
  --#ARGUMENTS    { 1 }
  --#SEVERITY     MAJOR
  --#TIMEINDEX    1
  --#HELPTAG      0
  --#STATE        OPERATIONAL
  ::=  14577413 

wfmMemoryFailure TRAP-TYPE
  ENTERPRISE wfmTrapInfo
  VARIABLES {
    wfmTrapDetails,
    wfmTrapType
  }
  DESCRIPTION
  "Memory failure"
  --#TYPE         "Memory failure"
  --#SUMMARY      "%s"
  --#ARGUMENTS    { 1 }
  --#SEVERITY     MAJOR
  --#TIMEINDEX    1
  --#HELPTAG      0
  --#STATE        OPERATIONAL
  ::=  14642950 

wfmFSCRompilotError TRAP-TYPE
  ENTERPRISE wfmTrapInfo
  VARIABLES {
    wfmTrapDetails,
    wfmTrapType
  }
  DESCRIPTION
  "FSC: Rompilot error."
  --#TYPE         "FSC: Rompilot error"
  --#SUMMARY      "%s"
  --#ARGUMENTS    { 1 }
  --#SEVERITY     INFORMATIONAL
  --#TIMEINDEX    1
  --#HELP         "Note: This is no error condition."
  --#HELPTAG      0
  --#STATE        OPERATIONAL
  ::=  14708480 

wfmMemoryPredictiveFailurePDAModule TRAP-TYPE
  ENTERPRISE wfmTrapInfo
  VARIABLES {
    wfmTrapDetails,
    wfmTrapType
  }
  DESCRIPTION
  "Memory: Predictive Failure (PDA) Module."
  --#TYPE         "Memory: Predictive Failure (PDA) Module"
  --#SUMMARY      "%s"
  --#ARGUMENTS    { 1 }
  --#SEVERITY     MAJOR
  --#TIMEINDEX    1
  --#HELPTAG      0
  --#STATE        OPERATIONAL
  ::=  14746625 

wfmFSCNonFSCMemoryModuleDetected TRAP-TYPE
  ENTERPRISE wfmTrapInfo
  VARIABLES {
    wfmTrapDetails,
    wfmTrapType
  }
  DESCRIPTION
  "FSC: Non FSC memory module detected."
  --#TYPE         "FSC: Non FSC memory module detected"
  --#SUMMARY      "%s"
  --#ARGUMENTS    { 1 }
  --#SEVERITY     INFORMATIONAL
  --#TIMEINDEX    1
  --#HELP         "Note: This is no error condition."
  --#HELPTAG      0
  --#STATE        OPERATIONAL
  ::=  14774016 

wfmFSCMemoryModuleReplaced TRAP-TYPE
  ENTERPRISE wfmTrapInfo
  VARIABLES {
    wfmTrapDetails,
    wfmTrapType
  }
  DESCRIPTION
  "FSC: Memory module replaced."
  --#TYPE         "FSC: Memory module replaced"
  --#SUMMARY      "%s"
  --#ARGUMENTS    { 1 }
  --#SEVERITY     MAJOR
  --#TIMEINDEX    1
  --#HELPTAG      0
  --#STATE        OPERATIONAL
  ::=  14774017 

wfmFSCFatalGeneralMemoryError TRAP-TYPE
  ENTERPRISE wfmTrapInfo
  VARIABLES {
    wfmTrapDetails,
    wfmTrapType
  }
  DESCRIPTION
  "FSC: Fatal general memory error."
  --#TYPE         "FSC: Fatal general memory error"
  --#SUMMARY      "%s"
  --#ARGUMENTS    { 1 }
  --#SEVERITY     CRITICAL
  --#TIMEINDEX    1
  --#HELPTAG      0
  --#STATE        OPERATIONAL
  ::=  14774018 

wfmFSCRecoverableGeneralMemoryError TRAP-TYPE
  ENTERPRISE wfmTrapInfo
  VARIABLES {
    wfmTrapDetails,
    wfmTrapType
  }
  DESCRIPTION
  "FSC: Recoverable general memory error."
  --#TYPE         "FSC: Recoverable general memory error"
  --#SUMMARY      "%s"
  --#ARGUMENTS    { 1 }
  --#SEVERITY     INFORMATIONAL
  --#TIMEINDEX    1
  --#HELP         "Note: This is no error condition."
  --#HELPTAG      0
  --#STATE        OPERATIONAL
  ::=  14774019 

wfmFSCRecoverableECCMemoryError TRAP-TYPE
  ENTERPRISE wfmTrapInfo
  VARIABLES {
    wfmTrapDetails,
    wfmTrapType
  }
  DESCRIPTION
  "FSC: Recoverable ECC memory error."
  --#TYPE         "FSC: Recoverable ECC memory error"
  --#SUMMARY      "%s"
  --#ARGUMENTS    { 1 }
  --#SEVERITY     INFORMATIONAL
  --#TIMEINDEX    1
  --#HELP         "Note: This is no error condition."
  --#HELPTAG      0
  --#STATE        OPERATIONAL
  ::=  14774020 

wfmFSCRecoverableCRCMemoryError TRAP-TYPE
  ENTERPRISE wfmTrapInfo
  VARIABLES {
    wfmTrapDetails,
    wfmTrapType
  }
  DESCRIPTION
  "FSC: Recoverable CRC memory error ."
  --#TYPE         "FSC: Recoverable CRC memory error"
  --#SUMMARY      "%s"
  --#ARGUMENTS    { 1 }
  --#SEVERITY     INFORMATIONAL
  --#TIMEINDEX    1
  --#HELP         "Note: This is no error condition."
  --#HELPTAG      0
  --#STATE        OPERATIONAL
  ::=  14774021 

wfmFSCFatalCRCMemoryError TRAP-TYPE
  ENTERPRISE wfmTrapInfo
  VARIABLES {
    wfmTrapDetails,
    wfmTrapType
  }
  DESCRIPTION
  "FSC: Fatal CRC memory error."
  --#TYPE         "FSC: Fatal CRC memory error"
  --#SUMMARY      "%s"
  --#ARGUMENTS    { 1 }
  --#SEVERITY     CRITICAL
  --#TIMEINDEX    1
  --#HELPTAG      0
  --#STATE        OPERATIONAL
  ::=  14774022 

wfmFSCRecoverableThermalMemoryEvent TRAP-TYPE
  ENTERPRISE wfmTrapInfo
  VARIABLES {
    wfmTrapDetails,
    wfmTrapType
  }
  DESCRIPTION
  "FSC: Recoverable thermal memory event."
  --#TYPE         "FSC: Recoverable thermal memory event"
  --#SUMMARY      "%s"
  --#ARGUMENTS    { 1 }
  --#SEVERITY     INFORMATIONAL
  --#TIMEINDEX    1
  --#HELP         "Note: This is no error condition."
  --#HELPTAG      0
  --#STATE        OPERATIONAL
  ::=  14774023 

wfmFSCFatalThermalMemoryError TRAP-TYPE
  ENTERPRISE wfmTrapInfo
  VARIABLES {
    wfmTrapDetails,
    wfmTrapType
  }
  DESCRIPTION
  "FSC: Fatal thermal memory error."
  --#TYPE         "FSC: Fatal thermal memory error"
  --#SUMMARY      "%s"
  --#ARGUMENTS    { 1 }
  --#SEVERITY     CRITICAL
  --#TIMEINDEX    1
  --#HELPTAG      0
  --#STATE        OPERATIONAL
  ::=  14774024 

wfmFSCTooManyCorrectableMemoryErrors TRAP-TYPE
  ENTERPRISE wfmTrapInfo
  VARIABLES {
    wfmTrapDetails,
    wfmTrapType
  }
  DESCRIPTION
  "FSC: Too many correctable memory errors."
  --#TYPE         "FSC: Too many correctable memory errors"
  --#SUMMARY      "%s"
  --#ARGUMENTS    { 1 }
  --#SEVERITY     MAJOR
  --#TIMEINDEX    1
  --#HELPTAG      0
  --#STATE        OPERATIONAL
  ::=  14774025 

wfmFSCUncorrectableParityMemoryError TRAP-TYPE
  ENTERPRISE wfmTrapInfo
  VARIABLES {
    wfmTrapDetails,
    wfmTrapType
  }
  DESCRIPTION
  "FSC: Uncorrectable Parity memory error."
  --#TYPE         "FSC: Uncorrectable Parity memory error"
  --#SUMMARY      "%s"
  --#ARGUMENTS    { 1 }
  --#SEVERITY     CRITICAL
  --#TIMEINDEX    1
  --#HELPTAG      0
  --#STATE        OPERATIONAL
  ::=  14774026 

wfmFSCMemoryModulesSwapped TRAP-TYPE
  ENTERPRISE wfmTrapInfo
  VARIABLES {
    wfmTrapDetails,
    wfmTrapType
  }
  DESCRIPTION
  "FSC: Memory Modules swapped."
  --#TYPE         "FSC: Memory Modules swapped"
  --#SUMMARY      "%s"
  --#ARGUMENTS    { 1 }
  --#SEVERITY     INFORMATIONAL
  --#TIMEINDEX    1
  --#HELP         "Note: This is no error condition."
  --#HELPTAG      0
  --#STATE        OPERATIONAL
  ::=  14774027 

wfmFSCMemoryModuleMoved TRAP-TYPE
  ENTERPRISE wfmTrapInfo
  VARIABLES {
    wfmTrapDetails,
    wfmTrapType
  }
  DESCRIPTION
  "FSC: Memory Module moved."
  --#TYPE         "FSC: Memory Module moved"
  --#SUMMARY      "%s"
  --#ARGUMENTS    { 1 }
  --#SEVERITY     INFORMATIONAL
  --#TIMEINDEX    1
  --#HELP         "Note: This is no error condition."
  --#HELPTAG      0
  --#STATE        OPERATIONAL
  ::=  14774028 

wfmFSCMemoryRemoved TRAP-TYPE
  ENTERPRISE wfmTrapInfo
  VARIABLES {
    wfmTrapDetails,
    wfmTrapType
  }
  DESCRIPTION
  "FSC: Memory removed."
  --#TYPE         "FSC: Memory removed"
  --#SUMMARY      "%s"
  --#ARGUMENTS    { 1 }
  --#SEVERITY     INFORMATIONAL
  --#TIMEINDEX    1
  --#HELP         "Note: This is no error condition."
  --#HELPTAG      0
  --#STATE        OPERATIONAL
  ::=  14774029 

wfmFSCMemoryReinserted TRAP-TYPE
  ENTERPRISE wfmTrapInfo
  VARIABLES {
    wfmTrapDetails,
    wfmTrapType
  }
  DESCRIPTION
  "FSC: Memory Re-inserted."
  --#TYPE         "FSC: Memory Re-inserted"
  --#SUMMARY      "%s"
  --#ARGUMENTS    { 1 }
  --#SEVERITY     INFORMATIONAL
  --#TIMEINDEX    1
  --#HELP         "Note: This is no error condition."
  --#HELPTAG      0
  --#STATE        OPERATIONAL
  ::=  14774030 

wfmFSCMemoryModulesChanged TRAP-TYPE
  ENTERPRISE wfmTrapInfo
  VARIABLES {
    wfmTrapDetails,
    wfmTrapType
  }
  DESCRIPTION
  "FSC: Memory module(s) changed."
  --#TYPE         "FSC: Memory module(s) changed"
  --#SUMMARY      "%s"
  --#ARGUMENTS    { 1 }
  --#SEVERITY     INFORMATIONAL
  --#TIMEINDEX    1
  --#HELP         "Note: This is no error condition."
  --#HELPTAG      0
  --#STATE        OPERATIONAL
  ::=  14774031 

wfmMemoryModeuleReplacementFinished TRAP-TYPE
  ENTERPRISE wfmTrapInfo
  VARIABLES {
    wfmTrapDetails,
    wfmTrapType
  }
  DESCRIPTION
  "Memory modeule replacement finished"
  --#TYPE         "Memory modeule replacement finished"
  --#SUMMARY      "%s"
  --#ARGUMENTS    { 1 }
  --#SEVERITY     INFORMATIONAL
  --#TIMEINDEX    1
  --#HELP         "Note: This is no error condition."
  --#HELPTAG      0
  --#STATE        OPERATIONAL
  ::=  14774145 

wfmFSCThermalConditionMemoryModuleOK TRAP-TYPE
  ENTERPRISE wfmTrapInfo
  VARIABLES {
    wfmTrapDetails,
    wfmTrapType
  }
  DESCRIPTION
  "FSC: Thermal condition memory module OK."
  --#TYPE         "FSC: Thermal condition memory module OK"
  --#SUMMARY      "%s"
  --#ARGUMENTS    { 1 }
  --#SEVERITY     INFORMATIONAL
  --#TIMEINDEX    1
  --#HELP         "Note: This is no error condition."
  --#HELPTAG      0
  --#STATE        OPERATIONAL
  ::=  14774151 

wfmFSCMemoryInserted TRAP-TYPE
  ENTERPRISE wfmTrapInfo
  VARIABLES {
    wfmTrapDetails,
    wfmTrapType
  }
  DESCRIPTION
  "FSC: Memory inserted."
  --#TYPE         "FSC: Memory inserted"
  --#SUMMARY      "%s"
  --#ARGUMENTS    { 1 }
  --#SEVERITY     INFORMATIONAL
  --#TIMEINDEX    1
  --#HELP         "Note: This is no error condition."
  --#HELPTAG      0
  --#STATE        OPERATIONAL
  ::=  14774157 

wfmRecoverableCRCMemoryErrorOnMemoryLink TRAP-TYPE
  ENTERPRISE wfmTrapInfo
  VARIABLES {
    wfmTrapDetails,
    wfmTrapType
  }
  DESCRIPTION
  "Recoverable CRC memory error on memory link."
  --#TYPE         "Recoverable CRC memory error on memory link"
  --#SUMMARY      "%s"
  --#ARGUMENTS    { 1 }
  --#SEVERITY     INFORMATIONAL
  --#TIMEINDEX    1
  --#HELP         "Note: This is no error condition."
  --#HELPTAG      0
  --#STATE        OPERATIONAL
  ::=  14774272 

wfmFatalCRCMemoryErrorOnMemoryLink TRAP-TYPE
  ENTERPRISE wfmTrapInfo
  VARIABLES {
    wfmTrapDetails,
    wfmTrapType
  }
  DESCRIPTION
  "Fatal CRC memory error on memory link"
  --#TYPE         "Fatal CRC memory error on memory link"
  --#SUMMARY      "%s"
  --#ARGUMENTS    { 1 }
  --#SEVERITY     CRITICAL
  --#TIMEINDEX    1
  --#HELPTAG      0
  --#STATE        OPERATIONAL
  ::=  14774273 

wfmFSCSystemPoweredOnReason TRAP-TYPE
  ENTERPRISE wfmTrapInfo
  VARIABLES {
    wfmTrapDetails,
    wfmTrapType
  }
  DESCRIPTION
  "FSC: System powered on reason."
  --#TYPE         "FSC: System powered on reason"
  --#SUMMARY      "%s"
  --#ARGUMENTS    { 1 }
  --#SEVERITY     INFORMATIONAL
  --#TIMEINDEX    1
  --#HELP         "Note: This is no error condition."
  --#HELPTAG      0
  --#STATE        OPERATIONAL
  ::=  14839552 

wfmTrustedPlatformModuleTPMFailureOrStateChange TRAP-TYPE
  ENTERPRISE wfmTrapInfo
  VARIABLES {
    wfmTrapDetails,
    wfmTrapType
  }
  DESCRIPTION
  "Trusted Platform Module (TPM): Failure or state change"
  --#TYPE         "Trusted Platform Module (TPM): Failure or state change"
  --#SUMMARY      "%s"
  --#ARGUMENTS    { 1 }
  --#SEVERITY     MAJOR
  --#TIMEINDEX    1
  --#HELPTAG      0
  --#STATE        OPERATIONAL
  ::=  14905088 

wfmFSCNoUsableCPU TRAP-TYPE
  ENTERPRISE wfmTrapInfo
  VARIABLES {
    wfmTrapDetails,
    wfmTrapType
  }
  DESCRIPTION
  "FSC: No usable CPU."
  --#TYPE         "FSC: No usable CPU"
  --#SUMMARY      "%s"
  --#ARGUMENTS    { 1 }
  --#SEVERITY     CRITICAL
  --#TIMEINDEX    1
  --#HELPTAG      0
  --#STATE        OPERATIONAL
  ::=  14905090 

wfmFSCSystemConfigurationDataError TRAP-TYPE
  ENTERPRISE wfmTrapInfo
  VARIABLES {
    wfmTrapDetails,
    wfmTrapType
  }
  DESCRIPTION
  "FSC: System configuration Data error."
  --#TYPE         "FSC: System configuration Data error"
  --#SUMMARY      "%s"
  --#ARGUMENTS    { 1 }
  --#SEVERITY     MAJOR
  --#TIMEINDEX    1
  --#HELPTAG      0
  --#STATE        OPERATIONAL
  ::=  14970624 

wfmFSCResourceConflict TRAP-TYPE
  ENTERPRISE wfmTrapInfo
  VARIABLES {
    wfmTrapDetails,
    wfmTrapType
  }
  DESCRIPTION
  "FSC: Resource Conflict."
  --#TYPE         "FSC: Resource Conflict"
  --#SUMMARY      "%s"
  --#ARGUMENTS    { 1 }
  --#SEVERITY     MAJOR
  --#TIMEINDEX    1
  --#HELPTAG      0
  --#STATE        OPERATIONAL
  ::=  14970625 

wfmFSCIRQNotConfigured TRAP-TYPE
  ENTERPRISE wfmTrapInfo
  VARIABLES {
    wfmTrapDetails,
    wfmTrapType
  }
  DESCRIPTION
  "FSC: IRQ not configured."
  --#TYPE         "FSC: IRQ not configured"
  --#SUMMARY      "%s"
  --#ARGUMENTS    { 1 }
  --#SEVERITY     MAJOR
  --#TIMEINDEX    1
  --#HELPTAG      0
  --#STATE        OPERATIONAL
  ::=  14970626 

wfmFSCDeviceNodeAllocationError TRAP-TYPE
  ENTERPRISE wfmTrapInfo
  VARIABLES {
    wfmTrapDetails,
    wfmTrapType
  }
  DESCRIPTION
  "FSC: Device node allocation error."
  --#TYPE         "FSC: Device node allocation error"
  --#SUMMARY      "%s"
  --#ARGUMENTS    { 1 }
  --#SEVERITY     MAJOR
  --#TIMEINDEX    1
  --#HELPTAG      0
  --#STATE        OPERATIONAL
  ::=  14970627 

wfmFSCExpansionROMSlotNotInitialized TRAP-TYPE
  ENTERPRISE wfmTrapInfo
  VARIABLES {
    wfmTrapDetails,
    wfmTrapType
  }
  DESCRIPTION
  "FSC: Expansion ROM Slot not initialized."
  --#TYPE         "FSC: Expansion ROM Slot not initialized"
  --#SUMMARY      "%s"
  --#ARGUMENTS    { 1 }
  --#SEVERITY     MAJOR
  --#TIMEINDEX    1
  --#HELPTAG      0
  --#STATE        OPERATIONAL
  ::=  14970628 

wfmSystemPerformanceLimitedByBMC TRAP-TYPE
  ENTERPRISE wfmTrapInfo
  VARIABLES {
    wfmTrapDetails,
    wfmTrapType
  }
  DESCRIPTION
  "System performance limited by BMC"
  --#TYPE         "System performance limited by BMC"
  --#SUMMARY      "%s"
  --#ARGUMENTS    { 1 }
  --#SEVERITY     INFORMATIONAL
  --#TIMEINDEX    1
  --#HELP         "Note: This is no error condition."
  --#HELPTAG      0
  --#STATE        OPERATIONAL
  ::=  15036160 

wfmFSCFanONRunning TRAP-TYPE
  ENTERPRISE wfmTrapInfo
  VARIABLES {
    wfmTrapDetails,
    wfmTrapType
  }
  DESCRIPTION
  "FSC: Fan ON, running."
  --#TYPE         "FSC: Fan ON, running"
  --#SUMMARY      "%s"
  --#ARGUMENTS    { 1 }
  --#SEVERITY     INFORMATIONAL
  --#TIMEINDEX    1
  --#HELP         "Note: This is no error condition."
  --#HELPTAG      0
  --#STATE        OPERATIONAL
  ::=  15101696 

wfmFSCFanFailed TRAP-TYPE
  ENTERPRISE wfmTrapInfo
  VARIABLES {
    wfmTrapDetails,
    wfmTrapType
  }
  DESCRIPTION
  "FSC: Fan failed."
  --#TYPE         "FSC: Fan failed"
  --#SUMMARY      "%s"
  --#ARGUMENTS    { 1 }
  --#SEVERITY     CRITICAL
  --#TIMEINDEX    1
  --#HELPTAG      0
  --#STATE        OPERATIONAL
  ::=  15101697 

wfmFSCFanPrefailure TRAP-TYPE
  ENTERPRISE wfmTrapInfo
  VARIABLES {
    wfmTrapDetails,
    wfmTrapType
  }
  DESCRIPTION
  "FSC: Fan pre-failure."
  --#TYPE         "FSC: Fan pre-failure"
  --#SUMMARY      "%s"
  --#ARGUMENTS    { 1 }
  --#SEVERITY     MAJOR
  --#TIMEINDEX    1
  --#HELPTAG      0
  --#STATE        OPERATIONAL
  ::=  15101698 

wfmFSCRedundantFanFailed TRAP-TYPE
  ENTERPRISE wfmTrapInfo
  VARIABLES {
    wfmTrapDetails,
    wfmTrapType
  }
  DESCRIPTION
  "FSC: Redundant fan failed."
  --#TYPE         "FSC: Redundant fan failed"
  --#SUMMARY      "%s"
  --#ARGUMENTS    { 1 }
  --#SEVERITY     MAJOR
  --#TIMEINDEX    1
  --#HELPTAG      0
  --#STATE        OPERATIONAL
  ::=  15101699 

wfmFSCFanNotManageable TRAP-TYPE
  ENTERPRISE wfmTrapInfo
  VARIABLES {
    wfmTrapDetails,
    wfmTrapType
  }
  DESCRIPTION
  "FSC: Fan not manageable."
  --#TYPE         "FSC: Fan not manageable"
  --#SUMMARY      "%s"
  --#ARGUMENTS    { 1 }
  --#SEVERITY     INFORMATIONAL
  --#TIMEINDEX    1
  --#HELP         "Note: This is no error condition."
  --#HELPTAG      0
  --#STATE        OPERATIONAL
  ::=  15101700 

wfmFSCFanNotInstalled TRAP-TYPE
  ENTERPRISE wfmTrapInfo
  VARIABLES {
    wfmTrapDetails,
    wfmTrapType
  }
  DESCRIPTION
  "FSC: Fan not installed."
  --#TYPE         "FSC: Fan not installed"
  --#SUMMARY      "%s"
  --#ARGUMENTS    { 1 }
  --#SEVERITY     INFORMATIONAL
  --#TIMEINDEX    1
  --#HELP         "Note: This is no error condition."
  --#HELPTAG      0
  --#STATE        OPERATIONAL
  ::=  15101701 

wfmFSCHDDNotPresentOrEmptySlot TRAP-TYPE
  ENTERPRISE wfmTrapInfo
  VARIABLES {
    wfmTrapDetails,
    wfmTrapType
  }
  DESCRIPTION
  "FSC: HDD Not present or empty slot."
  --#TYPE         "FSC: HDD Not present or empty slot"
  --#SUMMARY      "%s"
  --#ARGUMENTS    { 1 }
  --#SEVERITY     INFORMATIONAL
  --#TIMEINDEX    1
  --#HELP         "Note: This is no error condition."
  --#HELPTAG      0
  --#STATE        OPERATIONAL
  ::=  15167232 

wfmFSCHDDStatusOK TRAP-TYPE
  ENTERPRISE wfmTrapInfo
  VARIABLES {
    wfmTrapDetails,
    wfmTrapType
  }
  DESCRIPTION
  "FSC: HDD Status OK."
  --#TYPE         "FSC: HDD Status OK"
  --#SUMMARY      "%s"
  --#ARGUMENTS    { 1 }
  --#SEVERITY     INFORMATIONAL
  --#TIMEINDEX    1
  --#HELP         "Note: This is no error condition."
  --#HELPTAG      0
  --#STATE        OPERATIONAL
  ::=  15167233 

wfmFSCHDDPrefailure TRAP-TYPE
  ENTERPRISE wfmTrapInfo
  VARIABLES {
    wfmTrapDetails,
    wfmTrapType
  }
  DESCRIPTION
  "FSC: HDD Pre-failure."
  --#TYPE         "FSC: HDD Pre-failure"
  --#SUMMARY      "%s"
  --#ARGUMENTS    { 1 }
  --#SEVERITY     MAJOR
  --#TIMEINDEX    1
  --#HELPTAG      0
  --#STATE        OPERATIONAL
  ::=  15167234 

wfmFSCHDDFailed TRAP-TYPE
  ENTERPRISE wfmTrapInfo
  VARIABLES {
    wfmTrapDetails,
    wfmTrapType
  }
  DESCRIPTION
  "FSC: HDD Failed."
  --#TYPE         "FSC: HDD Failed"
  --#SUMMARY      "%s"
  --#ARGUMENTS    { 1 }
  --#SEVERITY     CRITICAL
  --#TIMEINDEX    1
  --#HELPTAG      0
  --#STATE        OPERATIONAL
  ::=  15167235 

wfmFSCHDDIdentify TRAP-TYPE
  ENTERPRISE wfmTrapInfo
  VARIABLES {
    wfmTrapDetails,
    wfmTrapType
  }
  DESCRIPTION
  "FSC: HDD Identify."
  --#TYPE         "FSC: HDD Identify"
  --#SUMMARY      "%s"
  --#ARGUMENTS    { 1 }
  --#SEVERITY     INFORMATIONAL
  --#TIMEINDEX    1
  --#HELP         "Note: This is no error condition."
  --#HELPTAG      0
  --#STATE        OPERATIONAL
  ::=  15167236 

wfmFSCHDDRebuilding TRAP-TYPE
  ENTERPRISE wfmTrapInfo
  VARIABLES {
    wfmTrapDetails,
    wfmTrapType
  }
  DESCRIPTION
  "FSC: HDD Rebuilding."
  --#TYPE         "FSC: HDD Rebuilding"
  --#SUMMARY      "%s"
  --#ARGUMENTS    { 1 }
  --#SEVERITY     INFORMATIONAL
  --#TIMEINDEX    1
  --#HELP         "Note: This is no error condition."
  --#HELPTAG      0
  --#STATE        OPERATIONAL
  ::=  15167237 

wfmFSCHDDPresent TRAP-TYPE
  ENTERPRISE wfmTrapInfo
  VARIABLES {
    wfmTrapDetails,
    wfmTrapType
  }
  DESCRIPTION
  "FSC: HDD Present."
  --#TYPE         "FSC: HDD Present"
  --#SUMMARY      "%s"
  --#ARGUMENTS    { 1 }
  --#SEVERITY     INFORMATIONAL
  --#TIMEINDEX    1
  --#HELP         "Note: This is no error condition."
  --#HELPTAG      0
  --#STATE        OPERATIONAL
  ::=  15167360 

wfmFSCHDDStatusNotOK TRAP-TYPE
  ENTERPRISE wfmTrapInfo
  VARIABLES {
    wfmTrapDetails,
    wfmTrapType
  }
  DESCRIPTION
  "FSC: HDD Status not OK."
  --#TYPE         "FSC: HDD Status not OK"
  --#SUMMARY      "%s"
  --#ARGUMENTS    { 1 }
  --#SEVERITY     MAJOR
  --#TIMEINDEX    1
  --#HELPTAG      0
  --#STATE        OPERATIONAL
  ::=  15167361 

wfmRAIDControllerLogicalDriveOperational TRAP-TYPE
  ENTERPRISE wfmTrapInfo
  VARIABLES {
    wfmTrapDetails,
    wfmTrapType
  }
  DESCRIPTION
  "RAID controller: Logical drive operational"
  --#TYPE         "RAID controller: Logical drive operational"
  --#SUMMARY      "%s"
  --#ARGUMENTS    { 1 }
  --#SEVERITY     INFORMATIONAL
  --#TIMEINDEX    1
  --#HELP         "Note: This is no error condition."
  --#HELPTAG      0
  --#STATE        OPERATIONAL
  ::=  15171072 

wfmRAIDControllerLogicalDrivePartiallyDegraded TRAP-TYPE
  ENTERPRISE wfmTrapInfo
  VARIABLES {
    wfmTrapDetails,
    wfmTrapType
  }
  DESCRIPTION
  "RAID controller: Logical drive partially degraded"
  --#TYPE         "RAID controller: Logical drive partially degraded"
  --#SUMMARY      "%s"
  --#ARGUMENTS    { 1 }
  --#SEVERITY     MAJOR
  --#TIMEINDEX    1
  --#HELPTAG      0
  --#STATE        OPERATIONAL
  ::=  15171073 

wfmRAIDControllerLogicalDriveDegraded TRAP-TYPE
  ENTERPRISE wfmTrapInfo
  VARIABLES {
    wfmTrapDetails,
    wfmTrapType
  }
  DESCRIPTION
  "RAID controller: Logical drive degraded"
  --#TYPE         "RAID controller: Logical drive degraded"
  --#SUMMARY      "%s"
  --#ARGUMENTS    { 1 }
  --#SEVERITY     MAJOR
  --#TIMEINDEX    1
  --#HELPTAG      0
  --#STATE        OPERATIONAL
  ::=  15171074 

wfmRAIDControllerLogicalDriveFailed TRAP-TYPE
  ENTERPRISE wfmTrapInfo
  VARIABLES {
    wfmTrapDetails,
    wfmTrapType
  }
  DESCRIPTION
  "RAID controller: Logical drive failed"
  --#TYPE         "RAID controller: Logical drive failed"
  --#SUMMARY      "%s"
  --#ARGUMENTS    { 1 }
  --#SEVERITY     MAJOR
  --#TIMEINDEX    1
  --#HELPTAG      0
  --#STATE        OPERATIONAL
  ::=  15171075 

wfmFSCRedundantPowerSupplyNotPresent TRAP-TYPE
  ENTERPRISE wfmTrapInfo
  VARIABLES {
    wfmTrapDetails,
    wfmTrapType
  }
  DESCRIPTION
  "FSC: Redundant power supply not present."
  --#TYPE         "FSC: Redundant power supply not present"
  --#SUMMARY      "%s"
  --#ARGUMENTS    { 1 }
  --#SEVERITY     INFORMATIONAL
  --#TIMEINDEX    1
  --#HELP         "Note: This is no error condition."
  --#HELPTAG      0
  --#STATE        OPERATIONAL
  ::=  15232768 

wfmFSCRedundantPowerSupplyOK TRAP-TYPE
  ENTERPRISE wfmTrapInfo
  VARIABLES {
    wfmTrapDetails,
    wfmTrapType
  }
  DESCRIPTION
  "FSC: Redundant power supply OK."
  --#TYPE         "FSC: Redundant power supply OK"
  --#SUMMARY      "%s"
  --#ARGUMENTS    { 1 }
  --#SEVERITY     INFORMATIONAL
  --#TIMEINDEX    1
  --#HELP         "Note: This is no error condition."
  --#HELPTAG      0
  --#STATE        OPERATIONAL
  ::=  15232769 

wfmFSCRedundantPowerSupplyFailed TRAP-TYPE
  ENTERPRISE wfmTrapInfo
  VARIABLES {
    wfmTrapDetails,
    wfmTrapType
  }
  DESCRIPTION
  "FSC: Redundant power supply Failed."
  --#TYPE         "FSC: Redundant power supply Failed"
  --#SUMMARY      "%s"
  --#ARGUMENTS    { 1 }
  --#SEVERITY     MAJOR
  --#TIMEINDEX    1
  --#HELPTAG      0
  --#STATE        OPERATIONAL
  ::=  15232770 

wfmFSCRedundantPowerSupplyACFail TRAP-TYPE
  ENTERPRISE wfmTrapInfo
  VARIABLES {
    wfmTrapDetails,
    wfmTrapType
  }
  DESCRIPTION
  "FSC: Redundant power supply AC fail."
  --#TYPE         "FSC: Redundant power supply AC fail"
  --#SUMMARY      "%s"
  --#ARGUMENTS    { 1 }
  --#SEVERITY     MAJOR
  --#TIMEINDEX    1
  --#HELPTAG      0
  --#STATE        OPERATIONAL
  ::=  15232771 

wfmFSCRedundantPowerSupplyDCFail TRAP-TYPE
  ENTERPRISE wfmTrapInfo
  VARIABLES {
    wfmTrapDetails,
    wfmTrapType
  }
  DESCRIPTION
  "FSC: Redundant power supply DC fail."
  --#TYPE         "FSC: Redundant power supply DC fail"
  --#SUMMARY      "%s"
  --#ARGUMENTS    { 1 }
  --#SEVERITY     MAJOR
  --#TIMEINDEX    1
  --#HELPTAG      0
  --#STATE        OPERATIONAL
  ::=  15232772 

wfmFSCRedundantPowerSupplyCritTemp TRAP-TYPE
  ENTERPRISE wfmTrapInfo
  VARIABLES {
    wfmTrapDetails,
    wfmTrapType
  }
  DESCRIPTION
  "FSC: Redundant power supply Crit. Temp.."
  --#TYPE         "FSC: Redundant power supply Crit. Temp."
  --#SUMMARY      "%s"
  --#ARGUMENTS    { 1 }
  --#SEVERITY     MAJOR
  --#TIMEINDEX    1
  --#HELPTAG      0
  --#STATE        OPERATIONAL
  ::=  15232773 

wfmFSCRedundantPowerSupplyNotManageable TRAP-TYPE
  ENTERPRISE wfmTrapInfo
  VARIABLES {
    wfmTrapDetails,
    wfmTrapType
  }
  DESCRIPTION
  "FSC: Redundant power supply not manageable."
  --#TYPE         "FSC: Redundant power supply not manageable"
  --#SUMMARY      "%s"
  --#ARGUMENTS    { 1 }
  --#SEVERITY     INFORMATIONAL
  --#TIMEINDEX    1
  --#HELP         "Note: This is no error condition."
  --#HELPTAG      0
  --#STATE        OPERATIONAL
  ::=  15232774 

wfmFSCPowerSupplyFanPrefailure TRAP-TYPE
  ENTERPRISE wfmTrapInfo
  VARIABLES {
    wfmTrapDetails,
    wfmTrapType
  }
  DESCRIPTION
  "FSC: Power supply fan prefailure."
  --#TYPE         "FSC: Power supply fan prefailure"
  --#SUMMARY      "%s"
  --#ARGUMENTS    { 1 }
  --#SEVERITY     MAJOR
  --#TIMEINDEX    1
  --#HELPTAG      0
  --#STATE        OPERATIONAL
  ::=  15232775 

wfmFSCPowerSupplyFanFailed TRAP-TYPE
  ENTERPRISE wfmTrapInfo
  VARIABLES {
    wfmTrapDetails,
    wfmTrapType
  }
  DESCRIPTION
  "FSC: Power supply fan failed."
  --#TYPE         "FSC: Power supply fan failed"
  --#SUMMARY      "%s"
  --#ARGUMENTS    { 1 }
  --#SEVERITY     CRITICAL
  --#TIMEINDEX    1
  --#HELPTAG      0
  --#STATE        OPERATIONAL
  ::=  15232776 

wfmFSCPowerSupplyDCFailed TRAP-TYPE
  ENTERPRISE wfmTrapInfo
  VARIABLES {
    wfmTrapDetails,
    wfmTrapType
  }
  DESCRIPTION
  "FSC: Power supply DC failed."
  --#TYPE         "FSC: Power supply DC failed"
  --#SUMMARY      "%s"
  --#ARGUMENTS    { 1 }
  --#SEVERITY     CRITICAL
  --#TIMEINDEX    1
  --#HELPTAG      0
  --#STATE        OPERATIONAL
  ::=  15232778 

wfmFSCPowerSupplyACFailed TRAP-TYPE
  ENTERPRISE wfmTrapInfo
  VARIABLES {
    wfmTrapDetails,
    wfmTrapType
  }
  DESCRIPTION
  "FSC: Power supply AC failed."
  --#TYPE         "FSC: Power supply AC failed"
  --#SUMMARY      "%s"
  --#ARGUMENTS    { 1 }
  --#SEVERITY     MAJOR
  --#TIMEINDEX    1
  --#HELPTAG      0
  --#STATE        OPERATIONAL
  ::=  15232779 

wfmFSCPowerSupplyRedundancyPresent TRAP-TYPE
  ENTERPRISE wfmTrapInfo
  VARIABLES {
    wfmTrapDetails,
    wfmTrapType
  }
  DESCRIPTION
  "FSC: Power supply redundancy present."
  --#TYPE         "FSC: Power supply redundancy present"
  --#SUMMARY      "%s"
  --#ARGUMENTS    { 1 }
  --#SEVERITY     INFORMATIONAL
  --#TIMEINDEX    1
  --#HELP         "Note: This is no error condition."
  --#HELPTAG      0
  --#STATE        OPERATIONAL
  ::=  15298304 

wfmFSCPowerSupplyRedundancyLost TRAP-TYPE
  ENTERPRISE wfmTrapInfo
  VARIABLES {
    wfmTrapDetails,
    wfmTrapType
  }
  DESCRIPTION
  "FSC: Power supply redundancy lost."
  --#TYPE         "FSC: Power supply redundancy lost"
  --#SUMMARY      "%s"
  --#ARGUMENTS    { 1 }
  --#SEVERITY     MAJOR
  --#TIMEINDEX    1
  --#HELPTAG      0
  --#STATE        OPERATIONAL
  ::=  15298432 

wfmCPUThrottlingByBMCFWIsFinishedReturnedToNormalOperation TRAP-TYPE
  ENTERPRISE wfmTrapInfo
  VARIABLES {
    wfmTrapDetails,
    wfmTrapType
  }
  DESCRIPTION
  "CPU Throttling by BMC FW is finished. Returned to normal operation.."
  --#TYPE         "CPU Throttling by BMC FW is finished. Returned to normal operation."
  --#SUMMARY      "%s"
  --#ARGUMENTS    { 1 }
  --#SEVERITY     INFORMATIONAL
  --#TIMEINDEX    1
  --#HELP         "Note: This is no error condition."
  --#HELPTAG      0
  --#STATE        OPERATIONAL
  ::=  15429376 

wfmCPUThrottlingActivatedByPowerLimiting TRAP-TYPE
  ENTERPRISE wfmTrapInfo
  VARIABLES {
    wfmTrapDetails,
    wfmTrapType
  }
  DESCRIPTION
  "CPU Throttling activated by Power Limiting."
  --#TYPE         "CPU Throttling activated by Power Limiting"
  --#SUMMARY      "%s"
  --#ARGUMENTS    { 1 }
  --#SEVERITY     INFORMATIONAL
  --#TIMEINDEX    1
  --#HELP         "Note: This is no error condition."
  --#HELPTAG      0
  --#STATE        OPERATIONAL
  ::=  15429377 

wfmCPUThrottlingActivatedByMinimumPowerControlMode TRAP-TYPE
  ENTERPRISE wfmTrapInfo
  VARIABLES {
    wfmTrapDetails,
    wfmTrapType
  }
  DESCRIPTION
  "CPU Throttling activated by minimum power control mode."
  --#TYPE         "CPU Throttling activated by minimum power control mode"
  --#SUMMARY      "%s"
  --#ARGUMENTS    { 1 }
  --#SEVERITY     INFORMATIONAL
  --#TIMEINDEX    1
  --#HELP         "Note: This is no error condition."
  --#HELPTAG      0
  --#STATE        OPERATIONAL
  ::=  15429378 

wfmCPUThrottlingActivatedByPowerCapping TRAP-TYPE
  ENTERPRISE wfmTrapInfo
  VARIABLES {
    wfmTrapDetails,
    wfmTrapType
  }
  DESCRIPTION
  "CPU Throttling activated by Power Capping."
  --#TYPE         "CPU Throttling activated by Power Capping"
  --#SUMMARY      "%s"
  --#ARGUMENTS    { 1 }
  --#SEVERITY     INFORMATIONAL
  --#TIMEINDEX    1
  --#HELP         "Note: This is no error condition."
  --#HELPTAG      0
  --#STATE        OPERATIONAL
  ::=  15429379 

wfmCPUThrottlingActivatedByPowerSafeGuard TRAP-TYPE
  ENTERPRISE wfmTrapInfo
  VARIABLES {
    wfmTrapDetails,
    wfmTrapType
  }
  DESCRIPTION
  "CPU Throttling activated by Power SafeGuard."
  --#TYPE         "CPU Throttling activated by Power SafeGuard"
  --#SUMMARY      "%s"
  --#ARGUMENTS    { 1 }
  --#SEVERITY     INFORMATIONAL
  --#TIMEINDEX    1
  --#HELP         "Note: This is no error condition."
  --#HELPTAG      0
  --#STATE        OPERATIONAL
  ::=  15429380 

wfmCPUThrottlingActivatedBySensorStateMachine TRAP-TYPE
  ENTERPRISE wfmTrapInfo
  VARIABLES {
    wfmTrapDetails,
    wfmTrapType
  }
  DESCRIPTION
  "CPU Throttling activated by Sensor State Machine."
  --#TYPE         "CPU Throttling activated by Sensor State Machine"
  --#SUMMARY      "%s"
  --#ARGUMENTS    { 1 }
  --#SEVERITY     INFORMATIONAL
  --#TIMEINDEX    1
  --#HELP         "Note: This is no error condition."
  --#HELPTAG      0
  --#STATE        OPERATIONAL
  ::=  15429381 

wfmCPUThrottlingActivatedByLowNoiseMode TRAP-TYPE
  ENTERPRISE wfmTrapInfo
  VARIABLES {
    wfmTrapDetails,
    wfmTrapType
  }
  DESCRIPTION
  "CPU Throttling activated by Low Noise Mode."
  --#TYPE         "CPU Throttling activated by Low Noise Mode"
  --#SUMMARY      "%s"
  --#ARGUMENTS    { 1 }
  --#SEVERITY     INFORMATIONAL
  --#TIMEINDEX    1
  --#HELP         "Note: This is no error condition."
  --#HELPTAG      0
  --#STATE        OPERATIONAL
  ::=  15429382 

wfmOnlineFirmwareFlash TRAP-TYPE
  ENTERPRISE wfmTrapInfo
  VARIABLES {
    wfmTrapDetails,
    wfmTrapType
  }
  DESCRIPTION
  "Online Firmware Flash."
  --#TYPE         "Online Firmware Flash"
  --#SUMMARY      "%s"
  --#ARGUMENTS    { 1 }
  --#SEVERITY     INFORMATIONAL
  --#TIMEINDEX    1
  --#HELP         "Note: This is no error condition."
  --#HELPTAG      0
  --#STATE        OPERATIONAL
  ::=  15494912 

wfmOnlineFirmwareFlashBMCReboot TRAP-TYPE
  ENTERPRISE wfmTrapInfo
  VARIABLES {
    wfmTrapDetails,
    wfmTrapType
  }
  DESCRIPTION
  "Online Firmware Flash BMC reboot."
  --#TYPE         "Online Firmware Flash BMC reboot"
  --#SUMMARY      "%s"
  --#ARGUMENTS    { 1 }
  --#SEVERITY     INFORMATIONAL
  --#TIMEINDEX    1
  --#HELP         "Note: This is no error condition."
  --#HELPTAG      0
  --#STATE        OPERATIONAL
  ::=  15494913 

wfmBIOSTFTPFlashOK TRAP-TYPE
  ENTERPRISE wfmTrapInfo
  VARIABLES {
    wfmTrapDetails,
    wfmTrapType
  }
  DESCRIPTION
  "BIOS TFTP Flash: OK."
  --#TYPE         "BIOS TFTP FlashOK"
  --#SUMMARY      "%s"
  --#ARGUMENTS    { 1 }
  --#SEVERITY     INFORMATIONAL
  --#TIMEINDEX    1
  --#HELP         "Note: This is no error condition."
  --#HELPTAG      0
  --#STATE        OPERATIONAL
  ::=  15494914 

wfmBIOSTFTPFlashFailed TRAP-TYPE
  ENTERPRISE wfmTrapInfo
  VARIABLES {
    wfmTrapDetails,
    wfmTrapType
  }
  DESCRIPTION
  "BIOS TFTP Flash: failed."
  --#TYPE         "BIOS TFTP Flash: failed"
  --#SUMMARY      "%s"
  --#ARGUMENTS    { 1 }
  --#SEVERITY     MAJOR
  --#TIMEINDEX    1
  --#HELPTAG      0
  --#STATE        OPERATIONAL
  ::=  15494915 

wfmiRMCTFTPFlashOK TRAP-TYPE
  ENTERPRISE wfmTrapInfo
  VARIABLES {
    wfmTrapDetails,
    wfmTrapType
  }
  DESCRIPTION
  "iRMC TFTP Flash: OK."
  --#TYPE         "iRMC TFTP FlashOK"
  --#SUMMARY      "%s"
  --#ARGUMENTS    { 1 }
  --#SEVERITY     INFORMATIONAL
  --#TIMEINDEX    1
  --#HELP         "Note: This is no error condition."
  --#HELPTAG      0
  --#STATE        OPERATIONAL
  ::=  15494916 

wfmiRMCTFTPFlashFailed TRAP-TYPE
  ENTERPRISE wfmTrapInfo
  VARIABLES {
    wfmTrapDetails,
    wfmTrapType
  }
  DESCRIPTION
  "iRMC TFTP Flash: failed."
  --#TYPE         "iRMC TFTP Flash: failed"
  --#SUMMARY      "%s"
  --#ARGUMENTS    { 1 }
  --#SEVERITY     MAJOR
  --#TIMEINDEX    1
  --#HELPTAG      0
  --#STATE        OPERATIONAL
  ::=  15494917 

wfmWarrantyVoidedTemperatureExceededForTooManyHours TRAP-TYPE
  ENTERPRISE wfmTrapInfo
  VARIABLES {
    wfmTrapDetails,
    wfmTrapType
  }
  DESCRIPTION
  "Warranty voided: temperature exceeded for too many hours."
  --#TYPE         "Warranty voided: temperature exceeded for too many hours"
  --#SUMMARY      "%s"
  --#ARGUMENTS    { 1 }
  --#SEVERITY     MAJOR
  --#TIMEINDEX    1
  --#HELPTAG      0
  --#STATE        OPERATIONAL
  ::=  15560448 

wfmWarrantyVoidedTooManyTemperatureEvents TRAP-TYPE
  ENTERPRISE wfmTrapInfo
  VARIABLES {
    wfmTrapDetails,
    wfmTrapType
  }
  DESCRIPTION
  "Warranty voided: too many temperature events."
  --#TYPE         "Warranty voided: too many temperature events"
  --#SUMMARY      "%s"
  --#ARGUMENTS    { 1 }
  --#SEVERITY     MAJOR
  --#TIMEINDEX    1
  --#HELPTAG      0
  --#STATE        OPERATIONAL
  ::=  15560449 

wfmFSCPowerOn TRAP-TYPE
  ENTERPRISE wfmTrapInfo
  VARIABLES {
    wfmTrapDetails,
    wfmTrapType
  }
  DESCRIPTION
  "FSC: Power On."
  --#TYPE         "FSC: Power On"
  --#SUMMARY      "%s"
  --#ARGUMENTS    { 1 }
  --#SEVERITY     INFORMATIONAL
  --#TIMEINDEX    1
  --#HELP         "Note: This is no error condition."
  --#HELPTAG      0
  --#STATE        OPERATIONAL
  ::=  15600128 

wfmFSCPowerOff TRAP-TYPE
  ENTERPRISE wfmTrapInfo
  VARIABLES {
    wfmTrapDetails,
    wfmTrapType
  }
  DESCRIPTION
  "FSC: Power Off."
  --#TYPE         "FSC: Power Off"
  --#SUMMARY      "%s"
  --#ARGUMENTS    { 1 }
  --#SEVERITY     INFORMATIONAL
  --#TIMEINDEX    1
  --#HELP         "Note: This is no error condition."
  --#HELPTAG      0
  --#STATE        OPERATIONAL
  ::=  15600130 

wfmSystemPoweredOnOrReboot TRAP-TYPE
  ENTERPRISE wfmTrapInfo
  VARIABLES {
    wfmTrapDetails,
    wfmTrapType
  }
  DESCRIPTION
  "System powered on or reboot"
  --#TYPE         "System powered on or reboot"
  --#SUMMARY      "%s"
  --#ARGUMENTS    { 1 }
  --#SEVERITY     INFORMATIONAL
  --#TIMEINDEX    1
  --#HELP         "Note: This is no error condition."
  --#HELPTAG      0
  --#STATE        OPERATIONAL
  ::=  15625984 

wfmSystemPoweredOff TRAP-TYPE
  ENTERPRISE wfmTrapInfo
  VARIABLES {
    wfmTrapDetails,
    wfmTrapType
  }
  DESCRIPTION
  "System powered off"
  --#TYPE         "System powered off"
  --#SUMMARY      "%s"
  --#ARGUMENTS    { 1 }
  --#SEVERITY     INFORMATIONAL
  --#TIMEINDEX    1
  --#HELP         "Note: This is no error condition."
  --#HELPTAG      0
  --#STATE        OPERATIONAL
  ::=  15625986 

wfmASRRCounterExceededRestartTries TRAP-TYPE
  ENTERPRISE wfmTrapInfo
  VARIABLES {
    wfmTrapDetails,
    wfmTrapType
  }
  DESCRIPTION
  "ASR & R counter exceeded restart tries"
  --#TYPE         "ASR & R counter exceeded restart tries"
  --#SUMMARY      "%s"
  --#ARGUMENTS    { 1 }
  --#SEVERITY     INFORMATIONAL
  --#TIMEINDEX    1
  --#HELP         "Note: This is no error condition."
  --#HELPTAG      0
  --#STATE        OPERATIONAL
  ::=  15625987 

wfmChassisIDPROMMotherboardExchangeDetected TRAP-TYPE
  ENTERPRISE wfmTrapInfo
  VARIABLES {
    wfmTrapDetails,
    wfmTrapType
  }
  DESCRIPTION
  "Chassis IDPROM: Motherboard Exchange detected."
  --#TYPE         "Chassis IDPROM: Motherboard Exchange detected"
  --#SUMMARY      "%s"
  --#ARGUMENTS    { 1 }
  --#SEVERITY     INFORMATIONAL
  --#TIMEINDEX    1
  --#HELP         "Note: This is no error condition."
  --#HELPTAG      0
  --#STATE        OPERATIONAL
  ::=  15691520 

wfmChassisIDPROMReadOrWriteError TRAP-TYPE
  ENTERPRISE wfmTrapInfo
  VARIABLES {
    wfmTrapDetails,
    wfmTrapType
  }
  DESCRIPTION
  "Chassis IDPROM: Read or Write error."
  --#TYPE         "Chassis IDPROM: Read or Write error"
  --#SUMMARY      "%s"
  --#ARGUMENTS    { 1 }
  --#SEVERITY     MINOR
  --#TIMEINDEX    1
  --#HELPTAG      0
  --#STATE        OPERATIONAL
  ::=  15691521 

wfmChassisIDPROMRestoreSuccessful TRAP-TYPE
  ENTERPRISE wfmTrapInfo
  VARIABLES {
    wfmTrapDetails,
    wfmTrapType
  }
  DESCRIPTION
  "Chassis IDPROM: Restore successful."
  --#TYPE         "Chassis IDPROM: Restore successful"
  --#SUMMARY      "%s"
  --#ARGUMENTS    { 1 }
  --#SEVERITY     INFORMATIONAL
  --#TIMEINDEX    1
  --#HELP         "Note: This is no error condition."
  --#HELPTAG      0
  --#STATE        OPERATIONAL
  ::=  15691522 

wfmChassisIDPROMRestoreFailed TRAP-TYPE
  ENTERPRISE wfmTrapInfo
  VARIABLES {
    wfmTrapDetails,
    wfmTrapType
  }
  DESCRIPTION
  "Chassis IDPROM: Restore failed."
  --#TYPE         "Chassis IDPROM: Restore failed"
  --#SUMMARY      "%s"
  --#ARGUMENTS    { 1 }
  --#SEVERITY     MAJOR
  --#TIMEINDEX    1
  --#HELPTAG      0
  --#STATE        OPERATIONAL
  ::=  15691523 

wfmChassisIDPROMBackupSuccessful TRAP-TYPE
  ENTERPRISE wfmTrapInfo
  VARIABLES {
    wfmTrapDetails,
    wfmTrapType
  }
  DESCRIPTION
  "Chassis IDPROM: Backup successful."
  --#TYPE         "Chassis IDPROM: Backup successful"
  --#SUMMARY      "%s"
  --#ARGUMENTS    { 1 }
  --#SEVERITY     INFORMATIONAL
  --#TIMEINDEX    1
  --#HELP         "Note: This is no error condition."
  --#HELPTAG      0
  --#STATE        OPERATIONAL
  ::=  15691524 

wfmChassisIDPROMBackupFailed TRAP-TYPE
  ENTERPRISE wfmTrapInfo
  VARIABLES {
    wfmTrapDetails,
    wfmTrapType
  }
  DESCRIPTION
  "Chassis IDPROM: Backup failed."
  --#TYPE         "Chassis IDPROM: Backup failed"
  --#SUMMARY      "%s"
  --#ARGUMENTS    { 1 }
  --#SEVERITY     MAJOR
  --#TIMEINDEX    1
  --#HELPTAG      0
  --#STATE        OPERATIONAL
  ::=  15691525 

wfmChassisIDPROMFeatureDisabled TRAP-TYPE
  ENTERPRISE wfmTrapInfo
  VARIABLES {
    wfmTrapDetails,
    wfmTrapType
  }
  DESCRIPTION
  "Chassis IDPROM: Feature disabled."
  --#TYPE         "Chassis IDPROM: Feature disabled"
  --#SUMMARY      "%s"
  --#ARGUMENTS    { 1 }
  --#SEVERITY     INFORMATIONAL
  --#TIMEINDEX    1
  --#HELP         "Note: This is no error condition."
  --#HELPTAG      0
  --#STATE        OPERATIONAL
  ::=  15691526 

wfmChassisIDPROMFunctionNotAvailable TRAP-TYPE
  ENTERPRISE wfmTrapInfo
  VARIABLES {
    wfmTrapDetails,
    wfmTrapType
  }
  DESCRIPTION
  "Chassis IDPROM: Function Not Available."
  --#TYPE         "Chassis IDPROM: Function Not Available"
  --#SUMMARY      "%s"
  --#ARGUMENTS    { 1 }
  --#SEVERITY     MINOR
  --#TIMEINDEX    1
  --#HELPTAG      0
  --#STATE        OPERATIONAL
  ::=  15691527 

wfmBIOSSingleParameterBackupAndRestoreFailed TRAP-TYPE
  ENTERPRISE wfmTrapInfo
  VARIABLES {
    wfmTrapDetails,
    wfmTrapType
  }
  DESCRIPTION
  "BIOS single parameter backup and restore failed."
  --#TYPE         "BIOS single parameter backup and restore failed"
  --#SUMMARY      "%s"
  --#ARGUMENTS    { 1 }
  --#SEVERITY     MAJOR
  --#TIMEINDEX    1
  --#HELPTAG      0
  --#STATE        OPERATIONAL
  ::=  15691528 

wfmBIOSSingleParameterBackupOk TRAP-TYPE
  ENTERPRISE wfmTrapInfo
  VARIABLES {
    wfmTrapDetails,
    wfmTrapType
  }
  DESCRIPTION
  "BIOS single parameter backup ok."
  --#TYPE         "BIOS single parameter backup ok"
  --#SUMMARY      "%s"
  --#ARGUMENTS    { 1 }
  --#SEVERITY     INFORMATIONAL
  --#TIMEINDEX    1
  --#HELP         "Note: This is no error condition."
  --#HELPTAG      0
  --#STATE        OPERATIONAL
  ::=  15691529 

wfmBIOSSingleParameterBackupFailed TRAP-TYPE
  ENTERPRISE wfmTrapInfo
  VARIABLES {
    wfmTrapDetails,
    wfmTrapType
  }
  DESCRIPTION
  "BIOS single parameter backup failed."
  --#TYPE         "BIOS single parameter backup failed"
  --#SUMMARY      "%s"
  --#ARGUMENTS    { 1 }
  --#SEVERITY     MAJOR
  --#TIMEINDEX    1
  --#HELPTAG      0
  --#STATE        OPERATIONAL
  ::=  15691530 

wfmBIOSSingleParameterRestoreOk TRAP-TYPE
  ENTERPRISE wfmTrapInfo
  VARIABLES {
    wfmTrapDetails,
    wfmTrapType
  }
  DESCRIPTION
  "BIOS single parameter restore ok."
  --#TYPE         "BIOS single parameter restore ok"
  --#SUMMARY      "%s"
  --#ARGUMENTS    { 1 }
  --#SEVERITY     INFORMATIONAL
  --#TIMEINDEX    1
  --#HELP         "Note: This is no error condition."
  --#HELPTAG      0
  --#STATE        OPERATIONAL
  ::=  15691531 

wfmBIOSSingleParameterRestoreFailed TRAP-TYPE
  ENTERPRISE wfmTrapInfo
  VARIABLES {
    wfmTrapDetails,
    wfmTrapType
  }
  DESCRIPTION
  "BIOS single parameter restore failed."
  --#TYPE         "BIOS single parameter restore failed"
  --#SUMMARY      "%s"
  --#ARGUMENTS    { 1 }
  --#SEVERITY     MAJOR
  --#TIMEINDEX    1
  --#HELPTAG      0
  --#STATE        OPERATIONAL
  ::=  15691532 

wfmBIOSSingleParameterRestoreInvalidParameter TRAP-TYPE
  ENTERPRISE wfmTrapInfo
  VARIABLES {
    wfmTrapDetails,
    wfmTrapType
  }
  DESCRIPTION
  "BIOS single parameter restore invalid parameter."
  --#TYPE         "BIOS single parameter restore invalid parameter"
  --#SUMMARY      "%s"
  --#ARGUMENTS    { 1 }
  --#SEVERITY     MINOR
  --#TIMEINDEX    1
  --#HELPTAG      0
  --#STATE        OPERATIONAL
  ::=  15691533 

wfmiRMCNVRAMDefaultsLoaded TRAP-TYPE
  ENTERPRISE wfmTrapInfo
  VARIABLES {
    wfmTrapDetails,
    wfmTrapType
  }
  DESCRIPTION
  "iRMC NVRAM defaults loaded."
  --#TYPE         "iRMC NVRAM defaults loaded"
  --#SUMMARY      "%s"
  --#ARGUMENTS    { 1 }
  --#SEVERITY     INFORMATIONAL
  --#TIMEINDEX    1
  --#HELP         "Note: This is no error condition."
  --#HELPTAG      0
  --#STATE        OPERATIONAL
  ::=  15691535 

wfmVIOMCommandError TRAP-TYPE
  ENTERPRISE wfmTrapInfo
  VARIABLES {
    wfmTrapDetails,
    wfmTrapType
  }
  DESCRIPTION
  "VIOM command error."
  --#TYPE         "VIOM command error"
  --#SUMMARY      "%s"
  --#ARGUMENTS    { 1 }
  --#SEVERITY     MAJOR
  --#TIMEINDEX    1
  --#HELPTAG      0
  --#STATE        OPERATIONAL
  ::=  15757056 

wfmVIOMIncorrectData TRAP-TYPE
  ENTERPRISE wfmTrapInfo
  VARIABLES {
    wfmTrapDetails,
    wfmTrapType
  }
  DESCRIPTION
  "VIOM incorrect data."
  --#TYPE         "VIOM incorrect data"
  --#SUMMARY      "%s"
  --#ARGUMENTS    { 1 }
  --#SEVERITY     MAJOR
  --#TIMEINDEX    1
  --#HELPTAG      0
  --#STATE        OPERATIONAL
  ::=  15757057 

wfmVIOMEmulexError TRAP-TYPE
  ENTERPRISE wfmTrapInfo
  VARIABLES {
    wfmTrapDetails,
    wfmTrapType
  }
  DESCRIPTION
  "VIOM Emulex Error."
  --#TYPE         "VIOM Emulex Error"
  --#SUMMARY      "%s"
  --#ARGUMENTS    { 1 }
  --#SEVERITY     MAJOR
  --#TIMEINDEX    1
  --#HELPTAG      0
  --#STATE        OPERATIONAL
  ::=  15757058 

wfmVIOMBroadcomError TRAP-TYPE
  ENTERPRISE wfmTrapInfo
  VARIABLES {
    wfmTrapDetails,
    wfmTrapType
  }
  DESCRIPTION
  "VIOM Broadcom Error."
  --#TYPE         "VIOM Broadcom Error"
  --#SUMMARY      "%s"
  --#ARGUMENTS    { 1 }
  --#SEVERITY     MAJOR
  --#TIMEINDEX    1
  --#HELPTAG      0
  --#STATE        OPERATIONAL
  ::=  15757059 

wfmVIOMMMBError TRAP-TYPE
  ENTERPRISE wfmTrapInfo
  VARIABLES {
    wfmTrapDetails,
    wfmTrapType
  }
  DESCRIPTION
  "VIOM MMB Error."
  --#TYPE         "VIOM MMB Error"
  --#SUMMARY      "%s"
  --#ARGUMENTS    { 1 }
  --#SEVERITY     MAJOR
  --#TIMEINDEX    1
  --#HELPTAG      0
  --#STATE        OPERATIONAL
  ::=  15757060 

wfmVIOMCLPCommandNotSupported TRAP-TYPE
  ENTERPRISE wfmTrapInfo
  VARIABLES {
    wfmTrapDetails,
    wfmTrapType
  }
  DESCRIPTION
  "VIOM CLP Command not supported."
  --#TYPE         "VIOM CLP Command not supported"
  --#SUMMARY      "%s"
  --#ARGUMENTS    { 1 }
  --#SEVERITY     MAJOR
  --#TIMEINDEX    1
  --#HELPTAG      0
  --#STATE        OPERATIONAL
  ::=  15757061 

wfmVIOMCLPCommandInvalidArg TRAP-TYPE
  ENTERPRISE wfmTrapInfo
  VARIABLES {
    wfmTrapDetails,
    wfmTrapType
  }
  DESCRIPTION
  "VIOM CLP Command invalid arg."
  --#TYPE         "VIOM CLP Command invalid arg"
  --#SUMMARY      "%s"
  --#ARGUMENTS    { 1 }
  --#SEVERITY     MAJOR
  --#TIMEINDEX    1
  --#HELPTAG      0
  --#STATE        OPERATIONAL
  ::=  15757062 

wfmVIOMCLPCommandFailed TRAP-TYPE
  ENTERPRISE wfmTrapInfo
  VARIABLES {
    wfmTrapDetails,
    wfmTrapType
  }
  DESCRIPTION
  "VIOM CLP Command failed."
  --#TYPE         "VIOM CLP Command failed"
  --#SUMMARY      "%s"
  --#ARGUMENTS    { 1 }
  --#SEVERITY     MAJOR
  --#TIMEINDEX    1
  --#HELPTAG      0
  --#STATE        OPERATIONAL
  ::=  15757063 

wfmVIOMCLPCommandTimeout TRAP-TYPE
  ENTERPRISE wfmTrapInfo
  VARIABLES {
    wfmTrapDetails,
    wfmTrapType
  }
  DESCRIPTION
  "VIOM CLP Command Timeout."
  --#TYPE         "VIOM CLP Command Timeout"
  --#SUMMARY      "%s"
  --#ARGUMENTS    { 1 }
  --#SEVERITY     MAJOR
  --#TIMEINDEX    1
  --#HELPTAG      0
  --#STATE        OPERATIONAL
  ::=  15757064 

wfmVIOMIRMCConnectionToVIOMCMSFailedTimeoutAfterRetries TRAP-TYPE
  ENTERPRISE wfmTrapInfo
  VARIABLES {
    wfmTrapDetails,
    wfmTrapType
  }
  DESCRIPTION
  "VIOM: iRMC connection to VIOM CMS failed. Timeout after retries."
  --#TYPE         "VIOM: iRMC connection to VIOM CMS failed. Timeout after retries"
  --#SUMMARY      "%s"
  --#ARGUMENTS    { 1 }
  --#SEVERITY     CRITICAL
  --#TIMEINDEX    1
  --#HELPTAG      0
  --#STATE        OPERATIONAL
  ::=  15757067 

wfmVIOMIRMCConnectionToVIOMCMSSuccessful TRAP-TYPE
  ENTERPRISE wfmTrapInfo
  VARIABLES {
    wfmTrapDetails,
    wfmTrapType
  }
  DESCRIPTION
  "VIOM: iRMC connection to VIOM CMS successful."
  --#TYPE         "VIOM: iRMC connection to VIOM CMS successful"
  --#SUMMARY      "%s"
  --#ARGUMENTS    { 1 }
  --#SEVERITY     INFORMATIONAL
  --#TIMEINDEX    1
  --#HELP         "Note: This is no error condition."
  --#HELPTAG      0
  --#STATE        OPERATIONAL
  ::=  15757068 

wfmVIOMDisabledByUser TRAP-TYPE
  ENTERPRISE wfmTrapInfo
  VARIABLES {
    wfmTrapDetails,
    wfmTrapType
  }
  DESCRIPTION
  "VIOM disabled by user."
  --#TYPE         "VIOM disabled by user"
  --#SUMMARY      "%s"
  --#ARGUMENTS    { 1 }
  --#SEVERITY     INFORMATIONAL
  --#TIMEINDEX    1
  --#HELP         "Note: This is no error condition."
  --#HELPTAG      0
  --#STATE        OPERATIONAL
  ::=  15757069 

wfmVIOMTableClearedByVIOMLockTimeoutOnVIOMTableWrites TRAP-TYPE
  ENTERPRISE wfmTrapInfo
  VARIABLES {
    wfmTrapDetails,
    wfmTrapType
  }
  DESCRIPTION
  "VIOM Table cleared by VIOM lock timeout on VIOM Table writes."
  --#TYPE         "VIOM Table cleared by VIOM lock timeout on VIOM Table writes"
  --#SUMMARY      "%s"
  --#ARGUMENTS    { 1 }
  --#SEVERITY     MAJOR
  --#TIMEINDEX    1
  --#HELPTAG      0
  --#STATE        OPERATIONAL
  ::=  15757070 

wfmFSCSMITimeoutSeeXMBRecords TRAP-TYPE
  ENTERPRISE wfmTrapInfo
  VARIABLES {
    wfmTrapDetails,
    wfmTrapType
  }
  DESCRIPTION
  "FSC: SMI Timeout - see XMB records."
  --#TYPE         "FSC: SMI Timeout - see XMB records"
  --#SUMMARY      "%s"
  --#ARGUMENTS    { 1 }
  --#SEVERITY     INFORMATIONAL
  --#TIMEINDEX    1
  --#HELP         "Note: This is no error condition."
  --#HELPTAG      0
  --#STATE        OPERATIONAL
  ::=  15926017 



END
