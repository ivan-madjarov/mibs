--
-- This SMIv1 module has been generated by smidump 0.2.5. Do not edit.
--

UPS-MIB DEFINITIONS ::= BEGIN

IMPORTS
    OBJECT-TYPE
        FROM RFC-1212
    TRAP-TYPE
        FROM RFC-1215
    Counter, Gauge
        FROM RFC1155-SMI
    AutonomousType, TestAndIncr, TimeInterval, TimeStamp
        FROM SNMPv2-TC;

upsMIB OBJECT IDENTIFIER
    ::= { mib-2 33 }

-- upsMIB MODULE-IDENTITY
--     LAST-UPDATED "199402230000Z"
--     ORGANIZATION 
--         "IETF UPS MIB Working Group"
--     CONTACT-INFO 
--         "        Jeffrey D. Case
--          
--          Postal: SNMP Research, Incorporated
--                  3001 Kimberlin Heights Road
--                  Knoxville, TN  37920
--                  US
--          
--             Tel: +1 615 573 1434
--             Fax: +1 615 573 9197
--          
--          E-mail: case@snmp.com"
--     DESCRIPTION 
--         "The MIB module to describe Uninterruptible Power
--          Supplies."
--     ::= { mib-2 33 }


PositiveInteger ::=
    INTEGER (1..2147483647)

-- PositiveInteger ::= TEXTUAL-CONVENTION
--     DISPLAY-HINT "d"
--     STATUS      mandatory
--     DESCRIPTION 
--         "This data type is a non-zero and non-negative value."
--     SYNTAX      INTEGER (1..2147483647)

NonNegativeInteger ::=
    INTEGER (0..2147483647)

-- NonNegativeInteger ::= TEXTUAL-CONVENTION
--     DISPLAY-HINT "d"
--     STATUS      mandatory
--     DESCRIPTION 
--         "This data type is a non-negative value."
--     SYNTAX      INTEGER (0..2147483647)

upsObjects OBJECT IDENTIFIER
    ::= { upsMIB 1 }

upsIdent OBJECT IDENTIFIER
    ::= { upsObjects 1 }

upsIdentManufacturer OBJECT-TYPE
    SYNTAX      DisplayString (SIZE(0..31))
    ACCESS      read-only
    STATUS      mandatory
    DESCRIPTION 
        "The name of the UPS manufacturer."
    ::= { upsIdent 1 }

upsIdentModel OBJECT-TYPE
    SYNTAX      DisplayString (SIZE(0..63))
    ACCESS      read-only
    STATUS      mandatory
    DESCRIPTION 
        "The UPS Model designation."
    ::= { upsIdent 2 }

upsIdentUPSSoftwareVersion OBJECT-TYPE
    SYNTAX      DisplayString (SIZE(0..63))
    ACCESS      read-only
    STATUS      mandatory
    DESCRIPTION 
        "The UPS firmware/software version(s).  This variable
         may or may not have the same value as
         upsIdentAgentSoftwareVersion in some implementations."
    ::= { upsIdent 3 }

upsIdentAgentSoftwareVersion OBJECT-TYPE
    SYNTAX      DisplayString (SIZE(0..63))
    ACCESS      read-only
    STATUS      mandatory
    DESCRIPTION 
        "The UPS agent software version.  This variable may or
         may not have the same value as
         upsIdentUPSSoftwareVersion in some implementations."
    ::= { upsIdent 4 }

upsIdentName OBJECT-TYPE
    SYNTAX      DisplayString (SIZE(0..63))
    ACCESS      read-write
    STATUS      mandatory
    DESCRIPTION 
        "A string identifying the UPS.  This object should be
         set by the administrator."
    ::= { upsIdent 5 }

upsIdentAttachedDevices OBJECT-TYPE
    SYNTAX      DisplayString (SIZE(0..63))
    ACCESS      read-write
    STATUS      mandatory
    DESCRIPTION 
        "A string identifying the devices attached to the
         output(s) of the UPS.  This object should be set by
         the administrator."
    ::= { upsIdent 6 }

upsBattery OBJECT IDENTIFIER
    ::= { upsObjects 2 }

upsBatteryStatus OBJECT-TYPE
    SYNTAX      INTEGER { unknown(1), batteryNormal(2), batteryLow(3), 
                    batteryDepleted(4) }
    ACCESS      read-only
    STATUS      mandatory
    DESCRIPTION 
        "The indication of the capacity remaining in the UPS
         system's batteries.   A value of batteryNormal
         indicates that the remaining run-time is greater than
         upsConfigLowBattTime.  A value of batteryLow indicates
         that the remaining battery run-time is less than or
         equal to upsConfigLowBattTime.  A value of
         batteryDepleted indicates that the UPS will be unable
         to sustain the present load when and if the utility
         power is lost (including the possibility that the
         utility power is currently absent and the UPS is
         unable to sustain the output)."
    ::= { upsBattery 1 }

upsSecondsOnBattery OBJECT-TYPE
    SYNTAX      NonNegativeInteger
    ACCESS      read-only
    STATUS      mandatory
    DESCRIPTION 
        "If the unit is on battery power, the elapsed time
         since the UPS last switched to battery power, or the
         time since the network management subsystem was last
         restarted, whichever is less.  Zero shall be returned
         if the unit is not on battery power."
    ::= { upsBattery 2 }

upsEstimatedMinutesRemaining OBJECT-TYPE
    SYNTAX      PositiveInteger
    ACCESS      read-only
    STATUS      mandatory
    DESCRIPTION 
        "An estimate of the time to battery charge depletion
         under the present load conditions if the utility power
         is off and remains off, or if it were to be lost and
         remain off."
    ::= { upsBattery 3 }

upsEstimatedChargeRemaining OBJECT-TYPE
    SYNTAX      INTEGER (0..100)
    ACCESS      read-only
    STATUS      mandatory
    DESCRIPTION 
        "An estimate of the battery charge remaining expressed
         as a percent of full charge."
    ::= { upsBattery 4 }

upsBatteryVoltage OBJECT-TYPE
    SYNTAX      NonNegativeInteger
    ACCESS      read-only
    STATUS      mandatory
    DESCRIPTION 
        "The magnitude of the present battery voltage."
    ::= { upsBattery 5 }

upsBatteryCurrent OBJECT-TYPE
    SYNTAX      INTEGER
    ACCESS      read-only
    STATUS      mandatory
    DESCRIPTION 
        "The present battery current."
    ::= { upsBattery 6 }

upsBatteryTemperature OBJECT-TYPE
    SYNTAX      INTEGER
    ACCESS      read-only
    STATUS      mandatory
    DESCRIPTION 
        "The ambient temperature at or near the UPS Battery
         casing."
    ::= { upsBattery 7 }

upsInput OBJECT IDENTIFIER
    ::= { upsObjects 3 }

upsInputLineBads OBJECT-TYPE
    SYNTAX      Counter
    ACCESS      read-only
    STATUS      mandatory
    DESCRIPTION 
        "A count of the number of times the input entered an
         out-of-tolerance condition as defined by the
         manufacturer.  This count is incremented by one each
         time the input transitions from zero out-of-tolerance
         lines to one or more input lines out-of-tolerance."
    ::= { upsInput 1 }

upsInputNumLines OBJECT-TYPE
    SYNTAX      NonNegativeInteger
    ACCESS      read-only
    STATUS      mandatory
    DESCRIPTION 
        "The number of input lines utilized in this device.
         This variable indicates the number of rows in the
         input table."
    ::= { upsInput 2 }

upsInputTable OBJECT-TYPE
    SYNTAX      SEQUENCE OF UpsInputEntry
    ACCESS      not-accessible
    STATUS      mandatory
    DESCRIPTION 
        "A list of input table entries.  The number of entries
         is given by the value of upsInputNumLines."
    ::= { upsInput 3 }

upsInputEntry OBJECT-TYPE
    SYNTAX      UpsInputEntry
    ACCESS      not-accessible
    STATUS      mandatory
    DESCRIPTION 
        "An entry containing information applicable to a
         particular input line."
    INDEX       { upsInputLineIndex }
    ::= { upsInputTable 1 }

UpsInputEntry ::= SEQUENCE {
    upsInputLineIndex   PositiveInteger,
    upsInputFrequency   NonNegativeInteger,
    upsInputVoltage     NonNegativeInteger,
    upsInputCurrent     NonNegativeInteger,
    upsInputTruePower   NonNegativeInteger
}

upsInputLineIndex OBJECT-TYPE
    SYNTAX      PositiveInteger
    ACCESS      not-accessible
    STATUS      mandatory
    DESCRIPTION 
        "The input line identifier."
    ::= { upsInputEntry 1 }

upsInputFrequency OBJECT-TYPE
    SYNTAX      NonNegativeInteger
    ACCESS      read-only
    STATUS      mandatory
    DESCRIPTION 
        "The present input frequency."
    ::= { upsInputEntry 2 }

upsInputVoltage OBJECT-TYPE
    SYNTAX      NonNegativeInteger
    ACCESS      read-only
    STATUS      mandatory
    DESCRIPTION 
        "The magnitude of the present input voltage."
    ::= { upsInputEntry 3 }

upsInputCurrent OBJECT-TYPE
    SYNTAX      NonNegativeInteger
    ACCESS      read-only
    STATUS      mandatory
    DESCRIPTION 
        "The magnitude of the present input current."
    ::= { upsInputEntry 4 }

upsInputTruePower OBJECT-TYPE
    SYNTAX      NonNegativeInteger
    ACCESS      read-only
    STATUS      mandatory
    DESCRIPTION 
        "The magnitude of the present input true power."
    ::= { upsInputEntry 5 }

upsOutput OBJECT IDENTIFIER
    ::= { upsObjects 4 }

upsOutputSource OBJECT-TYPE
    SYNTAX      INTEGER { other(1), none(2), normal(3), bypass(4), 
                    battery(5), booster(6), reducer(7) }
    ACCESS      read-only
    STATUS      mandatory
    DESCRIPTION 
        "The present source of output power.  The enumeration
         none(2) indicates that there is no source of output
         power (and therefore no output power), for example,
         the system has opened the output breaker."
    ::= { upsOutput 1 }

upsOutputFrequency OBJECT-TYPE
    SYNTAX      NonNegativeInteger
    ACCESS      read-only
    STATUS      mandatory
    DESCRIPTION 
        "The present output frequency."
    ::= { upsOutput 2 }

upsOutputNumLines OBJECT-TYPE
    SYNTAX      NonNegativeInteger
    ACCESS      read-only
    STATUS      mandatory
    DESCRIPTION 
        "The number of output lines utilized in this device.
         This variable indicates the number of rows in the
         output table."
    ::= { upsOutput 3 }

upsOutputTable OBJECT-TYPE
    SYNTAX      SEQUENCE OF UpsOutputEntry
    ACCESS      not-accessible
    STATUS      mandatory
    DESCRIPTION 
        "A list of output table entries.  The number of
         entries is given by the value of upsOutputNumLines."
    ::= { upsOutput 4 }

upsOutputEntry OBJECT-TYPE
    SYNTAX      UpsOutputEntry
    ACCESS      not-accessible
    STATUS      mandatory
    DESCRIPTION 
        "An entry containing information applicable to a
         particular output line."
    INDEX       { upsOutputLineIndex }
    ::= { upsOutputTable 1 }

UpsOutputEntry ::= SEQUENCE {
    upsOutputLineIndex      PositiveInteger,
    upsOutputVoltage        NonNegativeInteger,
    upsOutputCurrent        NonNegativeInteger,
    upsOutputPower          NonNegativeInteger,
    upsOutputPercentLoad    INTEGER
}

upsOutputLineIndex OBJECT-TYPE
    SYNTAX      PositiveInteger
    ACCESS      not-accessible
    STATUS      mandatory
    DESCRIPTION 
        "The output line identifier."
    ::= { upsOutputEntry 1 }

upsOutputVoltage OBJECT-TYPE
    SYNTAX      NonNegativeInteger
    ACCESS      read-only
    STATUS      mandatory
    DESCRIPTION 
        "The present output voltage."
    ::= { upsOutputEntry 2 }

upsOutputCurrent OBJECT-TYPE
    SYNTAX      NonNegativeInteger
    ACCESS      read-only
    STATUS      mandatory
    DESCRIPTION 
        "The present output current."
    ::= { upsOutputEntry 3 }

upsOutputPower OBJECT-TYPE
    SYNTAX      NonNegativeInteger
    ACCESS      read-only
    STATUS      mandatory
    DESCRIPTION 
        "The present output true power."
    ::= { upsOutputEntry 4 }

upsOutputPercentLoad OBJECT-TYPE
    SYNTAX      INTEGER (0..200)
    ACCESS      read-only
    STATUS      mandatory
    DESCRIPTION 
        "The percentage of the UPS power capacity presently
         being used on this output line, i.e., the greater of
         the percent load of true power capacity and the
         percent load of VA."
    ::= { upsOutputEntry 5 }

upsBypass OBJECT IDENTIFIER
    ::= { upsObjects 5 }

upsBypassFrequency OBJECT-TYPE
    SYNTAX      NonNegativeInteger
    ACCESS      read-only
    STATUS      mandatory
    DESCRIPTION 
        "The present bypass frequency."
    ::= { upsBypass 1 }

upsBypassNumLines OBJECT-TYPE
    SYNTAX      NonNegativeInteger
    ACCESS      read-only
    STATUS      mandatory
    DESCRIPTION 
        "The number of bypass lines utilized in this device.
         This entry indicates the number of rows in the bypass
         table."
    ::= { upsBypass 2 }

upsBypassTable OBJECT-TYPE
    SYNTAX      SEQUENCE OF UpsBypassEntry
    ACCESS      not-accessible
    STATUS      mandatory
    DESCRIPTION 
        "A list of bypass table entries.  The number of
         entries is given by the value of upsBypassNumLines."
    ::= { upsBypass 3 }

upsBypassEntry OBJECT-TYPE
    SYNTAX      UpsBypassEntry
    ACCESS      not-accessible
    STATUS      mandatory
    DESCRIPTION 
        "An entry containing information applicable to a
         particular bypass input."
    INDEX       { upsBypassLineIndex }
    ::= { upsBypassTable 1 }

UpsBypassEntry ::= SEQUENCE {
    upsBypassLineIndex  PositiveInteger,
    upsBypassVoltage    NonNegativeInteger,
    upsBypassCurrent    NonNegativeInteger,
    upsBypassPower      NonNegativeInteger
}

upsBypassLineIndex OBJECT-TYPE
    SYNTAX      PositiveInteger
    ACCESS      not-accessible
    STATUS      mandatory
    DESCRIPTION 
        "The bypass line identifier."
    ::= { upsBypassEntry 1 }

upsBypassVoltage OBJECT-TYPE
    SYNTAX      NonNegativeInteger
    ACCESS      read-only
    STATUS      mandatory
    DESCRIPTION 
        "The present bypass voltage."
    ::= { upsBypassEntry 2 }

upsBypassCurrent OBJECT-TYPE
    SYNTAX      NonNegativeInteger
    ACCESS      read-only
    STATUS      mandatory
    DESCRIPTION 
        "The present bypass current."
    ::= { upsBypassEntry 3 }

upsBypassPower OBJECT-TYPE
    SYNTAX      NonNegativeInteger
    ACCESS      read-only
    STATUS      mandatory
    DESCRIPTION 
        "The present true power conveyed by the bypass."
    ::= { upsBypassEntry 4 }

upsAlarm OBJECT IDENTIFIER
    ::= { upsObjects 6 }

upsAlarmsPresent OBJECT-TYPE
    SYNTAX      Gauge
    ACCESS      read-only
    STATUS      mandatory
    DESCRIPTION 
        "The present number of active alarm conditions."
    ::= { upsAlarm 1 }



upsWellKnownAlarms OBJECT IDENTIFIER
    ::= { upsAlarm 3 }

upsAlarmBatteryBad OBJECT IDENTIFIER
    ::= { upsWellKnownAlarms 1 }

upsAlarmOnBattery OBJECT IDENTIFIER
    ::= { upsWellKnownAlarms 2 }

upsAlarmLowBattery OBJECT IDENTIFIER
    ::= { upsWellKnownAlarms 3 }

upsAlarmDepletedBattery OBJECT IDENTIFIER
    ::= { upsWellKnownAlarms 4 }

upsAlarmTempBad OBJECT IDENTIFIER
    ::= { upsWellKnownAlarms 5 }

upsAlarmInputBad OBJECT IDENTIFIER
    ::= { upsWellKnownAlarms 6 }

upsAlarmOutputBad OBJECT IDENTIFIER
    ::= { upsWellKnownAlarms 7 }

upsAlarmOutputOverload OBJECT IDENTIFIER
    ::= { upsWellKnownAlarms 8 }

upsAlarmOnBypass OBJECT IDENTIFIER
    ::= { upsWellKnownAlarms 9 }

upsAlarmBypassBad OBJECT IDENTIFIER
    ::= { upsWellKnownAlarms 10 }

upsAlarmOutputOffAsRequested OBJECT IDENTIFIER
    ::= { upsWellKnownAlarms 11 }

upsAlarmUpsOffAsRequested OBJECT IDENTIFIER
    ::= { upsWellKnownAlarms 12 }

upsAlarmChargerFailed OBJECT IDENTIFIER
    ::= { upsWellKnownAlarms 13 }

upsAlarmUpsOutputOff OBJECT IDENTIFIER
    ::= { upsWellKnownAlarms 14 }

upsAlarmUpsSystemOff OBJECT IDENTIFIER
    ::= { upsWellKnownAlarms 15 }

upsAlarmFanFailure OBJECT IDENTIFIER
    ::= { upsWellKnownAlarms 16 }

upsAlarmFuseFailure OBJECT IDENTIFIER
    ::= { upsWellKnownAlarms 17 }

upsAlarmGeneralFault OBJECT IDENTIFIER
    ::= { upsWellKnownAlarms 18 }

upsAlarmDiagnosticTestFailed OBJECT IDENTIFIER
    ::= { upsWellKnownAlarms 19 }

upsAlarmCommunicationsLost OBJECT IDENTIFIER
    ::= { upsWellKnownAlarms 20 }

upsAlarmAwaitingPower OBJECT IDENTIFIER
    ::= { upsWellKnownAlarms 21 }

upsAlarmShutdownPending OBJECT IDENTIFIER
    ::= { upsWellKnownAlarms 22 }

upsAlarmShutdownImminent OBJECT IDENTIFIER
    ::= { upsWellKnownAlarms 23 }

upsAlarmTestInProgress OBJECT IDENTIFIER
    ::= { upsWellKnownAlarms 24 }


upsControl OBJECT IDENTIFIER
    ::= { upsObjects 8 }

upsShutdownType OBJECT-TYPE
    SYNTAX      INTEGER { output(1), system(2) }
    ACCESS      read-write
    STATUS      mandatory
    DESCRIPTION 
        "This object determines the nature of the action to be
         taken at the time when the countdown of the
         upsShutdownAfterDelay and upsRebootWithDuration
         objects reaches zero.
         
         Setting this object to output(1) indicates that
         shutdown requests should cause only the output of the
         UPS to turn off.  Setting this object to system(2)
         indicates that shutdown requests will cause the entire
         UPS system to turn off."
    ::= { upsControl 1 }

upsShutdownAfterDelay OBJECT-TYPE
    SYNTAX      INTEGER (-2147483648..-1)
    ACCESS      read-write
    STATUS      mandatory
    DESCRIPTION 
        "Setting this object will shutdown (i.e., turn off)
         either the UPS output or the UPS system (as determined
         by the value of upsShutdownType at the time of
         shutdown) after the indicated number of seconds, or
         less if the UPS batteries become depleted. Setting
         this object to 0 will cause the shutdown to occur
         immediately.  Setting this object to -1 will abort the
         countdown.  If the system is already in the desired
         state at the time the countdown reaches 0, then
         nothing will happen.  That is, there is no additional
         action at that time if upsShutdownType = system and
         the system is already off.  Similarly, there is no
         additional action at that time if upsShutdownType =
         output and the output is already off.  When read,
         upsShutdownAfterDelay will return the number of
         seconds remaining until shutdown, or -1 if no shutdown
         countdown is in effect.  On some systems, if the agent
         is restarted while a shutdown countdown is in effect,
         the countdown may be aborted.  Sets to this object
         override any upsShutdownAfterDelay already in effect."
    ::= { upsControl 2 }

upsStartupAfterDelay OBJECT-TYPE
    SYNTAX      INTEGER (-2147483648..-1)
    ACCESS      read-write
    STATUS      mandatory
    DESCRIPTION 
        "Setting this object will start the output after the
         indicated number of seconds, including starting the
         UPS, if necessary.  Setting this object to 0 will
         cause the startup to occur immediately.  Setting this
         object to -1 will abort the countdown.  If the output
         is already on at the time the countdown reaches 0,
         then nothing will happen.  Sets to this object
         override the effect of any upsStartupAfterDelay
         countdown or upsRebootWithDuration countdown in
         progress.  When read, upsStartupAfterDelay will return
         the number of seconds until startup, or -1 if no
         startup countdown is in effect.  If the countdown
         expires during a utility failure, the startup shall
         not occur until the utility power is restored.  On
         some systems, if the agent is restarted while a
         startup countdown is in effect, the countdown is
         aborted."
    ::= { upsControl 3 }

upsRebootWithDuration OBJECT-TYPE
    SYNTAX      INTEGER (-1..300)
    ACCESS      read-write
    STATUS      mandatory
    DESCRIPTION 
        "Setting this object will immediately shutdown (i.e.,
         turn off) either the UPS output or the UPS system (as
         determined by the value of upsShutdownType at the time
         of shutdown) for a period equal to the indicated
         number of seconds, after which time the output will be
         started, including starting the UPS, if necessary.  If
         the number of seconds required to perform the request
         is greater than the requested duration, then the
         requested shutdown and startup cycle shall be
         performed in the minimum time possible, but in no case
         shall this require more than the requested duration
         plus 60 seconds.  When read, upsRebootWithDuration
         shall return the number of seconds remaining in the
         countdown, or -1 if no countdown is in progress.  If
         the startup should occur during a utility failure, the
         startup shall not occur until the utility power is
         restored."
    ::= { upsControl 4 }

upsAutoRestart OBJECT-TYPE
    SYNTAX      INTEGER { on(1), off(2) }
    ACCESS      read-write
    STATUS      mandatory
    DESCRIPTION 
        "Setting this object to 'on' will cause the UPS system
         to restart after a shutdown if the shutdown occurred
         during a power loss as a result of either a
         upsShutdownAfterDelay or an internal battery depleted
         condition.  Setting this object to 'off' will prevent
         the UPS system from restarting after a shutdown until
         an operator manually or remotely explicitly restarts
         it.  If the UPS is in a startup or reboot countdown,
         then the UPS will not restart until that delay has
         been satisfied."
    ::= { upsControl 5 }

upsConfig OBJECT IDENTIFIER
    ::= { upsObjects 9 }

upsConfigInputVoltage OBJECT-TYPE
    SYNTAX      NonNegativeInteger
    ACCESS      read-write
    STATUS      mandatory
    DESCRIPTION 
        "The magnitude of the nominal input voltage.  On those
         systems which support read-write access to this
         object, if there is an attempt to set this variable to
         a value that is not supported, the request must be
         rejected and the agent shall respond with an
         appropriate error message, i.e., badValue for SNMPv1,
         or inconsistentValue for SNMPv2."
    ::= { upsConfig 1 }

upsConfigInputFreq OBJECT-TYPE
    SYNTAX      NonNegativeInteger
    ACCESS      read-write
    STATUS      mandatory
    DESCRIPTION 
        "The nominal input frequency.  On those systems which
         support read-write access to this object, if there is
         an attempt to set this variable to a value that is not
         supported, the request must be rejected and the agent
         shall respond with an appropriate error message, i.e.,
         badValue for SNMPv1, or inconsistentValue for SNMPv2."
    ::= { upsConfig 2 }

upsConfigOutputVoltage OBJECT-TYPE
    SYNTAX      NonNegativeInteger
    ACCESS      read-write
    STATUS      mandatory
    DESCRIPTION 
        "The magnitude of the nominal output voltage.  On
         those systems which support read-write access to this
         object, if there is an attempt to set this variable to
         a value that is not supported, the request must be
         rejected and the agent shall respond with an
         appropriate error message, i.e., badValue for SNMPv1,
         or inconsistentValue for SNMPv2."
    ::= { upsConfig 3 }

upsConfigOutputFreq OBJECT-TYPE
    SYNTAX      NonNegativeInteger
    ACCESS      read-write
    STATUS      mandatory
    DESCRIPTION 
        "The nominal output frequency.  On those systems which
         support read-write access to this object, if there is
         an attempt to set this variable to a value that is not
         supported, the request must be rejected and the agent
         shall respond with an appropriate error message, i.e.,
         badValue for SNMPv1, or inconsistentValue for SNMPv2."
    ::= { upsConfig 4 }

upsConfigOutputVA OBJECT-TYPE
    SYNTAX      NonNegativeInteger
    ACCESS      read-only
    STATUS      mandatory
    DESCRIPTION 
        "The magnitude of the nominal Volt-Amp rating."
    ::= { upsConfig 5 }

upsConfigOutputPower OBJECT-TYPE
    SYNTAX      NonNegativeInteger
    ACCESS      read-only
    STATUS      mandatory
    DESCRIPTION 
        "The magnitude of the nominal true power rating."
    ::= { upsConfig 6 }

upsConfigLowBattTime OBJECT-TYPE
    SYNTAX      NonNegativeInteger
    ACCESS      read-write
    STATUS      mandatory
    DESCRIPTION 
        "The value of upsEstimatedMinutesRemaining at which a
         lowBattery condition is declared.  For agents which
         support only discrete (discontinuous) values, then the
         agent shall round up to the next supported value.  If
         the requested value is larger than the largest
         supported value, then the largest supported value
         shall be selected."
    ::= { upsConfig 7 }

upsConfigAudibleStatus OBJECT-TYPE
    SYNTAX      INTEGER { disabled(1), enabled(2), muted(3) }
    ACCESS      read-write
    STATUS      mandatory
    DESCRIPTION 
        "The requested state of the audible alarm.  When in
         the disabled state, the audible alarm should never
         sound.  The enabled state is self-describing.  Setting
         this object to muted(3) when the audible alarm is
         sounding shall temporarily silence the alarm.  It will
         remain muted until it would normally stop sounding and
         the value returned for read operations during this
         period shall equal muted(3).  At the end of this
         period, the value shall revert to enabled(2).  Writes
         of the value muted(3) when the audible alarm is not
         sounding shall be accepted but otherwise shall have no
         effect."
    ::= { upsConfig 8 }

upsConfigLowVoltageTransferPoint OBJECT-TYPE
    SYNTAX      NonNegativeInteger
    ACCESS      read-write
    STATUS      mandatory
    DESCRIPTION 
        "The minimum input line voltage allowed before the UPS
         system transfers to battery backup."
    ::= { upsConfig 9 }

upsConfigHighVoltageTransferPoint OBJECT-TYPE
    SYNTAX      NonNegativeInteger
    ACCESS      read-write
    STATUS      mandatory
    DESCRIPTION 
        "The maximum line voltage allowed before the UPS
         system transfers to battery backup."
    ::= { upsConfig 10 }

upsTraps OBJECT IDENTIFIER
    ::= { upsMIB 2 }

upsConformance OBJECT IDENTIFIER
    ::= { upsMIB 3 }

upsCompliances OBJECT IDENTIFIER
    ::= { upsConformance 1 }

upsGroups OBJECT IDENTIFIER
    ::= { upsConformance 2 }

upsSubsetGroups OBJECT IDENTIFIER
    ::= { upsGroups 1 }

upsBasicGroups OBJECT IDENTIFIER
    ::= { upsGroups 2 }

upsFullGroups OBJECT IDENTIFIER
    ::= { upsGroups 3 }

upsTrapOnBattery TRAP-TYPE
    ENTERPRISE  upsTraps
    VARIABLES   { upsSecondsOnBattery, 
                  upsConfigLowBattTime }
--     STATUS      mandatory
    DESCRIPTION 
        "The UPS is operating on battery power.  This trap is
         persistent and is resent at one minute intervals until
         the UPS either turns off or is no longer running on
         battery."
	 --#TYPE	"UPS on Battery"
	 --#SUMMARY	"The UPS is on battery power since %d seconds"
	 --#ARGUMENTS	{0,1}
	 --#SEVERITY	CRITICAL
    ::= 1

upsTrapTestCompleted TRAP-TYPE
    ENTERPRISE  upsTraps
    VARIABLES   { upsTestId, upsTestSpinLock, upsTestResultsSummary, 
                  upsTestResultsDetail, upsTestStartTime, 
                  upsTestElapsedTime }
--     STATUS      mandatory
    DESCRIPTION 
        "This trap is sent upon completion of a UPS diagnostic
         test."
	 --#TYPE	"UPS Test Completed"
	 --#SEVERITY	INFORMATIONAL
    ::= 2

upsTrapAlarmEntryAdded TRAP-TYPE
    ENTERPRISE  upsTraps
    VARIABLES   { upsAlarmId, upsAlarmDescr }
--     STATUS      mandatory
    DESCRIPTION 
        "This trap is sent each time an alarm is inserted into
         to the alarm table.  It is sent on the insertion of
         all alarms except for upsAlarmOnBattery and
         upsAlarmTestInProgress."
	 --#TYPE	"UPS Alarm Entry Added"
	 --#SEVERITY	INFORMATIONAL
    ::= 3

upsTrapAlarmEntryRemoved TRAP-TYPE
    ENTERPRISE  upsTraps
    VARIABLES   { upsAlarmId, upsAlarmDescr }
--     STATUS      mandatory
    DESCRIPTION 
        "This trap is sent each time an alarm is removed from
         the alarm table.  It is sent on the removal of all
         alarms except for upsAlarmTestInProgress."
	 --#TYPE	"UPS Alarm Entry Removed"
	 --#SEVERITY	INFORMATIONAL
    ::= 4

upsSubsetIdentGroup OBJECT IDENTIFIER
    ::= { upsSubsetGroups 1 }

-- upsSubsetIdentGroup OBJECT-GROUP
--     OBJECTS     { upsIdentManufacturer, upsIdentModel, 
--                   upsIdentAgentSoftwareVersion, upsIdentName, 
--                   upsIdentAttachedDevices }
--     STATUS      mandatory
--     DESCRIPTION 
--         "The upsSubsetIdentGroup defines objects which are
--          common across all UPSs which meet subset compliance.
--          Most devices which conform to the upsSubsetIdentGroup
--          will provide access to these objects via a proxy
--          agent.  If the proxy agent is compatible with multiple
--          UPS types, configuration of the proxy agent will
--          require specifying some of these values, either
--          individually, or as a group (perhaps through a table
--          lookup mechanism based on the UPS model number)."
--     ::= { upsSubsetGroups 1 }

upsSubsetBatteryGroup OBJECT IDENTIFIER
    ::= { upsSubsetGroups 2 }

-- upsSubsetBatteryGroup OBJECT-GROUP
--     OBJECTS     { upsBatteryStatus, upsSecondsOnBattery }
--     STATUS      mandatory
--     DESCRIPTION 
--         "The upsSubsetBatteryGroup defines the objects that
--          are common to battery groups of two-contact UPSs."
--     ::= { upsSubsetGroups 2 }

upsSubsetInputGroup OBJECT IDENTIFIER
    ::= { upsSubsetGroups 3 }

-- upsSubsetInputGroup OBJECT-GROUP
--     OBJECTS     { upsInputLineBads }
--     STATUS      mandatory
--     DESCRIPTION 
--         "The upsSubsetInputGroup defines the objects that are
--          common to the Input groups of two-contact UPSs."
--     ::= { upsSubsetGroups 3 }

upsSubsetOutputGroup OBJECT IDENTIFIER
    ::= { upsSubsetGroups 4 }

-- upsSubsetOutputGroup OBJECT-GROUP
--     OBJECTS     { upsOutputSource }
--     STATUS      mandatory
--     DESCRIPTION 
--         "The upsSubsetOutputGroup defines the objects that are
--          common to the Output groups of two-contact UPSs."
--     ::= { upsSubsetGroups 4 }

upsSubsetAlarmGroup OBJECT IDENTIFIER
    ::= { upsSubsetGroups 6 }

-- upsSubsetAlarmGroup OBJECT-GROUP
--     OBJECTS     { upsAlarmsPresent, upsAlarmDescr, upsAlarmTime }
--     STATUS      mandatory
--     DESCRIPTION 
--         "The upsSubsetAlarmGroup defines the objects that are
--          common to the Alarm groups of two-contact UPSs."
--     ::= { upsSubsetGroups 6 }

upsSubsetControlGroup OBJECT IDENTIFIER
    ::= { upsSubsetGroups 8 }

-- upsSubsetControlGroup OBJECT-GROUP
--     OBJECTS     { upsShutdownType, upsShutdownAfterDelay, 
--                   upsAutoRestart }
--     STATUS      mandatory
--     DESCRIPTION 
--         "The upsSubsetControlGroup defines the objects that
--          are common to the Control groups of two-contact UPSs."
--     ::= { upsSubsetGroups 8 }

upsSubsetConfigGroup OBJECT IDENTIFIER
    ::= { upsSubsetGroups 9 }

-- upsSubsetConfigGroup OBJECT-GROUP
--     OBJECTS     { upsConfigInputVoltage, upsConfigInputFreq, 
--                   upsConfigOutputVoltage, upsConfigOutputFreq, 
--                   upsConfigOutputVA, upsConfigOutputPower }
--     STATUS      mandatory
--     DESCRIPTION 
--         "The upsSubsetConfigGroup defines the objects that are
--          common to the Config groups of two-contact UPSs."
--     ::= { upsSubsetGroups 9 }

upsBasicIdentGroup OBJECT IDENTIFIER
    ::= { upsBasicGroups 1 }

-- upsBasicIdentGroup OBJECT-GROUP
--     OBJECTS     { upsIdentManufacturer, upsIdentModel, 
--                   upsIdentUPSSoftwareVersion, 
--                   upsIdentAgentSoftwareVersion, upsIdentName }
--     STATUS      mandatory
--     DESCRIPTION 
--         "The upsBasicIdentGroup defines objects which are
--          common to the Ident group of compliant UPSs which
--          support basic functions."
--     ::= { upsBasicGroups 1 }

upsBasicBatteryGroup OBJECT IDENTIFIER
    ::= { upsBasicGroups 2 }

-- upsBasicBatteryGroup OBJECT-GROUP
--     OBJECTS     { upsBatteryStatus, upsSecondsOnBattery }
--     STATUS      mandatory
--     DESCRIPTION 
--         "The upsBasicBatteryGroup defines the objects that are
--          common to the battery groups of compliant UPSs which
--          support basic functions."
--     ::= { upsBasicGroups 2 }

upsBasicInputGroup OBJECT IDENTIFIER
    ::= { upsBasicGroups 3 }

-- upsBasicInputGroup OBJECT-GROUP
--     OBJECTS     { upsInputLineBads, upsInputNumLines, 
--                   upsInputFrequency, upsInputVoltage }
--     STATUS      mandatory
--     DESCRIPTION 
--         "The upsBasicInputGroup defines the objects that are
--          common to the Input groups of compliant UPSs which
--          support basic functions."
--     ::= { upsBasicGroups 3 }

upsBasicOutputGroup OBJECT IDENTIFIER
    ::= { upsBasicGroups 4 }

-- upsBasicOutputGroup OBJECT-GROUP
--     OBJECTS     { upsOutputSource, upsOutputFrequency, 
--                   upsOutputNumLines, upsOutputVoltage }
--     STATUS      mandatory
--     DESCRIPTION 
--         "The upsBasicOutputGroup defines the objects that are
--          common to the Output groups of compliant UPSs which
--          support basic functions."
--     ::= { upsBasicGroups 4 }

upsBasicBypassGroup OBJECT IDENTIFIER
    ::= { upsBasicGroups 5 }

-- upsBasicBypassGroup OBJECT-GROUP
--     OBJECTS     { upsBypassFrequency, upsBypassNumLines, 
--                   upsBypassVoltage }
--     STATUS      mandatory
--     DESCRIPTION 
--         "The upsBasicBypassGroup defines the objects that are
--          common to the Bypass groups of compliant UPSs which
--          support basic functions."
--     ::= { upsBasicGroups 5 }

upsBasicAlarmGroup OBJECT IDENTIFIER
    ::= { upsBasicGroups 6 }

-- upsBasicAlarmGroup OBJECT-GROUP
--     OBJECTS     { upsAlarmsPresent, upsAlarmDescr, upsAlarmTime }
--     STATUS      mandatory
--     DESCRIPTION 
--         "The upsBasicAlarmGroup defines the objects that are
--          common to the Alarm  groups of compliant UPSs which
--          support basic functions."
--     ::= { upsBasicGroups 6 }

upsBasicTestGroup OBJECT IDENTIFIER
    ::= { upsBasicGroups 7 }

-- upsBasicTestGroup OBJECT-GROUP
--     OBJECTS     { upsTestId, upsTestSpinLock, upsTestResultsSummary, 
--                   upsTestResultsDetail, upsTestStartTime, 
--                   upsTestElapsedTime }
--     STATUS      mandatory
--     DESCRIPTION 
--         "The upsBasicTestGroup defines the objects that are
--          common to the Test groups of compliant UPSs which
--          support basic functions."
--     ::= { upsBasicGroups 7 }

upsBasicControlGroup OBJECT IDENTIFIER
    ::= { upsBasicGroups 8 }

-- upsBasicControlGroup OBJECT-GROUP
--     OBJECTS     { upsShutdownType, upsShutdownAfterDelay, 
--                   upsStartupAfterDelay, upsRebootWithDuration, 
--                   upsAutoRestart }
--     STATUS      mandatory
--     DESCRIPTION 
--         "The upsBasicControlGroup defines the objects that are
--          common to the Control groups of compliant UPSs which
--          support basic functions."
--     ::= { upsBasicGroups 8 }

upsBasicConfigGroup OBJECT IDENTIFIER
    ::= { upsBasicGroups 9 }

-- upsBasicConfigGroup OBJECT-GROUP
--     OBJECTS     { upsConfigInputVoltage, upsConfigInputFreq, 
--                   upsConfigOutputVoltage, upsConfigOutputFreq, 
--                   upsConfigOutputVA, upsConfigOutputPower, 
--                   upsConfigLowBattTime, upsConfigAudibleStatus }
--     STATUS      mandatory
--     DESCRIPTION 
--         "The upsBasicConfigGroup defines the objects that are
--          common to the Config groups of UPSs which support
--          basic functions."
--     ::= { upsBasicGroups 9 }

upsFullIdentGroup OBJECT IDENTIFIER
    ::= { upsFullGroups 1 }

-- upsFullIdentGroup OBJECT-GROUP
--     OBJECTS     { upsIdentManufacturer, upsIdentModel, 
--                   upsIdentUPSSoftwareVersion, 
--                   upsIdentAgentSoftwareVersion, upsIdentName, 
--                   upsIdentAttachedDevices }
--     STATUS      mandatory
--     DESCRIPTION 
--         "The upsFullIdentGroup defines objects which are
--          common to the Ident group of fully compliant UPSs."
--     ::= { upsFullGroups 1 }

upsFullBatteryGroup OBJECT IDENTIFIER
    ::= { upsFullGroups 2 }

-- upsFullBatteryGroup OBJECT-GROUP
--     OBJECTS     { upsBatteryStatus, upsSecondsOnBattery, 
--                   upsEstimatedMinutesRemaining, 
--                   upsEstimatedChargeRemaining }
--     STATUS      mandatory
--     DESCRIPTION 
--         "The upsFullBatteryGroup defines the objects that are
--          common to the battery groups of fully compliant UPSs."
--     ::= { upsFullGroups 2 }

upsFullInputGroup OBJECT IDENTIFIER
    ::= { upsFullGroups 3 }

-- upsFullInputGroup OBJECT-GROUP
--     OBJECTS     { upsInputLineBads, upsInputNumLines, 
--                   upsInputFrequency, upsInputVoltage }
--     STATUS      mandatory
--     DESCRIPTION 
--         "The upsFullInputGroup defines the objects that are
--          common to the Input groups of fully compliant UPSs."
--     ::= { upsFullGroups 3 }

upsFullOutputGroup OBJECT IDENTIFIER
    ::= { upsFullGroups 4 }

-- upsFullOutputGroup OBJECT-GROUP
--     OBJECTS     { upsOutputSource, upsOutputFrequency, 
--                   upsOutputNumLines, upsOutputVoltage, 
--                   upsOutputCurrent, upsOutputPower, 
--                   upsOutputPercentLoad }
--     STATUS      mandatory
--     DESCRIPTION 
--         "The upsFullOutputGroup defines the objects that are
--          common to the Output groups of fully compliant UPSs."
--     ::= { upsFullGroups 4 }

upsFullBypassGroup OBJECT IDENTIFIER
    ::= { upsFullGroups 5 }

-- upsFullBypassGroup OBJECT-GROUP
--     OBJECTS     { upsBypassFrequency, upsBypassNumLines, 
--                   upsBypassVoltage }
--     STATUS      mandatory
--     DESCRIPTION 
--         "The upsFullBypassGroup defines the objects that are
--          common to the Bypass groups of fully compliant UPSs."
--     ::= { upsFullGroups 5 }

upsFullAlarmGroup OBJECT IDENTIFIER
    ::= { upsFullGroups 6 }

-- upsFullAlarmGroup OBJECT-GROUP
--     OBJECTS     { upsAlarmsPresent, upsAlarmDescr, upsAlarmTime }
--     STATUS      mandatory
--     DESCRIPTION 
--         "The upsFullAlarmGroup defines the objects that are
--          common to the Alarm  groups of fully compliant UPSs."
--     ::= { upsFullGroups 6 }

upsFullTestGroup OBJECT IDENTIFIER
    ::= { upsFullGroups 7 }

-- upsFullTestGroup OBJECT-GROUP
--     OBJECTS     { upsTestId, upsTestSpinLock, upsTestResultsSummary, 
--                   upsTestResultsDetail, upsTestStartTime, 
--                   upsTestElapsedTime }
--     STATUS      mandatory
--     DESCRIPTION 
--         "The upsFullTestGroup defines the objects that are
--          common to the Test groups of fully compliant UPSs."
--     ::= { upsFullGroups 7 }

upsFullControlGroup OBJECT IDENTIFIER
    ::= { upsFullGroups 8 }

-- upsFullControlGroup OBJECT-GROUP
--     OBJECTS     { upsShutdownType, upsShutdownAfterDelay, 
--                   upsStartupAfterDelay, upsRebootWithDuration, 
--                   upsAutoRestart }
--     STATUS      mandatory
--     DESCRIPTION 
--         "The upsFullControlGroup defines the objects that are
--          common to the Control groups of fully compliant UPSs."
--     ::= { upsFullGroups 8 }

upsFullConfigGroup OBJECT IDENTIFIER
    ::= { upsFullGroups 9 }

-- upsFullConfigGroup OBJECT-GROUP
--     OBJECTS     { upsConfigInputVoltage, upsConfigInputFreq, 
--                   upsConfigOutputVoltage, upsConfigOutputFreq, 
--                   upsConfigOutputVA, upsConfigOutputPower, 
--                   upsConfigLowBattTime, upsConfigAudibleStatus }
--     STATUS      mandatory
--     DESCRIPTION 
--         "The upsFullConfigGroup defines the objects that are
--          common to the Config groups of fully compliant UPSs."
--     ::= { upsFullGroups 9 }

upsSubsetCompliance OBJECT IDENTIFIER
    ::= { upsCompliances 1 }

-- upsSubsetCompliance MODULE-COMPLIANCE
--     STATUS      mandatory
--     DESCRIPTION 
--         "The compliance statement for UPSs that only support
--          the two-contact communication protocol."

--     MODULE      -- -- this module

--         MANDATORY-GROUPS        { upsSubsetIdentGroup, 
--                   upsSubsetBatteryGroup, upsSubsetInputGroup, 
--                   upsSubsetOutputGroup, upsSubsetAlarmGroup, 
--                   upsSubsetControlGroup, upsSubsetConfigGroup }

--         OBJECT  upsBatteryStatus
--         SYNTAX  INTEGER
--                   { batteryNormal(2), batteryLow(3) }
--         DESCRIPTION   
--         "Support of the values unknown(1) and
--          batteryDepleted(4) is not required."

--         OBJECT  upsAlarmDescr
--         DESCRIPTION   
--         "Support of all `well known' alarm types is not
--          required.  The well known alarm types which must be
--          supported are: upsAlarmOnBattery, upsAlarmLowBattery,
--          upsAlarmInputBad, upsAlarmUpsOutputOff,
--          upsAlarmUpsSystemOff, and upsAlarmTestInProgress."

--         OBJECT  upsOutputSource
--         SYNTAX  INTEGER
--                   { normal(2), battery(4) }
--         DESCRIPTION   
--         "Support of the values other(1), none(2), bypass(4),
--          booster(6) and reducer(7) is not required."

--         OBJECT  upsShutdownType
--         MIN-ACCESS  read-only
--         DESCRIPTION   
--         "Read-write access is not required, i.e., compliant
--          systems need not support more than one shutdown type."

--         OBJECT  upsAutoRestart
--         MIN-ACCESS  read-only
--         DESCRIPTION   
--         "Read-write access is not required, i.e., compliant
--          systems need not support more than one restart type."

--         OBJECT  upsConfigInputVoltage
--         MIN-ACCESS  read-only
--         DESCRIPTION   
--         "Read-write access is not required."

--         OBJECT  upsConfigInputFreq
--         MIN-ACCESS  read-only
--         DESCRIPTION   
--         "Read-write access is not required."

--         OBJECT  upsConfigOutputVoltage
--         MIN-ACCESS  read-only
--         DESCRIPTION   
--         "Read-write access is not required."

--         OBJECT  upsConfigOutputFreq
--         MIN-ACCESS  read-only
--         DESCRIPTION   
--         "Read-write access is not required."

--     ::= { upsCompliances 1 }

upsBasicCompliance OBJECT IDENTIFIER
    ::= { upsCompliances 2 }

-- upsBasicCompliance MODULE-COMPLIANCE
--     STATUS      mandatory
--     DESCRIPTION 
--         "The compliance statement for UPSs that support
--          full-featured functions, such as control."

--     MODULE      -- -- this module

--         MANDATORY-GROUPS        { upsBasicIdentGroup, 
--                   upsBasicBatteryGroup, upsBasicInputGroup, 
--                   upsBasicOutputGroup, upsBasicAlarmGroup, 
--                   upsBasicTestGroup, upsBasicControlGroup, 
--                   upsBasicConfigGroup }

--         GROUP   upsBasicBypassGroup
--         DESCRIPTION   
--         "The upsBasicBypassGroup is only required for UPSs
--          that have a Bypass present."

--         OBJECT  upsAlarmDescr
--         DESCRIPTION   
--         "Support of all `well known' alarm types is not
--          required.  The well known alarm types which must be
--          supported are: upsAlarmOnBattery, upsAlarmLowBattery,
--          upsAlarmDepletedBattery, upsAlarmTempBad,
--          upsAlarmInputBad, upsAlarmOutputOverload,
--          upsAlarmOnBypass, upsAlarmBypassBad,
--          upsAlarmOutputOffAsRequested,
--          upsAlarmUpsOffAsRequested, upsAlarmUpsOutputOff,
--          upsAlarmUpsSystemOff, upsAlarmGeneralFault,
--          upsAlarmDiagnosticTestFailed,
--          upsAlarmCommunicationsLost, upsAlarmShutdownPending,
--          and upsAlarmTestInProgress."

--         OBJECT  upsTestId
--         DESCRIPTION   
--         "Support of all `well known' test types is not
--          required.  If no tests are supported, then the only
--          well known test type which must be supported is
--          upsTestNoTestsInitiated."

--         OBJECT  upsOutputSource
--         SYNTAX  INTEGER
--                   { normal(2), battery(4) }
--         DESCRIPTION   
--         "Support of the values other(1), none(2), bypass(4),
--          booster(6) and reducer(7) is not required."

--         OBJECT  upsShutdownType
--         MIN-ACCESS  read-only
--         DESCRIPTION   
--         "Read-write access is not required, i.e., compliant
--          systems need not support more than one shutdown type."

--         OBJECT  upsAutoRestart
--         MIN-ACCESS  read-only
--         DESCRIPTION   
--         "Read-write access is not required, i.e., compliant
--          systems need not support more than one restart type."

--         OBJECT  upsConfigInputVoltage
--         MIN-ACCESS  read-only
--         DESCRIPTION   
--         "Read-write access is not required."

--         OBJECT  upsConfigInputFreq
--         MIN-ACCESS  read-only
--         DESCRIPTION   
--         "Read-write access is not required."

--         OBJECT  upsConfigOutputVoltage
--         MIN-ACCESS  read-only
--         DESCRIPTION   
--         "Read-write access is not required."

--         OBJECT  upsConfigOutputFreq
--         MIN-ACCESS  read-only
--         DESCRIPTION   
--         "Read-write access is not required."

--         OBJECT  upsConfigLowBattTime
--         DESCRIPTION   
--         "Implementation of all possible values may be onerous
--          for some systems.  Consequently, not all possible
--          values must be supported.  However, at least two
--          different manufacturer-selected values must be
--          supported."

--     ::= { upsCompliances 2 }

upsFullCompliance OBJECT IDENTIFIER
    ::= { upsCompliances 3 }

-- upsFullCompliance MODULE-COMPLIANCE
--     STATUS      mandatory
--     DESCRIPTION 
--         "The compliance statement for UPSs that support
--          advanced full-featured functions."

--     MODULE      -- -- this module

--         MANDATORY-GROUPS        { upsFullIdentGroup, 
--                   upsFullBatteryGroup, upsFullInputGroup, 
--                   upsFullOutputGroup, upsFullAlarmGroup, 
--                   upsFullTestGroup, upsFullControlGroup, 
--                   upsFullConfigGroup }

--         GROUP   upsFullBypassGroup
--         DESCRIPTION   
--         "The upsFullBypassGroup is only required for UPSs that
--          have a Bypass present."

--         OBJECT  upsAlarmDescr
--         DESCRIPTION   
--         "Support of all `well known' alarm types is not
--          required.  The well known alarm types which must be
--          supported are: upsAlarmBatteryBad, upsAlarmOnBattery,
--          upsAlarmLowBattery, upsAlarmDepletedBattery,
--          upsAlarmTempBad, upsAlarmInputBad, upsAlarmOnBypass,
--          upsAlarmBypassBad, upsAlarmOutputOffAsRequested,
--          upsAlarmUpsOffAsRequested, upsAlarmUpsOutputOff,
--          upsAlarmUpsSystemOff, upsAlarmGeneralFault,
--          upsAlarmDiagnosticTestFailed,
--          upsAlarmCommunicationsLost, upsAlarmShutdownPending,
--          and upsAlarmTestInProgress."

--         OBJECT  upsTestId
--         DESCRIPTION   
--         "Support of all `well known' test types is not
--          required.  The well known test types which must be
--          supported are: upsTestNoTestsInitiated,
--          upsTestGeneralSystemsTest, and
--          upsTestQuickBatteryTest."

--         OBJECT  upsOutputSource
--         SYNTAX  INTEGER
--                   { normal(2), battery(4) }
--         DESCRIPTION   
--         "Support of the values other(1), none(2), bypass(4),
--          booster(6) and reducer(7) is not required."

--         OBJECT  upsShutdownType
--         MIN-ACCESS  read-only
--         DESCRIPTION   
--         "Read-write access is not required, i.e., compliant
--          systems need not support more than one shutdown type."

--         OBJECT  upsAutoRestart
--         MIN-ACCESS  read-only
--         DESCRIPTION   
--         "Read-write access is not required, i.e., compliant
--          systems need not support more than one restart type."

--         OBJECT  upsConfigInputVoltage
--         MIN-ACCESS  read-only
--         DESCRIPTION   
--         "Read-write access is not required."

--         OBJECT  upsConfigInputFreq
--         MIN-ACCESS  read-only
--         DESCRIPTION   
--         "Read-write access is not required."

--         OBJECT  upsConfigOutputVoltage
--         MIN-ACCESS  read-only
--         DESCRIPTION   
--         "Read-write access is not required."

--         OBJECT  upsConfigOutputFreq
--         MIN-ACCESS  read-only
--         DESCRIPTION   
--         "Read-write access is not required."

--         OBJECT  upsConfigLowBattTime
--         DESCRIPTION   
--         "Implementation of all possible values may be onerous
--          for some systems.  Consequently, not all possible
--          values must be supported.  However, at least two
--          different manufacturer-selected values must be
--          supported."

--     ::= { upsCompliances 3 }

END -- end of module UPS-MIB.
