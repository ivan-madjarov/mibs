--
-- This SMIv1 module has been generated by smidump 0.4.0. Do not edit.
--

SANMgrV2-MIB DEFINITIONS ::= BEGIN

IMPORTS
    OBJECT-TYPE
        FROM RFC-1212
    TRAP-TYPE
        FROM RFC-1215
    enterprises
    	FROM RFC1155-SMI
    Gauge, TimeTicks
		FROM RFC1155-SMI
	DisplayString
    	FROM RFC1213-MIB;

pathlight OBJECT IDENTIFIER
    ::= { enterprises 2935 }

-- pathlight MODULE-IDENTITY
--     LAST-UPDATED "199901260000Z"
--     ORGANIZATION 
--         "Pathlight Technology, Inc."
--     CONTACT-INFO 
--         "  Software Engineering Group 
--          
--          Postal: Pathlight Technology Inc.
--                  9 Brown Road
--                  Ithaca, NY 14850-1255
--                  USA
--          
--             Tel: +1 607 266 4000
--          
--          E-mail: mib@pathlight.com"
--     DESCRIPTION 
--         "The enterprise MIB module for Pathlight SAN Data Gateway."
--     REVISION    "199901260000Z"
--     DESCRIPTION 
--         "This MIB module covers the Pathlight Technology 
--          Storage Area Network (SAN) Data Gateway."
--     ::= { enterprises 2935 }


ProductID ::=
    OBJECT IDENTIFIER

PathlightProduct ::=
    INTEGER { sanGateway(1), sanRouter(2), sanBridge(3), adicFCR2(4), 
                    dellFCR2(5), siemensFCR2(6), sanHoneoye(7), 
                    adicHoneoye(8), dellHoneoye(9), siemensHoneoye(10), 
                    ibmGatewayModule(11), ibmHoneoye(12), 
                    adicPlt5000(13), dellPlt5000(14), ibmPlt5000(15), 
                    adicSNC4000(16), dellSNC4000(17) }

Boolean ::=
    INTEGER { true(1), false(2) }

RowStatus ::=
    INTEGER { active(1), notInService(2), notReady(3), createAndGo(4), 
                    createAndWait(5), destroy(6) }

LogCommand ::=
    INTEGER { idle(0), snapshot(1), scroll(2), save(3), clear(4), 
                    removeFile(5), logModeCurrent(6), logModeAbsolute(7), 
                    doHealthCheck(8) }

PltStatus ::=
    INTEGER { failed(1), down(2), testing(3), up(4) }

FcStatus ::=
    INTEGER { configWait(0), loopInit(1), login(2), ready(3), 
                    lostSync(4), error(5), reinit(6), nonPart(7), 
                    failed(8) }

Interface ::=
    INTEGER { none(0), sanGateway(1), ssa(2), fibreChannel(3), scsi(4), 
                    ethernet(5), unknown(6), any(7), sanReplication(8) }

Reset ::=
    INTEGER { run(0), reset(1), reboot(2) }

BaudRate ::=
    INTEGER { baud9600(0), baud19200(1), baud38400(2) }

HealthCheckLevel ::=
    INTEGER { none(0), system(1), interface(2), simpleDevice(3), 
                    deviceReady(4) }

LogViewingLevel ::=
    INTEGER { private(0), notice(1), warning(2), information(3) }

DeviceType ::=
    INTEGER { directAccess(0), sequentialAccess(1), printer(2), 
                    processor(3), worm(4), cd(5), scanner(6), 
                    opticalMemory(7), mediumChanger(8), 
                    communications(9), ascIt81(10), ascIt82(11), 
                    storageArrayController(12), enclosure(13), 
                    simplifiedDirectAccess(14), opticalCardReader(15), 
                    unknown(31) }

VendorIDInt ::=
    INTEGER { unknown(0), symbios(4096), amd(4130), qlogic(4215), 
                    pathlight(4537) }

FibreMedia ::=
    INTEGER { unknown(0), copper(1), shortWaveOptical(2), 
                    longWaveOptical(3), shortWaveOpticalDual(4), 
                    longWaveOpticalDual(5), 
                    shortWaveOpticalLongDistance(6), 
                    longWaveOpticalLongDistance(7), gbicSWOneGB(8), 
                    gbicLW1300OneGB(9), gbicLW1300HPOneGB(10), 
                    gbicLW1550HPOneGB(11), gbicCopperHSSDCOneGB(12), 
                    gbicCopperDB9OneGB(13), gbicSWTwoGB(14), 
                    gbicLW1300TwoGB(15), gbicLW1300HPTwoGB(16), 
                    gbicLW1550HPTwoGB(17), gbicCopperHSSDCTwoGB(18), 
                    gbicCopperDB9TwoGB(19), noGBIC(20), sfpSWTwoGB(21) }

FibrePort ::=
    INTEGER { nodeLoop(0), node(1), fabricLoop(3), fabric(4), none(255) }

FibreLoopIDMode ::=
    INTEGER { soft(0), hard(1) }

FibrePortMode ::=
    INTEGER { privateTargetOnly(1), privateInitiatorOnly(2), 
                    privateTargetAndInitiator(3), publicTargetOnly(17), 
                    publicInitiatorOnly(18), 
                    publicTargetAndInitiator(19) }

FibreConnOptions ::=
    INTEGER { loopOnly(0), pointToPointOnly(1), loopPreferred(2), 
                    pointToPointPreferred(3) }

SsaSpeed ::=
    INTEGER { ssa80(1), ssa160(2) }

PathingAlgorithm ::=
    INTEGER { default(0), skipInitiators(1), unknown(2) }

ScsiSpeed ::=
    INTEGER { async(0), fast(1), ultra(2), ultra2(3), ultra160(4) }

ScsiRole ::=
    INTEGER { target(0), initiator(1) }

ScsiTermination ::=
    INTEGER { disabled(0), enabled(1), notPresent(2) }

ScsiCardType ::=
    INTEGER { none(0), differentialNoTermination(1), 
                    differentialTerminated(2), 
                    singleEndedNoTermination(3), 
                    singleEndedTerminated(4), unknown(5), 
                    lowVoltageSingleEnded(6), lowVoltageDifferential(7), 
                    lowVoltageMultiFunction(8) }

ScsiAnsiLevel ::=
    INTEGER { notScsi(0), scsi-1(1), scsi-2(2), scsi-3(3) }

HostLUNType ::=
    INTEGER { bit8(0), bit16(1), vsa(2) }

products OBJECT IDENTIFIER
    ::= { pathlight 1 }

sanGateway OBJECT IDENTIFIER
    ::= { products 1 }

sanGateway1 OBJECT IDENTIFIER
    ::= { sanGateway 1 }

sanGateway2 OBJECT IDENTIFIER
    ::= { sanGateway 2 }

agent OBJECT IDENTIFIER
    ::= { pathlight 2 }

paIdentify OBJECT-TYPE
    SYNTAX      INTEGER
    ACCESS      read-write
    STATUS      mandatory
    DESCRIPTION 
        "Flash the READY light on the
         SAN Data Gateway front panel.
         A non-zero value turns the 
         LED on for the specified 
         number of seconds.  Zero
         turns LED off."
    ::= { agent 1 }

paReboot OBJECT-TYPE
    SYNTAX      Reset
    ACCESS      read-write
    STATUS      mandatory
    DESCRIPTION 
        "Writing a reboot(2) value here 
         causes immediate reboot."
    ::= { agent 2 }

paHealthCheckValue OBJECT-TYPE
    SYNTAX      Gauge
    ACCESS      read-only
    STATUS      mandatory
    DESCRIPTION 
        "Value in percent of health check 
         tests passed."
    ::= { agent 3 }

paHealthCheckLevel OBJECT-TYPE
    SYNTAX      HealthCheckLevel
    ACCESS      read-write
    STATUS      mandatory
    DESCRIPTION 
        "Scrutiny level of health check function."
    ::= { agent 4 }

paHealthCheckInterval OBJECT-TYPE
    SYNTAX      Gauge
    ACCESS      read-write
    STATUS      mandatory
    DESCRIPTION 
        "Health Check interval in minutes."
    ::= { agent 5 }

paEvRptLevel OBJECT-TYPE
    SYNTAX      LogViewingLevel
    ACCESS      read-write
    STATUS      mandatory
    DESCRIPTION 
        "Used when retrieving Event Log. Events with 
         log level greater than paEvRptLevel are not
         retrieved."
    ::= { agent 6 }

paEventLogLevels OBJECT-TYPE
    SYNTAX      OCTET STRING (SIZE(256))
    ACCESS      read-write
    STATUS      mandatory
    DESCRIPTION 
        "Each of 255 event types has an 8-bit level
         used when reading log.  Currently valid LogLevel
         range is 0-3."
    ::= { agent 7 }

paTrapThresholds OBJECT-TYPE
    SYNTAX      OCTET STRING (SIZE(256))
    ACCESS      read-write
    STATUS      mandatory
    DESCRIPTION 
        "Each of 255 event types has an 8-bit threshold.
         When the number of events exceeds the Trap Threshold,
         a trap is generated and sent to all parties listed 
         in the trap destination table (also under SNMP
         control) .
         Threshold       0  means  Never
         Threshold       1  means  Always
         Threshold 2 - 255  means  Number of events per
                                   10 minute period"
    ::= { agent 8 }

paBaudRate OBJECT-TYPE
    SYNTAX      BaudRate
    ACCESS      read-write
    STATUS      mandatory
    DESCRIPTION 
        "Serial baud rate for SAN Gateway Service Port.
         Currently, the Agent does not support baud rate 
         change: the rate is hard-coded to 19200 baud."
    ::= { agent 9 }

paEventLog OBJECT-TYPE
    SYNTAX      SEQUENCE OF LogEntry
    ACCESS      not-accessible
    STATUS      mandatory
    DESCRIPTION 
        "Entry point for the Agent Event Log Table."
    ::= { agent 10 }

paEventLogEntry OBJECT-TYPE
    SYNTAX      LogEntry
    ACCESS      not-accessible
    STATUS      mandatory
    DESCRIPTION 
        " "
    INDEX       { paIndex }
    ::= { paEventLog 1 }

LogEntry ::= SEQUENCE {
    paIndex         INTEGER,
	paTime          TimeTicks,
    paProducer      INTEGER,
    paEventClass    INTEGER,
    paEventCode     INTEGER,
    paSeq           INTEGER,
    paEventVars     DisplayString
}

paIndex OBJECT-TYPE
    SYNTAX      INTEGER
    ACCESS      read-only
    STATUS      mandatory
    DESCRIPTION 
        "MIB EventLogEntry Table index."
    ::= { paEventLogEntry 1 }

paTime OBJECT-TYPE
    SYNTAX      TimeTicks
    ACCESS      read-only
    STATUS      mandatory
    DESCRIPTION 
        "Time stamp (since boot)."
    ::= { paEventLogEntry 2 }

paProducer OBJECT-TYPE
    SYNTAX      INTEGER
    ACCESS      read-only
    STATUS      mandatory
    DESCRIPTION 
        "Numeric identifier for this event's producer."
    ::= { paEventLogEntry 3 }

paEventClass OBJECT-TYPE
    SYNTAX      INTEGER
    ACCESS      read-only
    STATUS      mandatory
    DESCRIPTION 
        "Numeric identifier for this event's class."
    ::= { paEventLogEntry 4 }

paEventCode OBJECT-TYPE
    SYNTAX      INTEGER
    ACCESS      read-only
    STATUS      mandatory
    DESCRIPTION 
        "Numeric code for this event."
    ::= { paEventLogEntry 5 }

paSeq OBJECT-TYPE
    SYNTAX      INTEGER
    ACCESS      read-only
    STATUS      mandatory
    DESCRIPTION 
        "Sequence number (relative record number)
         since boot."
    ::= { paEventLogEntry 6 }

paEventVars OBJECT-TYPE
    SYNTAX      DisplayString
    ACCESS      read-only
    STATUS      mandatory
    DESCRIPTION 
        "Text description of event."
    ::= { paEventLogEntry 7 }

paLogSize OBJECT-TYPE
    SYNTAX      Gauge
    ACCESS      read-write
    STATUS      mandatory
    DESCRIPTION 
        "Number of records in entire event log.
         (Not just current records since boot.)"
    ::= { agent 11 }

paCommand OBJECT-TYPE
    SYNTAX      LogCommand
    ACCESS      read-write
    STATUS      mandatory
    DESCRIPTION 
        "Used for issuing command to SNMP agent."
    ::= { agent 12 }

paLogBoot OBJECT-TYPE
    SYNTAX      Gauge
    ACCESS      read-only
    STATUS      mandatory
    DESCRIPTION 
        "Absolute index of first log entry at boot."
    ::= { agent 13 }

paLogNCurrent OBJECT-TYPE
    SYNTAX      Gauge
    ACCESS      read-write
    STATUS      mandatory
    DESCRIPTION 
        "SNMP Get (read) returns number of records 
         since boot subject to viewing level filtering.
         SNMP Set (write) copies this number of records
         since boot (subject to level filtering) into a
         buffer from which records are read.  This mode
         of use is deprecated.  The preferred way to get
         the event log since boot is to read paLogBoot,
         set paEvRptLevel and do a series of SNMP GetNext
         calls starting at instance paLogBoot until end
         of event log MIB table is reached."
    ::= { agent 14 }

paLogChronFirst OBJECT-TYPE
    SYNTAX      Gauge
    ACCESS      read-write
    STATUS      mandatory
    DESCRIPTION 
        "Used to request range of records from 
         paLogChronFirst to paLogChronLast"
    ::= { agent 15 }

paLogChronLast OBJECT-TYPE
    SYNTAX      Gauge
    ACCESS      read-write
    STATUS      mandatory
    DESCRIPTION 
        "Used to request range of records from 
         paLogChronFirst to paLogChronLast"
    ::= { agent 16 }

paLogScroll OBJECT-TYPE
    SYNTAX      INTEGER
    ACCESS      read-write
    STATUS      mandatory
    DESCRIPTION 
        "Used to request previous/next range of records  
         event log"
    ::= { agent 17 }

paLogFilename OBJECT-TYPE
    SYNTAX      DisplayString
    ACCESS      read-write
    STATUS      mandatory
    DESCRIPTION 
        "Used to save event log to a file."
    ::= { agent 18 }

paEnvironmentState OBJECT-TYPE
    SYNTAX      INTEGER
    ACCESS      read-only
    STATUS      mandatory
    DESCRIPTION 
        "Temperature and Voltage Status of 
         SAN Data Gateway:
         **********************************
         (LSB) bit 0  Auxiliary Power 
               bit 1  Main Power 
               bit 2  Temperature Warning
               bit 3  Temperature Alarm"
    ::= { agent 19 }

paGatewayFWRev OBJECT-TYPE
    SYNTAX      DisplayString
    ACCESS      read-only
    STATUS      mandatory
    DESCRIPTION 
        "SAN Data Gateway Firmware Revision information."
    ::= { agent 20 }

paGatewayHWRev OBJECT-TYPE
    SYNTAX      DisplayString
    ACCESS      read-only
    STATUS      mandatory
    DESCRIPTION 
        "SAN Data Gateway Hardware Revision information."
    ::= { agent 21 }

paSnmpFWRev OBJECT-TYPE
    SYNTAX      DisplayString
    ACCESS      read-only
    STATUS      mandatory
    DESCRIPTION 
        "SNMP Agent Firmware Revision information."
    ::= { agent 22 }

paRidTag OBJECT-TYPE
    SYNTAX      DisplayString
    ACCESS      read-only
    STATUS      mandatory
    DESCRIPTION 
        "SAN Data Gateway RIDTag."
    ::= { agent 23 }

paSerialNumber OBJECT-TYPE
    SYNTAX      DisplayString
    ACCESS      read-only
    STATUS      mandatory
    DESCRIPTION 
        "SAN Data Gateway Serial Number."
    ::= { agent 24 }

paServerVersion OBJECT-TYPE
    SYNTAX      INTEGER
    ACCESS      read-write
    STATUS      mandatory
    DESCRIPTION 
        "Remote Management software writes Server
         version information here to customize SNMP
         Agent behavior."
    ::= { agent 25 }

paProductType OBJECT-TYPE
    SYNTAX      PathlightProduct
    ACCESS      read-only
    STATUS      mandatory
    DESCRIPTION 
        "Type of SAN device"
    ::= { agent 26 }

paVPSEnabled OBJECT-TYPE
    SYNTAX      Boolean
    ACCESS      read-only
    STATUS      mandatory
    DESCRIPTION 
        "State of ITL MAX-ACCESS Control enable."
    ::= { agent 27 }

paLicenseKey OBJECT-TYPE
    SYNTAX      DisplayString
    ACCESS      read-write
    STATUS      mandatory
    DESCRIPTION 
        "Used to pass feature enabling license keys."
    ::= { agent 28 }

paThirdPartyCopyEnabled OBJECT-TYPE
    SYNTAX      Boolean
    ACCESS      read-only
    STATUS      mandatory
    DESCRIPTION 
        "State of Extended 3rd Party Copy enable.
         Enabled means that a valid license key
         has been entered for this feature."
    ::= { agent 29 }

paVPSStatus OBJECT-TYPE
    SYNTAX      INTEGER
    ACCESS      read-write
    STATUS      mandatory
    DESCRIPTION 
        "State of Virtual Private SAN feature.
         bit 0 :   active or inactive.
         bit 1 : licensed or not licensed.
         Bit 1 is redundant with MIB var paVPSEnabled.
         Writing 1 to bit 0 makes VPS active if licensed.
         Writing 0 to bit 0 makes VPS inactive if licensed."
    ::= { agent 30 }

paThirdPartyCopyStatus OBJECT-TYPE
    SYNTAX      INTEGER
    ACCESS      read-write
    STATUS      mandatory
    DESCRIPTION 
        "State of Extended 3rd Party Copy feature.
         bit 0 :   active or inactive.
         bit 1 : licensed or not licensed.
         Bit 1 is redundant with MIB var paThirdPartyCopyEnabled.
         Writing 1 to bit 0 makes Third Party Copy active if licensed.
         Writing 0 to bit 0 makes Third Party Copy inactive if licensed."
    ::= { agent 31 }

paCommandControlLUN OBJECT-TYPE
    SYNTAX      INTEGER
    ACCESS      read-write
    STATUS      mandatory
    DESCRIPTION 
        "Gateway/Router Command and Control LUN"
    ::= { agent 32 }

paSanDirectorEnabled OBJECT-TYPE
    SYNTAX      Boolean
    ACCESS      read-only
    STATUS      mandatory
    DESCRIPTION 
        "State of SAN Director Support for this device.
         To enable, user must write a valid license key
         to OID paLicenseKey or enter the license key
         from the service port."
    ::= { agent 33 }

paNodeName OBJECT-TYPE
    SYNTAX      OCTET STRING (SIZE(8))
    ACCESS      read-only
    STATUS      mandatory
    DESCRIPTION 
        "SAN Gateway Node Name."
    ::= { agent 34 }

paVPMStatus OBJECT-TYPE
    SYNTAX      INTEGER
    ACCESS      read-write
    STATUS      mandatory
    DESCRIPTION 
        "State of Virtual Private Map feature.
         bit 0 :   active or inactive.
         bit 1 : licensed or not licensed."
    ::= { agent 35 }

paSRSStatus OBJECT-TYPE
    SYNTAX      INTEGER
    ACCESS      read-write
    STATUS      mandatory
    DESCRIPTION 
        "State of SAN Replication Services feature.
         bit 0 :   active or inactive.
         bit 1 : licensed or not licensed."
    ::= { agent 36 }

paEthernetType OBJECT-TYPE
    SYNTAX      DisplayString
    ACCESS      read-only
    STATUS      mandatory
    DESCRIPTION 
        "Current Ethernet Speed."
    ::= { agent 37 }

paTrapSequenceNumber OBJECT-TYPE
    SYNTAX      INTEGER
    ACCESS      read-only
    STATUS      mandatory
    DESCRIPTION 
        "Sequence number of last trap sent by this
         SNMP Agent."
    ::= { agent 38 }

paSysNodeNameMode OBJECT-TYPE
    SYNTAX      INTEGER { 
					sameForEachPort(0), 
					differentForEachPort(1)
				}
    ACCESS      read-write
    STATUS      mandatory
    DESCRIPTION 
        "Algorithm used when computing Fibre Channel
         World Wide Node Name for each port.  If the 
         value is sameForEachPort(0), then the World
         Wide Node Name is the same for each port and
         computed based on the World Wide Node Name of 
         the gateway.  If the value is differentForEachPort(1),
         then the World Wide Node Name is different for  
         each port, computed based on the World Wide 
         Port Name for that port."
    ::= { agent 39 }

paGhostIOTimeToLive OBJECT-TYPE
    SYNTAX      INTEGER
    ACCESS      read-write
    STATUS      mandatory
    DESCRIPTION 
        "The amount of time that commands can remain
         queued in the SNC before being considered stale
         and discarded.
         0      : Never discard (ghost I/O disabled) 
         1 - 30 : TTL in ticks (60th of a second)"
    ::= { agent 40 }

paMaxLun OBJECT-TYPE
    SYNTAX      INTEGER
    ACCESS      read-only
    STATUS      mandatory
    DESCRIPTION 
        "The maximum LUN value possible."
    ::= { agent 41 }

paEVPSEnabled OBJECT-TYPE
    SYNTAX      INTEGER
    ACCESS      read-write
    STATUS      mandatory
    DESCRIPTION 
        "Bit 0:  EVPS active if 1, inactive if 0
         Bit 1:  EVPS licensed if 1, unlicensed if 0"
    ::= { agent 42 }

paMaxHostLun OBJECT-TYPE
    SYNTAX      INTEGER
    ACCESS      read-only
    STATUS      mandatory
    DESCRIPTION 
        "The number of devices one host can see"
    ::= { agent 43 }

paAMPStatus OBJECT-TYPE
    SYNTAX      INTEGER
    ACCESS      read-write
    STATUS      mandatory
    DESCRIPTION 
        "Status of Automatic Multipath feature.
         bit 0 : active or inactive.
         bit 1 : licensed or not licensed."
    ::= { agent 44 }

devices OBJECT IDENTIFIER
    ::= { pathlight 3 }

pdDevices OBJECT-TYPE
    SYNTAX      SEQUENCE OF DevEntry
    ACCESS      not-accessible
    STATUS      mandatory
    DESCRIPTION 
        "Pathlight Physical Device Group
         ***********************************
         Each device attached to the Gateway
         has an entry here."
    ::= { devices 1 }

pdDevEntry OBJECT-TYPE
    SYNTAX      DevEntry
    ACCESS      not-accessible
    STATUS      mandatory
    DESCRIPTION 
        " "
    INDEX       { pdIndex }
    ::= { pdDevices 1 }

DevEntry ::= SEQUENCE {
    pdIndex             INTEGER,
    pdUID               DisplayString,
    pdType              DeviceType,
    pdVendor            DisplayString,
    pdProduct           DisplayString,
    pdBlockSize         INTEGER,
    pdCapacity          Gauge,
    pdAccess            INTEGER,
    pdRemovable         Boolean,
    pdStatus            PltStatus,
    pdSpeed             INTEGER,
    pdWidth             INTEGER,
    pdSerial            DisplayString,
    pdIdentify          INTEGER,
    pdInterfaceType     Interface,
    pdBus               INTEGER,
    pdId                INTEGER,
    pdLun               INTEGER,
    pdCtlrIndex         INTEGER,
    pdHWRev             DisplayString,
    pdFWRev             DisplayString,
    pdReset             Reset,
    pdStatusBits        INTEGER,
    pdScsiAnsiLevel     ScsiAnsiLevel,
    pdTargetLun         INTEGER,
    pdIpAddress         IpAddress,
    pdAltVendor         DisplayString,
    pdAltProduct        DisplayString
}

pdIndex OBJECT-TYPE
    SYNTAX      INTEGER
    ACCESS      read-only
    STATUS      mandatory
    DESCRIPTION 
        "MIB table index"
    ::= { pdDevEntry 1 }

pdUID OBJECT-TYPE
    SYNTAX      DisplayString(SIZE(16))
    ACCESS      read-only
    STATUS      mandatory
    DESCRIPTION 
        "Universal Identifier"
    ::= { pdDevEntry 2 }

pdType OBJECT-TYPE
    SYNTAX      DeviceType
    ACCESS      read-only
    STATUS      mandatory
    DESCRIPTION 
        "Device Type i.e. disk/tape/cd etc."
    ::= { pdDevEntry 3 }

pdVendor OBJECT-TYPE
    SYNTAX      DisplayString(SIZE(8))
    ACCESS      read-only
    STATUS      mandatory
    DESCRIPTION 
        "Device Vendor"
    ::= { pdDevEntry 4 }

pdProduct OBJECT-TYPE
    SYNTAX      DisplayString(SIZE(8))
    ACCESS      read-only
    STATUS      mandatory
    DESCRIPTION 
        "Device Product Identifier"
    ::= { pdDevEntry 5 }

pdBlockSize OBJECT-TYPE
    SYNTAX      INTEGER
    ACCESS      read-only
    STATUS      mandatory
    DESCRIPTION 
        "Block size in Bytes"
    ::= { pdDevEntry 6 }

pdCapacity OBJECT-TYPE
    SYNTAX      Gauge
    ACCESS      read-only
    STATUS      mandatory
    DESCRIPTION 
        "Capacity in BLOCKS (see pdBlockSize)"
    ::= { pdDevEntry 7 }

pdAccess OBJECT-TYPE
    SYNTAX      INTEGER
    ACCESS      read-only
    STATUS      mandatory
    DESCRIPTION 
        " "
    ::= { pdDevEntry 8 }

pdRemovable OBJECT-TYPE
    SYNTAX      Boolean
    ACCESS      read-only
    STATUS      mandatory
    DESCRIPTION 
        "Is device removable ?"
    ::= { pdDevEntry 9 }

pdStatus OBJECT-TYPE
    SYNTAX      PltStatus
    ACCESS      read-only
    STATUS      mandatory
    DESCRIPTION 
        "Device Status"
    ::= { pdDevEntry 10 }

pdSpeed OBJECT-TYPE
    SYNTAX      INTEGER
    ACCESS      read-only
    STATUS      mandatory
    DESCRIPTION
        "Device Speed in MBytes/second"
    ::= { pdDevEntry 11 }

pdWidth OBJECT-TYPE
    SYNTAX      INTEGER
    ACCESS      read-only
    STATUS      mandatory
    DESCRIPTION 
        "Data path width in bits"
    ::= { pdDevEntry 12 }

pdSerial OBJECT-TYPE
    SYNTAX      DisplayString( SIZE(0..32))
    ACCESS      read-only
    STATUS      mandatory
    DESCRIPTION 
        "Device Serial Number"
    ::= { pdDevEntry 13 }

pdIdentify OBJECT-TYPE
    SYNTAX      INTEGER
    ACCESS      read-write
    STATUS      mandatory
    DESCRIPTION 
        "Number of seconds to flash identifying LED.
         Write here to flash LED on device if
         supported by Gateway and device.  Zero
         turns LED off."
    ::= { pdDevEntry 14 }

pdInterfaceType OBJECT-TYPE
    SYNTAX      Interface
    ACCESS      read-only
    STATUS      mandatory
    DESCRIPTION 
        "This device's type of communication interface."
    ::= { pdDevEntry 15 }

pdBus OBJECT-TYPE
    SYNTAX      INTEGER
    ACCESS      read-only
    STATUS      mandatory
    DESCRIPTION 
        "SCSI bus number"
    ::= { pdDevEntry 16 }

pdId OBJECT-TYPE
    SYNTAX      INTEGER
    ACCESS      read-only
    STATUS      mandatory
    DESCRIPTION 
        "SCSI Address ID"
    ::= { pdDevEntry 17 }

pdLun OBJECT-TYPE
    SYNTAX      INTEGER
    ACCESS      read-only
    STATUS      mandatory
    DESCRIPTION 
        "SCSI Logical Unit Number."
    ::= { pdDevEntry 18 }

pdCtlrIndex OBJECT-TYPE
    SYNTAX      INTEGER
    ACCESS      read-only
    STATUS      mandatory
    DESCRIPTION 
        "Index of this device's controller in the
         Controllers MIB table and type-specific 
         controller tables"
    ::= { pdDevEntry 19 }

pdHWRev OBJECT-TYPE
    SYNTAX      DisplayString( SIZE(0..32))
    ACCESS      read-only
    STATUS      mandatory
    DESCRIPTION 
        "Device hardware revision number/identifier"
    ::= { pdDevEntry 20 }

pdFWRev OBJECT-TYPE
    SYNTAX      DisplayString( SIZE(0..32))
    ACCESS      read-only
    STATUS      mandatory
    DESCRIPTION 
        "Device firmware revision number/identifier"
    ::= { pdDevEntry 21 }

pdReset OBJECT-TYPE
    SYNTAX      Reset
    ACCESS      read-write
    STATUS      mandatory
    DESCRIPTION 
        "Generic device reset if supported.
         Write reset(1) here to reset device
         if supported by Gateway firmware
         and device."
    ::= { pdDevEntry 22 }

pdStatusBits OBJECT-TYPE
    SYNTAX      INTEGER
    ACCESS      read-only
    STATUS      mandatory
    DESCRIPTION 
        "Device status bits as per SCSI spec."
    ::= { pdDevEntry 23 }

pdScsiAnsiLevel OBJECT-TYPE
    SYNTAX      ScsiAnsiLevel
    ACCESS      read-only
    STATUS      mandatory
    DESCRIPTION 
        "Device SCSI level."
    ::= { pdDevEntry 24 }

pdTargetLun OBJECT-TYPE
    SYNTAX      INTEGER
    ACCESS      read-only
    STATUS      mandatory
    DESCRIPTION 
        "This target device's Logical Unit Number as 
         seen from attached host."
    ::= { pdDevEntry 25 }

pdIpAddress OBJECT-TYPE
    SYNTAX      IpAddress
    ACCESS      read-only
    STATUS      mandatory
    DESCRIPTION 
        "This target device's IP Address if applicable.
         In case of SAN Gateway or Router, this information
         is used to allow arbitrary drill-down capability."
    ::= { pdDevEntry 26 }

pdAltVendor OBJECT-TYPE
    SYNTAX      DisplayString(SIZE(8))
    ACCESS      read-only
    STATUS      mandatory
    DESCRIPTION 
        "Device alternate Vendor"
    ::= { pdDevEntry 27 }

pdAltProduct OBJECT-TYPE
    SYNTAX      DisplayString(SIZE(16))
    ACCESS      read-only
    STATUS      mandatory
    DESCRIPTION 
        "Device alternate Product Identifier"
    ::= { pdDevEntry 28 }

controllers OBJECT IDENTIFIER
    ::= { pathlight 4 }

pcControllers OBJECT-TYPE
    SYNTAX      SEQUENCE OF CtlrEntry
    ACCESS      not-accessible
    STATUS      mandatory
    DESCRIPTION 
        "Pathlight Controller Group
         *******************************
         All controllers installed in
         the SAN Data Gateway have an
         entry here AND a parallel entry
         in the controller-type specific
         table (Fibre Channnel, SSA, or 
         SCSI)."
    ::= { controllers 1 }

pcCtlrEntry OBJECT-TYPE
    SYNTAX      CtlrEntry
    ACCESS      not-accessible
    STATUS      mandatory
    DESCRIPTION 
        " "
    INDEX       { pcIndex }
    ::= { pcControllers 1 }

CtlrEntry ::= SEQUENCE {
    pcIndex         INTEGER,
    pcType          Interface,
    pcVendorId      VendorIDInt,
    pcProductId     INTEGER,
    pcRevision      DisplayString,
    pcSubVendor     INTEGER,
    pcSubProduct    INTEGER,
    pcMaxBurst      INTEGER,
    pcLatency       INTEGER,
    pcIdentify      INTEGER,
    pcPCIBus        INTEGER,
    pcPCIDev        INTEGER,
    pcPCIFunc       INTEGER,
    pcReset         Reset,
    pcRescan        Boolean,
    pcLED           OCTET STRING,
    pcHWRev         DisplayString,
    pcFWRev         DisplayString,
    pcPCISlot       INTEGER,
    pcPMCSlot       INTEGER,
    pcPCIClass      OCTET STRING,
    pcSplitMode     Boolean,
    pcChannelMask   Gauge,
    pcPortHostType  DisplayString
}

pcIndex OBJECT-TYPE
    SYNTAX      INTEGER
    ACCESS      read-only
    STATUS      mandatory
    DESCRIPTION 
        "MIB Table index."
    ::= { pcCtlrEntry 1 }

pcType OBJECT-TYPE
    SYNTAX      Interface
    ACCESS      read-only
    STATUS      mandatory
    DESCRIPTION 
        "Communication Interface type."
    ::= { pcCtlrEntry 2 }

pcVendorId OBJECT-TYPE
    SYNTAX      VendorIDInt
    ACCESS      read-only
    STATUS      mandatory
    DESCRIPTION 
        "Integer vendor ID for this controller."
    ::= { pcCtlrEntry 3 }

pcProductId OBJECT-TYPE
    SYNTAX      INTEGER
    ACCESS      read-only
    STATUS      mandatory
    DESCRIPTION 
        "Vendor's integer ID for this controller."
    ::= { pcCtlrEntry 4 }

pcRevision OBJECT-TYPE
    SYNTAX      DisplayString (SIZE(0..32))
    ACCESS      read-only
    STATUS      obsolete
    DESCRIPTION 
        "Revision information for this controller.
         See also pcHWRev and pcFWRev."
    ::= { pcCtlrEntry 5 }

pcSubVendor OBJECT-TYPE
    SYNTAX      INTEGER
    ACCESS      read-only
    STATUS      mandatory
    DESCRIPTION 
        "Integer sub-vendor ID for this controller."
    ::= { pcCtlrEntry 6 }

pcSubProduct OBJECT-TYPE
    SYNTAX      INTEGER
    ACCESS      read-only
    STATUS      mandatory
    DESCRIPTION 
        "Vendor's integer sub-product ID for this
         controller."
    ::= { pcCtlrEntry 7 }

pcMaxBurst OBJECT-TYPE
    SYNTAX      INTEGER
    ACCESS      read-write
    STATUS      mandatory
    DESCRIPTION 
        "Maximum burst transfer rate in MBytes/second"
    ::= { pcCtlrEntry 8 }

pcLatency OBJECT-TYPE
    SYNTAX      INTEGER (0..255)
    ACCESS      read-write
    STATUS      mandatory
    DESCRIPTION 
        "Latency Timer in Clock Ticks."
    ::= { pcCtlrEntry 9 }

pcIdentify OBJECT-TYPE
    SYNTAX      INTEGER
    ACCESS      read-write
    STATUS      mandatory
    DESCRIPTION 
        "Reserved for flashing identifying LED
         on device."
    ::= { pcCtlrEntry 10 }

pcPCIBus OBJECT-TYPE
    SYNTAX      INTEGER
    ACCESS      read-only
    STATUS      mandatory
    DESCRIPTION 
        "PCI Bus number in SAN Data Gateway for
         this controller."
    ::= { pcCtlrEntry 11 }

pcPCIDev OBJECT-TYPE
    SYNTAX      INTEGER
    ACCESS      read-only
    STATUS      mandatory
    DESCRIPTION 
        "PCI device number in SAN Data Gateway for
         this controller."
    ::= { pcCtlrEntry 12 }

pcPCIFunc OBJECT-TYPE
    SYNTAX      INTEGER
    ACCESS      read-only
    STATUS      mandatory
    DESCRIPTION 
        "PCI Function number in SAN Data Gateway for
         this contoller."
    ::= { pcCtlrEntry 13 }

pcReset OBJECT-TYPE
    SYNTAX      Reset
    ACCESS      read-write
    STATUS      mandatory
    DESCRIPTION 
        "Generic controller reset variable.  Not
         supported for all controller types."
    ::= { pcCtlrEntry 14 }

pcRescan OBJECT-TYPE
    SYNTAX      Boolean
    ACCESS      read-write
    STATUS      mandatory
    DESCRIPTION 
        "Writing true(1) here causes controller to 
         rescan its bus if rescan is supported for 
         this controller type."
    ::= { pcCtlrEntry 15 }

pcLED OBJECT-TYPE
    SYNTAX      OCTET STRING (SIZE(2))
    ACCESS      read-only
    STATUS      mandatory
    DESCRIPTION 
        "Is LED on?"
    ::= { pcCtlrEntry 16 }

pcHWRev OBJECT-TYPE
    SYNTAX      DisplayString (SIZE(0..32))
    ACCESS      read-only
    STATUS      mandatory
    DESCRIPTION 
        "Hardware revision for this controller."
    ::= { pcCtlrEntry 17 }

pcFWRev OBJECT-TYPE
    SYNTAX      DisplayString (SIZE(0..32))
    ACCESS      read-only
    STATUS      mandatory
    DESCRIPTION 
        "Firmware revision for this controller"
    ::= { pcCtlrEntry 18 }

pcPCISlot OBJECT-TYPE
    SYNTAX      INTEGER
    ACCESS      read-only
    STATUS      mandatory
    DESCRIPTION 
        "Location of Channel Card on PCI bus"
    ::= { pcCtlrEntry 19 }

pcPMCSlot OBJECT-TYPE
    SYNTAX      INTEGER
    ACCESS      read-only
    STATUS      mandatory
    DESCRIPTION 
        "Location of Card: PMC 1, 2 or 3.
         0=> Not a PMC card"
    ::= { pcCtlrEntry 20 }

pcPCIClass OBJECT-TYPE
    SYNTAX      OCTET STRING (SIZE(3))
    ACCESS      read-only
    STATUS      mandatory
    DESCRIPTION 
        "Device class code as per PCI specification."
    ::= { pcCtlrEntry 21 }

pcSplitMode OBJECT-TYPE
    SYNTAX      Boolean
    ACCESS      read-write
    STATUS      mandatory
    DESCRIPTION 
        "Enable/Disable Split Mode for this
         controller."
    ::= { pcCtlrEntry 22 }

pcChannelMask OBJECT-TYPE
	SYNTAX  	Gauge
    ACCESS      read-write
    STATUS      mandatory
    DESCRIPTION 
        "Specifies MAX-ACCESS permissions for this initiator 
         in bits 0 through 18
         *************************************************
                     -* SCSI Channels *-
         Bit 0 => Is MAX-ACCESS DISALLOWED to SCSI channel 1 ? 
         Bit 1 => Is MAX-ACCESS DISALLOWED to SCSI channel 2 ? 
         Bit 2 => Is MAX-ACCESS DISALLOWED to SCSI channel 3 ? 
         Bit 3 => Is MAX-ACCESS DISALLOWED to SCSI channel 4 ?
                    -* Ultra SCSI Channels *-
         Bit 4 => Is MAX-ACCESS DISALLOWED to Ultra SCSI channel 1 ?
         Bit 5 => Is MAX-ACCESS DISALLOWED to Ultra SCSI channel 2 ?
         Bit 6 => Is MAX-ACCESS DISALLOWED to Ultra SCSI channel 3 ?
         Bit 7 => Is MAX-ACCESS DISALLOWED to Ultra SCSI channel 4 ?
         Bit 8 => Is MAX-ACCESS DISALLOWED to Ultra SCSI channel 5 ?
         Bit 9 => Is MAX-ACCESS DISALLOWED to Ultra SCSI channel 6 ?
                      -* Fibre Channel *-
         Bit 10 => Is MAX-ACCESS DISALLOWED to Fibre Channel 1 ?
         Bit 11 => Is MAX-ACCESS DISALLOWED to Fibre Channel 2 ?
         Bit 12 => Is MAX-ACCESS DISALLOWED to Fibre Channel 3 ?
         Bit 13 => Is MAX-ACCESS DISALLOWED to Fibre Channel 4 ?
         Bit 14 => Is MAX-ACCESS DISALLOWED to Fibre Channel 5 ?
         Bit 15 => Is MAX-ACCESS DISALLOWED to Fibre Channel 6 ?
                      -* SSA Channels *-
         Bit 16 => Is MAX-ACCESS DISALLOWED to SSA channel 1 ?
         Bit 17 => Is MAX-ACCESS DISALLOWED to SSA Channel 2 ?
         Bit 18 => Is MAX-ACCESS DISALLOWED to SSA Channel 3 ?"
    ::= { pcCtlrEntry 23 }

pcPortHostType OBJECT-TYPE
    SYNTAX      DisplayString (SIZE(0..32))
    ACCESS      read-write
    STATUS      mandatory
    DESCRIPTION 
        "Host type for this port.  Used if VPS
         is not enabled."
    ::= { pcCtlrEntry 24 }

pcFCCtlrs OBJECT-TYPE
    SYNTAX      SEQUENCE OF FcCtlrEntry
    ACCESS      not-accessible
    STATUS      mandatory
    DESCRIPTION 
        "Entry point for Fibre Channel Controller Device Group
         ******************************************************
         This table parallels the Controller Table:  a Fibre
         Channel controller with pcIndex N in the controller
         table appears here as index N as well, and in general
         there are rows in this table which are empty."
    ::= { controllers 2 }

fcCtlrEntry OBJECT-TYPE
    SYNTAX      FcCtlrEntry
    ACCESS      not-accessible
    STATUS      mandatory
    DESCRIPTION 
        " "
    INDEX       { pcIndex }
    ::= { pcFCCtlrs 1 }

FcCtlrEntry ::= SEQUENCE {
    fcStatus                FcStatus,
    fcMaxSpeed              Gauge,
    fcWWID                  DisplayString,
    fcFWRev                 DisplayString,
    fcHWRev                 DisplayString,
    fcLoopID                INTEGER,
    fcFrameSize             INTEGER,
    fcPortType              FibrePort,
    fcMedia                 FibreMedia,
    fcSerialNumber          DisplayString,
    fcLoopIDMode            FibreLoopIDMode,
    fcALPhysicalAddress     INTEGER,
    fcPortMode              FibrePortMode,
    fcConnectionOptions     FibreConnOptions,
    fcCtlrChipType          INTEGER,
    fcTapeFeature           Boolean,
    fcHardID                INTEGER,
    fcCurrentSpeedSetting   INTEGER,
    fcCurrentSpeed          INTEGER,
    fcFrameBufferSize       INTEGER,
    fcLinkFailureCount      INTEGER,
    fcLossSyncCount         INTEGER,
    fcLossSignalCount       INTEGER,
    fcProtocolErrorCount    INTEGER,
    fcInvalidTxWordCount    INTEGER,
    fcInvalidCRCCount       INTEGER,
    fcWWNodeName            DisplayString
}

fcStatus OBJECT-TYPE
    SYNTAX      FcStatus
    ACCESS      read-only
    STATUS      mandatory
    DESCRIPTION 
        "Status of the Fibre Channel Controller"
    ::= { fcCtlrEntry 1 }

fcMaxSpeed OBJECT-TYPE
    SYNTAX  Gauge
    ACCESS      read-only
    STATUS      mandatory
    DESCRIPTION 
        "Maximum Transfer Speed in MBytes per second."
    ::= { fcCtlrEntry 2 }

fcWWID OBJECT-TYPE
    SYNTAX      DisplayString (SIZE(17))
    ACCESS      read-only
    STATUS      mandatory
    DESCRIPTION 
        "World Wide Identifier for this Fibre Channel
         Controller."
    ::= { fcCtlrEntry 3 }

fcFWRev OBJECT-TYPE
    SYNTAX      DisplayString (SIZE(0..32))
    ACCESS      read-only
    STATUS      mandatory
    DESCRIPTION 
        "Firmware revision number/identifier for this
         Fibre Channel Controller."
    ::= { fcCtlrEntry 4 }

fcHWRev OBJECT-TYPE
    SYNTAX      DisplayString (SIZE(0..32))
    ACCESS      read-only
    STATUS      mandatory
    DESCRIPTION 
        "Hardware revision number/identifier for this
         Fibre Channel Controller."
    ::= { fcCtlrEntry 5 }

fcLoopID OBJECT-TYPE
    SYNTAX      INTEGER (-1..127)
    ACCESS      read-write
    STATUS      mandatory
    DESCRIPTION 
        "Fibre Channel Loop ID.
         soft = -1"
    ::= { fcCtlrEntry 6 }

fcFrameSize OBJECT-TYPE
    SYNTAX      INTEGER
    ACCESS      read-write
    STATUS      mandatory
    DESCRIPTION 
        "Fibre Channel frame size."
    ::= { fcCtlrEntry 7 }

fcPortType OBJECT-TYPE
    SYNTAX      FibrePort
    ACCESS      read-write
    STATUS      mandatory
    DESCRIPTION 
        "Fibre Channel Port Type"
    ::= { fcCtlrEntry 8 }

fcMedia OBJECT-TYPE
    SYNTAX      FibreMedia
    ACCESS      read-only
    STATUS      mandatory
    DESCRIPTION 
        "Media type for this Fibre Channel Controller"
    ::= { fcCtlrEntry 9 }

fcSerialNumber OBJECT-TYPE
    SYNTAX      DisplayString (SIZE(0..32))
    ACCESS      read-only
    STATUS      mandatory
    DESCRIPTION 
        "Serial Number for this Fibre Channel
         Controller."
    ::= { fcCtlrEntry 10 }

fcLoopIDMode OBJECT-TYPE
    SYNTAX      FibreLoopIDMode
    ACCESS      read-only
    STATUS      mandatory
    DESCRIPTION 
        "Fibre Channel Loop ID mode (soft or hard)"
    ::= { fcCtlrEntry 11 }

fcALPhysicalAddress OBJECT-TYPE
    SYNTAX      INTEGER
    ACCESS      read-only
    STATUS      mandatory
    DESCRIPTION 
        "Arbitrated Loop Physical Address (ALPA)"
    ::= { fcCtlrEntry 12 }

fcPortMode OBJECT-TYPE
    SYNTAX      FibrePortMode
    ACCESS      read-write
    STATUS      mandatory
    DESCRIPTION 
        "Fibre Channel Port Mode."
    ::= { fcCtlrEntry 13 }

fcConnectionOptions OBJECT-TYPE
    SYNTAX      FibreConnOptions
    ACCESS      read-write
    STATUS      mandatory
    DESCRIPTION 
        "Connection options for ISP2200 FC chip.
         Values 4 - 8 are reserved."
    ::= { fcCtlrEntry 14 }

fcCtlrChipType OBJECT-TYPE
    SYNTAX      INTEGER
    ACCESS      read-only
    STATUS      mandatory
    DESCRIPTION 
        "Type of Fibre Channel controller chip.
         Valid types are 2100 , 2200 for QLogic
         ISP2100 and ISP2200 chips."
    ::= { fcCtlrEntry 15 }

fcTapeFeature OBJECT-TYPE
    SYNTAX      Boolean
    ACCESS      read-only
    STATUS      mandatory
    DESCRIPTION 
        "Status of Fibre Channel Tape Specification support.  
         true  means this controller supports FC Tape
         false means this controller does not support FC Tape"
    ::= { fcCtlrEntry 16 }

fcHardID OBJECT-TYPE
    SYNTAX      INTEGER (-1..256)
    ACCESS      read-write
    STATUS      mandatory
    DESCRIPTION 
        "Fibre Channel Hard ID, the preferred loop ID
         for this controller.  Even if the controller is 
         in Hard Loop ID mode, the actual loop ID
         is not guaranteed to be fcHardID."
    ::= { fcCtlrEntry 17 }

fcCurrentSpeedSetting OBJECT-TYPE
    SYNTAX      INTEGER
    ACCESS      read-write
    STATUS      mandatory
    DESCRIPTION 
        "Speed in Gb/sec. 0: Auto, 1: 1Gb, 2: 2Gb"
    ::= { fcCtlrEntry 18 }

fcCurrentSpeed OBJECT-TYPE
    SYNTAX      INTEGER
    ACCESS      read-only
    STATUS      mandatory
    DESCRIPTION 
        "Current Speed Indicator Gb/sec."
    ::= { fcCtlrEntry 19 }

fcFrameBufferSize OBJECT-TYPE
    SYNTAX      INTEGER
    ACCESS      read-only
    STATUS      mandatory
    DESCRIPTION 
        "Fibre Channel Frame Buffer Size"
    ::= { fcCtlrEntry 20 }

fcLinkFailureCount OBJECT-TYPE
    SYNTAX      INTEGER
    ACCESS      read-only
    STATUS      mandatory
    DESCRIPTION 
        "Fibre Channel Link Failure Count "
    ::= { fcCtlrEntry 21 }

fcLossSyncCount OBJECT-TYPE
    SYNTAX      INTEGER
    ACCESS      read-only
    STATUS      mandatory
    DESCRIPTION 
        "Fibre Channel Loss of Sync Count "
    ::= { fcCtlrEntry 22 }

fcLossSignalCount OBJECT-TYPE
    SYNTAX      INTEGER
    ACCESS      read-only
    STATUS      mandatory
    DESCRIPTION 
        "Fibre Channel Loss of Signal Count "
    ::= { fcCtlrEntry 23 }

fcProtocolErrorCount OBJECT-TYPE
    SYNTAX      INTEGER
    ACCESS      read-only
    STATUS      mandatory
    DESCRIPTION 
        "Fibre Channel Primitive Sequence Protocol Error Count "
    ::= { fcCtlrEntry 24 }

fcInvalidTxWordCount OBJECT-TYPE
    SYNTAX      INTEGER
    ACCESS      read-only
    STATUS      mandatory
    DESCRIPTION 
        "Fibre Channel Invalid Transmission Word Count "
    ::= { fcCtlrEntry 25 }

fcInvalidCRCCount OBJECT-TYPE
    SYNTAX      INTEGER
    ACCESS      read-only
    STATUS      mandatory
    DESCRIPTION 
        "Fibre Channel Invalid CRC Count "
    ::= { fcCtlrEntry 26 }

fcWWNodeName OBJECT-TYPE
    SYNTAX      DisplayString (SIZE(17))
    ACCESS      read-only
    STATUS      mandatory
    DESCRIPTION 
        "The World Wide Node Name for this Fibre Channel
         Controller. The Node Name for this port may
         computer strictly on the World Wide Node Name
         for the gateway, or on a per port basis which
         uses the World Wide Port Name (fcWWID), thus 
         giving each port a different Node Name.  See 
         paSysNodeNameMode to get or set which algorithm
         is in use."
    ::= { fcCtlrEntry 27 }

pcSSACtlrs OBJECT-TYPE
    SYNTAX      SEQUENCE OF SSACtlrEntry
    ACCESS      not-accessible
    STATUS      mandatory
    DESCRIPTION 
        "Entry point for SSA Controller Device Group
         ****************************************************
         This table parallels the Controller Table:  an SSA
         controller with pcIndex N in the controller
         table appears here as row index N as well, and in 
         general there are rows in this table which are empty."
    ::= { controllers 3 }

ssaCtlrEntry OBJECT-TYPE
    SYNTAX      SSACtlrEntry
    ACCESS      not-accessible
    STATUS      mandatory
    DESCRIPTION 
        " "
    INDEX       { pcIndex }
    ::= { pcSSACtlrs 1 }

SSACtlrEntry ::= SEQUENCE {
    ssaStatus1          PltStatus,
    ssaStatus2          PltStatus,
    ssaSpeed            SsaSpeed,
    ssaUID              DisplayString,
    ssaFWRev            DisplayString,
   	ssaMaxTarg          Gauge,
    ssaMaxInit          Gauge,
    ssaPathAlg          PathingAlgorithm,
    ssaHWRev            DisplayString,
    ssaMasterPriority   INTEGER,
    ssaSATAQuota        INTEGER,
    ssaSATBQuota        INTEGER,
    ssaSATIQuota        INTEGER
}

ssaStatus1 OBJECT-TYPE
    SYNTAX      PltStatus
    ACCESS      read-only
    STATUS      mandatory
    DESCRIPTION 
        "Status on port 1 of dual port SSA card"
    ::= { ssaCtlrEntry 1 }

ssaStatus2 OBJECT-TYPE
    SYNTAX      PltStatus
    ACCESS      read-only
    STATUS      mandatory
    DESCRIPTION 
        "Status on port 2 of dual port SSA card"
    ::= { ssaCtlrEntry 2 }

ssaSpeed OBJECT-TYPE
    SYNTAX      SsaSpeed
    ACCESS      read-write
    STATUS      mandatory
    DESCRIPTION 
        "SSA transfer speed 
         80 Mbytes/second or 160 MBytes/second "
    ::= { ssaCtlrEntry 3 }

ssaUID OBJECT-TYPE
    SYNTAX      DisplayString (SIZE(16))
    ACCESS      read-only
    STATUS      mandatory
    DESCRIPTION 
        "Universal Identifier for this SSA Controller."
    ::= { ssaCtlrEntry 4 }

ssaFWRev OBJECT-TYPE
    SYNTAX      DisplayString (SIZE(0..32))
    ACCESS      read-only
    STATUS      mandatory
    DESCRIPTION 
        "Firmware revision number/identifier for this
         SSA controller."
    ::= { ssaCtlrEntry 5 }

ssaMaxTarg OBJECT-TYPE
	SYNTAX  	Gauge
    ACCESS      read-write
    STATUS      mandatory
    DESCRIPTION 
        "Maximum number of targets supported."
    ::= { ssaCtlrEntry 6 }

ssaMaxInit OBJECT-TYPE
    SYNTAX      Gauge
    ACCESS      read-write
    STATUS      mandatory
    DESCRIPTION 
        "Maximum number of initiators supported."
    ::= { ssaCtlrEntry 7 }

ssaPathAlg OBJECT-TYPE
    SYNTAX      PathingAlgorithm
    ACCESS      read-write
    STATUS      mandatory
    DESCRIPTION 
        "SSA pathing algorithm."
    ::= { ssaCtlrEntry 8 }

ssaHWRev OBJECT-TYPE
    SYNTAX      DisplayString (SIZE(0..32))
    ACCESS      read-only
    STATUS      mandatory
    DESCRIPTION 
        "Hardware revision number/identifier for this
         SSA controller."
    ::= { ssaCtlrEntry 9 }

ssaMasterPriority OBJECT-TYPE
    SYNTAX      INTEGER (0..7)
    ACCESS      read-only
    STATUS      mandatory
    DESCRIPTION 
        "The SSA Master Priority of an SSA node
         is a number from 0 to 7.  SSA initiators 
         elect a master based on this priority.  
         If more than one SSA node has the same 
         priority then the node with the highest 
         UID is elected.  Pathlight SSA host adapters 
         default to a Master Priority of 4.  
         SAN Gateway SSA Target adapters default to a
         priority of 5 to ensure that the Gateway
         node will be master in a multi-initiator loop.
         This value should never be set to 7 because 
         this is the priority used to guarantee 
         mastership to a node that is entering 
         Service Mode."
    ::= { ssaCtlrEntry 10 }

ssaSATAQuota OBJECT-TYPE
    SYNTAX      INTEGER (0..255)
    ACCESS      read-only
    STATUS      mandatory
    DESCRIPTION 
        "The SSA SAT Quota A parameter is an 8 bit 
         number that determines 'the maximum number 
         of frames which can be originated from this 
         port before the port is SATisfied and forwards 
         the SAT character.  A value of zero means that
         no SATs are forwarded or issued from this port.'"
    ::= { ssaCtlrEntry 11 }

ssaSATBQuota OBJECT-TYPE
    SYNTAX      INTEGER (0..255)
    ACCESS      read-only
    STATUS      mandatory
    DESCRIPTION 
        "The SSA SAT Quota B parameter is an 8 bit 
         number that determines 'the maximum number
         of frames which this port can originate 
         without forwarding a SAT character. A value
         of zero means that an infinite number of 
         frames can be sent without being subject to
         SAT pacing.'"
    ::= { ssaCtlrEntry 12 }

ssaSATIQuota OBJECT-TYPE
    SYNTAX      INTEGER (0..255)
    ACCESS      read-only
    STATUS      mandatory
    DESCRIPTION 
        " "
    ::= { ssaCtlrEntry 13 }

pcSCSICtlrs OBJECT-TYPE
    SYNTAX      SEQUENCE OF SCSICtlrEntry
    ACCESS      not-accessible
    STATUS      mandatory
    DESCRIPTION 
        "Entry point for SCSI Controller Device Group
         ****************************************************
         This table parallels the Controller Table:  a SCSI
         controller with pcIndex N in the controller
         table appears here as row index N as well, and in 
         general there are rows in this table which are empty."
    ::= { controllers 4 }

scsiCtlrEntry OBJECT-TYPE
    SYNTAX      SCSICtlrEntry
    ACCESS      not-accessible
    STATUS      mandatory
    DESCRIPTION 
        " "
    INDEX       { pcIndex }
    ::= { pcSCSICtlrs 1 }

SCSICtlrEntry ::= SEQUENCE {
    scsiStatus              PltStatus,
    scsiSpeed               ScsiSpeed,
    scsiRole                ScsiRole,
    scsiHostId              INTEGER,
    scsiMaxSpeed            ScsiSpeed,
    scsiTerm                ScsiTermination,
    scsiIoCard              ScsiCardType,
    scsiMaxIds              INTEGER,
    scsiMaxLuns             INTEGER,
    scsiMaxWidth            INTEGER,
    scsiHWRev               DisplayString,
    scsiFWRev               DisplayString,
    scsiResetOnPowerUp      Boolean,
    scsiMultiInitEnabled    Boolean,
    scsiAlternateHostId     INTEGER
}

scsiStatus OBJECT-TYPE
    SYNTAX      PltStatus
    ACCESS      read-only
    STATUS      mandatory
    DESCRIPTION 
        "Status for this SCSI controller."
    ::= { scsiCtlrEntry 1 }

scsiSpeed OBJECT-TYPE
    SYNTAX      ScsiSpeed
    ACCESS      read-write
    STATUS      mandatory
    DESCRIPTION 
        "SCSI Transaction speed."
    ::= { scsiCtlrEntry 2 }

scsiRole OBJECT-TYPE
    SYNTAX      ScsiRole
    ACCESS      read-write
    STATUS      mandatory
    DESCRIPTION 
        "Is this a Target or Initiator ?"
    ::= { scsiCtlrEntry 3 }

scsiHostId OBJECT-TYPE
    SYNTAX      INTEGER (0..15)
    ACCESS      read-write
    STATUS      mandatory
    DESCRIPTION 
        "Host ID defaults to 7."
    ::= { scsiCtlrEntry 4 }

scsiMaxSpeed OBJECT-TYPE
    SYNTAX      ScsiSpeed
    ACCESS      read-write
    STATUS      mandatory
    DESCRIPTION 
        "Maximum Speed of this SCSI Channel."
    ::= { scsiCtlrEntry 5 }

scsiTerm OBJECT-TYPE
    SYNTAX      ScsiTermination
    ACCESS      read-write
    STATUS      mandatory
    DESCRIPTION 
        "State of internal SCSI bus 
         terminations, if any."
    ::= { scsiCtlrEntry 6 }

scsiIoCard OBJECT-TYPE
    SYNTAX      ScsiCardType
    ACCESS      read-only
    STATUS      mandatory
    DESCRIPTION 
        "Type of SCSI controller hardware."
    ::= { scsiCtlrEntry 7 }

scsiMaxIds OBJECT-TYPE
    SYNTAX      INTEGER
    ACCESS      read-write
    STATUS      mandatory
    DESCRIPTION 
        "Maximum Number of IDs for this
         SCSI controller."
    ::= { scsiCtlrEntry 8 }

scsiMaxLuns OBJECT-TYPE
    SYNTAX      INTEGER
    ACCESS      read-write
    STATUS      mandatory
    DESCRIPTION 
        "Maximum Number of LUNs for this
         SCSI controller."
    ::= { scsiCtlrEntry 9 }

scsiMaxWidth OBJECT-TYPE
    SYNTAX      INTEGER
    ACCESS      read-only
    STATUS      mandatory
    DESCRIPTION 
        "Maximum transfer width in bits."
    ::= { scsiCtlrEntry 10 }

scsiHWRev OBJECT-TYPE
    SYNTAX      DisplayString (SIZE(0..32))
    ACCESS      read-only
    STATUS      mandatory
    DESCRIPTION 
        "Hardware revision for this
         SCSI controller."
    ::= { scsiCtlrEntry 11 }

scsiFWRev OBJECT-TYPE
    SYNTAX      DisplayString (SIZE(0..32))
    ACCESS      read-only
    STATUS      mandatory
    DESCRIPTION 
        "Firmware revision for this
         SCSI controller."
    ::= { scsiCtlrEntry 12 }

scsiResetOnPowerUp OBJECT-TYPE
    SYNTAX      Boolean
    ACCESS      read-write
    STATUS      mandatory
    DESCRIPTION 
        "Enables/Disables SCSI bus reset
         upon Gateway power-up for this 
         SCSI controller."
    ::= { scsiCtlrEntry 13 }

scsiMultiInitEnabled OBJECT-TYPE
    SYNTAX      Boolean
    ACCESS      read-write
    STATUS      mandatory
    DESCRIPTION 
        "Enables/Disables multi-initiator
         support on for this SCSI controller."
    ::= { scsiCtlrEntry 14 }

scsiAlternateHostId OBJECT-TYPE
    SYNTAX      INTEGER (-1..15)
    ACCESS      read-write
    STATUS      mandatory
    DESCRIPTION 
        "Alternate Host ID for this 
         SCSI controller.  -1 means
         use automatic."
    ::= { scsiCtlrEntry 15 }

notification OBJECT IDENTIFIER
    ::= { pathlight 5 }

pnTrapDest OBJECT-TYPE
    SYNTAX      SEQUENCE OF TrapDestEntry
    ACCESS      not-accessible
    STATUS      mandatory
    DESCRIPTION 
        "Trap destination Group Table
         ******************************************
         A list of IP addresses to which SNMP Traps
         are sent in parallel using UDP Port 162."
    ::= { notification 1 }

pnTrapDestEntry OBJECT-TYPE
    SYNTAX      TrapDestEntry
    ACCESS      not-accessible
    STATUS      mandatory
    DESCRIPTION 
        " "
    INDEX       { pnIPAddr, pnUdpPort }
    ::= { pnTrapDest 1 }

TrapDestEntry ::= SEQUENCE {
    pnIndex         INTEGER,
    pnIPAddr        IpAddress,
    pnUdpPort       INTEGER,
    pnTrapStyle     INTEGER
}

pnIndex OBJECT-TYPE
    SYNTAX      INTEGER
    ACCESS      read-write
    STATUS      mandatory
    DESCRIPTION 
        "Index into TrapDest table "
    ::= { pnTrapDestEntry 1 }

pnIPAddr OBJECT-TYPE
    SYNTAX      IpAddress
    ACCESS      read-write
    STATUS      mandatory
    DESCRIPTION 
        "IP Address of destination entity 
         to which traps are sent."
    ::= { pnTrapDestEntry 2 }

pnUdpPort OBJECT-TYPE
    SYNTAX      INTEGER (0..65535)
    ACCESS      read-write
    STATUS      mandatory
    DESCRIPTION 
        "UDP Port on which traps are sent
         to this entity."
    ::= { pnTrapDestEntry 3 }

pnTrapStyle OBJECT-TYPE
    SYNTAX      INTEGER { 
					proprietary(1), 
					rfc1215(2) 
				}
    ACCESS      read-write
    STATUS      mandatory
    DESCRIPTION 
        "Style to be used when building a trap PDU
         to be sent to this entity.  A value of 
         proprietary(1) selects the proprietary 
         format used by the Pathlight SAN Director
         management application.  A value of rfc1215(2)
         selects the format as described in the RFC 1215
         TRAP-TYPE objects included in this MIB document.
         The default is proprietary(1)."
    ::= { pnTrapDestEntry 4 }

pnTrapBroadcastMode OBJECT-TYPE
    SYNTAX      INTEGER { 
					disable(0), 
					enable(1) 
				}
    ACCESS      read-write
    STATUS      mandatory
    DESCRIPTION 
        "Used to Enable/Disable the broadcasting of traps."
    ::= { notification 2 }

panelLED OBJECT IDENTIFIER
    ::= { pathlight 6 }

ledReady OBJECT-TYPE
    SYNTAX      OCTET STRING (SIZE(1))
    ACCESS      read-only
    STATUS      mandatory
    DESCRIPTION 
        "ON/OFF state of READY LED."
    ::= { panelLED 1 }

ledAuxPower OBJECT-TYPE
    SYNTAX      OCTET STRING (SIZE(1))
    ACCESS      read-only
    STATUS      mandatory
    DESCRIPTION 
        "ON/OFF state of AUXILIARY POWER LED."
    ::= { panelLED 2 }

ledMainPower OBJECT-TYPE
    SYNTAX      OCTET STRING (SIZE(1))
    ACCESS      read-only
    STATUS      mandatory
    DESCRIPTION 
        "ON/OFF state of MAIN POWER LED."
    ::= { panelLED 3 }

ledTempAlarm OBJECT-TYPE
    SYNTAX      OCTET STRING (SIZE(1))
    ACCESS      read-only
    STATUS      mandatory
    DESCRIPTION 
        "ON/OFF state of Temperature Alarm LED."
    ::= { panelLED 4 }

ledTempWarn OBJECT-TYPE
    SYNTAX      OCTET STRING (SIZE(1))
    ACCESS      read-only
    STATUS      mandatory
    DESCRIPTION 
        "ON/OFF state of Temperature Warning LED."
    ::= { panelLED 5 }

ledEtherCollision OBJECT-TYPE
    SYNTAX      OCTET STRING (SIZE(1))
    ACCESS      read-only
    STATUS      mandatory
    DESCRIPTION 
        "Is Ethernet Collison LED on?"
    ::= { panelLED 6 }

ledEtherTransmit OBJECT-TYPE
    SYNTAX      OCTET STRING (SIZE(1))
    ACCESS      read-only
    STATUS      mandatory
    DESCRIPTION 
        "ON/OFF state of Ethernet Transmit LED."
    ::= { panelLED 7 }

ledEtherLink OBJECT-TYPE
    SYNTAX      OCTET STRING (SIZE(1))
    ACCESS      read-only
    STATUS      mandatory
    DESCRIPTION 
        "ON/OFF state of Ethernet Link LED."
    ::= { panelLED 8 }

ledScsi1 OBJECT-TYPE
    SYNTAX      OCTET STRING (SIZE(1))
    ACCESS      read-only
    STATUS      mandatory
    DESCRIPTION 
        "ON/OFF state of SCSI Channel 1 LED."
    ::= { panelLED 9 }

ledScsi2 OBJECT-TYPE
    SYNTAX      OCTET STRING (SIZE(1))
    ACCESS      read-only
    STATUS      mandatory
    DESCRIPTION 
        "ON/OFF state of SCSI Channel 2 LED."
    ::= { panelLED 10 }

ledScsi3 OBJECT-TYPE
    SYNTAX      OCTET STRING (SIZE(1))
    ACCESS      read-only
    STATUS      mandatory
    DESCRIPTION 
        "ON/OFF state of SCSI Channel 3 LED."
    ::= { panelLED 11 }

ledScsi4 OBJECT-TYPE
    SYNTAX      OCTET STRING (SIZE(1))
    ACCESS      read-only
    STATUS      mandatory
    DESCRIPTION 
        "ON/OFF state of SCSI Channel 4 LED."
    ::= { panelLED 12 }

ledActivity1 OBJECT-TYPE
    SYNTAX      OCTET STRING (SIZE(1))
    ACCESS      read-only
    STATUS      mandatory
    DESCRIPTION 
        "ON/OFF state of Network Connection 
         Channel 1 Activity LED."
    ::= { panelLED 13 }

ledActivity2 OBJECT-TYPE
    SYNTAX      OCTET STRING (SIZE(1))
    ACCESS      read-only
    STATUS      mandatory
    DESCRIPTION 
        "ON/OFF state of Network Connection
         Channel 2 Activity LED."
    ::= { panelLED 14 }

ledActivity3 OBJECT-TYPE
    SYNTAX      OCTET STRING (SIZE(1))
    ACCESS      read-only
    STATUS      mandatory
    DESCRIPTION 
        "ON/OFF state of Network Connection 
         Channel 3 Activity LED."
    ::= { panelLED 15 }

ledStatus1 OBJECT-TYPE
    SYNTAX      OCTET STRING (SIZE(1))
    ACCESS      read-only
    STATUS      mandatory
    DESCRIPTION 
        "ON/OFF state of Network Connection 
         Channel 1 Status LED."
    ::= { panelLED 16 }

ledStatus2 OBJECT-TYPE
    SYNTAX      OCTET STRING (SIZE(1))
    ACCESS      read-only
    STATUS      mandatory
    DESCRIPTION 
        "ON/OFF state of Network Connection
         Channel 2 Status LED."
    ::= { panelLED 17 }

ledStatus3 OBJECT-TYPE
    SYNTAX      OCTET STRING (SIZE(1))
    ACCESS      read-only
    STATUS      mandatory
    DESCRIPTION 
        "ON/OFF state of Network Connection
         Channel 1 Status LED."
    ::= { panelLED 18 }

ledAll OBJECT-TYPE
    SYNTAX      INTEGER
    ACCESS      read-only
    STATUS      mandatory
    DESCRIPTION 
        "      All LED values in one INTEGER Value
         ***********************************************
         Bit  0 Ready                  Bit  8 Scsi1
         Bit  1 AuxPower               Bit  9 Scsi2
         Bit  2 MainPower              Bit 10 Scsi3        
         Bit  3 TempAlarm              Bit 11 Scsi4
         Bit  4 TempWarn               Bit 12 Activity1
         Bit  5 EtherCollision         Bit 13 Activity2
         Bit  6 EtherTransmit          Bit 14 Activity3
         Bit  7 EtherLink              Bit 15 Status1
                                       Bit 16 Status2
                                       Bit 17 Status3
                                       Bit 18 Error
                                       Bit 19 Ethernet Speed"
    ::= { panelLED 19 }

ledError OBJECT-TYPE
    SYNTAX      OCTET STRING (SIZE(1))
    ACCESS      read-only
    STATUS      mandatory
    DESCRIPTION 
        "Turned on to indicate an Alarm
         or Warning condition."
    ::= { panelLED 20 }

ledEthernetSpeed OBJECT-TYPE
    SYNTAX      OCTET STRING (SIZE(1))
    ACCESS      read-only
    STATUS      mandatory
    DESCRIPTION 
        "ON/OFF state of Ethernet Speed indicator LED.
         0 means 10 Base-T , 1 means 100 Base-T."
    ::= { panelLED 21 }

paHost OBJECT IDENTIFIER
    ::= { pathlight 7 }

hostCommand OBJECT-TYPE
    SYNTAX      INTEGER
    ACCESS      read-write
    STATUS      mandatory
    DESCRIPTION 
        "Used to issue commands to ITL control
         software. "
    ::= { paHost 1 }

hostInitiator OBJECT-TYPE
    SYNTAX      SEQUENCE OF InitiatorEntry
    ACCESS      not-accessible
    STATUS      mandatory
    DESCRIPTION 
        "Attached Host Group Table
         ***************************
         List of attached hosts and
         pertinent information."
    ::= { paHost 2 }

hostInitiatorEntry OBJECT-TYPE
    SYNTAX      InitiatorEntry
    ACCESS      not-accessible
    STATUS      mandatory
    DESCRIPTION 
        " "
    INDEX       { hostIndex }
    ::= { hostInitiator 1 }

InitiatorEntry ::= SEQUENCE {
    hostIndex           INTEGER,
    hostRowStatus       INTEGER,
    hostWWName          DisplayString,
    hostName            DisplayString,
    hostType            DisplayString,
    hostPortID          DisplayString,
    hostSANConnection   INTEGER,
    hostConnectionType  INTEGER,
    hostITLData         OCTET STRING,
	hostIPAddr          IpAddress,
    hostLunType         HostLUNType,
    hostLunMap          OCTET STRING,
    hostInbandAccess    INTEGER
}

hostIndex OBJECT-TYPE
    SYNTAX      INTEGER
    ACCESS      read-write
    STATUS      mandatory
    DESCRIPTION 
        "Index into Host Initiator table "
    ::= { hostInitiatorEntry 1 }

hostRowStatus OBJECT-TYPE
    SYNTAX      INTEGER
    ACCESS      read-write
    STATUS      mandatory
    DESCRIPTION 
        "Row Status for this row. "
    ::= { hostInitiatorEntry 2 }

hostWWName OBJECT-TYPE
    SYNTAX      DisplayString (SIZE(0..32))
    ACCESS      read-write
    STATUS      mandatory
    DESCRIPTION 
        "World Wide name of this Initiator. "
    ::= { hostInitiatorEntry 3 }

hostName OBJECT-TYPE
    SYNTAX      DisplayString (SIZE(0..32))
    ACCESS      read-write
    STATUS      mandatory
    DESCRIPTION 
        "Name for this Initiator. "
    ::= { hostInitiatorEntry 4 }

hostType OBJECT-TYPE
    SYNTAX      DisplayString (SIZE(0..32))
    ACCESS      read-write
    STATUS      mandatory
    DESCRIPTION 
        "Operating System and other
         host environment information. "
    ::= { hostInitiatorEntry 5 }

hostPortID OBJECT-TYPE
    SYNTAX      DisplayString (SIZE(0..32))
    ACCESS      read-write
    STATUS      mandatory
    DESCRIPTION 
        " "
    ::= { hostInitiatorEntry 6 }

hostSANConnection OBJECT-TYPE
    SYNTAX      INTEGER
    ACCESS      read-only
    STATUS      mandatory
    DESCRIPTION 
        "SAN Connection (1-6) to which
         this host is connected. "
    ::= { hostInitiatorEntry 7 }

hostConnectionType OBJECT-TYPE
    SYNTAX      INTEGER
    ACCESS      read-only
    STATUS      mandatory
    DESCRIPTION 
        "Type of SAN connection (FCAL , etc.) "
    ::= { hostInitiatorEntry 8 }

hostITLData OBJECT-TYPE
    SYNTAX      OCTET STRING (SIZE(256))
    ACCESS      read-write
    STATUS      mandatory
    DESCRIPTION 
        "ITL MAX-ACCESS Control data for
         this host.  256 possible LUNs
         with one Byte of data per LUN. "
    ::= { hostInitiatorEntry 9 }

hostIPAddr OBJECT-TYPE
    SYNTAX      IpAddress
    ACCESS      read-only
    STATUS      mandatory
    DESCRIPTION 
        "IP Address of this host.  Host is
         not required to have an IP address."
    ::= { hostInitiatorEntry 10 }

hostLunType OBJECT-TYPE
    SYNTAX      HostLUNType
    ACCESS      read-write
    STATUS      mandatory
    DESCRIPTION 
        "The type of this host for EVPS.  8-bit, 16-bit, or volume set"
    ::= { hostInitiatorEntry 11 }

hostLunMap OBJECT-TYPE
    SYNTAX      OCTET STRING (SIZE(512))
    ACCESS      read-write
    STATUS      mandatory
    DESCRIPTION 
        "EVPS Map data.
         256 possible LUNs
         with two Bytes of
         data for each lun"
    ::= { hostInitiatorEntry 12 }

hostInbandAccess OBJECT-TYPE
    SYNTAX      INTEGER
    ACCESS      read-write
    STATUS      mandatory
    DESCRIPTION 
        "The in-band MAX-ACCESS level of the host"
    ::= { hostInitiatorEntry 13 }

scsiMap OBJECT IDENTIFIER
    ::= { pathlight 8 }

scsiMapCommand OBJECT-TYPE
    SYNTAX      INTEGER
    ACCESS      read-write
    STATUS      mandatory
    DESCRIPTION 
        "Used to issue commands to SCSI Channel map
         map routines. "
    ::= { scsiMap 1 }

scsiChannelMap OBJECT-TYPE
    SYNTAX      SEQUENCE OF ScsiMapEntry
    ACCESS      not-accessible
    STATUS      mandatory
    DESCRIPTION 
        "SCSI Channel Device Map Table
         ******************************
         List of devices presented to
         SCSI attached initiator.  The
         initiator sees a series of 
         (Target ID , LUN ) SCSI targets
         which are mapped to a logical
         device identified by a Pathlight
         assigned LUN."
    ::= { scsiMap 2 }

scsiMapEntry OBJECT-TYPE
    SYNTAX      ScsiMapEntry
    ACCESS      not-accessible
    STATUS      mandatory
    DESCRIPTION 
        " "
    INDEX       { scsiMapPort, scsiMapTid, scsiMapLun }
    ::= { scsiChannelMap 1 }

ScsiMapEntry ::= SEQUENCE {
    scsiMapRowStatus    RowStatus,
    scsiMapPort         INTEGER,
    scsiMapTid          INTEGER,
    scsiMapLun          INTEGER,
    scsiMapAssignedLun  INTEGER,
    scsiMapComments     DisplayString,
    scsiMapPdIndex      INTEGER
}

scsiMapRowStatus OBJECT-TYPE
    SYNTAX      RowStatus
    ACCESS      read-write
    STATUS      mandatory
    DESCRIPTION 
        "Specifies the state of the row."
    ::= { scsiMapEntry 1 }

scsiMapPort OBJECT-TYPE
    SYNTAX      INTEGER
    ACCESS      read-only
    STATUS      mandatory
    DESCRIPTION 
        "SCSI port (bus) number for this entry (1 thru 10). "
    ::= { scsiMapEntry 2 }

scsiMapTid OBJECT-TYPE
    SYNTAX      INTEGER
    ACCESS      read-only
    STATUS      mandatory
    DESCRIPTION 
        "SCSI Target ID for this entry. "
    ::= { scsiMapEntry 3 }

scsiMapLun OBJECT-TYPE
    SYNTAX      INTEGER
    ACCESS      read-only
    STATUS      mandatory
    DESCRIPTION 
        "SCSI LUN for this entry. "
    ::= { scsiMapEntry 4 }

scsiMapAssignedLun OBJECT-TYPE
    SYNTAX      INTEGER
    ACCESS      read-write
    STATUS      mandatory
    DESCRIPTION 
        "Pathlight LUN assigned to this entry. 
         This assigned LUN maps to some device
         connected to the Gateway/Router by some
         other means (FC, SSA, SCSI, ...)."
    ::= { scsiMapEntry 5 }

scsiMapComments OBJECT-TYPE
    SYNTAX      DisplayString (SIZE(0..80))
    ACCESS      read-write
    STATUS      mandatory
    DESCRIPTION 
        "User's comments for this entry."
    ::= { scsiMapEntry 6 }

scsiMapPdIndex OBJECT-TYPE
    SYNTAX      INTEGER
    ACCESS      read-only
    STATUS      mandatory
    DESCRIPTION 
        "Index into Pathlight SANMgr MIB
         Device Table ( pd group ).  The Device
         Table has more detailed information about 
         attached devices."
    ::= { scsiMapEntry 7 }

deviceMap OBJECT IDENTIFIER
    ::= { pathlight 9 }

deviceMapCommand OBJECT-TYPE
    SYNTAX      INTEGER { 
							clearCopy(1),
							commit(2), 
							winnow(3),
                    		mapClearDatabase(4)
					}
    ACCESS      read-write
    STATUS      mandatory
    DESCRIPTION 
        "Used to issue commands to device map
         map routines. "
    ::= { deviceMap 1 }

dmDeviceMap OBJECT-TYPE
    SYNTAX      SEQUENCE OF DevMapEntry
    ACCESS      not-accessible
    STATUS      mandatory
    DESCRIPTION 
        "Device Map Group
         ***********************************
         Each device attached to the Gateway
         has an entry here.  Historical data
         of devices not presently connected 
         may also appear here."
    ::= { deviceMap 2 }

dmDevMapEntry OBJECT-TYPE
    SYNTAX      DevMapEntry
    ACCESS      not-accessible
    STATUS      mandatory
    DESCRIPTION 
        " "
    INDEX       { dmAssignedLun }
    ::= { dmDeviceMap 1 }

DevMapEntry ::= SEQUENCE {
    dmRowStatus     RowStatus,
    dmAssignedLun   INTEGER,
    dmType          Interface,
    dmPort          INTEGER,
    dmTargetId      INTEGER,
    dmTargetLun     INTEGER,
    dmUid           OCTET STRING,
    dmPath          INTEGER,
    dmSerialNum     DisplayString
}

dmRowStatus OBJECT-TYPE
    SYNTAX      RowStatus
    ACCESS      read-write
    STATUS      mandatory
    DESCRIPTION 
        "Row Control Object for this row"
    ::= { dmDevMapEntry 1 }

dmAssignedLun OBJECT-TYPE
    SYNTAX      INTEGER
    ACCESS      read-only
    STATUS      mandatory
    DESCRIPTION 
        "Logical Unit Number assigned to this
         attached device.  Range is 0 thru 255."
    ::= { dmDevMapEntry 2 }

dmType OBJECT-TYPE
    SYNTAX      Interface
    ACCESS      read-write
    STATUS      mandatory
    DESCRIPTION 
        "Type of device (FC, SCSI, SNA, SSA)."
    ::= { dmDevMapEntry 3 }

dmPort OBJECT-TYPE
    SYNTAX      INTEGER
    ACCESS      read-write
    STATUS      mandatory
    DESCRIPTION 
        "SAN Gateway Port to which this device is 
         connected.  May be 1 thru 10 for SCSI,
         1 thru 6 for Fibre Channel, 1 thru 3 for
         SSA."
    ::= { dmDevMapEntry 4 }

dmTargetId OBJECT-TYPE
    SYNTAX      INTEGER
    ACCESS      read-write
    STATUS      mandatory
    DESCRIPTION 
        "The Target ID of the attached target
         device.  This is the actual target ID
         of the device, not fabricated by the
         Gateway or Router."
    ::= { dmDevMapEntry 5 }

dmTargetLun OBJECT-TYPE
    SYNTAX      INTEGER
    ACCESS      read-write
    STATUS      mandatory
    DESCRIPTION 
        "The Logical Unit Number of the attached
         target device.  This is the actual LUN
         of the device, not fabricated by the
         Gateway or Router."
    ::= { dmDevMapEntry 6 }

dmUid OBJECT-TYPE
    SYNTAX      OCTET STRING (SIZE(8))
    ACCESS      read-write
    STATUS      mandatory
    DESCRIPTION 
        "A universally unique identifier for this 
         target device."
    ::= { dmDevMapEntry 7 }

dmPath OBJECT-TYPE
    SYNTAX      INTEGER { 
					single(0), 
					manual(1), 
					auto(2) 
					}
    ACCESS      read-only
    STATUS      mandatory
    DESCRIPTION 
        "The Multipath Mode of the device. The 
         mode can only be single(0), manual(1), 
                             or auto(1)."
    ::= { dmDevMapEntry 8 }

dmSerialNum OBJECT-TYPE
    SYNTAX      DisplayString (SIZE(0..64))
    ACCESS      read-only
    STATUS      mandatory
    DESCRIPTION 
        "The Serial Number of the device."
    ::= { dmDevMapEntry 9 }

deviceMapMultipathMode OBJECT-TYPE
    SYNTAX      INTEGER { 
					single(0), 
					manual(1), 
					auto(2) 
				}
    ACCESS      read-write
    STATUS      mandatory
    DESCRIPTION 
        "Used to set the Multipath mode."
    ::= { deviceMap 3 }

deviceMapRemoveDevice OBJECT-TYPE
    SYNTAX      INTEGER
    ACCESS      read-write
    STATUS      mandatory
    DESCRIPTION 
        "Used to remove a device from the Device Map given its Device-Id. 
         Warning: This command stops the IO for this device before removing"
    ::= { deviceMap 4 }

replication OBJECT IDENTIFIER
    ::= { pathlight 10 }

srsDevTable OBJECT-TYPE
    SYNTAX      SEQUENCE OF SRSDevEntry
    ACCESS      not-accessible
    STATUS      mandatory
    DESCRIPTION 
        "Entry point for SAN Replication Service Device Group
         *****************************************************
         Each SAN Replication Service Device has an entry in 
         this table"
    ::= { replication 1 }

srsDevEntry OBJECT-TYPE
    SYNTAX      SRSDevEntry
    ACCESS      not-accessible
    STATUS      mandatory
    DESCRIPTION 
        " "
    INDEX       { srsDevId }
    ::= { srsDevTable 1 }

SRSDevEntry ::= SEQUENCE {
    srsDevId                INTEGER,
    srsDevState             INTEGER,
    srsDevCommand           INTEGER,
    srsDevAssignedLun       INTEGER,
    srsDevMemberCount       INTEGER,
    srsDevMembersOnline     INTEGER,
    srsDevFlags             INTEGER,
    srsDevSizeInBlocks      Gauge,
    srsDevBlockSize         INTEGER,
    srsDevPrimary           INTEGER
}

srsDevId OBJECT-TYPE
    SYNTAX      INTEGER
    ACCESS      read-only
    STATUS      mandatory
    DESCRIPTION 
        "Device ID for this SRS Device."
    ::= { srsDevEntry 1 }

srsDevState OBJECT-TYPE
    SYNTAX      INTEGER { unknown(0), initialized(1), online(2), 
                    error(3), deleted(4) }
    ACCESS      read-only
    STATUS      mandatory
    DESCRIPTION 
        "State of this LUN Replicated Device."
    ::= { srsDevEntry 2 }

srsDevCommand OBJECT-TYPE
    SYNTAX      INTEGER { create(1), remove(2) }
    ACCESS      read-write
    STATUS      mandatory
    DESCRIPTION 
        "Used to invoke SAN Replication Services API 
         commands.  Parameters may be passed in the 
         same SNMP Set varbind list with the srsDevCommand
         as the last varbind.
         *********************************************
         create(1)         - Creates a new SRS Device
         delete(2)         - Deletes an existing SRS Device"
    ::= { srsDevEntry 3 }

srsDevAssignedLun OBJECT-TYPE
    SYNTAX      INTEGER
    ACCESS      read-write
    STATUS      mandatory
    DESCRIPTION 
        "Assigned LUN of the SAN Replication Service Device's
         Primary."
    ::= { srsDevEntry 4 }

srsDevMemberCount OBJECT-TYPE
    SYNTAX      INTEGER
    ACCESS      read-only
    STATUS      mandatory
    DESCRIPTION 
        "Number of members of this LUN Replicated Device."
    ::= { srsDevEntry 5 }

srsDevMembersOnline OBJECT-TYPE
    SYNTAX      INTEGER
    ACCESS      read-only
    STATUS      mandatory
    DESCRIPTION 
        "Number of members online."
    ::= { srsDevEntry 6 }

srsDevFlags OBJECT-TYPE
    SYNTAX      INTEGER
    ACCESS      read-write
    STATUS      mandatory
    DESCRIPTION 
        "SCSI device flags for this SAN Replication Service Device."
    ::= { srsDevEntry 7 }

srsDevSizeInBlocks OBJECT-TYPE
    SYNTAX  Gauge
    ACCESS      read-write
    STATUS      mandatory
    DESCRIPTION 
        "Size in blocks of this SAN Replication Services Device."
    ::= { srsDevEntry 8 }

srsDevBlockSize OBJECT-TYPE
    SYNTAX      INTEGER
    ACCESS      read-write
    STATUS      mandatory
    DESCRIPTION 
        "Block size in octets."
    ::= { srsDevEntry 9 }

srsDevPrimary OBJECT-TYPE
    SYNTAX      INTEGER
    ACCESS      read-write
    STATUS      mandatory
    DESCRIPTION 
        "The Assigned LUN of this SRS Device's Primary."
    ::= { srsDevEntry 10 }

srsMemTable OBJECT-TYPE
    SYNTAX      SEQUENCE OF SRSMemEntry
    ACCESS      not-accessible
    STATUS      mandatory
    DESCRIPTION 
        "Entry point for SAN Replication Services Member Group
         *****************************************************
         This table lists the Members of each SRS Device."
    ::= { replication 2 }

srsMemEntry OBJECT-TYPE
    SYNTAX      SRSMemEntry
    ACCESS      not-accessible
    STATUS      mandatory
    DESCRIPTION 
        " "
    INDEX       { srsMemDeviceId, srsMemId }
    ::= { srsMemTable 1 }

SRSMemEntry ::= SEQUENCE {
    srsMemDeviceId      INTEGER,
    srsMemId            INTEGER,
    srsMemState         INTEGER,
    srsMemCommand       INTEGER,
    srsMemType          INTEGER,
    srsMemSyncPoint     INTEGER,
    srsMemAssignedLun   INTEGER,
    srsMemReadOptions   INTEGER,
    srsMemWriteOptions  INTEGER
}

srsMemDeviceId OBJECT-TYPE
    SYNTAX      INTEGER
    ACCESS      read-only
    STATUS      mandatory
    DESCRIPTION 
        "Device ID of the SAN Replication Services Device 
         to which this member belongs."
    ::= { srsMemEntry 1 }

srsMemId OBJECT-TYPE
    SYNTAX      INTEGER
    ACCESS      read-only
    STATUS      mandatory
    DESCRIPTION 
        "Member ID (index) of this member device."
    ::= { srsMemEntry 2 }

srsMemState OBJECT-TYPE
    SYNTAX      INTEGER { unknown(0), online(1), synchronized(2), 
                    synchronizing(3), suspended(4), readError(5), 
                    writeError(6), offline(7) }
    ACCESS      read-only
    STATUS      mandatory
    DESCRIPTION 
        "State of this SAN Replication Services Device Member."
    ::= { srsMemEntry 3 }

srsMemCommand OBJECT-TYPE
    SYNTAX      INTEGER { memberAdd(1), suspend(2), resume(3), remove(4), 
                    primarySet(5), fullSynchronize(6), 
                    quickSynchronize(7), memberChange(8) }
    ACCESS      read-write
    STATUS      mandatory
    DESCRIPTION 
        "Used to invoke SAN Replication Services API 
         methods.  Parameters may be passed in the same 
         SNMP Set varbind list with the lrmCommand as 
         the last varbind."
    ::= { srsMemEntry 4 }

srsMemType OBJECT-TYPE
    SYNTAX      INTEGER { primary(1), secondary(2) }
    ACCESS      read-only
    STATUS      mandatory
    DESCRIPTION 
        "Is this device a primary or secondary member."
    ::= { srsMemEntry 5 }

srsMemSyncPoint OBJECT-TYPE
    SYNTAX      INTEGER
    ACCESS      read-only
    STATUS      mandatory
    DESCRIPTION 
        "Number of blocks synchronized so far.
         Used for monitoring synchronization."
    ::= { srsMemEntry 6 }

srsMemAssignedLun OBJECT-TYPE
    SYNTAX      INTEGER
    ACCESS      read-write
    STATUS      mandatory
    DESCRIPTION 
        "Assigned LUN for this SRS Member."
    ::= { srsMemEntry 7 }

srsMemReadOptions OBJECT-TYPE
    SYNTAX      INTEGER { enabled(0), disabled(1) }
    ACCESS      read-write
    STATUS      mandatory
    DESCRIPTION 
        "SRS Member read options."
    ::= { srsMemEntry 8 }

srsMemWriteOptions OBJECT-TYPE
    SYNTAX      INTEGER { synchronous(0), asynchronous(1) }
    ACCESS      read-write
    STATUS      mandatory
    DESCRIPTION 
        "SRS Member write options."
    ::= { srsMemEntry 9 }

envData OBJECT IDENTIFIER
    ::= { pathlight 11 }

envDataTable OBJECT-TYPE
    SYNTAX      SEQUENCE OF EnvDataEntry
    ACCESS      not-accessible
    STATUS      mandatory
    DESCRIPTION 
        "Entry point for Environmental Data Group
         *****************************************************
         This table lists the attributes of each environmental data."
    ::= { envData 1 }

envDataEntry OBJECT-TYPE
    SYNTAX      EnvDataEntry
    ACCESS      not-accessible
    STATUS      mandatory
    DESCRIPTION 
        " "
    INDEX       { envDataId }
    ::= { envDataTable 1 }

EnvDataEntry ::= SEQUENCE {
    envDataId       INTEGER,
    envDataName     DisplayString,
    envNominalLo    DisplayString,
    envNominalHi    DisplayString,
    envWarningLo    DisplayString,
    envWarningHi    DisplayString,
    envCurValue     DisplayString,
    envCurStatus    DisplayString,
    envUnit         DisplayString
}

envDataId OBJECT-TYPE
    SYNTAX      INTEGER
    ACCESS      read-only
    STATUS      mandatory
    DESCRIPTION 
        ""
    ::= { envDataEntry 1 }

envDataName OBJECT-TYPE
    SYNTAX      DisplayString (SIZE(0..64))
    ACCESS      read-only
    STATUS      mandatory
    DESCRIPTION 
        "Name of this environmental data"
    ::= { envDataEntry 2 }

envNominalLo OBJECT-TYPE
    SYNTAX      DisplayString (SIZE(0..32))
    ACCESS      read-only
    STATUS      mandatory
    DESCRIPTION 
        "Minimum value for Nominal status
         Warning state occurs if the current value is less than this"
    ::= { envDataEntry 3 }

envNominalHi OBJECT-TYPE
    SYNTAX      DisplayString (SIZE(0..32))
    ACCESS      read-only
    STATUS      mandatory
    DESCRIPTION 
        "Maximum Value for Nominal status
         Warning state occurs if the current value is greater than this."
    ::= { envDataEntry 4 }

envWarningLo OBJECT-TYPE
    SYNTAX      DisplayString (SIZE(0..32))
    ACCESS      read-only
    STATUS      mandatory
    DESCRIPTION 
        "Minimum value for Warning status
         Alarm state occurs if the current value is less than this"
    ::= { envDataEntry 5 }

envWarningHi OBJECT-TYPE
    SYNTAX      DisplayString (SIZE(0..32))
    ACCESS      read-only
    STATUS      mandatory
    DESCRIPTION 
        "Maximum Value for Warning status
         Alarm state occurs if the current value is greater than this."
    ::= { envDataEntry 6 }

envCurValue OBJECT-TYPE
    SYNTAX      DisplayString (SIZE(0..32))
    ACCESS      read-only
    STATUS      mandatory
    DESCRIPTION 
        "Current Value."
    ::= { envDataEntry 7 }

envCurStatus OBJECT-TYPE
    SYNTAX      DisplayString (SIZE(0..32))
    ACCESS      read-only
    STATUS      mandatory
    DESCRIPTION 
        "Current Status: Nominal, Warning, or Alarm."
    ::= { envDataEntry 8 }

envUnit OBJECT-TYPE
    SYNTAX      DisplayString (SIZE(0..32))
    ACCESS      read-only
    STATUS      mandatory
    DESCRIPTION 
        "Unit"
    ::= { envDataEntry 9 }

trapDefinition OBJECT IDENTIFIER
    ::= { pathlight 1000 }

trapDefinitionV2 OBJECT IDENTIFIER
    ::= { trapDefinition 0 }

ssaPortUpEvent TRAP-TYPE
    ENTERPRISE  trapDefinition
    VARIABLES   { paTrapSequenceNumber, paTime, paProducer, paEventClass, 
                  paEventCode, paSeq, paEventVars }
--     STATUS      mandatory
    DESCRIPTION 
        "An SSA Port Up Event has occurred."
    ::= 1

ssaPortDownEvent TRAP-TYPE
    ENTERPRISE  trapDefinition
    VARIABLES   { paTrapSequenceNumber, paTime, paProducer, paEventClass, 
                  paEventCode, paSeq, paEventVars }
--     STATUS      mandatory
    DESCRIPTION 
        "An SSA Port Down Event has occurred."
    ::= 2

ssaUidAddedEvent TRAP-TYPE
    ENTERPRISE  trapDefinition
    VARIABLES   { paTrapSequenceNumber, paTime, paProducer, paEventClass, 
                  paEventCode, paSeq, paEventVars }
--     STATUS      mandatory
    DESCRIPTION 
        "An SSA UID Added Event has occurred."
    ::= 3

ssaUidRemovedEvent TRAP-TYPE
    ENTERPRISE  trapDefinition
    VARIABLES   { paTrapSequenceNumber, paTime, paProducer, paEventClass, 
                  paEventCode, paSeq, paEventVars }
--     STATUS      mandatory
    DESCRIPTION 
        "An SSA UID Removed Event has occurred."
    ::= 4

ssaWebReconfiguredEvent TRAP-TYPE
    ENTERPRISE  trapDefinition
    VARIABLES   { paTrapSequenceNumber, paTime, paProducer, paEventClass, 
                  paEventCode, paSeq, paEventVars }
--     STATUS      mandatory
    DESCRIPTION 
        "An SSA Web Reconfigured Event has occurred."
    ::= 5

ssaAsyncErrorEvent TRAP-TYPE
    ENTERPRISE  trapDefinition
    VARIABLES   { paTrapSequenceNumber, paTime, paProducer, paEventClass, 
                  paEventCode, paSeq, paEventVars }
--     STATUS      mandatory
    DESCRIPTION 
        "An SSA Async Error Event has occurred."
    ::= 6

ssaAdapterEvent TRAP-TYPE
    ENTERPRISE  trapDefinition
    VARIABLES   { paTrapSequenceNumber, paTime, paProducer, paEventClass, 
                  paEventCode, paSeq, paEventVars }
--     STATUS      mandatory
    DESCRIPTION 
        "An SSA Adapter Event has occurred."
    ::= 7

senseDataEvent TRAP-TYPE
    ENTERPRISE  trapDefinition
    VARIABLES   { paTrapSequenceNumber, paTime, paProducer, paEventClass, 
                  paEventCode, paSeq, paEventVars }
--     STATUS      mandatory
    DESCRIPTION 
        "Sense Data recorded following a check condition.
         Normally, the host system will request and process
         sense data, and then perform error recovery."
    ::= 8

unitAttentionEvent TRAP-TYPE
    ENTERPRISE  trapDefinition
    VARIABLES   { paTrapSequenceNumber, paTime, paProducer, paEventClass, 
                  paEventCode, paSeq, paEventVars }
--     STATUS      mandatory
    DESCRIPTION 
        "A LUN reports a unit attention condition on
         a non-removable media device."
    ::= 9

ibfEvent TRAP-TYPE
    ENTERPRISE  trapDefinition
    VARIABLES   { paTrapSequenceNumber, paTime, paProducer, paEventClass, 
                  paEventCode, paSeq, paEventVars }
--     STATUS      mandatory
    DESCRIPTION 
        "An Internal Bus Fault event has occurred."
    ::= 10

temperatureChangeEvent TRAP-TYPE
    ENTERPRISE  trapDefinition
    VARIABLES   { paTrapSequenceNumber, paTime, paProducer, paEventClass, 
                  paEventCode, paSeq, paEventVars }
--     STATUS      mandatory
    DESCRIPTION 
        "A temperature sensor has reported a change from
         one of three possible states to a another.  The
         possible states are  OK, High, Very High.  The 
         display string contained in the varbind paEventVars
         indicates the initial and final temperature state."
    ::= 11

timeReferenceEvent TRAP-TYPE
    ENTERPRISE  trapDefinition
    VARIABLES   { paTrapSequenceNumber, paTime, paProducer, paEventClass, 
                  paEventCode, paSeq, paEventVars }
--     STATUS      mandatory
    DESCRIPTION 
        ""
    ::= 12

shutdownEvent TRAP-TYPE
    ENTERPRISE  trapDefinition
    VARIABLES   { paTrapSequenceNumber, paTime, paProducer, paEventClass, 
                  paEventCode, paSeq, paEventVars }
--     STATUS      mandatory
    DESCRIPTION 
        "This unit is shutting down as a result of
         a restart request."
    ::= 13

diagnosticEvent TRAP-TYPE
    ENTERPRISE  trapDefinition
    VARIABLES   { paTrapSequenceNumber, paTime, paProducer, paEventClass, 
                  paEventCode, paSeq, paEventVars }
--     STATUS      mandatory
    DESCRIPTION 
        "This event is used for diagnostic purposes."
    ::= 14

configurationEvent TRAP-TYPE
    ENTERPRISE  trapDefinition
    VARIABLES   { paTrapSequenceNumber, paTime, paProducer, paEventClass, 
                  paEventCode, paSeq, paEventVars }
--     STATUS      mandatory
    DESCRIPTION 
        ""
    ::= 15

unexpectedScsiInterruptEvent TRAP-TYPE
    ENTERPRISE  trapDefinition
    VARIABLES   { paTrapSequenceNumber, paTime, paProducer, paEventClass, 
                  paEventCode, paSeq, paEventVars }
--     STATUS      mandatory
    DESCRIPTION 
        "A SCSI bus reports an unexpected interrupt."
    ::= 16

lipResetEvent TRAP-TYPE
    ENTERPRISE  trapDefinition
    VARIABLES   { paTrapSequenceNumber, paTime, paProducer, paEventClass, 
                  paEventCode, paSeq, paEventVars }
--     STATUS      mandatory
    DESCRIPTION 
        "A Fibre Channel interface reports a LIP reset
         was received from a host."
    ::= 17

fcSystemErrorEvent TRAP-TYPE
    ENTERPRISE  trapDefinition
    VARIABLES   { paTrapSequenceNumber, paTime, paProducer, paEventClass, 
                  paEventCode, paSeq, paEventVars }
--     STATUS      mandatory
    DESCRIPTION 
        "A Fibre Channel interace reports a system error."
    ::= 18

fcRequestTransferErrorEvent TRAP-TYPE
    ENTERPRISE  trapDefinition
    VARIABLES   { paTrapSequenceNumber, paTime, paProducer, paEventClass, 
                  paEventCode, paSeq, paEventVars }
--     STATUS      mandatory
    DESCRIPTION 
        "A Fibre Channel interface reports an error
         processing a request."
    ::= 19

fcResponseTransferErrorEvent TRAP-TYPE
    ENTERPRISE  trapDefinition
    VARIABLES   { paTrapSequenceNumber, paTime, paProducer, paEventClass, 
                  paEventCode, paSeq, paEventVars }
--     STATUS      mandatory
    DESCRIPTION 
        "A Fibre Channel interface reports an error
         processing a response."
    ::= 20

memoryFaultEvent TRAP-TYPE
    ENTERPRISE  trapDefinition
    VARIABLES   { paTrapSequenceNumber, paTime, paProducer, paEventClass, 
                  paEventCode, paSeq, paEventVars }
--     STATUS      mandatory
    DESCRIPTION 
        "Processor memory fault detected."
    ::= 21

fcLipEvent TRAP-TYPE
    ENTERPRISE  trapDefinition
    VARIABLES   { paTrapSequenceNumber, paTime, paProducer, paEventClass, 
                  paEventCode, paSeq, paEventVars }
--     STATUS      mandatory
    DESCRIPTION 
        "A Fibre Channel interface detected a LIP."
    ::= 22

fcLoopUpEvent TRAP-TYPE
    ENTERPRISE  trapDefinition
    VARIABLES   { paTrapSequenceNumber, paTime, paProducer, paEventClass, 
                  paEventCode, paSeq, paEventVars }
--     STATUS      mandatory
    DESCRIPTION 
        "A Fibre Channel interface reports loop up."
    ::= 23

fcLoopDownEvent TRAP-TYPE
    ENTERPRISE  trapDefinition
    VARIABLES   { paTrapSequenceNumber, paTime, paProducer, paEventClass, 
                  paEventCode, paSeq, paEventVars }
--     STATUS      mandatory
    DESCRIPTION 
        "A Fibre Channel interface reports loop down."
    ::= 24

pciBusParityErrorEvent TRAP-TYPE
    ENTERPRISE  trapDefinition
    VARIABLES   { paTrapSequenceNumber, paTime, paProducer, paEventClass, 
                  paEventCode, paSeq, paEventVars }
--     STATUS      mandatory
    DESCRIPTION 
        "Parity error detected on unit internal PCI bus."
    ::= 25

pciInterfaceErrorEvent TRAP-TYPE
    ENTERPRISE  trapDefinition
    VARIABLES   { paTrapSequenceNumber, paTime, paProducer, paEventClass, 
                  paEventCode, paSeq, paEventVars }
--     STATUS      mandatory
    DESCRIPTION 
        "Interface error detected on unit internal PCI bus."
    ::= 26

scsiDeviceAddedEvent TRAP-TYPE
    ENTERPRISE  trapDefinition
    VARIABLES   { paTrapSequenceNumber, paTime, paProducer, paEventClass, 
                  paEventCode, paSeq, paEventVars }
--     STATUS      mandatory
    DESCRIPTION 
        "A device has been added to a SCSI bus."
    ::= 27

scsiBusResetEvent TRAP-TYPE
    ENTERPRISE  trapDefinition
    VARIABLES   { paTrapSequenceNumber, paTime, paProducer, paEventClass, 
                  paEventCode, paSeq, paEventVars }
--     STATUS      mandatory
    DESCRIPTION 
        "A SCSI interface reports a bus reset was detected."
    ::= 28

deviceAddedEvent TRAP-TYPE
    ENTERPRISE  trapDefinition
    VARIABLES   { paTrapSequenceNumber, paTime, paProducer, paEventClass, 
                  paEventCode, paSeq, paEventVars }
--     STATUS      mandatory
    DESCRIPTION 
        "This unit has added a device to its configuration
         table.  Note: This trap is held off until the unit 
         has been up for 60 seconds."
    ::= 29

deviceRemovedEvent TRAP-TYPE
    ENTERPRISE  trapDefinition
    VARIABLES   { paTrapSequenceNumber, paTime, paProducer, paEventClass, 
                  paEventCode, paSeq, paEventVars }
--     STATUS      mandatory
    DESCRIPTION 
        "This unit has removed a device from its configuration
         table."
    ::= 30

loggingStartedEvent TRAP-TYPE
    ENTERPRISE  trapDefinition
    VARIABLES   { paTrapSequenceNumber, paTime, paProducer, paEventClass, 
                  paEventCode, paSeq, paEventVars }
--     STATUS      mandatory
    DESCRIPTION 
        "Event logging service has started."
    ::= 31

loggingStoppedEvent TRAP-TYPE
    ENTERPRISE  trapDefinition
    VARIABLES   { paTrapSequenceNumber, paTime, paProducer, paEventClass, 
                  paEventCode, paSeq, paEventVars }
--     STATUS      mandatory
    DESCRIPTION 
        "Event logging service has stopped."
    ::= 32

interfaceBusFaultEvent TRAP-TYPE
    ENTERPRISE  trapDefinition
    VARIABLES   { paTrapSequenceNumber, paTime, paProducer, paEventClass, 
                  paEventCode, paSeq, paEventVars }
--     STATUS      mandatory
    DESCRIPTION 
        "An interface has detected a bus fault.  The
         display string contained in varbind paEventVars
         contains the details of which interface detected
         the fault."
    ::= 33

interfaceDeviceFaultEvent TRAP-TYPE
    ENTERPRISE  trapDefinition
    VARIABLES   { paTrapSequenceNumber, paTime, paProducer, paEventClass, 
                  paEventCode, paSeq, paEventVars }
--     STATUS      mandatory
    DESCRIPTION 
        "An interface has detected a device fault.  The
         display string contained in varbind paEventVars
         contains the details of which interface detected
         the fault."
    ::= 34

scsiUnexpectedDisconnectEvent TRAP-TYPE
    ENTERPRISE  trapDefinition
    VARIABLES   { paTrapSequenceNumber, paTime, paProducer, paEventClass, 
                  paEventCode, paSeq, paEventVars }
--     STATUS      mandatory
    DESCRIPTION 
        "A SCSI interface has reported an unexpected 
         disconnect by a device."
    ::= 35

scsiParityErrorEvent TRAP-TYPE
    ENTERPRISE  trapDefinition
    VARIABLES   { paTrapSequenceNumber, paTime, paProducer, paEventClass, 
                  paEventCode, paSeq, paEventVars }
--     STATUS      mandatory
    DESCRIPTION 
        "A SCSI interface has detected a parity error on 
         the bus."
    ::= 36

fcPortDatabaseChangeEvent TRAP-TYPE
    ENTERPRISE  trapDefinition
    VARIABLES   { paTrapSequenceNumber, paTime, paProducer, paEventClass, 
                  paEventCode, paSeq, paEventVars }
--     STATUS      mandatory
    DESCRIPTION 
        "Fibre Channel port databse change detected."
    ::= 37

ddfMemoryErrorEvent TRAP-TYPE
    ENTERPRISE  trapDefinition
    VARIABLES   { paTrapSequenceNumber, paTime, paProducer, paEventClass, 
                  paEventCode, paSeq, paEventVars }
--     STATUS      mandatory
    DESCRIPTION 
        "An error was detected on the Direct Data Flow memory board."
    ::= 38

fcDirectoryServerChangeEvent TRAP-TYPE
    ENTERPRISE  trapDefinition
    VARIABLES   { paTrapSequenceNumber, paTime, paProducer, paEventClass, 
                  paEventCode, paSeq, paEventVars }
--     STATUS      mandatory
    DESCRIPTION 
        "The Directory Server on the Fibre Channel fabric
         has changed."
    ::= 39

lunLimitExcededEvent TRAP-TYPE
    ENTERPRISE  trapDefinition
    VARIABLES   { paTrapSequenceNumber, paTime, paProducer, paEventClass, 
                  paEventCode, paSeq, paEventVars }
--     STATUS      mandatory
    DESCRIPTION 
        "The maximum LUN limit has been exceded, too many 
         devices connected."
    ::= 40

fcTransferFailureEvent TRAP-TYPE
    ENTERPRISE  trapDefinition
    VARIABLES   { paTrapSequenceNumber, paTime, paProducer, paEventClass, 
                  paEventCode, paSeq, paEventVars }
--     STATUS      mandatory
    DESCRIPTION 
        "Fibre Channel transfer error."
    ::= 41

deviceLimitExcededEvent TRAP-TYPE
    ENTERPRISE  trapDefinition
    VARIABLES   { paTrapSequenceNumber, paTime, paProducer, paEventClass, 
                  paEventCode, paSeq, paEventVars }
--     STATUS      mandatory
    DESCRIPTION 
        "The maximum device limit has been exceded, the persistent
         device map database is full."
    ::= 42

fcDebugDumpEvent TRAP-TYPE
    ENTERPRISE  trapDefinition
    VARIABLES   { paTrapSequenceNumber, paTime, paProducer, paEventClass, 
                  paEventCode, paSeq, paEventVars }
--     STATUS      mandatory
    DESCRIPTION 
        "A Fibre Channel interface driver has reported a
         a debug dump."
    ::= 43

excessiveScsiBusErrorsEvent TRAP-TYPE
    ENTERPRISE  trapDefinition
    VARIABLES   { paTrapSequenceNumber, paTime, paProducer, paEventClass, 
                  paEventCode, paSeq, paEventVars }
--     STATUS      mandatory
    DESCRIPTION 
        ""
    ::= 44

memoryScrubberErrorEvent TRAP-TYPE
    ENTERPRISE  trapDefinition
    VARIABLES   { paTrapSequenceNumber, paTime, paProducer, paEventClass, 
                  paEventCode, paSeq, paEventVars }
--     STATUS      mandatory
    DESCRIPTION 
        ""
    ::= 45

srsDeviceCreatedEvent TRAP-TYPE
    ENTERPRISE  trapDefinition
    VARIABLES   { paTrapSequenceNumber, paTime, paProducer, paEventClass, 
                  paEventCode, paSeq, paEventVars }
--     STATUS      mandatory
    DESCRIPTION 
        "A new SAN Replication Services device has 
         been created"
    ::= 46

srsDeviceOnlineEvent TRAP-TYPE
    ENTERPRISE  trapDefinition
    VARIABLES   { paTrapSequenceNumber, paTime, paProducer, paEventClass, 
                  paEventCode, paSeq, paEventVars }
--     STATUS      mandatory
    DESCRIPTION 
        "A SAN Replication Services device has entered 
         the online state."
    ::= 47

srsDeviceRemovedEvent TRAP-TYPE
    ENTERPRISE  trapDefinition
    VARIABLES   { paTrapSequenceNumber, paTime, paProducer, paEventClass, 
                  paEventCode, paSeq, paEventVars }
--     STATUS      mandatory
    DESCRIPTION 
        "A SAN Replication Services device has 
         been removed (deleted)."
    ::= 48

srsDeviceFailedEvent TRAP-TYPE
    ENTERPRISE  trapDefinition
    VARIABLES   { paTrapSequenceNumber, paTime, paProducer, paEventClass, 
                  paEventCode, paSeq, paEventVars }
--     STATUS      mandatory
    DESCRIPTION 
        "A SAN Replication Services device has failed."
    ::= 49

srsMemberAddedEvent TRAP-TYPE
    ENTERPRISE  trapDefinition
    VARIABLES   { paTrapSequenceNumber, paTime, paProducer, paEventClass, 
                  paEventCode, paSeq, paEventVars }
--     STATUS      mandatory
    DESCRIPTION 
        "A new member LUN has been added to a SAN 
         Replication Services device."
    ::= 50

srsMemberSuspendedEvent TRAP-TYPE
    ENTERPRISE  trapDefinition
    VARIABLES   { paTrapSequenceNumber, paTime, paProducer, paEventClass, 
                  paEventCode, paSeq, paEventVars }
--     STATUS      mandatory
    DESCRIPTION 
        "A SAN Replication Services member has been 
         suspended."
    ::= 51

srsMemberRemovedEvent TRAP-TYPE
    ENTERPRISE  trapDefinition
    VARIABLES   { paTrapSequenceNumber, paTime, paProducer, paEventClass, 
                  paEventCode, paSeq, paEventVars }
--     STATUS      mandatory
    DESCRIPTION 
        "A SAN Replication Services member has been 
         removed."
    ::= 52

srsMemberSyncStartedEvent TRAP-TYPE
    ENTERPRISE  trapDefinition
    VARIABLES   { paTrapSequenceNumber, paTime, paProducer, paEventClass, 
                  paEventCode, paSeq, paEventVars }
--     STATUS      mandatory
    DESCRIPTION 
        "A SAN Replication Service member has begun 
         synchronization to the primary member."
    ::= 53

srsMemberSyncDoneEvent TRAP-TYPE
    ENTERPRISE  trapDefinition
    VARIABLES   { paTrapSequenceNumber, paTime, paProducer, paEventClass, 
                  paEventCode, paSeq, paEventVars }
--     STATUS      mandatory
    DESCRIPTION 
        "A SAN Replication Service member has completed 
         synchronization to the primary member."
    ::= 54

srsMemberSyncErrorEvent TRAP-TYPE
    ENTERPRISE  trapDefinition
    VARIABLES   { paTrapSequenceNumber, paTime, paProducer, paEventClass, 
                  paEventCode, paSeq, paEventVars }
--     STATUS      mandatory
    DESCRIPTION 
        "An error was detect during synchronization
         of a SAN Replication Service member to the 
         primary member."
    ::= 55

srsMemberRetryEvent TRAP-TYPE
    ENTERPRISE  trapDefinition
    VARIABLES   { paTrapSequenceNumber, paTime, paProducer, paEventClass, 
                  paEventCode, paSeq, paEventVars }
--     STATUS      mandatory
    DESCRIPTION 
        "A command issued to a SAN Replication Services
         member has failed and is being retried."
    ::= 56

srsMemberErrorEvent TRAP-TYPE
    ENTERPRISE  trapDefinition
    VARIABLES   { paTrapSequenceNumber, paTime, paProducer, paEventClass, 
                  paEventCode, paSeq, paEventVars }
--     STATUS      mandatory
    DESCRIPTION 
        "A command issued to a SAN Replication Services
         member has resulted in an error."
    ::= 57

envPowerNominalEvent TRAP-TYPE
    ENTERPRISE  trapDefinition
    VARIABLES   { paTrapSequenceNumber, paTime, paProducer, paEventClass, 
                  paEventCode, paSeq, paEventVars }
--     STATUS      mandatory
    DESCRIPTION 
        "Power has returned to nominal state from
         a warning or alarm state."
    ::= 58

envPowerWarningEvent TRAP-TYPE
    ENTERPRISE  trapDefinition
    VARIABLES   { paTrapSequenceNumber, paTime, paProducer, paEventClass, 
                  paEventCode, paSeq, paEventVars }
--     STATUS      mandatory
    DESCRIPTION 
        "Power has entered a warning state from
         a nominal state (power degrading) or 
         alarm state (power improving)."
    ::= 59

envPowerAlarmEvent TRAP-TYPE
    ENTERPRISE  trapDefinition
    VARIABLES   { paTrapSequenceNumber, paTime, paProducer, paEventClass, 
                  paEventCode, paSeq, paEventVars }
--     STATUS      mandatory
    DESCRIPTION 
        "Power has entered an alarm state."
    ::= 60

envTemperatureNominalEvent TRAP-TYPE
    ENTERPRISE  trapDefinition
    VARIABLES   { paTrapSequenceNumber, paTime, paProducer, paEventClass, 
                  paEventCode, paSeq, paEventVars }
--     STATUS      mandatory
    DESCRIPTION 
        "Inlet air, outlet air, or I/O processor
         temperature has returned to nominal state from
         a warning or alarm state."
    ::= 61

envInletTemperatureWarningEvent TRAP-TYPE
    ENTERPRISE  trapDefinition
    VARIABLES   { paTrapSequenceNumber, paTime, paProducer, paEventClass, 
                  paEventCode, paSeq, paEventVars }
--     STATUS      mandatory
    DESCRIPTION 
        "Inlet air temperature has entered a warning 
         state from a nominal state (temperature increasing) 
         or an alarm state (temperature decreasing)."
    ::= 62

envInletTemperatureAlarmEvent TRAP-TYPE
    ENTERPRISE  trapDefinition
    VARIABLES   { paTrapSequenceNumber, paTime, paProducer, paEventClass, 
                  paEventCode, paSeq, paEventVars }
--     STATUS      mandatory
    DESCRIPTION 
        "Inlet air temperature has entered an alarm state."
    ::= 63

envOutletTemperatureWarningEvent TRAP-TYPE
    ENTERPRISE  trapDefinition
    VARIABLES   { paTrapSequenceNumber, paTime, paProducer, paEventClass, 
                  paEventCode, paSeq, paEventVars }
--     STATUS      mandatory
    DESCRIPTION 
        "Outlet air temperature has entered a warning 
         state from a nominal state (temperature increasing) 
         or an alarm state (temperature decreasing)."
    ::= 64

envOutletTemperatureAlarmEvent TRAP-TYPE
    ENTERPRISE  trapDefinition
    VARIABLES   { paTrapSequenceNumber, paTime, paProducer, paEventClass, 
                  paEventCode, paSeq, paEventVars }
--     STATUS      mandatory
    DESCRIPTION 
        "Outlet air temperature has entered an alarm state."
    ::= 65

envFanNominalEvent TRAP-TYPE
    ENTERPRISE  trapDefinition
    VARIABLES   { paTrapSequenceNumber, paTime, paProducer, paEventClass, 
                  paEventCode, paSeq, paEventVars }
--     STATUS      mandatory
    DESCRIPTION 
        "Fan has entered a nominal state from a fault state."
    ::= 66

envFanWarningEvent TRAP-TYPE
    ENTERPRISE  trapDefinition
    VARIABLES   { paTrapSequenceNumber, paTime, paProducer, paEventClass, 
                  paEventCode, paSeq, paEventVars }
--     STATUS      mandatory
    DESCRIPTION 
        "Fan has entered a warning range (tachometer 
         fans only)."
    ::= 67

envFanAlarmEvent TRAP-TYPE
    ENTERPRISE  trapDefinition
    VARIABLES   { paTrapSequenceNumber, paTime, paProducer, paEventClass, 
                  paEventCode, paSeq, paEventVars }
--     STATUS      mandatory
    DESCRIPTION 
        "Fan has entered an alarm range (tachometer 
         fans) or is stalled (rotor stall fans)."
    ::= 68

eccMemoryErrorEvent TRAP-TYPE
    ENTERPRISE  trapDefinition
    VARIABLES   { paTrapSequenceNumber, paTime, paProducer, paEventClass, 
                  paEventCode, paSeq, paEventVars }
--     STATUS      mandatory
    DESCRIPTION 
        "Error correcting code memory has detected
         an error."
    ::= 69

firmwareUploadCompleteEvent TRAP-TYPE
    ENTERPRISE  trapDefinition
    VARIABLES   { paTrapSequenceNumber, paTime, paProducer, paEventClass, 
                  paEventCode, paSeq, paEventVars }
--     STATUS      mandatory
    DESCRIPTION 
        "Firmware upload process has completed."
    ::= 70

restartCompleteEvent TRAP-TYPE
    ENTERPRISE  trapDefinition
    VARIABLES   { paTrapSequenceNumber, paTime, paProducer, paEventClass, 
                  paEventCode, paSeq, paEventVars }
--     STATUS      mandatory
    DESCRIPTION 
        "Restart process has completed."
    ::= 71

maxInitiatorsExceededEvent TRAP-TYPE
    ENTERPRISE  trapDefinition
    VARIABLES   { paTrapSequenceNumber, paTime, paProducer, paEventClass, 
                  paEventCode, paSeq, paEventVars }
--     STATUS      mandatory
    DESCRIPTION 
        "Maximum number of initiators has been exceeded."
    ::= 72

dataPathFailoverEvent TRAP-TYPE
    ENTERPRISE  trapDefinition
    VARIABLES   { paTrapSequenceNumber, paTime, paProducer, paEventClass, 
                  paEventCode, paSeq, paEventVars }
--     STATUS      mandatory
    DESCRIPTION 
        "Data path failover has occurred."
    ::= 73

powerSupplyOutOfSpecEvent TRAP-TYPE
    ENTERPRISE  trapDefinition
    VARIABLES   { paTrapSequenceNumber, paTime, paProducer, paEventClass, 
                  paEventCode, paSeq, paEventVars }
--     STATUS      mandatory
    DESCRIPTION 
        "The main power supply voltage is out
         of specified operating range."
    ::= 100

auxPowerOutOfSpecEvent TRAP-TYPE
    ENTERPRISE  trapDefinition
    VARIABLES   { paTrapSequenceNumber, paTime, paProducer, paEventClass, 
                  paEventCode, paSeq, paEventVars }
--     STATUS      mandatory
    DESCRIPTION 
        "The auxillary power supply voltage is out
         of specified operating range."
    ::= 101

newTemperatureChangeEvent TRAP-TYPE
    ENTERPRISE  trapDefinition
    VARIABLES   { paTrapSequenceNumber, paTime, paProducer, paEventClass, 
                  paEventCode, paSeq, paEventVars }
--     STATUS      mandatory
    DESCRIPTION 
        "Temperature change detected since last report.
         The possible temperature states are  OK, High, 
         and Very High."
    ::= 102

newPciErrorsEvent TRAP-TYPE
    ENTERPRISE  trapDefinition
    VARIABLES   { paTrapSequenceNumber, paTime, paProducer, paEventClass, 
                  paEventCode, paSeq, paEventVars }
--     STATUS      mandatory
    DESCRIPTION 
        ""
    ::= 103

newMemoryParityErrorsEvent TRAP-TYPE
    ENTERPRISE  trapDefinition
    VARIABLES   { paTrapSequenceNumber, paTime, paProducer, paEventClass, 
                  paEventCode, paSeq, paEventVars }
--     STATUS      mandatory
    DESCRIPTION 
        ""
    ::= 104

pciBusInterfaceErrorEvent TRAP-TYPE
    ENTERPRISE  trapDefinition
    VARIABLES   { paTrapSequenceNumber, paTime, paProducer, paEventClass, 
                  paEventCode, paSeq, paEventVars }
--     STATUS      mandatory
    DESCRIPTION 
        ""
    ::= 105

fcInterfaceFailureEvent TRAP-TYPE
    ENTERPRISE  trapDefinition
    VARIABLES   { paTrapSequenceNumber, paTime, paProducer, paEventClass, 
                  paEventCode, paSeq, paEventVars }
--     STATUS      mandatory
    DESCRIPTION 
        "Fibre Channel interface failed Health Check."
    ::= 106

scsiInterfaceFailureEvent TRAP-TYPE
    ENTERPRISE  trapDefinition
    VARIABLES   { paTrapSequenceNumber, paTime, paProducer, paEventClass, 
                  paEventCode, paSeq, paEventVars }
--     STATUS      mandatory
    DESCRIPTION 
        "SCSI interface failed Health Check."
    ::= 107

ssaInterfaceFailureEvent TRAP-TYPE
    ENTERPRISE  trapDefinition
    VARIABLES   { paTrapSequenceNumber, paTime, paProducer, paEventClass, 
                  paEventCode, paSeq, paEventVars }
--     STATUS      mandatory
    DESCRIPTION 
        "SSA interface failed Health Check."
    ::= 108

deviceFailureEvent TRAP-TYPE
    ENTERPRISE  trapDefinition
    VARIABLES   { paTrapSequenceNumber, paTime, paProducer, paEventClass, 
                  paEventCode, paSeq, paEventVars }
--     STATUS      mandatory
    DESCRIPTION 
        "Target device failed Health Check."
    ::= 109

fcLinkStatusChangeEvent TRAP-TYPE
    ENTERPRISE  trapDefinition
    VARIABLES   { paTrapSequenceNumber, paTime, paProducer, paEventClass, 
                  paEventCode, paSeq, paEventVars }
--     STATUS      mandatory
    DESCRIPTION 
        "Fibre Channel link status has changed."
    ::= 110

newFcTranferErrorsEvent TRAP-TYPE
    ENTERPRISE  trapDefinition
    VARIABLES   { paTrapSequenceNumber, paTime, paProducer, paEventClass, 
                  paEventCode, paSeq, paEventVars }
--     STATUS      mandatory
    DESCRIPTION 
        "New Fibre Channel transfer errors were detected
         since last report."
    ::= 111

logWillOverwriteEvent TRAP-TYPE
    ENTERPRISE  trapDefinition
--     STATUS      mandatory
    DESCRIPTION 
        "The event log circular buffer is about to 
         wrap, overwriting the oldest entries."
    ::= 150

bootCompletedEvent TRAP-TYPE
    ENTERPRISE  trapDefinition
--     STATUS      mandatory
    DESCRIPTION 
        "This unit has completed its boot sequence and
         is ready for SNMP communication with management
         applications.  During the time period between
         the initiation of the boot (or reboot) sequence
         and the issuing of the bootCompletedEvent trap, 
         certain data objects may not be completely
         initialized.  As such, management applications 
         should not attempt to retrieve data via SNMP
         until the bootCompletedEvent is issued."
    ::= 4444

END -- end of module SANMgrV2-MIB.
