-- Automatically generated from file
-- Fri Jul 13 08:15:56 W. Europe Standard Time 2007

HA-MIB DEFINITIONS ::= BEGIN

IMPORTS
        enterprises, Gauge, Counter, IpAddress, TimeTicks FROM RFC1155-SMI
        OBJECT-TYPE 	  FROM RFC1212
        TRAP-TYPE 	  FROM RFC1215

        entPhysicalIndex, entPhysicalName FROM ENTITY-MIB
        fibrechannel  FROM Brocade-REG-MIB
		swID, swSsn   FROM SW-MIB;

bcsi OBJECT IDENTIFIER ::= {enterprises 1588}

commDev OBJECT IDENTIFIER ::= {bcsi 2}

fibrechannel OBJECT IDENTIFIER ::= {commDev 1}

haMIB OBJECT IDENTIFIER ::= {fibrechannel 2}

highAvailability OBJECT IDENTIFIER ::= {haMIB 1}

haStatus 	OBJECT-TYPE
	SYNTAX INTEGER {
                               redundant (0),
                               nonredundant (1)
                        }
	ACCESS read-only
	STATUS mandatory
	DESCRIPTION
		"Whether the system is redundant or not."
	::= { highAvailability 1 }

fruTable 	OBJECT-TYPE
	SYNTAX SEQUENCE OF FRUEntry
	ACCESS not-accessible
	STATUS mandatory
	DESCRIPTION
		"This table inventories the field replaceable units (FRUs)
		 slots available. There is entry in this table for each entry
		 in the entPhysicalTable that has entPhysicalClass set to
		 'Container (5)' and has a child entry having entPhysicalIsFRU
		 field to be true"
	::= { highAvailability 5 }

fRUEntry 	OBJECT-TYPE
	SYNTAX FRUEntry
	ACCESS not-accessible
	STATUS mandatory
	DESCRIPTION
		"An entry for FRU slot in the fruTable"
	INDEX {
		entPhysicalIndex
	}
	::= { fruTable 1 }

FRUEntry ::= SEQUENCE {
	fruClass              INTEGER,
	fruStatus             INTEGER,
	fruObjectNum          INTEGER,
	fruSupplierId         OCTET STRING,
	fruSupplierPartNum    OCTET STRING,
	fruSupplierSerialNum  OCTET STRING,
	fruSupplierRevCode    OCTET STRING
	}

fruClass 	OBJECT-TYPE
	SYNTAX INTEGER {
                               other (1),
                               unknown (2),
                               chassis (3),
                               cp (4),
                               other-CP (5),
                               switchblade (6),
                               wwn (7),
                               powerSupply (8),
                               fan (9)
                        }
	ACCESS read-only
	STATUS mandatory
	DESCRIPTION
		"The type of the FRU object that these slot can hold"
	::= { fRUEntry 1 }

fruStatus 	OBJECT-TYPE
	SYNTAX INTEGER {
                               other (1),
                               unknown (2),
                               on (3),
                               off (4),
                               faulty (5)
                        }
	ACCESS read-only
	STATUS mandatory
	DESCRIPTION
		"The current status of the FRU object in the slot"
	::= { fRUEntry 2 }

fruObjectNum 	OBJECT-TYPE
	SYNTAX INTEGER
	ACCESS read-only
	STATUS mandatory
	DESCRIPTION
		"Gives the slot number of the blade and unit number for
		 everything else"
	::= { fRUEntry 3 }

fruSupplierId 	OBJECT-TYPE
	SYNTAX OCTET STRING
	ACCESS read-only
	STATUS mandatory
	DESCRIPTION
		"The supplier id."
	::= { fRUEntry 4 }

fruSupplierPartNum 	OBJECT-TYPE
	SYNTAX OCTET STRING
	ACCESS read-only
	STATUS mandatory
	DESCRIPTION
		"The supplier part number."
	::= { fRUEntry 5 }

fruSupplierSerialNum 	OBJECT-TYPE
	SYNTAX OCTET STRING
	ACCESS read-only
	STATUS mandatory
	DESCRIPTION
		"The supplier serial number."
	::= { fRUEntry 6 }

fruSupplierRevCode 	OBJECT-TYPE
	SYNTAX OCTET STRING
	ACCESS read-only
	STATUS mandatory
	DESCRIPTION
		"The supplier revision code."
	::= { fRUEntry 7 }

fruHistoryTable 	OBJECT-TYPE
	SYNTAX SEQUENCE OF FruHistoryEntry
	ACCESS not-accessible
	STATUS mandatory
	DESCRIPTION
		"This table gives the contents of the entire history
		 log of the FRU events"
	::= { highAvailability 6 }

fruHistoryEntry 	OBJECT-TYPE
	SYNTAX FruHistoryEntry
	ACCESS not-accessible
	STATUS mandatory
	DESCRIPTION
		"An entry in this table represents a particular FRU event"
	INDEX {
		fruHistoryIndex
	}
	::= { fruHistoryTable 1 }

FruHistoryEntry ::= SEQUENCE {
	fruHistoryIndex             INTEGER,
	fruHistoryClass             INTEGER,
	fruHistoryObjectNum         INTEGER,
	fruHistoryEvent             INTEGER,
	fruHistoryTime              OCTET STRING,
	fruHistoryFactoryPartNum    OCTET STRING,
	fruHistoryFactorySerialNum  OCTET STRING
	}

fruHistoryIndex 	OBJECT-TYPE
	SYNTAX INTEGER
	ACCESS read-only
	STATUS mandatory
	DESCRIPTION
		"Index of the FRU event in the history table"
	::= { fruHistoryEntry 1 }

fruHistoryClass 	OBJECT-TYPE
	SYNTAX INTEGER {
                               other (1),
                               unknown (2),
                               chassis (3),
                               cp (4),
                               other-CP (5),
                               switchblade (6),
                               wwn (7),
                               powerSupply (8),
                               fan (9)
                        }
	ACCESS read-only
	STATUS mandatory
	DESCRIPTION
		"The type of the FRU object related to the event"
	::= { fruHistoryEntry 2 }

fruHistoryObjectNum 	OBJECT-TYPE
	SYNTAX INTEGER
	ACCESS read-only
	STATUS mandatory
	DESCRIPTION
		"Gives the slot number of the blade and unit number for
		 everything else"
	::= { fruHistoryEntry 3 }

fruHistoryEvent 	OBJECT-TYPE
	SYNTAX INTEGER {
                               added (1),
                               removed (2),
                               invalid (3)
                        }
	ACCESS read-only
	STATUS mandatory
	DESCRIPTION
		"The type of the FRU event"
	::= { fruHistoryEntry 4 }

fruHistoryTime 	OBJECT-TYPE
	SYNTAX OCTET STRING
	ACCESS read-only
	STATUS mandatory
	DESCRIPTION
		"Gives the time at which this event happened"
	::= { fruHistoryEntry 5 }

fruHistoryFactoryPartNum 	OBJECT-TYPE
	SYNTAX OCTET STRING
	ACCESS read-only
	STATUS mandatory
	DESCRIPTION
		"Gives the factory part num of the FRU object"
	::= { fruHistoryEntry 6 }

fruHistoryFactorySerialNum 	OBJECT-TYPE
	SYNTAX OCTET STRING
	ACCESS read-only
	STATUS mandatory
	DESCRIPTION
		"Gives the factory serial num of the FRU object"
	::= { fruHistoryEntry 7 }

cpTable 	OBJECT-TYPE
	SYNTAX SEQUENCE OF CpEntry
	ACCESS not-accessible
	STATUS mandatory
	DESCRIPTION
		"This table lists all the CPs in the system"
	::= { highAvailability 7 }

cpEntry 	OBJECT-TYPE
	SYNTAX CpEntry
	ACCESS not-accessible
	STATUS mandatory
	DESCRIPTION
		"An entry represents a single CP in the system"
	INDEX {
		entPhysicalIndex
	}
	::= { cpTable 1 }

CpEntry ::= SEQUENCE {
	cpStatus     INTEGER,
	cpIpAddress  IpAddress,
	cpIpMask     IpAddress,
	cpIpGateway  IpAddress,
	cpLastEvent  INTEGER
	}

cpStatus 	OBJECT-TYPE
	SYNTAX INTEGER {
                               other (1),
                               unknown (2),
                               active (3),
                               standby (4),
                               failed (5)
                        }
	ACCESS read-only
	STATUS mandatory
	DESCRIPTION
		"Gives the current status of the CP"
	::= { cpEntry 1 }

cpIpAddress 	OBJECT-TYPE
	SYNTAX IpAddress
	ACCESS read-only
	STATUS mandatory
	DESCRIPTION
		"The IP Address of the Ethernet interface of this CP."
	::= { cpEntry 2 }

cpIpMask 	OBJECT-TYPE
	SYNTAX IpAddress
	ACCESS read-only
	STATUS mandatory
	DESCRIPTION
		"The IP Mask of the Ethernet interface of this CP."
	::= { cpEntry 3 }

cpIpGateway 	OBJECT-TYPE
	SYNTAX IpAddress
	ACCESS read-only
	STATUS mandatory
	DESCRIPTION
		"The IP Address of the IP Gateway for this CP."
	::= { cpEntry 4 }

cpLastEvent 	OBJECT-TYPE
	SYNTAX INTEGER {
                               other (1),
                               unknown (2),
                               haSync (3),
                               haOutSync (4),
                               cpFaulty (5),
                               cpHealthy (6),
                               cpActive (7),
                               configChange (8),
                               failOverStart (9),
                               failOverDone (10),
                               firmwareCommit (11),
                               firmwareUpgrade (12)
                        }
	ACCESS read-only
	STATUS mandatory
	DESCRIPTION
		"The last event related to this CP"
	::= { cpEntry 5 }

haMIBTraps OBJECT IDENTIFIER ::= {haMIB 2}

haMIBTrapPrefix OBJECT IDENTIFIER ::= {haMIBTraps 0}

fruStatusChanged 	TRAP-TYPE
	ENTERPRISE haMIBTraps
	VARIABLES {
		entPhysicalName,
		fruStatus
	}
	DESCRIPTION
		"This trap is sent when status of any FRU object is changed"
	::= 1

cpStatusChanged 	TRAP-TYPE
	ENTERPRISE haMIBTraps
	VARIABLES {
		cpStatus,
		cpLastEvent,
		swID,
		swSsn
	}
	DESCRIPTION
		"This trap is sent when status of any CP object is changed"
	::= 2

fruHistoryTrap 	TRAP-TYPE
	ENTERPRISE haMIBTraps
	VARIABLES {
		fruHistoryClass,
		fruHistoryObjectNum,
		fruHistoryEvent,
		fruHistoryTime,
		fruHistoryFactoryPartNum,
		fruHistoryFactorySerialNum
	}
	DESCRIPTION
		"This trap is sent when a FRU is added or removed"
	::= 3

END
