PSA-WinIntelixgbnTrap-MIB DEFINITIONS ::= BEGIN

--PRIMEQUEST system management MIB for Partition
--
--
--$Copyright$
--Copyright Fujitsu Limited 2010
--All rights reserved
--
--
--MIB Revision: 02000005
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaWinIntelixgbnTrap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise      OBJECT IDENTIFIER  ::={ partition 201 }
     psaComTrap              OBJECT IDENTIFIER  ::={ partitionEnterprise 1 }
     psaWinIntelE100Trap     OBJECT IDENTIFIER  ::={ partitionEnterprise 51 }
     psaWinIntelE1000Trap    OBJECT IDENTIFIER  ::={ partitionEnterprise 52 }
     psaWinBcm5700Trap       OBJECT IDENTIFIER  ::={ partitionEnterprise 53 }
     psaWinEmulexTrap        OBJECT IDENTIFIER  ::={ partitionEnterprise 54 }
     psaWinLsiLogicTrap      OBJECT IDENTIFIER  ::={ partitionEnterprise 55 }
     psaWinDiskTrap          OBJECT IDENTIFIER  ::={ partitionEnterprise 56 }
     psaWinGrmpdTrap         OBJECT IDENTIFIER  ::={ partitionEnterprise 57 }
     psaWinDiskMirrorTrap    OBJECT IDENTIFIER  ::={ partitionEnterprise 58 }
     psaWinXframe2Trap       OBJECT IDENTIFIER  ::={ partitionEnterprise 59 }
     psaWinIntelE1000expTrap OBJECT IDENTIFIER  ::={ partitionEnterprise 60 }
     psaWinSvsRaidTrap       OBJECT IDENTIFIER  ::={ partitionEnterprise 61 }
     psaWinMpdTrap           OBJECT IDENTIFIER  ::={ partitionEnterprise 62 }
     psaWinGlsTrap           OBJECT IDENTIFIER  ::={ partitionEnterprise 63 }
     psaWinIntele1expressTrap  OBJECT IDENTIFIER  ::={ partitionEnterprise 64 }
     psaWinIntelixgbnTrap  OBJECT IDENTIFIER  ::={ partitionEnterprise 65 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

--***************************************************************************************
--
--FUJITSU PRIMEQUEST system management TRAP definition for Partition
--	Trap enterprise:	psaWinIntelixgbnTrap (.1.3.6.1.4.1.211.1.31.1.2.201.65)
--
--***************************************************************************************

ixgbnWinEvent0 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (Could not allocate The MAP REGISTRES)"
   --#TYPE			"ixgbn Win Event 0"
   --#SUMMARY		"%s(PID=%d) %s %d %s ixgbn:%s Software error (Could not allocate The MAP REGISTRES)"
   --#ARGUMENTS		{ 0, 1, 2, 3, 4, 5 }
   --#SEVERITY		MINOR
   ::= 21850

ixgbnWinEvent1 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (Could not assign an interrupt)"
   --#TYPE			"ixgbn Win Event 1"
   --#SUMMARY		"%s(PID=%d) %s %d %s ixgbn:%s Software error (Could not assign an interrupt)"
   --#ARGUMENTS		{ 0, 1, 2, 3, 4, 5 }
   --#SEVERITY		MAJOR
   ::= 21851

ixgbnWinEvent2 TRAP-TYPE
   ENTERPRISE   psaWinIntelixgbnTrap
   VARIABLES {
      trapPartitionName,
      trapPartitionId,
      trapEventLevel,
      trapEventId,
      trapUnitName,
      trapSuspect,
      trapVendorId,
      trapDeviceId,
      trapRevision,
      trapMmbVip
   }
   DESCRIPTION "ixgbn: Adapter error (EEPROM error)"
   --#TYPE			"ixgbn Win Event 2"
   --#SUMMARY		"%s(PID=%d) %s %d %s ixgbn:%s Adapter error (EEPROM error) vendor-id=%s device-id=%s revision=%s"
   --#ARGUMENTS		{ 0, 1, 2, 3, 4, 5, 6, 7, 8 }
   --#SEVERITY		MAJOR
   ::= 21852

ixgbnWinEvent3 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (Could not start)"
   --#TYPE			"ixgbn Win Event 3"
   --#SUMMARY		"%s(PID=%d) %s %d %s ixgbn:%s Software error (Could not start)"
   --#ARGUMENTS		{ 0, 1, 2, 3, 4, 5 }
   --#SEVERITY		MINOR
   ::= 21853

ixgbnWinEvent4 TRAP-TYPE
   ENTERPRISE   psaWinIntelixgbnTrap
   VARIABLES {
      trapPartitionName,
      trapPartitionId,
      trapEventLevel,
      trapEventId,
      trapUnitName,
      trapSuspect,
      trapVendorId,
      trapDeviceId,
      trapRevision,
      trapMmbVip
   }
   DESCRIPTION "ixgbn: Adapter error (MAC address is invalid)"
   --#TYPE			"ixgbn Win Event 4"
   --#SUMMARY		"%s(PID=%d) %s %d %s ixgbn:%s Adapter error (MAC address is invalid) vendor-id=%s device-id=%s revision=%s"
   --#ARGUMENTS		{ 0, 1, 2, 3, 4, 5, 6, 7, 8 }
   --#SEVERITY		MAJOR
   ::= 21854

ixgbnWinEvent5 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (failed to initialize properly)"
   --#TYPE			"ixgbn Win Event 5"
   --#SUMMARY		"%s(PID=%d) %s %d %s ixgbn:%s Software error (failed to initialize properly)"
   --#ARGUMENTS		{ 0, 1, 2, 3, 4, 5 }
   --#SEVERITY		MINOR
   ::= 21855

ixgbnWinEvent6 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (Could not allocate shared memory)"
   --#TYPE			"ixgbn Win Event 6"
   --#SUMMARY		"%s(PID=%d) %s %d %s ixgbn:%s Software error (Could not allocate shared memory)"
   --#ARGUMENTS		{ 0, 1, 2, 3, 4, 5 }
   --#SEVERITY		MINOR
   ::= 21856

ixgbnWinEvent7 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (Could not allocate memory)"
   --#TYPE			"ixgbn Win Event 7"
   --#SUMMARY		"%s(PID=%d) %s %d %s ixgbn:%s Software error (Could not allocate memory)"
   --#ARGUMENTS		{ 0, 1, 2, 3, 4, 5 }
   --#SEVERITY		MAJOR
   ::= 21857

ixgbnWinEvent8 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (Could not allocate resource pool)"
   --#TYPE			"ixgbn Win Event 8"
   --#SUMMARY		"%s(PID=%d) %s %d %s ixgbn:%s Software error (Could not allocate resource pool)"
   --#ARGUMENTS		{ 0, 1, 2, 3, 4, 5 }
   --#SEVERITY		MAJOR
   ::= 21858

ixgbnWinEvent9 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (Could not initialize scatter-gather DMA resources)"
   --#TYPE			"ixgbn Win Event 9"
   --#SUMMARY		"%s(PID=%d) %s %d %s ixgbn:%s Software error (Could not initialize scatter-gather DMA resources)"
   --#ARGUMENTS		{ 0, 1, 2, 3, 4, 5 }
   --#SEVERITY		MAJOR
   ::= 21859

ixgbnWinEvent10 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (Could not map the network adapter flash)"
   --#TYPE			"ixgbn Win Event 10"
   --#SUMMARY		"%s(PID=%d) %s %d %s ixgbn:%s Software error (Could not map the network adapter flash)"
   --#ARGUMENTS		{ 0, 1, 2, 3, 4, 5 }
   --#SEVERITY		MAJOR
   ::= 21860

ixgbnWinEvent11 TRAP-TYPE
   ENTERPRISE   psaWinIntelixgbnTrap
   VARIABLES {
      trapPartitionName,
      trapPartitionId,
      trapEventLevel,
      trapEventId,
      trapUnitName,
      trapSuspect,
      trapVendorId,
      trapDeviceId,
      trapRevision,
      trapMmbVip
   }
   DESCRIPTION "ixgbn: Adapter error (The fan on the network adapter has failed)"
   --#TYPE			"ixgbn Win Event 11"
   --#SUMMARY		"%s(PID=%d) %s %d %s ixgbn:%s Adapter error (The fan on the network adapter has failed) vendor-id=%s device-id=%s revision=%s"
   --#ARGUMENTS		{ 0, 1, 2, 3, 4, 5, 6, 7, 8 }
   --#SEVERITY		MAJOR
   ::= 21861

ixgbnWinEvent12 TRAP-TYPE
   ENTERPRISE   psaWinIntelixgbnTrap
   VARIABLES {
      trapPartitionName,
      trapPartitionId,
      trapEventLevel,
      trapEventId,
      trapUnitName,
      trapSuspect,
      trapMmbVip
   }
   DESCRIPTION "ixgbn: Software error (unsupported SFP+ module)"
   --#TYPE			"ixgbn Win Event 12"
   --#SUMMARY		"%s(PID=%d) %s %d %s ixgbn:%s Software error (unsupported SFP+ module)"
   --#ARGUMENTS		{ 0, 1, 2, 3, 4, 5 }
   --#SEVERITY		MINOR
   ::= 21862

ixgbnWinEvent13 TRAP-TYPE
   ENTERPRISE   psaWinIntelixgbnTrap
   VARIABLES {
      trapPartitionName,
      trapPartitionId,
      trapEventLevel,
      trapEventId,
      trapUnitName,
      trapSuspect,
      trapVendorId,
      trapDeviceId,
      trapRevision,
      trapMmbVip
   }
   DESCRIPTION "ixgbn: Adapter error (overheated)"
   --#TYPE			"ixgbn Win Event 13"
   --#SUMMARY		"%s(PID=%d) %s %d %s ixgbn:%s Adapter error (overheated) vendor-id=%s device-id=%s revision=%s"
   --#ARGUMENTS		{ 0, 1, 2, 3, 4, 5, 6, 7, 8 }
   --#SEVERITY		MAJOR
   ::= 21863

END
