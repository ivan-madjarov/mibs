--------------------------------------------------------------------------------
--
-- LSI vendor unique environmental monitoring MIB for MegaRAID IDE/SATA controllers
-- Copyright(c) 2002, LSI Logic
-- MIB Version 1.10.1103
-- Date: 03-11-2004
-- Previous:  1.9.1022
-- Revision: 
-- Modified by Viet Nguyen
--------------------------------------------------------------------------------
LSIRAID-IDE-MIB DEFINITIONS ::= BEGIN
IMPORTS
   enterprises                 FROM RFC1155-SMI
   Gauge                       FROM RFC1155-SMI
   OBJECT-TYPE                 FROM RFC-1212
   DisplayString               FROM RFC1213-MIB
   TRAP-TYPE                   FROM RFC-1215;

--------------------------------------------------------------------------------
--
-- LSI specific object identifiers.
--
--------------------------------------------------------------------------------
lsi                     OBJECT IDENTIFIER ::= {enterprises 3582}
megaIDE                 OBJECT IDENTIFIER ::= {lsi 3}
ide                     OBJECT IDENTIFIER ::= {megaIDE 2}

--------------------------------------------------------------------------------
--
-- Management/monitoring MIB object groups.
--
--------------------------------------------------------------------------------
ideTrapInfo 	  		OBJECT IDENTIFIER ::= {ide 5}
versionInfo				OBJECT IDENTIFIER ::= {ide 4}
idePhysicalDrives       OBJECT IDENTIFIER ::= {ide 3}
ideLogicalDrives		OBJECT IDENTIFIER ::= {ide 2}
ideControllers			OBJECT IDENTIFIER ::= {ide 1}

--------------------------------------------------------------------------------
--
-- Version Information group.
--
-- This table contains version information MegaRAID IDE.
--
--------------------------------------------------------------------------------
mibVersion		        OBJECT-TYPE
    SYNTAX                      DisplayString (SIZE(0..63))
    ACCESS                      read-only
    STATUS                      mandatory
    DESCRIPTION                 "The MIB version in xx.yy.zz format"
    ::= { versionInfo 1 }

agentModuleName                 OBJECT-TYPE
    SYNTAX                      DisplayString (SIZE(0..63))
    ACCESS                      read-only
    STATUS                      mandatory
    DESCRIPTION                 "Module Name"
    ::= { versionInfo 2 }

agentModuleVersion              OBJECT-TYPE
    SYNTAX                      DisplayString (SIZE(0..63))
    ACCESS                      read-only
    STATUS                      mandatory
    DESCRIPTION                 "Module Version"
    ::= { versionInfo 3 }

companyName		        OBJECT-TYPE
    SYNTAX                      DisplayString (SIZE(0..63))
    ACCESS                      read-only
    STATUS                      mandatory
    DESCRIPTION                 "Company Name"
    ::= { versionInfo 4 }

releaseDate		        OBJECT-TYPE
    SYNTAX                      DisplayString (SIZE(0..63))
    ACCESS                      read-only
    STATUS                      mandatory
    DESCRIPTION                 "Release Date"
    ::= { versionInfo 5 }

--------------------------------------------------------------------------------
--
-- Controllers Information group.
--
-- This table contains information about the MegaRAID IDE Controllers in the system.
--
--------------------------------------------------------------------------------

    contTable                   OBJECT-TYPE
    SYNTAX                      SEQUENCE OF ContEntry
    ACCESS                      not-accessible
    STATUS                      mandatory
    DESCRIPTION                 "Each row describes a MegaRAID IDE Controller Information."
    ::= { ideControllers 2 }

contNumber                      OBJECT-TYPE
    SYNTAX                      Gauge
    ACCESS                      read-only
    STATUS                      mandatory
    DESCRIPTION                 "The present number of rows in the Controllers table."
    ::= { ideControllers 1 }

    contEntry                   OBJECT-TYPE
    SYNTAX                      ContEntry
    ACCESS                      not-accessible
    STATUS                      mandatory
    INDEX                       { contIndex }
    ::= { contTable 1 }

ContEntry ::=
    SEQUENCE { 
		contIndex				INTEGER,
		contControllerId		INTEGER,
		contModel				DisplayString,
		contBIOSVersion			DisplayString,
		contRevision			DisplayString,
		contDriverVersion		DisplayString,
		contBaseAddress			DisplayString,
		contInterrupt			DisplayString,
		contNumberOfChannels	INTEGER,
		contBuzzer               INTEGER,
		contRebRate              INTEGER,
		contBIOSState            INTEGER,
		contStopOnError          INTEGER,
		contNewDevConf           INTEGER,
		contFastInit             INTEGER,
		contCCState              INTEGER,
		contAutoRebuild          INTEGER,
		contBootLD               INTEGER,
		contPDSmartStatus        INTEGER,
		contPDSmartPollInterval  INTEGER
	}

contIndex                       OBJECT-TYPE
    SYNTAX                      INTEGER
    ACCESS                      read-only
    STATUS                      mandatory
    DESCRIPTION                 "Index of Controller Information entry."
    ::= { contEntry 1 }

contControllerId	        OBJECT-TYPE
    SYNTAX                      INTEGER 
    ACCESS                      read-only
    STATUS                      mandatory
    DESCRIPTION                 "MegaRAID IDE Controller Id."
    ::= { contEntry 2 }

contModel		        OBJECT-TYPE
    SYNTAX                      DisplayString (SIZE(0..63))
    ACCESS                      read-only
    STATUS                      mandatory
    DESCRIPTION                 "Model name."
    ::= { contEntry 3 }

contBIOSVersion                 OBJECT-TYPE
    SYNTAX                      DisplayString (SIZE(0..63))
    ACCESS                      read-only
    STATUS                      mandatory
    DESCRIPTION                 "BIOS version."
    ::= { contEntry 4 }

contRevision                    OBJECT-TYPE
    SYNTAX                      DisplayString (SIZE(0..63))
    ACCESS                      read-only
    STATUS                      mandatory
    DESCRIPTION                 "MegaRAID IDE Revision."
    ::= { contEntry 5 }

contDriverVersion               OBJECT-TYPE
    SYNTAX                      DisplayString (SIZE(0..63))
    ACCESS                      read-only
    STATUS                      mandatory
    DESCRIPTION                 "MegaRAID IDE driver version"
    ::= { contEntry 6 }

contBaseAddress		        OBJECT-TYPE
    SYNTAX                      DisplayString (SIZE(0..63))
    ACCESS                      read-only
    STATUS                      mandatory
    DESCRIPTION                 "Controller Bus Master Base address."
    ::= { contEntry 7 }
                                      
contInterrupt		        OBJECT-TYPE
    SYNTAX                      DisplayString (SIZE(0..63))
    ACCESS                      read-only
    STATUS                      mandatory
    DESCRIPTION                 "Controller interrupt."
    ::= { contEntry 8 }

contNumberOfChannels            OBJECT-TYPE
    SYNTAX                      INTEGER
    ACCESS                      read-only
    STATUS                      mandatory
    DESCRIPTION                 "Available IDE channels."
    ::= { contEntry 9 }

contBuzzer                      OBJECT-TYPE
    SYNTAX                      INTEGER {
                                disable(2),
                                enable(1)
                                }
    ACCESS                      read-write
    STATUS                      mandatory
    DESCRIPTION                 "Buzzer State."
    ::= { contEntry 10 }

contRebRate                     OBJECT-TYPE
    SYNTAX                      INTEGER (0..100)
    ACCESS                      read-write
    STATUS                      mandatory
    DESCRIPTION                 "Rebuild rate of physical drive(s)"
    ::= { contEntry 11 }

contBIOSState                   OBJECT-TYPE
    SYNTAX                      INTEGER {
                                disable(2),
                                enable(1)
                                }
    ACCESS                      read-write
    STATUS                      mandatory
    DESCRIPTION                 "Controller BIOS State"
    ::= { contEntry 12 }

contStopOnError                 OBJECT-TYPE
    SYNTAX                      INTEGER {
                                no(2),
                                yes(1)
                                }
    ACCESS                      read-write
    STATUS                      mandatory
    DESCRIPTION                 "Stop On Error"
    ::= { contEntry 13 }

contNewDevConf                  OBJECT-TYPE
    SYNTAX                      INTEGER {
                                autoConfiguration(2),
                                forceToCtrlM(1)
                                }
    ACCESS                      read-write
    STATUS                      mandatory
    DESCRIPTION                 "How new device(s) will configured."
    ::= { contEntry 14 }

contFastInit                    OBJECT-TYPE
    SYNTAX                      INTEGER {
                                disable(2),
                                enable(1)
                                }
    ACCESS                      read-write
    STATUS                      mandatory
    DESCRIPTION                 "How initialization will performed FAST/Complete."
    ::= { contEntry 15 }

contCCState                     OBJECT-TYPE
    SYNTAX                      INTEGER {
                                fixReport(2),
                                reportONLY(1)
                                }
    ACCESS                      read-write
    STATUS                      mandatory
    DESCRIPTION                 "Consistency Check Options"
    ::= { contEntry 16 }

contAutoRebuild                 OBJECT-TYPE
    SYNTAX                      INTEGER {
                                off(1),
                                on(2)
                                }
    ACCESS                      read-write
    STATUS                      mandatory
    DESCRIPTION                 "In case of drive failure Rebuild will be started Automatically."
    ::= { contEntry 17 }

contBootLD                      OBJECT-TYPE
    SYNTAX                      INTEGER (0..7)
    ACCESS                      read-write
    STATUS                      mandatory
    DESCRIPTION                 "Boot Logical drive"
    ::= { contEntry 18 }

contPDSmartStatus               OBJECT-TYPE
    SYNTAX                      INTEGER {
                                disable(2),
                                enable(1)
                                }
    ACCESS                      read-write
    STATUS                      mandatory
    DESCRIPTION                 "SMART status for drive(s) under this controller"
    ::= { contEntry 19 }

contPDSmartPollInterval         OBJECT-TYPE
    SYNTAX                      INTEGER
    ACCESS                      read-write
    STATUS                      mandatory
    DESCRIPTION                 "SMART polling interval in minutes"
    ::= { contEntry 20 }

--------------------------------------------------------------------------------
--
-- Logical Drive Information group.
--
-- This table contains information about the Logical Drive in the system.
--
--------------------------------------------------------------------------------

ldTable                        OBJECT-TYPE
    SYNTAX                      SEQUENCE OF LDEntry
    ACCESS                      not-accessible
    STATUS                      mandatory
    DESCRIPTION                 "Each row describes a LD Information."
    ::= { ideLogicalDrives 2 }

ldNumber                       OBJECT-TYPE
    SYNTAX                      Gauge
    ACCESS                      read-only
    STATUS                      mandatory
    DESCRIPTION                 "The present number of rows in the LD table."
    ::= { ideLogicalDrives 1 }
    
ldEntry                        OBJECT-TYPE
    SYNTAX                      LDEntry
    ACCESS                      not-accessible
    STATUS                      mandatory
    INDEX                       { ldIndex }
    ::= { ldTable 1 }


LDEntry ::=
    SEQUENCE { 
		ldIndex		        INTEGER,
		ldID		        INTEGER,
		ldName		        DisplayString,
		ldMode			DisplayString,
		ldStatus		INTEGER,
		ldStripeSize	        DisplayString,
		ldCapacity		DisplayString,
		ldDriveLetters	        DisplayString,
		ldNumStripes		INTEGER,
		ldSpans		        INTEGER,
		ldStartLBA              DisplayString,
		ldPDriveID	        DisplayString,
		ldOperation	        INTEGER,
		ldOpProgress	        INTEGER

	}

ldIndex                        OBJECT-TYPE
    SYNTAX                      INTEGER
    ACCESS                      read-only
    STATUS                      mandatory
    DESCRIPTION                 "Index of LD Information entry."
    ::= { ldEntry 1 }

ldID                        OBJECT-TYPE
    SYNTAX                      INTEGER
    ACCESS                      read-only
    STATUS                      mandatory
    DESCRIPTION                 "Logical drive ID."
    ::= { ldEntry 2 }

ldName	                OBJECT-TYPE
    SYNTAX                      DisplayString (SIZE(0..63)) 
    ACCESS                      read-only
    STATUS                      mandatory
    DESCRIPTION                 "LD Name"
    ::= { ldEntry 3 }

ldMode		                OBJECT-TYPE
    SYNTAX                      DisplayString (SIZE(0..63))
    ACCESS                      read-only
    STATUS                      mandatory
    DESCRIPTION                 "LD mode."
    ::= { ldEntry 4 }

ldStatus                       OBJECT-TYPE
    SYNTAX                     INTEGER{
				               online(1),
				               critical(2),
				               degraded(3),
				               offLine(4),
			    	           deleted(5),
			        	       notPresent(255)
			            	   }
    ACCESS                      read-only
    STATUS                      mandatory
    DESCRIPTION                 "LD status."
    ::= { ldEntry 5 }

ldStripeSize                   OBJECT-TYPE
    SYNTAX                      DisplayString (SIZE(0..63))
    ACCESS                      read-only
    STATUS                      mandatory
    DESCRIPTION                 "LD Stripe size."
    ::= { ldEntry 6 }

ldCapacity                     OBJECT-TYPE
    SYNTAX                      DisplayString (SIZE(0..63)) 
    ACCESS                      read-only
    STATUS                      mandatory
    DESCRIPTION                 "LD size."
    ::= { ldEntry 7 }

ldDriveLetters                OBJECT-TYPE
    SYNTAX                      DisplayString (SIZE(0..63))
    ACCESS                      read-only
    STATUS                      mandatory
    DESCRIPTION                 "Drive letters for particular LD."
    ::= { ldEntry 8 }

ldNumStripes			OBJECT-TYPE
    SYNTAX                      INTEGER (0..3)
    ACCESS                      read-only
    STATUS                      mandatory
    DESCRIPTION                 "No of stripes for this logical drive"
    ::= { ldEntry 9 }

ldSpans   			OBJECT-TYPE
    SYNTAX                      INTEGER (1..2)
    ACCESS                      read-only
    STATUS                      mandatory
    DESCRIPTION                 "No of span(s) for this logical drive"
    ::= { ldEntry 10 }

ldStartLBA                      OBJECT-TYPE
    SYNTAX                      DisplayString (SIZE(0..63))
    ACCESS                      read-only
    STATUS                      mandatory
    DESCRIPTION                 "Start LBA of this LD"
    ::= { ldEntry 11 }

ldPDriveID                      OBJECT-TYPE
    SYNTAX                      DisplayString (SIZE(0..63))
    ACCESS                      read-only
    STATUS                      mandatory
    DESCRIPTION                 "Physical drive ID(s) which are part of this LD"
    ::= { ldEntry 12 }

ldOperation   			OBJECT-TYPE
    SYNTAX                      INTEGER  {
                                noOperation(1),
                                consistencyCheck(2),
                                initialization(3)
                                }
    ACCESS                      read-only
    STATUS                      mandatory
    DESCRIPTION                 "Operation performing on this logical drive."
    ::= { ldEntry 13 }

ldOpProgress   			OBJECT-TYPE
    SYNTAX                      INTEGER (0..100)
    ACCESS                      read-only
    STATUS                      mandatory
    DESCRIPTION                 "Progress percentage for the operation."
    ::= { ldEntry 14 }


--------------------------------------------------------------------------------
--
-- Physical Drives Information group.
--
-- This table contains information about the Physical drives attached in MegaRAID controller.
-- --------------------------------------------------------------------------------

PdrEntry ::=
    SEQUENCE { 
		pdrIndex			INTEGER,
		pdrDriveId			INTEGER,
		pdrConnection		DisplayString,
		pdrModel			DisplayString,
		pdrStatus			INTEGER,
		pdrErrorCount		INTEGER,  
		pdrCapacity			DisplayString,
		pdrTransferMode		INTEGER,
		pdrSerialNumber		DisplayString,
		pdrContID			INTEGER,
		pdrFirmware			DisplayString,
		pdOpProgress        INTEGER,
		pdWriteCache        INTEGER,
		pdReadAhead         INTEGER,
		pdrSmartStatus      INTEGER
	}


pdrNumber                       OBJECT-TYPE
    SYNTAX                      Gauge
    ACCESS                      read-only
    STATUS                      mandatory
    DESCRIPTION                 "The present number of rows in the Physical Drive table."
    ::= { idePhysicalDrives 1 }



pdrTable                        OBJECT-TYPE
    SYNTAX                      SEQUENCE OF PdrEntry
    ACCESS                      not-accessible
    STATUS                      mandatory
    DESCRIPTION                 "Each row describes a Physical Drive Information."
    ::= { idePhysicalDrives 2 }

pdrEntry                        OBJECT-TYPE
    SYNTAX                      PdrEntry
    ACCESS                      not-accessible
    STATUS                      mandatory
    INDEX                       { pdrIndex }
    ::= { pdrTable 1 }

pdrIndex                        OBJECT-TYPE
    SYNTAX                      INTEGER
    ACCESS                      read-only
    STATUS                      mandatory
    DESCRIPTION                 "Index of Drives Information entry."
    ::= { pdrEntry 1 }

pdrDriveId						OBJECT-TYPE
    SYNTAX                      INTEGER 
    ACCESS                      read-only
    STATUS                      mandatory
    DESCRIPTION                 "Drive Id."
    ::= { pdrEntry 2 }

pdrConnection		 	        OBJECT-TYPE
    SYNTAX                      DisplayString (SIZE(0..63))
    ACCESS                      read-only
    STATUS                      mandatory
    DESCRIPTION                 "Physical Drive connection."
    ::= { pdrEntry 3 }                    

pdrModel		        OBJECT-TYPE
    SYNTAX                      DisplayString (SIZE(0..63))
    ACCESS                      read-only
    STATUS                      mandatory
    DESCRIPTION                 "Physical drive model."
    ::= { pdrEntry 4 }

pdrStatus                       OBJECT-TYPE
    SYNTAX                      INTEGER{
			               		online(16),
				               critical(1),
				               failed(2),
				               hotSpare(13),
			    	           rebuilding(14),
			        	       offLine(15),
			            	   undefined(255)
								}
    ACCESS                      read-only
    STATUS                      mandatory
    DESCRIPTION                 "Drive status."
    ::= { pdrEntry 5 }

pdrErrorCount                   OBJECT-TYPE
    SYNTAX                      INTEGER
    ACCESS                      read-only
    STATUS                      mandatory
    DESCRIPTION                 "Media errors count in drive."
    ::= { pdrEntry 6 }
    
                                                                  
pdrCapacity                     OBJECT-TYPE
    SYNTAX                      DisplayString (SIZE(0..63)) 
    ACCESS                      read-only
    STATUS                      mandatory
    DESCRIPTION                 "Physical drive size."
    ::= { pdrEntry 7 }

pdrTransferMode			OBJECT-TYPE
    SYNTAX                      INTEGER  {
                                         pioMode0(99),
                                         pioMode1(1),
                                         pioMode2(2),
                                         pioMode3(3),
                                         pioMode4(4),
                                         dmaMode0(5),
                                         dmaMode1(6),
                                         dmaMode2(7),
                                         udmaMode0(8),
                                         udmaMode1(9),
                                         udmaMode2(10),
                                         udmaMode3(11),
                                         udmaMode4(12),
                                         udmaMode5(13),
                                         udmaMode6(14)
                                }
    ACCESS                      read-write
    STATUS                      mandatory
    DESCRIPTION                 "Transfer mode."
    ::= { pdrEntry 8 }

pdrSerialNumber                 OBJECT-TYPE
    SYNTAX                      DisplayString (SIZE(0..63))
    ACCESS                      read-only
    STATUS                      mandatory
    DESCRIPTION                 "Drive's serial number."
    ::= { pdrEntry 9 }

pdrContID	                OBJECT-TYPE
    SYNTAX                      INTEGER
    ACCESS                      read-only
    STATUS                      mandatory
    DESCRIPTION                 "Controller ID where this Device is present."
    ::= { pdrEntry 10 }

pdrFirmware                     OBJECT-TYPE
    SYNTAX                      DisplayString (SIZE(0..63))
    ACCESS                      read-only
    STATUS                      mandatory
    DESCRIPTION                 "Drive's Firmware."
    ::= { pdrEntry 11 }

pdOpProgress   			OBJECT-TYPE
    SYNTAX                      INTEGER (0..100)
    ACCESS                      read-only
    STATUS                      mandatory
    DESCRIPTION                 "Progress percentage , if drive status is rebuilding"
    ::= { pdrEntry 12 }

pdWriteCache                    OBJECT-TYPE
    SYNTAX                      INTEGER {
                                off(2),
                                on(1)
                                }
    ACCESS                      read-write
    STATUS                      mandatory
    DESCRIPTION                 "Write cache option"
    ::= { pdrEntry 13 }

pdReadAhead                    OBJECT-TYPE
    SYNTAX                      INTEGER {
                                off(2),
                                on(1)
                                }
    ACCESS                      read-write
    STATUS                      mandatory
    DESCRIPTION                 "Read Ahead option"
    ::= { pdrEntry 14 }

pdrSmartStatus		        OBJECT-TYPE
    SYNTAX                      INTEGER {
                                no(2),
                                yes(1)
                                }
    ACCESS                      read-only
    STATUS                      mandatory
    DESCRIPTION                 "Is this device S.M.A.R.T. compliant?"
    ::= { pdrEntry 15 }

--------------------------------------------------------------------------------
--
-- Following are the Objects defined for Traps
--------------------------------------------------------------------------------
rtContID                        OBJECT-TYPE
     SYNTAX                     INTEGER
     ACCESS                     read-only
     STATUS                     optional
     DESCRIPTION                "Controller ID for which Trap is generated."
::= { ideTrapInfo 1 }

rtLDriveID                      OBJECT-TYPE
     SYNTAX                     INTEGER
     ACCESS                     read-only
     STATUS                     optional
     DESCRIPTION                "Logical Drive Number for which Trap is generated."
::= { ideTrapInfo 2 }

rtPDrvID                         OBJECT-TYPE
     SYNTAX                     INTEGER
     ACCESS                     read-only
     STATUS                     optional
     DESCRIPTION                "Device ID of the Physical Drive for which Trap is Generated."
::= { ideTrapInfo 3 }

rtPDriveStatus                  OBJECT-TYPE
     SYNTAX                     INTEGER{
			        		       online(99),
					               critical(1),
					               failed(2),
			    		           hotSpare(13),
			            		   rebuilding(14),
			                		offLine(15),
			  			           undefined(255)
			            		   }
     ACCESS                     not-accessible
     STATUS                     mandatory
     DESCRIPTION                "Physical drive status."
::= { ideTrapInfo 4 }


rtLDriveStatus                  OBJECT-TYPE
     SYNTAX                     INTEGER{
			               		online(99),
			               		critical(1),
			               		degraded(2),
			               		offLine(3),
			               		deleted(4),
			               		notPresent(255)
			               		}
     ACCESS                     not-accessible
     STATUS                     mandatory
     DESCRIPTION                "Logical drive status."
::= { ideTrapInfo 5 }

rtLDrvOPStatus                  OBJECT-TYPE
     SYNTAX                     INTEGER{
				               noOperation(99),
				               succeed(1),
				               aborted(2)
				               }
     ACCESS                     not-accessible
     STATUS                     mandatory
     DESCRIPTION                "Last operation status for Logical drive."
::= { ideTrapInfo 6 }


rtDriveErrorType                OBJECT-TYPE
     SYNTAX                     INTEGER{
			    	           unknown(255),
			        	   read(1),
				       	   write(2),
	               	        	   verify(3),
				           drive(4)
				               }
     ACCESS                     not-accessible
     STATUS                     mandatory
     DESCRIPTION                "Physical drive error types."
::= { ideTrapInfo 7 }

--------------------------------------------------------------------------------
--
-- MegaRAID IDE Trap Information group.
--
-- This subtree contains information about the MegaRAID IDE traps.
--
--------------------------------------------------------------------------------

trRebuildStarted_megaIDE TRAP-TYPE
ENTERPRISE  ide
VARIABLES
    {
    rtPDrvID
    }
DESCRIPTION "Rebuild on physical drive %d was started"
--#TYPE         "Rebuild started"
--#SUMMARY      "Rebuild on physical drive %d was started"
--#ARGUMENTS    { 0 }
--#SEVERITY     INFORMATIONAL
--#STATE        OPERATIONAL
::= 200

trRebuildStopped_megaIDE TRAP-TYPE
ENTERPRISE  ide
VARIABLES
    {
    rtPDrvID,
    rtLDrvOPStatus
    }
DESCRIPTION "Rebuild of physical drive %d finished"
--#TYPE         "Rebuild finished"
--#SUMMARY      "Rebuild of physical drive %d finished with result %d"
--#ARGUMENTS    { 0,1 }
--#SEVERITY     INFORMATIONAL
--#STATE        OPERATIONAL
::= 201

trConsistencyStarted_megaIDE TRAP-TYPE
ENTERPRISE  ide
VARIABLES
    {
    rtLDriveID
    }
DESCRIPTION "Consistency check on Logical drive %d was started"
--#TYPE         "RAID Trap: Consistency check started"
--#SUMMARY      "Consistency check on Logical drive %d was started"
--#ARGUMENTS    { 0 }
--#SEVERITY     INFORMATIONAL
--#STATE        OPERATIONAL
::= 202

trConsistencyStopped_megaIDE TRAP-TYPE
ENTERPRISE  ide
VARIABLES
    {
    rtLDriveID,
    rtLDrvOPStatus
    }
DESCRIPTION "Consistency check on Logical drive %d finished"
--#TYPE         "Consistency check finished"
--#SUMMARY      "Consistency check on Logical drive %d finished with result %d"
--#ARGUMENTS    { 0,1 }
--#SEVERITY     INFORMATIONAL
--#STATE        OPERATIONAL
::= 203


trPDriveStatusChanged_megaIDE TRAP-TYPE
ENTERPRISE  ide
VARIABLES
    {
    rtPDrvID,
    rtPDriveStatus
    }
DESCRIPTION "Physical drive(%d) Status has changed to %d"
--#TYPE         "Status of the drive has been changed "
--#SUMMARY      "Physical drive(%d) Status has changed to %d"
--#ARGUMENTS    { 0,1 }
--#SEVERITY     INFORMATIONAL
--#STATE        OPERATIONAL
::= 204

trLDriveStatusChanged_megaIDE TRAP-TYPE
ENTERPRISE  ide
VARIABLES
    {
    rtLDriveID,
    rtLDriveStatus
    }
DESCRIPTION "Logical drive(%d) Status has changed to %d"
--#TYPE         "Status of the logical drive has been changed "
--#SUMMARY      "Logical drive(%d) Status has changed to %d"
--#ARGUMENTS    { 0,1}
--#SEVERITY     INFORMATIONAL
--#TIMEINDEX    3
--#STATE        OPERATIONAL
::= 205

trDriveNewError_megaIDE TRAP-TYPE
ENTERPRISE  ide
VARIABLES
    {
    rtPDrvID,
    rtDriveErrorType
    }
DESCRIPTION "Error (%d) has been found on physical drive %d"
--#TYPE         "New error "
--#SUMMARY      "Error (%d) has been found on physical drive %d"
--#ARGUMENTS    { 1,0 }
--#SEVERITY     MINOR
--#STATE        OPERATIONAL
::= 206

trDriveSMARTError_megaIDE TRAP-TYPE
ENTERPRISE  ide
VARIABLES
    {
    rtPDrvID
    }
DESCRIPTION "A New S.M.A.R.T. Error found on physical drive %d"
--#TYPE         "New S.M.A.R.T. error."
--#SUMMARY      "A New S.M.A.R.T. Error found on physical drive %d"
--#ARGUMENTS    { 0 }
--#SEVERITY     MINOR
--#STATE        OPERATIONAL
::= 207

END
