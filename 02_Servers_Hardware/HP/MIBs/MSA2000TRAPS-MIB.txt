-- ----------------------------------------------------------------------------
-- MSA2000 Array MIB for SNMP Traps
--
-- $Revision: 1.4 $
--
-- Copyright (c) 2008 Hewlett-Packard Development Company, L.P.
-- Copyright (c) 2005-2008 Dot Hill Systems Corp.
-- Confidential computer software. Valid license from HP required for possession,
-- use or copying. Consistent with FAR 12.211 and 12.212, Commercial Computer
-- Software, Computer Software Documentation, and Technical Data for Commercial
-- Items are licensed to the U.S. Government under vendor's standard commercial
-- license.
--
--   MSA2000traps MIB Revision
--  ==========================
-- Revision 1.1  2008/02/27
-- Initial revision
-- Revision 1.2  2008/03/18
     -- Updated copyright notice
-- Revision 1.3  2008/06/26
     -- Replaced filename 'fa-mib40' with module name 'FCMGMT-MIB'.
     -- Added OIDs hp, nm and hpMSA
     -- Added Object type mibName
     -- Above changes made to work for HP StorageWorks Management
     -- Pack for SCOM 2007.
--
-- ----------------------------------------------------------------------------

MSA2000TRAPS-MIB
-- Last edit date: Feb 27th, 2008
DEFINITIONS ::= BEGIN
  IMPORTS
    enterprises, OBJECT-TYPE
        FROM RFC1155-SMI
    TRAP-TYPE
        FROM RFC-1215
    connUnitEventId, connUnitEventType, connUnitEventDescr
        FROM FCMGMT-MIB;


    --Textual conventions for this MIB

----------------------------------------------------------------------
    -- vendor
    hp      OBJECT IDENTIFIER ::= { enterprises 11 }
    nm      OBJECT IDENTIFIER ::= { hp 2 }
    hpMSA   OBJECT IDENTIFIER ::= { nm 51 }

    mibName OBJECT-TYPE
        SYNTAX INTEGER
        ACCESS read-only
        STATUS mandatory
        DESCRIPTION
  	    "Product name"
        ::= { hpMSA 1 }

    -- Related traps

    msaEventInfoTrap TRAP-TYPE
        ENTERPRISE hpMSA
        VARIABLES { connUnitEventId,
                    connUnitEventType,
                    connUnitEventDescr }
        DESCRIPTION
            "An event has been generated by the storage array.
            Recommended severity level (for filtering): info"

        -- Trap annotations are as follows:
        --#TYPE "Informational storage event"
        --#SUMMARY "Informational storage event # %d, type %d, description: %s"
        --#ARGUMENTS {0,1,2}
        --#SEVERITY INFORMATIONAL
        --#TIMEINDEX 6
        ::= 3001

    msaEventWarningTrap TRAP-TYPE
        ENTERPRISE hpMSA
        VARIABLES { connUnitEventId,
                    connUnitEventType,
                    connUnitEventDescr }
        DESCRIPTION
            "An event has been generated by the storage array.
            Recommended severity level (for filtering): warning"

        -- Trap annotations are as follows:
        --#TYPE "Warning storage event"
        --#SUMMARY "Warning storage event # %d, type %d, description: %s"
        --#ARGUMENTS {0,1,2}
        --#SEVERITY MINOR
        --#TIMEINDEX 6
        ::= 3002

    msaEventErrorTrap TRAP-TYPE
        ENTERPRISE hpMSA
        VARIABLES { connUnitEventId,
                    connUnitEventType,
                    connUnitEventDescr }
        DESCRIPTION
            "An event has been generated by the storage array.
            Recommended severity level (for filtering): error"

        -- Trap annotations are as follows:
        --#TYPE "Error storage event"
        --#SUMMARY "Error storage event # %d, type %d, description: %s"
        --#ARGUMENTS {0,1,2}
        --#SEVERITY MAJOR
        --#TIMEINDEX 6
        ::= 3003

    msaEventCriticalTrap TRAP-TYPE
        ENTERPRISE hpMSA
        VARIABLES { connUnitEventId,
                    connUnitEventType,
                    connUnitEventDescr }
        DESCRIPTION
            "An event has been generated by the storage array.
            Recommended severity level (for filtering): critical"

        -- Trap annotations are as follows:
        --#TYPE "Critical storage event"
        --#SUMMARY "Critical storage event # %d, type %d, description: %s"
        --#ARGUMENTS {0,1,2}
        --#SEVERITY CRITICAL
        --#TIMEINDEX 6
        ::= 3004


END
