--**MOD+***********************************************************************
--* Module:    hpicfDevConf.mib
--*
--* Copyright (C) 2015 Hewlett Packard Enterprise Development LP
--* All Rights Reserved.
--* 
--* The contents of this software are proprietary and confidential
--* to the Hewlett Packard Enterprise Development LP.  No part of this
--* program may be photocopied, reproduced, or translated into another
--* programming language without prior written consent of the
--* Hewlett Packard Enterprise Development LP.
--*
--* Purpose: This file contains MIB definition of HP-ICF-DEV-CONF-MIB
--*
--**MOD-***********************************************************************

HP-ICF-DEV-CONF-MIB DEFINITIONS ::= BEGIN
 
    IMPORTS
        hpSwitch
            FROM HP-ICF-OID
	VidList
             FROM HP-ICF-TC
        OBJECT-GROUP, MODULE-COMPLIANCE
            FROM SNMPv2-CONF
        Unsigned32, OBJECT-TYPE, MODULE-IDENTITY
            FROM SNMPv2-SMI
        MacAddress, RowStatus, TEXTUAL-CONVENTION
            FROM SNMPv2-TC
        InterfaceIndex
            FROM IF-MIB;

    hpicfDevConf MODULE-IDENTITY
       LAST-UPDATED "201509080000Z" -- September 8, 2015
       ORGANIZATION "HP Networking"
       CONTACT-INFO
            "Hewlett Packard Enterprise Development LP.
             8000 Foothills Blvd.
             Roseville, CA 95747"
        DESCRIPTION
            "This MIB module contains HP proprietary objects for 
             managing the auto-configuration feature."

        REVISION "201509080000Z"  -- September 8, 2015
        DESCRIPTION
            "Initial version."             
        ::= { hpSwitch 126 }

-- ----------------------------------------------------------------------
-- Starting node of auto-configuration feature is "hpicfDevConf".
-- hpicfDevConf is added to 125th position of "hpSwitch".
-- OID of "hpicfDevConf"
-- 1.3.6.1.4.1.11.2.14.11.5.1.126 --
-- ----------------------------------------------------------------------
-- Node definitions.
-- ----------------------------------------------------------------------
-- Node zero of hpicfDevConf is reserved for notifications.
-- Node one of hpicfDevConf is reserved for scalars.
-- Node two of hpicfDevConf is reserved for globals.
-- Node three of hpicfDevConf is for conformance.
-- Node four of hpicfDevConf is for device configuration.
-- ----------------------------------------------------------------------
    hpSwitchDevNotifications OBJECT IDENTIFIER  ::= { hpicfDevConf 0 } 
    hpSwitchDevScalar OBJECT IDENTIFIER 	::= { hpicfDevConf 1 } 
    hpSwitchDevGlobals OBJECT IDENTIFIER 	::= { hpicfDevConf 2 } 
    hpSwitchDevConformance OBJECT IDENTIFIER 	::= { hpicfDevConf 3 }
    hpSwitchDevConfig OBJECT IDENTIFIER 	::= { hpicfDevConf 4 }

--------------------------------------------------------------------------
-- Textual Conventions
--------------------------------------------------------------------------
    HpPartnerDeviceType  ::=  TEXTUAL-CONVENTION
        STATUS           current
        DESCRIPTION 	 "This textual convention is an enum that contains the
			  types of devices supported by the auto-configuration
			  and QoS port trust mode features."
        SYNTAX  INTEGER  {
                         none(1),
                         arubaAccessPoint(2),
                         arubaBridgeRouter (3),
                         hpBridgeRouter (4),
                         ciscoBridgeRouter (5),
                         ciscoPhone (6)                    
                   	 }

-- ---------------------------------------------------------------------
-- "hpSwitchDevConfig" is the 4th node of "hpicfDevConf"
--  and has 5 child nodes.
-- 1 for Profiles.
-- 2 for Association.
-- 3 for Rogue-AP.
-- 4 for whitelist MAC
-- 5 for displaying device connected to each port and
--   the profile associated with it.
-- ---------------------------------------------------------------------

-- ---------------------------------------------------------------------
-- 1st member of hpSwitchDevConfig.
-- This is for storing Device Profiles 
-- ---------------------------------------------------------------------
   hpSwitchDevProfTable OBJECT-TYPE
        SYNTAX      	SEQUENCE OF HpSwitchDevProfEntry
        MAX-ACCESS  	not-accessible
        STATUS      	current
        DESCRIPTION 	"The device profile configuration table."
        ::= { hpSwitchDevConfig 1 }

   hpSwitchDevProfEntry OBJECT-TYPE
        SYNTAX         	HpSwitchDevProfEntry
        MAX-ACCESS      not-accessible
        STATUS      	current
        DESCRIPTION 	"The device profile configuration entry."
        INDEX { hpSwitchProfIndex }
        ::= { hpSwitchDevProfTable 1 }

   HpSwitchDevProfEntry ::=
        SEQUENCE {
           		hpSwitchProfIndex                Unsigned32,
			hpSwitchProfRowStatus	   	 RowStatus,
            		hpSwitchProfName                 OCTET STRING,
           		hpSwitchProfUntaggedVlanID       Unsigned32,
			hpSwitchProfTaggedVlanList	 VidList,
			hpSwitchProfIngressBandwidth     Unsigned32,
			hpSwitchProfEgressBandwidth      Unsigned32,
			hpSwitchProfCosPriority          Unsigned32,
			hpSwitchProfPortSpeed            INTEGER,
			hpSwitchProfPoeMaxPower          Unsigned32,
			hpSwitchProfPoePriority	    	 INTEGER
                 }

   hpSwitchProfIndex OBJECT-TYPE
        SYNTAX     	 Unsigned32 (1..2147483647)
        MAX-ACCESS 	 not-accessible
        STATUS     	 current
        DESCRIPTION	 "The index value which uniquely identifies a row
                   	  in the profile table."
        ::= { hpSwitchDevProfEntry 1 }

    hpSwitchProfRowStatus OBJECT-TYPE
      SYNTAX      	RowStatus
      MAX-ACCESS 	read-create
      STATUS      	current
      DESCRIPTION	"The row status of this device profile entry. Allows 
                         creation/deletion of the device profile entry. Row cannot
                         be deleted if the device profile is associated with a 
                         device."
      ::= { hpSwitchDevProfEntry 2 }	

   hpSwitchProfName OBJECT-TYPE
        SYNTAX     	 OCTET STRING ( SIZE (1..32))
        MAX-ACCESS     	 read-create
        STATUS     	 current
        DESCRIPTION 	 "The name of the device profile. The maximum length 
			  supported is 32 characters."
        ::= { hpSwitchDevProfEntry 3 }

   hpSwitchProfUntaggedVlanID OBJECT-TYPE
        SYNTAX   	 Unsigned32 (0..4094)
        MAX-ACCESS    	 read-create
        STATUS     	 current
        DESCRIPTION 	 "The untagged VLAN ID associated with this profile."
        ::= { hpSwitchDevProfEntry 4 }

   hpSwitchProfTaggedVlanList OBJECT-TYPE
        SYNTAX          VidList
        MAX-ACCESS      read-create
        STATUS          current
        DESCRIPTION     "The set of tagged VLANs associated with this profile."
        ::= { hpSwitchDevProfEntry 5 }
  
 hpSwitchProfIngressBandwidth OBJECT-TYPE
        SYNTAX      	Unsigned32 (0..100)
        MAX-ACCESS      read-create
        STATUS     	current
        DESCRIPTION 	"The bandwidth percentage of ingress traffic allowed on
			 the port associated with this profile."
        ::= { hpSwitchDevProfEntry 6 }

 hpSwitchProfEgressBandwidth OBJECT-TYPE
        SYNTAX      	Unsigned32 (0..100)
        MAX-ACCESS      read-create
        STATUS     	current
        DESCRIPTION 	"The bandwidth percentage of egress traffic allowed on
			 the port associated with this profile."
        ::= { hpSwitchDevProfEntry 7 }
		
   hpSwitchProfCosPriority OBJECT-TYPE
        SYNTAX     	 Unsigned32 (0..255)
        MAX-ACCESS     	 read-create
        STATUS           current
        DESCRIPTION 	 "The Class of Service (CoS) priority for traffic entering
                          the port associated with this profile."
        ::= { hpSwitchDevProfEntry 8 }		
			
   hpSwitchProfPortSpeed OBJECT-TYPE
        SYNTAX      INTEGER {
		                halfDuplex10Mbits(1),
		                halfDuplex100Mbits(2),
		                fullDuplex10Mbits(3),
		                fullDuplex100Mbits(4),
		                autoNeg(5),
		                fullDuplex1000Mbits(6),
		                auto10Mbits(7),
		                auto100Mbits(8),
		                auto1000Mbits(9),
		                auto10Gbits(10),
		                auto10or100Mbits(11),
		                auto40Gbits(12),
		                auto2500Mbits(13),
		                auto5000Mbits(14),
		                auto2500or5000Mbits(15),
				auto1000or2500Mbits(16),
				auto1000or2500or5000Mbits(17)
			    }
        MAX-ACCESS      read-create
        STATUS     	current
        DESCRIPTION 	"The port speed configuration associated with this profile."
	::= { hpSwitchDevProfEntry 9 }	
		
    hpSwitchProfPoeMaxPower OBJECT-TYPE
        SYNTAX     	 Unsigned32
        MAX-ACCESS 	 read-create
        STATUS     	 current
        DESCRIPTION	 "The maximum power allocation measured in watts (W) for 
			  the port associated with this profile. This value must be
			  less than or equal to 33W."
        ::= { hpSwitchDevProfEntry 10 }
	
    hpSwitchProfPoePriority OBJECT-TYPE
        SYNTAX      INTEGER {
                        	critical(1),
                        	high(2),
				low(3)
                   	     }
        MAX-ACCESS      read-create
        STATUS      	current
        DESCRIPTION     "The PoE priority defined for the port associated with this
			 profile."
        ::= { hpSwitchDevProfEntry 11 } 	

----------------------------------------------------------------------
-- 2 nd member of hpSwitchDevConfig MIB.
-- This is for storing details of device associations
-- Profile attached to device, status (enable/disable) etc.
----------------------------------------------------------------------

  hpSwitchDevAssociationTable OBJECT-TYPE
        SYNTAX     	SEQUENCE OF HpSwitchDevAssociationEntry
        MAX-ACCESS  	not-accessible
        STATUS      	current
        DESCRIPTION 	"The device association configuration table."
        ::= { hpSwitchDevConfig 2 }

   hpSwitchDevAssociationEntry OBJECT-TYPE
        SYNTAX     	HpSwitchDevAssociationEntry
        MAX-ACCESS  	not-accessible
        STATUS      	current
        DESCRIPTION 	"The device association configuration entry."
          INDEX { hpSwitchDevAssociationType }
        ::= { hpSwitchDevAssociationTable 1 }

   HpSwitchDevAssociationEntry ::=
        SEQUENCE {
		    hpSwitchDevAssociationType        	HpPartnerDeviceType,
		    hpSwitchDevAssociationProfName	OCTET STRING,
		    hpSwitchDevAssociationProfID   	Unsigned32,
            	    hpSwitchDevAssociationStatus        INTEGER
	          }
		
   hpSwitchDevAssociationType OBJECT-TYPE
        SYNTAX     	HpPartnerDeviceType
        MAX-ACCESS  	not-accessible
        STATUS     	current
        DESCRIPTION 	"The type of the auto-configurable device."
        ::= { hpSwitchDevAssociationEntry 1 }
	
   hpSwitchDevAssociationProfName OBJECT-TYPE
        SYNTAX      	OCTET STRING ( SIZE (1..32))
        MAX-ACCESS  	read-create
        STATUS      	current
        DESCRIPTION 	"The name of the profile associated with this device."
        ::= { hpSwitchDevAssociationEntry 2 }		
		
   hpSwitchDevAssociationProfID OBJECT-TYPE
        SYNTAX      	Unsigned32 (1..2147483647)
        MAX-ACCESS  	read-create
        STATUS      	current
        DESCRIPTION     "The ID of the profile associated with this device."
        ::= { hpSwitchDevAssociationEntry 3 }	
		
    hpSwitchDevAssociationStatus OBJECT-TYPE
        SYNTAX      	INTEGER {
                      		enable(1),
                       		disable(2)
                                }
        MAX-ACCESS     	read-create
        STATUS      	current
        DESCRIPTION 	"The auto-configuration feature status for this device-type.
			 By default, the status is disabled. If enabled, the profile 
			 configuration is applied." 
        ::= { hpSwitchDevAssociationEntry 4 }	

	
-- ------------------------------------------------------------
-- 3 rd member of hpSwitchDevConfig MIB.
-- This is for Rogue MAX-ACCESS Points configurations
-- ------------------------------------------------------------	
hpSwitchRogueDevice OBJECT IDENTIFIER ::= { hpSwitchDevConfig 3 }

    hpSwitchRogueDevStatus OBJECT-TYPE
        SYNTAX     	 INTEGER {
                     		   enable(1),
                      	  	   disable(2)
                    		 }
        MAX-ACCESS      read-write
        STATUS      	current
        DESCRIPTION 	"The rogue AP Isolation feature status."
        ::= { hpSwitchRogueDevice 1 }

    hpSwitchRogueDevAction OBJECT-TYPE
        SYNTAX     	 INTEGER {
                     		   block(1),
                      	  	   log(2)
                    		 }
        MAX-ACCESS      read-write
        STATUS      	current
        DESCRIPTION 	"Action to be performed when a rogue AP device is detected."
        ::= { hpSwitchRogueDevice 2 }

   hpSwitchRogueDevMacTable OBJECT-TYPE
        SYNTAX     	SEQUENCE OF HpSwitchRogueDevMacEntry
        MAX-ACCESS  	not-accessible
        STATUS      	current
        DESCRIPTION 	"The MAC entry table for any rogue AP device."
        ::= { hpSwitchRogueDevice 3 }

   hpSwitchRogueDevMacEntry OBJECT-TYPE
        SYNTAX     	HpSwitchRogueDevMacEntry
        MAX-ACCESS  	not-accessible
        STATUS      	current
        DESCRIPTION 	"The MAC entry for the rogue AP device."
          INDEX { hpSwitchRogueDevMacAddress }
        ::= { hpSwitchRogueDevMacTable 1 }

   HpSwitchRogueDevMacEntry ::=
        SEQUENCE {
		    hpSwitchRogueDevMacAddress	   	 MacAddress,
		    hpSwitchNeighborDevMacAddress	 MacAddress
                 }

   hpSwitchRogueDevMacAddress OBJECT-TYPE
        SYNTAX      	MacAddress
        MAX-ACCESS  	not-accessible
        STATUS     	current
        DESCRIPTION 	"The MAC address of rogue AP device."
        ::= { hpSwitchRogueDevMacEntry 1 }

   hpSwitchNeighborDevMacAddress OBJECT-TYPE
        SYNTAX      	MacAddress
        MAX-ACCESS  	read-only
        STATUS      	current
        DESCRIPTION  	"The MAC address of the access point that detected the rogue 
			 AP device."
        ::= { hpSwitchRogueDevMacEntry 2 }

-- ------------------------------------------------------------
-- 4 th member of hpSwitchDevConfig MIB.
-- This is for Rogue access points whitelist configurations
-- ------------------------------------------------------------
   hpSwitchWhitelistMacTable OBJECT-TYPE
        SYNTAX     	SEQUENCE OF HpSwitchWhitelistMacEntry
        MAX-ACCESS  	not-accessible
        STATUS      	current
        DESCRIPTION 	"The rogue AP device whitelist table. MAC addresses added
		         to this table are not considered to be rogue devices."
        ::= { hpSwitchDevConfig 4 }

   hpSwitchWhitelistMacEntry OBJECT-TYPE
        SYNTAX     	HpSwitchWhitelistMacEntry
        MAX-ACCESS  	not-accessible
        STATUS      	current
        DESCRIPTION 	"The whitelist table entry."
          INDEX { hpSwitchWhitelistMacAddress }
        ::= { hpSwitchWhitelistMacTable 1 }

   HpSwitchWhitelistMacEntry ::=
        SEQUENCE {
		    hpSwitchWhitelistMacAddress	    MacAddress,
		    hpSwitchWhitelistRowStatus	    RowStatus
                 }

   hpSwitchWhitelistMacAddress OBJECT-TYPE
        SYNTAX          MacAddress
        MAX-ACCESS      not-accessible
        STATUS          current
        DESCRIPTION     "The MAC address of whitelisted AP device."
        ::= { hpSwitchWhitelistMacEntry 1 }

   hpSwitchWhitelistRowStatus OBJECT-TYPE
      SYNTAX      	RowStatus
      MAX-ACCESS  	read-create
      STATUS      	current
      DESCRIPTION 	"The row status of rogue AP whitelist table."
      ::= { hpSwitchWhitelistMacEntry 2 }


-- ----------------------------------------------------------------------------
-- 5 th member of hpSwitchDevConfig MIB.	
--   This node is for displaying devices connected to each port and
--   the profiles associated with them.
-------------------------------------------------------------------------------
   hpSwitchDevPortTable OBJECT-TYPE
        SYNTAX     	SEQUENCE OF HpSwitchDevPortEntry
        MAX-ACCESS  	not-accessible
        STATUS      	current
        DESCRIPTION 	"The table shows per-port connected devices and any 
			 profiles associated with them."
        ::= { hpSwitchDevConfig 5 }

   hpSwitchDevPortEntry OBJECT-TYPE
        SYNTAX     	HpSwitchDevPortEntry
        MAX-ACCESS  	not-accessible
        STATUS      	current
        DESCRIPTION 	"The table entry showing the device connected to this
			 port and any profile associated with it."
          INDEX { hpSwitchDevPortIndex }
        ::= { hpSwitchDevPortTable 1 }

   HpSwitchDevPortEntry ::=
        SEQUENCE {
		    hpSwitchDevPortIndex          InterfaceIndex,
		    hpSwitchDevPortType		  HpPartnerDeviceType,	
		    hpSwitchDevPortProfName	  OCTET STRING
                 }

    hpSwitchDevPortIndex OBJECT-TYPE	
        SYNTAX      	InterfaceIndex
        MAX-ACCESS  	not-accessible
        STATUS      	current
        DESCRIPTION 	"Index of the interface on this switch."
        ::= { hpSwitchDevPortEntry 1 }

   hpSwitchDevPortType OBJECT-TYPE
        SYNTAX     	HpPartnerDeviceType
        MAX-ACCESS  	read-only
        STATUS     	current
        DESCRIPTION 	"The type of partner device connected to this port."
        ::= { hpSwitchDevPortEntry 2 }

    hpSwitchDevPortProfName OBJECT-TYPE
        SYNTAX      	OCTET STRING ( SIZE (1..255))
        MAX-ACCESS  	read-only
        STATUS      	current
        DESCRIPTION 	"The name of the profile associated with the partner 
			 device connected to this port."
        ::= { hpSwitchDevPortEntry 3 }


-------------------------------------------------------------------------------
-- "hpSwitchDevConformance" is the 3rd node of "hpicfDevConf"
--  and has two child nodes.
-- 1 for Compliance Statements
-- 2 for Group Declarations
-------------------------------------------------------------------------------
--  Compliance Statements
-------------------------------------------------------------------------------
    hpSwitchDevCompliances OBJECT IDENTIFIER ::= { hpSwitchDevConformance 1 }

    hpSwitchDevCompliance MODULE-COMPLIANCE
        STATUS		 current
        DESCRIPTION      "The compliance statement for switches that support 
			  device auto-configuration."
        MODULE -- this module
        MANDATORY-GROUPS {
                         hpSwitchDevProfileGroup,
			 hpSwitchDevAssociationGroup,
			 hpSwitchRogueDevGroup,
			 hpSwitchWhitelistGroup,
			 hpSwitchDevPortGroup
                         }
        ::= { hpSwitchDevCompliances 1 }

------------------------------------------------------------------------------
--  Group Declarations
------------------------------------------------------------------------------
    hpSwitchDevConfigGroups OBJECT IDENTIFIER ::= { hpSwitchDevConformance 2 }

    hpSwitchDevProfileGroup OBJECT-GROUP
        OBJECTS 	{
            		hpSwitchProfName,
			hpSwitchProfRowStatus,
           		hpSwitchProfUntaggedVlanID,
			hpSwitchProfTaggedVlanList,
			hpSwitchProfIngressBandwidth,
			hpSwitchProfEgressBandwidth,
			hpSwitchProfCosPriority,
			hpSwitchProfPortSpeed,
			hpSwitchProfPoeMaxPower,
			hpSwitchProfPoePriority
			}
        STATUS 		current
        DESCRIPTION     "A collection of objects containing device profile
			 information."
        ::= { hpSwitchDevConfigGroups 1 }

    hpSwitchDevAssociationGroup OBJECT-GROUP
        OBJECTS 	{
			hpSwitchDevAssociationProfName,
		  	hpSwitchDevAssociationProfID,
            	 	hpSwitchDevAssociationStatus
		 	}
        STATUS 		current
        DESCRIPTION     "A collection of objects containing information about 
			 associated devices."
        ::= { hpSwitchDevConfigGroups 2 }

    hpSwitchRogueDevGroup OBJECT-GROUP
        OBJECTS 	{
		    	hpSwitchRogueDevStatus,
		   	hpSwitchRogueDevAction,
			hpSwitchNeighborDevMacAddress
                	}
        STATUS 		current
        DESCRIPTION     "A collection of objects containing rogue device information."
        ::= { hpSwitchDevConfigGroups 3 }

    hpSwitchWhitelistGroup OBJECT-GROUP
        OBJECTS		 {
			 hpSwitchWhitelistRowStatus
                	 }
        STATUS 		 current
        DESCRIPTION      "A collection of objects containing information about
			  whitelisted devices."
        ::= { hpSwitchDevConfigGroups 4 }

    hpSwitchDevPortGroup OBJECT-GROUP
        OBJECTS		 {
			 hpSwitchDevPortType,
			 hpSwitchDevPortProfName
                	 }
        STATUS 		 current
        DESCRIPTION      "A collection of objects containing per-port device 
			  connections and any profiles associated with them."
        ::= { hpSwitchDevConfigGroups 5 }
 ------------------------------------------------------------------------------	
END
