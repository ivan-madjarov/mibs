---------------------------------------------------------------------------
--
-- Title: Lenovo XClarity Controller SNMP Alert MIB
--
-- Version: 1.0.0
--
-- Release Date: 2016.05.20
--
-- Description: This MIB is used by the XCC to generate traps
--              for Alert conditions detected by the management firmware.
--
-- Copyright (c) 2016 Lenovo Corp.
-- All Rights Reserved.
--
--
-- OID Format Legend:
--   <a> = attribute ID
--   <i> = index ID
--
---------------------------------------------------------------------------
-- Revisions:                   
--  First version, 2016/5/20
--  Add support for the Lenovo part number, 2017/10/13  

---------------------------------------------------------------------------
LENOVO-XCC-ALERT-MIB DEFINITIONS ::= BEGIN

        IMPORTS
            OBJECT-TYPE                          FROM RFC-1212
            enterprises,
            Counter, TimeTicks, IpAddress        FROM RFC1155-SMI
            mib-2,
            DisplayString                        FROM RFC1213-MIB
            supportProcessor                     FROM LENOVO-XCC-MIB;
		
		lenovoXCCAlertMIB MODULE-IDENTITY
			LAST-UPDATED "201608150000Z"
			ORGANIZATION "Lenovo Group Ltd."
			CONTACT-INFO
				"Lenovo
				 Postal: 1009 Think Place
				 Morrisville, NC 27560
				 USA
				 Tel: +1 (919) 968-4465
				 E-mail: snmp@lenovo.com"
			DESCRIPTION
				 "This MIB is used by the XCC to define traps for Alert conditions detected by the management firmware."
			REVISION      "201610271830Z"
			DESCRIPTION
				"Initial version."
		::= { supportProcessor 5 }
	
        -- MIB for XCC Alerts starts here
		
        -- the nfspalt generic trap generator group

        xcctrapg      OBJECT IDENTIFIER ::=   { lenovoXCCAlertMIB 1 }

        altDateTime    OBJECT-TYPE
                       SYNTAX  DisplayString
                       ACCESS  read-only
                       STATUS  mandatory
                       DESCRIPTION
                       "Timestamp of Local Date and Time when alert was generated"
                       ::= { xcctrapg 1 }

        altSpTxtId        OBJECT-TYPE
                       SYNTAX  DisplayString
                       ACCESS  read-only
                       STATUS  mandatory
                       DESCRIPTION
                       "SP System Identification - Text Identification"
                       ::= { xcctrapg 3 }

        altSysUuid     OBJECT-TYPE
                       SYNTAX  DisplayString
                       ACCESS  read-only
                       STATUS  mandatory
                       DESCRIPTION
                       "Host System UUID(Universal Unique ID)"
                       ::= { xcctrapg 5 }
                       
        altSysSern     OBJECT-TYPE
                       SYNTAX  DisplayString
                       ACCESS  read-only
                       STATUS  mandatory
                       DESCRIPTION
                       "Host System Serial Number"
                       ::= { xcctrapg 6 }
        
        altPriority     OBJECT-TYPE
                       SYNTAX  INTEGER (0..65535)
                       ACCESS  read-only
                       STATUS  mandatory
                       DESCRIPTION
                       "Alert Severity Value
                          - Critical Alert(0)
                          - Non-Critical Alert(2)
                          - System Alert(4)
                          - Recovery(8)"
                       ::= { xcctrapg 8 }

        altMsgText     OBJECT-TYPE
                       SYNTAX  DisplayString
                       ACCESS  read-only
                       STATUS  mandatory
                       DESCRIPTION
                       "Alert Message Text"
                       ::= { xcctrapg 9 }

        altMsgID       OBJECT-TYPE
                       SYNTAX  INTEGER
                       ACCESS  read-only
                       STATUS  mandatory
                       DESCRIPTION
                       "Alert Message ID"
                       ::= { xcctrapg 10 }

        altMsgIDPrefix OBJECT-TYPE
                       SYNTAX  DisplayString
                       ACCESS  read-only
                       STATUS  mandatory
                       DESCRIPTION
                       "Alert Message ID"
                       ::= { xcctrapg 11 }	
                       
				   
        altHostContact  OBJECT-TYPE
                       SYNTAX  DisplayString
                       ACCESS  read-only
                       STATUS  mandatory
                       DESCRIPTION
                       "Host Contact"
                       ::= { xcctrapg 12 }

        altHostLocation  OBJECT-TYPE
                       SYNTAX  DisplayString
                       ACCESS  read-only
                       STATUS  mandatory
                       DESCRIPTION
                       "Host Location"
                       ::= { xcctrapg 13 }

        altHostRoomID  OBJECT-TYPE
                       SYNTAX  DisplayString
                       ACCESS  read-only
                       STATUS  mandatory
                       DESCRIPTION
                       "Host Location - Room ID"
                       ::= { xcctrapg 14 }

        altHostRackID  OBJECT-TYPE
                       SYNTAX  DisplayString
                       ACCESS  read-only
                       STATUS  mandatory
                       DESCRIPTION
                       "Host Location - Rack ID"
                       ::= { xcctrapg 15 }

        altHostLowestUpos  OBJECT-TYPE
                       SYNTAX  DisplayString
                       ACCESS  read-only
                       STATUS  mandatory
                       DESCRIPTION
                       "Host Location - Lowest U-position"
                       ::= { xcctrapg 16 }

        altHostBladeBay  OBJECT-TYPE
                       SYNTAX  DisplayString
                       ACCESS  read-only
                       STATUS  mandatory
                       DESCRIPTION
                       "Host Location - BladeBay"
                       ::= { xcctrapg 17 }

        altEventID     OBJECT-TYPE
                       SYNTAX  DisplayString
                       ACCESS  read-only
                       STATUS  mandatory
                       DESCRIPTION
                       "Event Identifier"
                       ::= { xcctrapg 18 }

        altServiceable OBJECT-TYPE
                       SYNTAX  INTEGER {
                       notServiceable(0),
                       serviceableByLenovo(1),
                       serviceableByCustomer(2)
                       }
                       ACCESS  read-only
                       STATUS  mandatory
                       DESCRIPTION
                       "Serviceability information."
                       ::= { xcctrapg 19 }

        altTest        OBJECT-TYPE
                       SYNTAX  INTEGER {
                       false(0),
                       true(1)
                       }
                       ACCESS  read-only
                       STATUS  mandatory
                       DESCRIPTION
                       "This event generated for test purposes."
                       ::= { xcctrapg 20 }

        altFailingFRUs OBJECT-TYPE
                       SYNTAX  DisplayString
                       ACCESS  read-only
                       STATUS  mandatory
                       DESCRIPTION
                       "Ordered list of Failing FRU Numbers, separated by commas."
                       ::= { xcctrapg 21 }

        altHostMTM     OBJECT-TYPE
                       SYNTAX  DisplayString
                       ACCESS  read-only
                       STATUS  mandatory
                       DESCRIPTION
                       "Machine Type and Model for failing host."
                       ::= { xcctrapg 22 }

        altAuxData     OBJECT-TYPE
                       SYNTAX  DisplayString
                       ACCESS  read-only
                       STATUS  mandatory
                       DESCRIPTION
                       "Auxiliary data that may be included for some events."
                       ::= { xcctrapg 23 }

        altCommonEventID OBJECT-TYPE
                       SYNTAX DisplayString
                       ACCESS read-only
                       STATUS mandatory
                       DESCRIPTION
                       "Common Event Identifier"
                       ::= { xcctrapg 24 }
 
        altEventType   OBJECT-TYPE
                       SYNTAX INTEGER (0..65535)
                       ACCESS read-only
                       STATUS mandatory
                       DESCRIPTION
                       "The type of event"
                       ::= { xcctrapg 25 }
 
        altDetectorID  OBJECT-TYPE
                       SYNTAX DisplayString
                       ACCESS read-only
                       STATUS mandatory
                       DESCRIPTION
                       "Reporting source of event"
                       ::= { xcctrapg 26 }

        altDIMMPartNumber  OBJECT-TYPE
                       SYNTAX DisplayString
                       ACCESS read-only
                       STATUS mandatory
                       DESCRIPTION
                       "Reporting DIMM part number information"
                       ::= { xcctrapg 27 }

-- ******************************************
-- Critical Traps
-- ******************************************
        lenovoSpTrapTempC     TRAP-TYPE
                              ENTERPRISE  lenovoXCCAlertMIB
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Critical Alert: Temperature threshold exceeded."
                                  ::= 0

        lenovoSpTrapVoltC     TRAP-TYPE
                              ENTERPRISE  lenovoXCCAlertMIB  
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Critical Alert: Voltage threshold exceeded."
                                ::= 1

        lenovoSpTrapPowerC    TRAP-TYPE
                              ENTERPRISE  lenovoXCCAlertMIB
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Critical Alert: Power failure."
                                ::= 4

        lenovoSpTrapHdC          TRAP-TYPE
                              ENTERPRISE  lenovoXCCAlertMIB
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "Critical Alert: Hard disk drive failure."
                                ::= 5

        lenovoSpTrapFanC         TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "Critical Alert: Single Fan failure."
                                ::= 11


        lenovoSpTrapIhcC      TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Critical Alert: Incompatible hardware configuration."
                                ::= 36

        lenovoSpTrapCPUC         TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "Critical Alert: CPU Error."
                                ::= 40

        lenovoSpTrapMemoryC   TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Critical Alert: Memory Error."
                                ::= 41

        lenovoSpTrapRdpsC       TRAP-TYPE
                                ENTERPRISE  lenovoXCCAlertMIB 
                                VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                  }
                                  DESCRIPTION
                                    "Critical Alert: Redundant Power Supply failure."
                                  ::= 9

        lenovoSpTrapHardwareC  TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Critical Alert: Other Failure - refer to Message ID for specific condition."
                                ::= 50

-- ******************************************
-- Non-Critical Traps
-- ******************************************

        lenovoSpTrapRdpsN       TRAP-TYPE
                                ENTERPRISE  lenovoXCCAlertMIB 
                                VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                  }
                                  DESCRIPTION
                                    "Non-Critical Alert: Redundant Power Supply failure."
                                  ::= 10

        lenovoSpTrapTempN     TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Non-Critical Alert: Temperature threshold exceeded."
                                ::= 12

        lenovoSpTrapVoltN     TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Non-Critical Alert: Voltage threshold exceeded."
                                ::= 13

        lenovoSpTrapPowerN    TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Non-Critical Alert: Power."
                                ::= 164

        lenovoSpTrapFanN      TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "Non-Critical Alert: Fan Error."
                                ::= 165

        lenovoSpTrapCPUN      TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "Non-Critical Alert: CPU Error."
                                ::= 42

        lenovoSpTrapMemoryN   TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Non-Critical Alert: Memory Error."
                                ::= 43

        lenovoSpTrapHardwareN    TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID,
                                altDIMMPartNumber
                                }
                                DESCRIPTION
                                  "Non-Critical Alert: Warning - refer to Message ID for specific condition."
                                ::= 60

-- ******************************************
-- System Traps
-- ******************************************

        lenovoSpTrapRLogin    TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "Sev-Off Alert: Event Remote Login."
                                ::= 30


        lenovoSpTrapOsToS     TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: OS Timeout value exceeded."
                                ::= 21

        lenovoSpTrapAppS      TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: Application Alert. Refer to Message ID for specific condition."
                                ::= 22

        lenovoSpTrapPoffS     TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: Power Off."
                                ::= 23

        lenovoSpTrapPonS      TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: Power On."
                                ::= 24

        lenovoSpTrapBootS     TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: System Boot Failure."
                                ::= 25

        lenovoSpTrapLdrToS    TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: OS Loader Timeout."
                                ::= 26

        lenovoSpTrapPFAS      TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: Predictive Failure Analysis(PFA) information."
                                ::= 27

        lenovoSpTrapSysLogS   TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: System Log 75% full."
                                ::= 35

        lenovoSpTrapNwChangeS    TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: Network change notification."
                                ::= 37
        lenovoSpTrapNICLinkStateS    TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: Host NIC link state(down/up)."
                                ::= 38
        lenovoSpTrapDriveHotplugS    TRAP-TYPE
                              ENTERPRISE  lenovoXCCAlertMIB 
                              VARIABLES
                                {
                                altDateTime,
                                altSpTxtId,
                                altSysUuid,
                                altSysSern,
                                altMsgID,
                                altMsgIDPrefix,
                                altPriority,
                                altMsgText,
                                altHostContact,
                                altHostLocation,
                                altHostRoomID,
                                altHostRackID,
                                altHostLowestUpos,
                                altHostBladeBay,
                                altEventID,
                                altServiceable,
                                altTest,
                                altFailingFRUs,
                                altHostMTM,
                                altAuxData,
                                altCommonEventID,
                                altEventType,
                                altDetectorID
                                }
                                DESCRIPTION
                                  "System Alert: Drive Hotplug."
                                ::= 39
END
