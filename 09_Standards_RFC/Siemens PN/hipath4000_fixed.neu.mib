-- Project DTS/HTS - Proxy Agent MIB
--
-- comments of the form	'-	BEGIN BLOCK' or are used to automate splitting
-- of this MIB into several sub-MIBs for each of the subabgents

-- BLOCK LIST system alarm error hard soft topo sql discov

-- BEGIN BLOCK common

SIEMENS-PN-MIB DEFINITIONS	::=	BEGIN

IMPORTS
	MODULE-IDENTITY, OBJECT-TYPE, NOTIFICATION-TYPE,
        Counter32, Integer32
                   FROM SNMPv2-SMI
	enterprises
                   FROM RFC1155-SMI
	TEXTUAL-CONVENTION, DisplayString, RowStatus, TestAndIncr
                   FROM SNMPv2-TC
	OBJECT-GROUP
                   FROM SNMPv2-CONF;


hicomMib MODULE-IDENTITY
	LAST-UPDATED	"201401011300Z"

	ORGANIZATION
		"Unify"
	CONTACT-INFO
		"Unify Customer Support"
	DESCRIPTION
		"This is the MIB for OpenScape/HiPath 4000 systems. It includes
		topology and system management, alarm management and hard/software
		management."
        REVISION      "201401011300Z"
        DESCRIPTION
                "Complete revision for OpenScape4000 and SMIv1 syntax"
	::=	{ pn 1 }

sni				OBJECT IDENTIFIER ::= { enterprises 231 }
siemensUnits			OBJECT IDENTIFIER ::= { sni 7 }
pn				OBJECT IDENTIFIER ::= { siemensUnits 2 }

-- the hicom mib consists of the following subtrees/groups

hicomControl			OBJECT IDENTIFIER ::= { hicomMib 0 }
hicomSystem			OBJECT IDENTIFIER ::= { hicomMib 1 }
hicomAlarms			OBJECT IDENTIFIER ::= { hicomMib 2 }
hicomErrors			OBJECT IDENTIFIER ::= { hicomMib 3 }
hicomAlConf			OBJECT IDENTIFIER ::= { hicomMib 4 }
hicomSoft			OBJECT IDENTIFIER ::= { hicomMib 5 }
hicomHard			OBJECT IDENTIFIER ::= { hicomMib 6 }
hicomTopo			OBJECT IDENTIFIER ::= { hicomMib 7 }
hicomSQL			OBJECT IDENTIFIER ::= { hicomMib 8 }
hicomDiscov			OBJECT IDENTIFIER ::= { hicomMib 9 }
hipath4000Supervisor		OBJECT IDENTIFIER ::= { hicomMib 10 }
commonManagement		OBJECT IDENTIFIER ::= { hicomMib 11 }
hicomMibConformance		OBJECT IDENTIFIER ::= { hicomMib 20 }

hicomTrapGroup			OBJECT IDENTIFIER ::= { hicomMib 21 }
hicomTrapVariables		OBJECT IDENTIFIER ::= { hicomTrapGroup 1 }
hicomTraps			OBJECT IDENTIFIER ::= { hicomTrapGroup 2 }

hicomSystemTrapVariables	OBJECT IDENTIFIER ::= { hicomTrapVariables 1}
hicomAlarmTrapVariables		OBJECT IDENTIFIER ::= { hicomTrapVariables 2}
hicomErrorTrapVariables		OBJECT IDENTIFIER ::= { hicomTrapVariables 3}
hicomSWTrapVariables         	OBJECT IDENTIFIER ::= { hicomTrapVariables 4}
hicomAlConfTrapVariables	OBJECT IDENTIFIER ::= { hicomTrapVariables 5}
hicomHWTrapVariables		OBJECT IDENTIFIER ::= { hicomTrapVariables 6}
hicomTopoTrapVariables		OBJECT IDENTIFIER ::= { hicomTrapVariables 7}
hicomSQLTrapVariables		OBJECT IDENTIFIER ::= { hicomTrapVariables 8}
hicomDiscTrapVariables		OBJECT IDENTIFIER ::= { hicomTrapVariables 9}
hipath4000SupervisorTrapVariables	OBJECT IDENTIFIER ::= { hicomTrapVariables 10}

hicomSystemTraps		OBJECT IDENTIFIER ::= { hicomTraps 1 }
hicomAlarmTraps			OBJECT IDENTIFIER ::= { hicomTraps 2 }
hicomErrorTraps			OBJECT IDENTIFIER ::= { hicomTraps 3 }
hicomAlConfTraps		OBJECT IDENTIFIER ::= { hicomTraps 4 }
hicomSWTraps			OBJECT IDENTIFIER ::= { hicomTraps 5 }
hicomHWTraps			OBJECT IDENTIFIER ::= { hicomTraps 6 }
hicomTopoTraps			OBJECT IDENTIFIER ::= { hicomTraps 7 }
hicomSQLTraps			OBJECT IDENTIFIER ::= { hicomTraps 8 }
hicomDiscTraps			OBJECT IDENTIFIER ::= { hicomTraps 9 }
hipath4000SupervisorTraps	OBJECT IDENTIFIER ::= { hicomTraps 10 }

hicomMibGroups			OBJECT IDENTIFIER ::= { hicomMibConformance 1 }

hicomCntrlTree			OBJECT IDENTIFIER ::= { hicomMibGroups 0 }
hicomSysTree			OBJECT IDENTIFIER ::= { hicomMibGroups 1 }
hicomAlarmTree			OBJECT IDENTIFIER ::= { hicomMibGroups 2 }
hicomErrorTree			OBJECT IDENTIFIER ::= {	hicomMibGroups 3 }
hicomAlConfTree			OBJECT IDENTIFIER ::= { hicomMibGroups 4 }
hicomSoftTree			OBJECT IDENTIFIER ::= {	hicomMibGroups 5 }
hicomHardTree			OBJECT IDENTIFIER ::= { hicomMibGroups 6 }
hicomTopoTree			OBJECT IDENTIFIER ::= { hicomMibGroups 7 }
hicomSQLtree 			OBJECT IDENTIFIER ::= { hicomMibGroups 8 }
hicomDiscovTree 		OBJECT IDENTIFIER ::= { hicomMibGroups 9 }
hipath4000SupervisorTree	OBJECT IDENTIFIER ::= { hicomMibGroups 10 }

-- common definitions 
DiscoveryStates ::= TEXTUAL-CONVENTION
      STATUS current
      DESCRIPTION 
               "Represents status of discovery process"
      SYNTAX INTEGER {
			done (1), error (2), busy (3), finok (4), finerr (5), 
			kill (6),
			masterDone(11), masterError(12), masterBusy(13),
			masterFinok(14), masterFinerr(15), errdelDone(21),
			errdelError(22), errdelBusy(23), errdelFinok(24),
			errdelFinerr(25) }

DiscoveryModes	  ::= TEXTUAL-CONVENTION
      STATUS current
      DESCRIPTION
                "Represents type of discovery activation"
      SYNTAX INTEGER { man (1), auto (2), undef (9) }

AlarmFilterStates ::= TEXTUAL-CONVENTION
      STATUS current
      DESCRIPTION
                "Represents status of alarm filtering"
      SYNTAX INTEGER { filterOn (1), filterOff (2) }

AlarmPriorities   ::= TEXTUAL-CONVENTION
      STATUS current
      DESCRIPTION
                "Represents alarm priority"
      SYNTAX INTEGER { minor (1), major (2), device (3) }

-- BEGIN BLOCK system

-- the hicomControl Object Definitions

         hicomProxyName OBJECT-TYPE
            SYNTAX        DisplayString
            MAX-ACCESS    read-only
            STATUS        current
            DESCRIPTION
                  "Name of the Hicom proxy agent."
            ::= { hicomControl 1 }

         hicomAgentVersion OBJECT-TYPE
            SYNTAX        DisplayString
            MAX-ACCESS    read-only
            STATUS        current
            DESCRIPTION
                  "Version of the Hicom proxy agent. "
            ::= { hicomControl 2 }

         hicomMIBVersion OBJECT-TYPE
            SYNTAX        DisplayString
            MAX-ACCESS    read-only
            STATUS        current
            DESCRIPTION
                  "MIB Version of the Hicom proxy agent. "
            ::= { hicomControl 3 }


hicomControlGroup OBJECT-GROUP
	OBJECTS	{ 
			hicomProxyName, hicomAgentVersion, hicomMIBVersion
		}
	STATUS current
	DESCRIPTION
		"Conformance statement of the hicomControlGroup."
	::=	{ hicomCntrlTree 1 }


-- The hicomSystem MIB group provides system information of the hicom network

-- the hicomSystem group

hicomNumHicoms		OBJECT-TYPE
	SYNTAX		Integer32
	MAX-ACCESS	read-only
	STATUS		current
	DESCRIPTION	"The number of Hicom systems managed by this agent."
	::=	{ hicomSystem 1 }

hicomSystemChanges	OBJECT-TYPE
	SYNTAX		Counter32
	MAX-ACCESS	read-only
	STATUS		current
	DESCRIPTION		"When a change (SET) is made on hicomSysTable
				 or hicomForeignSysTable, the variable is
				 incremented by one."
	::=	{ hicomSystem 2 }

-- the hicomSysTable

hicomSysTable	OBJECT-TYPE
	SYNTAX		SEQUENCE OF	HicomSysEntry
	MAX-ACCESS	not-accessible
	STATUS		current
	DESCRIPTION	"The table of Hicom systems."
	::=	{ hicomSystem 3}

	hicomSysEntry	OBJECT-TYPE
		SYNTAX		HicomSysEntry
		MAX-ACCESS	not-accessible
		STATUS		current
		DESCRIPTION	"Each entry describes a Hicom system."
		INDEX		{ hicomSysPabxId }
		::=	{ hicomSysTable 1 }

	HicomSysEntry ::=
		SEQUENCE {
			hicomSysPabxId		Integer32,
			hicomSysConNo		DisplayString,
			hicomSysEstabl		Integer32,
			hicomSysPosNo		DisplayString,
			hicomSysMnemonic	DisplayString,
			hicomSysCustName	DisplayString,
			hicomSysCbCode		DisplayString,
			hicomSysTelNo		DisplayString,
			hicomSysCutOver		DisplayString,
			hicomSysPabxNo		DisplayString,
			hicomSysClnr		DisplayString,
			hicomSysLocation	DisplayString,
			hicomSysRemark		DisplayString,
			hicomSysSwLic		DisplayString,
			hicomSysSysType		DisplayString,
            hicomSysApsPa       DisplayString,
			hicomSysTimeStamp	Integer32,
			hicomSysDescription	DisplayString,
			hicomSysVersion		DisplayString,
			hicomSysCustomerSpecific	DisplayString,
			hicomSysStreetAddress	DisplayString,
			hicomSysLineType	DisplayString,
            hicomSysProduct     DisplayString,
			hicomSysCustomerContact	DisplayString,
			hicomSysServiceDistrict	DisplayString,
			hicomSysCustomerContract	DisplayString,
			hicomSysTimeOfLastFm    Integer32,
			hicomSysHicomSwVersion	DisplayString,
			hicomSysEndWarranty	DisplayString,
            hicomSysBatteryType DisplayString,
            hicomSysBatteryCapac    DisplayString,
            hicomSysInterface   DisplayString,
			hicomSysSystemRoomTel	DisplayString,
-- new unity fields 71-
			hicomSysNoType           DisplayString,
			hicomSysCustServer       DisplayString,
			hicomSysCustNoid         DisplayString,
  			hicomSysNoName           DisplayString,
			hicomSysRemarkCd         DisplayString,
			hicomSysHSystemRelease   DisplayString,
			hicomSysHcmAmolang       DisplayString,
			hicomSysRemarkCon        DisplayString,
			hicomSysIpAddress        DisplayString,
  			hicomSysRemarkCom        DisplayString,
  			hicomSysMsvProgNum       Integer32,
  			hicomSysMsvRegNum        Integer32,
  			hicomSysHcEquipNr1       DisplayString,
  			hicomSysHcEquipNr2       DisplayString,
  			hicomSysDaUrl            DisplayString,
			hicomSysHcmCorrState     DisplayString,
-- zusatzinfo fields 100 -
			hicomSysNodeNo		Integer32,
			hicomSysLang		INTEGER,
			hicomSysMgrNetId	OCTET STRING,
			hicomSysMgrSubNetId	OCTET STRING,
			hicomSysMgrPhysNetId	OCTET STRING,
			hicomSysMgrFlags	Integer32,
			hicomSysDiscTimeOutEvnt	INTEGER,
			hicomSysDiscAgedData	INTEGER,
			hicomSysDiscComType	INTEGER,
		    hicomSysAgentFlags    Integer32	
		}

-- the chdmain table
-- -----------------
	hicomSysPabxId		OBJECT-TYPE
		SYNTAX		Integer32 (1..2147483647)
		MAX-ACCESS	read-only
		STATUS		current
		DESCRIPTION	"Unique identifier of a Hicom system."
		::=	{ hicomSysEntry 1 }

	hicomSysConNo	OBJECT-TYPE
		SYNTAX		DisplayString
		MAX-ACCESS	read-only
		STATUS		current
		DESCRIPTION	"Customer contract number."
		::=	{ hicomSysEntry 2 }

	hicomSysEstabl		OBJECT-TYPE
		SYNTAX		Integer32
		MAX-ACCESS	read-only
		STATUS		current
		DESCRIPTION	"Contract (2.-3.)"
		::=	{ hicomSysEntry 3 }

	hicomSysPosNo	OBJECT-TYPE
		SYNTAX		DisplayString
		MAX-ACCESS	read-only
		STATUS		current
		DESCRIPTION	"Contract (10.-14)"
		::=	{ hicomSysEntry 4 }

	hicomSysMnemonic	OBJECT-TYPE
		SYNTAX		DisplayString
		MAX-ACCESS read-only
		STATUS		current
		DESCRIPTION	"Mnemonic name of the Hicom system."
		::=	{ hicomSysEntry 5 }

	hicomSysCustName	OBJECT-TYPE
		SYNTAX		DisplayString
		MAX-ACCESS read-only
		STATUS		current
		DESCRIPTION		"Name of the service technician."
		::=	{ hicomSysEntry 6 }

	hicomSysCbCode		OBJECT-TYPE
		SYNTAX		DisplayString
		MAX-ACCESS	read-only
		STATUS		current
		DESCRIPTION	"Call back"
		::=	{ hicomSysEntry 7 }

	hicomSysTelNo		OBJECT-TYPE
		SYNTAX		DisplayString
		MAX-ACCESS read-only
		STATUS		current
		DESCRIPTION		"Call number of the customer."
		::=	{ hicomSysEntry 8 }

	hicomSysCutOver		OBJECT-TYPE
		SYNTAX		DisplayString
		MAX-ACCESS read-only
		STATUS		current
		DESCRIPTION		"CutOver date for Hicom."
		::=	{ hicomSysEntry 9 }

    hicomSysClnr     OBJECT-TYPE
        SYNTAX      DisplayString
        MAX-ACCESS  read-only
        STATUS  current
        DESCRIPTION     "Call number of the Hicom service. "
        ::= { hicomSysEntry 11 }


	hicomSysPabxNo		OBJECT-TYPE
		SYNTAX		DisplayString
		MAX-ACCESS read-only
		STATUS		current
		DESCRIPTION		"Chdmain pabx_no field."
		::=	{ hicomSysEntry 12 }

	hicomSysLocation	OBJECT-TYPE
		SYNTAX		DisplayString
		MAX-ACCESS read-only
		STATUS	current
		DESCRIPTION		"Location of the Hicom system. "
		::=	{ hicomSysEntry 13 }

	hicomSysRemark		OBJECT-TYPE
		SYNTAX		DisplayString
		MAX-ACCESS read-only
		STATUS		current
		DESCRIPTION		"Optional remarks. "
		::=	{ hicomSysEntry 14 }

	hicomSysSwLic		OBJECT-TYPE
		SYNTAX		DisplayString
		MAX-ACCESS read-only
		STATUS		current
		DESCRIPTION		"Software licence number."
		::=	{ hicomSysEntry 15 }

	hicomSysSysType		OBJECT-TYPE
		SYNTAX		DisplayString
		MAX-ACCESS read-only
		STATUS		current
		DESCRIPTION		"Type of equipment."
		::=	{ hicomSysEntry 16 }

    hicomSysApsPa       OBJECT-TYPE
        SYNTAX      DisplayString
        MAX-ACCESS read-only
        STATUS      current
        DESCRIPTION     "Chdmain aps_pa field."
        ::= { hicomSysEntry 17 }


	hicomSysTimeStamp	OBJECT-TYPE
		SYNTAX		Integer32
		MAX-ACCESS read-only
		STATUS		current
		DESCRIPTION		"Chdmain timstamp field."
		::=	{ hicomSysEntry 26 }

	hicomSysDescription	OBJECT-TYPE
		SYNTAX		DisplayString
		MAX-ACCESS read-only
		STATUS		current
		DESCRIPTION		"Chdmain longname field."
		::=	{ hicomSysEntry 34 }

	hicomSysVersion	OBJECT-TYPE
		SYNTAX		DisplayString
		MAX-ACCESS read-only
		STATUS		current
		DESCRIPTION		"Installed version of the
					Hicom system."
		::=	{ hicomSysEntry 39 }

	hicomSysCustomerSpecific	OBJECT-TYPE
		SYNTAX		DisplayString
		MAX-ACCESS read-only
		STATUS		current
		DESCRIPTION		"Chdmain customer_specific field."
		::=	{ hicomSysEntry 44 }

	hicomSysStreetAddress	OBJECT-TYPE
		SYNTAX		DisplayString
		MAX-ACCESS read-only
		STATUS		current
		DESCRIPTION		"Chdmain street_address field."
		::=	{ hicomSysEntry 45 }

	hicomSysLineType	OBJECT-TYPE
		SYNTAX		DisplayString
		MAX-ACCESS read-only
		STATUS		current
		DESCRIPTION		"Chdmain line_type field."
		::=	{ hicomSysEntry 46 }

    hicomSysProduct     OBJECT-TYPE
        SYNTAX      DisplayString
        MAX-ACCESS read-only
        STATUS      current
        DESCRIPTION     "Chdmain product field."
        ::= { hicomSysEntry 48 }


	hicomSysCustomerContact	OBJECT-TYPE
		SYNTAX		DisplayString
		MAX-ACCESS read-only
		STATUS		current
		DESCRIPTION		"Chdmain customer_contact field."
		::=	{ hicomSysEntry 49 }

	hicomSysServiceDistrict	OBJECT-TYPE
		SYNTAX		DisplayString
		MAX-ACCESS read-only
		STATUS		current
		DESCRIPTION		"Chdmain service_district field."
		::=	{ hicomSysEntry 50 }

	hicomSysCustomerContract OBJECT-TYPE
		SYNTAX		DisplayString
		MAX-ACCESS read-only
		STATUS		current
		DESCRIPTION		"Chdmain customer_contract field."
		::=	{ hicomSysEntry 51 }

	hicomSysTimeOfLastFm	OBJECT-TYPE
		SYNTAX		Integer32
		MAX-ACCESS read-only
		STATUS		current
		DESCRIPTION		"Chdmain time_of_last_fm field."
		::=	{ hicomSysEntry 53 }

	hicomSysHicomSwVersion	OBJECT-TYPE
		SYNTAX		DisplayString
		MAX-ACCESS read-only
		STATUS		current
		DESCRIPTION		"Chdmain hicom_sw_version field."
		::=	{ hicomSysEntry 55 }

	hicomSysEndWarranty	OBJECT-TYPE
		SYNTAX		DisplayString
		MAX-ACCESS read-only
		STATUS		current
		DESCRIPTION		"Chdmain end_warranty field."
		::=	{ hicomSysEntry 58 }

    hicomSysBatteryType OBJECT-TYPE
        SYNTAX      DisplayString
        MAX-ACCESS read-only
        STATUS      current
        DESCRIPTION     "Chdmain battery_type field."
        ::= { hicomSysEntry 61 }

    hicomSysBatteryCapac    OBJECT-TYPE
        SYNTAX      DisplayString
        MAX-ACCESS read-only
        STATUS      current
        DESCRIPTION     "Chdmain battery_capacity field."
        ::= { hicomSysEntry 62 }

    hicomSysInterface   OBJECT-TYPE
        SYNTAX      DisplayString
        MAX-ACCESS read-only
        STATUS      current
        DESCRIPTION     "Chdmain interface field."
        ::= { hicomSysEntry 63 }

	hicomSysSystemRoomTel	OBJECT-TYPE
		SYNTAX		DisplayString
		MAX-ACCESS read-only
		STATUS		current
		DESCRIPTION		"Chdmain system_room_tel field."
		::=	{ hicomSysEntry 64 }

-- new unity fields 71-90

	hicomSysNoType	OBJECT-TYPE
		SYNTAX		DisplayString
		MAX-ACCESS read-only
		STATUS		current
		DESCRIPTION	"Network Object icon default display name."
		::=	{ hicomSysEntry 71 }

	hicomSysCustServer	OBJECT-TYPE
		SYNTAX		DisplayString
		MAX-ACCESS read-only
		STATUS		current
		DESCRIPTION	"Network Object ID (mnemonic) of the Network Manager Unity A&S server."
		::=	{ hicomSysEntry 72 }

	hicomSysCustNoid	OBJECT-TYPE
		SYNTAX		DisplayString
		MAX-ACCESS read-only
		STATUS		current
		DESCRIPTION	"NOId (mnemonic) of the uploaded NO (H300) in customer server."
		::=	{ hicomSysEntry 73 }


  	hicomSysNoName	OBJECT-TYPE
  		SYNTAX		DisplayString
  		MAX-ACCESS read-only
  		STATUS		current
  		DESCRIPTION	"Network Object icon default display name."
  		::=	{ hicomSysEntry 74 }

	hicomSysRemarkCd	OBJECT-TYPE
		SYNTAX		DisplayString
		MAX-ACCESS read-only
		STATUS		current
		DESCRIPTION	"remarks to customer data."
		::=	{ hicomSysEntry 75 }

	hicomSysHSystemRelease	OBJECT-TYPE
		SYNTAX		DisplayString
		MAX-ACCESS read-only
		STATUS		current
		DESCRIPTION	"Sachnummer of resident SWU (switching unit) 
                     APS (Anlagen Programm System)."
		::=	{ hicomSysEntry 76 }

	hicomSysHcmAmolang	OBJECT-TYPE
		SYNTAX		DisplayString
		MAX-ACCESS read-only
		STATUS		current
		DESCRIPTION	"AMO language 1=de 2=en ."
		::=	{ hicomSysEntry 77 }

	hicomSysRemarkCon	OBJECT-TYPE
		SYNTAX		DisplayString
		MAX-ACCESS read-only
		STATUS		current
		DESCRIPTION	"Remarks to contract data."
		::=	{ hicomSysEntry 78 }

	hicomSysIpAddress	OBJECT-TYPE
		SYNTAX		DisplayString
		MAX-ACCESS read-only
		STATUS		current
		DESCRIPTION	"IP address or DNS entry of Hicom/Network Object."
		::=	{ hicomSysEntry 79 }

  	hicomSysRemarkCom	OBJECT-TYPE
  		SYNTAX		DisplayString
  		MAX-ACCESS read-only
  		STATUS		current
  		DESCRIPTION	"Remarks to communication."
  		::=	{ hicomSysEntry 80 }

  	hicomSysMsvProgNum	OBJECT-TYPE
  		SYNTAX		Integer32
  		MAX-ACCESS read-only
  		STATUS		current
  		DESCRIPTION	"This Hicom number is needed for MSVx connectivity
                     over dial up or leased lines, generated."
  		::=	{ hicomSysEntry 81 }

  	hicomSysMsvRegNum	OBJECT-TYPE
  		SYNTAX		Integer32
  		MAX-ACCESS read-only
  		STATUS		current
  		DESCRIPTION	"This region number is needed for MSVx connectivity 
                      over dial up or leased lines, generated (Teilnetz Id)."
  		::=	{ hicomSysEntry 82 }

  	hicomSysHcEquipNr1	OBJECT-TYPE
  		SYNTAX		DisplayString
  		MAX-ACCESS read-only
  		STATUS		current
  		DESCRIPTION	"First part of the hicom equipment number, 
                       SP(Systemprogramm) Sachnummer 1."
  		::=	{ hicomSysEntry 83 }

  	hicomSysHcEquipNr2	OBJECT-TYPE
  		SYNTAX		DisplayString
  		MAX-ACCESS read-only
  		STATUS		current
  		DESCRIPTION	"Secon part of the hicom equipment number, 
                       SP(Systemprogramm) Sachnummmer 2."
  		::=	{ hicomSysEntry 84 }

  	hicomSysDaUrl	OBJECT-TYPE
  		SYNTAX		DisplayString
  		MAX-ACCESS read-only
  		STATUS		current
   		DESCRIPTION	"URL for Web based DA application."
  		::=	{ hicomSysEntry 85 }

	hicomSysHcmCorrState	OBJECT-TYPE
		SYNTAX		DisplayString
		MAX-ACCESS read-only
		STATUS		current
		DESCRIPTION	"Correction State of the Hicom (Patches/APS)."
		::=	{ hicomSysEntry 86 }

-- Zusatzinfo Table 	
-- ----------------

	hicomSysNodeNo		OBJECT-TYPE
		SYNTAX		Integer32
		MAX-ACCESS read-only
		STATUS		current
		DESCRIPTION		"Node number of the Hicom system."
		DEFVAL { 0 }
		::=	{ hicomSysEntry 100 }

	hicomSysLang		OBJECT-TYPE
		SYNTAX		INTEGER	{ undef	(1), german (2), english (3) }
		MAX-ACCESS	read-only
		STATUS		current
		DESCRIPTION	"Configured system language."
		DEFVAL		{ undef }
		::=	{ hicomSysEntry 101 }

	hicomSysMgrNetId	OBJECT-TYPE
		SYNTAX		OCTET STRING (SIZE (0..32))
		MAX-ACCESS 	read-write
		STATUS		current
		DESCRIPTION		"Identifier of the customer network.
					The field is set and maintained by
					the manager application."
		::=	{ hicomSysEntry 102 }

	hicomSysMgrSubNetId OBJECT-TYPE
		SYNTAX		OCTET STRING  (SIZE (0..64))
		MAX-ACCESS 	read-write
		STATUS		current
		DESCRIPTION		"Identifier of the customer's 
					sub-network.
					The field is set and maintained by
					the manager application."
		::=	{ hicomSysEntry 103 }

	hicomSysMgrPhysNetId OBJECT-TYPE
		SYNTAX		OCTET STRING  (SIZE (0..32))
		MAX-ACCESS 	read-write
		STATUS		current
		DESCRIPTION		"Identifier of a customer's 
					physical network.
					The field is set and maintained by
					the manager application."
		::=	{ hicomSysEntry 104 }

	hicomSysMgrFlags	OBJECT-TYPE
		SYNTAX		Integer32
		MAX-ACCESS 	read-write
		STATUS		current
		DESCRIPTION		"Private flags of manager application.
					The field is set and maintained by
					the manager application."
		::=	{ hicomSysEntry 105 }

	hicomSysDiscTimeOutEvnt	OBJECT-TYPE
		SYNTAX		INTEGER (24..65535)
		MAX-ACCESS 	read-write
		STATUS		current
		DESCRIPTION		"Acceptable maximum time interval 
					(unit is hours) not getting an 
					event from the hicom system.
					
					E1: (DiscTimeOutEvnt < t1 - t2)
					t1 = current Time
					t2 = Time of last Event

					If the expression E1 becomes true
					a discovery operation will started 
					for the hicom. 
					DiscTimeOutEvnt shall be set greater
					or equal to 24 hours.
					The field is set and maintained by 
					the manager application."
		DEFVAL		{ 24 }
		::=	{ hicomSysEntry 106 }

	hicomSysDiscAgedData	OBJECT-TYPE
		SYNTAX		INTEGER (168..65535)
		MAX-ACCESS 	read-write
		STATUS		current
		DESCRIPTION		"Acceptable maximum time interval 
					(unit is hours) since last discovery 
					date and current event date.

					E2: (DiscAgedData < t1 - t2)
					t1 = current Event Time
					t2 = time last discovery succeeded

					If the expression E2 becomes true 
					a discovery operation will started 
					for the hicom. 
					DiscAgedData shall be set greater or
					equal to 168 hours (7 days).
					The field is set and maintained by the 
					manager application."
		DEFVAL	{ 168 }
		::=	{ hicomSysEntry 107 }

	hicomSysDiscComType OBJECT-TYPE
		SYNTAX		INTEGER { addBatchJob (1), online (2) }
		MAX-ACCESS 	read-write
		STATUS		current
		DESCRIPTION		"Identifies the communication interface
					between DMS and Hicom."
		DEFVAL		{ addBatchJob }
		::=	{ hicomSysEntry 108 }

    hicomSysAgentFlags    OBJECT-TYPE
        SYNTAX      Integer32
        MAX-ACCESS  read-write
        STATUS      current
        DESCRIPTION     "Private flags of the Agent.
                    The field is set and maintained by
                    the manager/agent application."
        ::= { hicomSysEntry 109 }

hicomSysSubagentLastMsgNo	OBJECT-TYPE
	SYNTAX		Integer32
	MAX-ACCESS	read-only
	STATUS		current
	DESCRIPTION	"The last message, warning or error number 
				issued by the Alarm subagent."
	::=	{ hicomSystem 4 }

hicomSysSubagentLastMsgText	OBJECT-TYPE
	SYNTAX		DisplayString
	MAX-ACCESS	read-only
	STATUS		current
	DESCRIPTION	"The last message, warning or error text
				issued by the Alarm subagent."
	::=	{ hicomSystem 5 }

hicomForeignSysTable	OBJECT-TYPE
	SYNTAX		SEQUENCE OF	HicomForeignSysEntry
	MAX-ACCESS	not-accessible
	STATUS		current
	DESCRIPTION	"The table describes foreign systems connected to 
			the Hicom network. 
			The content of the table is created and maintained 
			by the manager application."
	::=	{ hicomSystem 6}

	hicomForeignSysEntry	OBJECT-TYPE
		SYNTAX		HicomForeignSysEntry
		MAX-ACCESS	not-accessible
		STATUS		current
		DESCRIPTION	"Each entry describes a foreing system 
				connected to the Hicom network."
		INDEX		{ hicomForSysPhysNetId, hicomForSysNodeNo }
		::=	{ hicomForeignSysTable 1 }

	HicomForeignSysEntry ::=
		SEQUENCE {
			hicomForSysPhysNetId	OCTET STRING,
			hicomForSysNodeNo	Integer32,
			hicomForSysName		OCTET STRING,
			hicomForSysNetId	OCTET STRING,
			hicomForSysSubNetId	OCTET STRING,
			hicomForSysProvNetId	OCTET STRING,
			hicomForSysProvSubNetId	OCTET STRING,
			hicomForSysRowStat	RowStatus
		}

	hicomForSysPhysNetId	OBJECT-TYPE
		SYNTAX		OCTET STRING   (SIZE (1..32))
		MAX-ACCESS 	not-accessible
		STATUS		current
		DESCRIPTION		"Physical net identification of the 
					foreign system."
		::=	{ hicomForeignSysEntry 1 }

	hicomForSysNodeNo	OBJECT-TYPE
		SYNTAX		Integer32 (1..2147483647)
		MAX-ACCESS 	not-accessible
		STATUS		current
		DESCRIPTION		"Node number (physical net) of the 
					foreign system."
		::=	{ hicomForeignSysEntry 2 }

	hicomForSysName		OBJECT-TYPE
		SYNTAX		OCTET STRING   (SIZE (0..32))
		MAX-ACCESS 	read-create
		STATUS		current
		DESCRIPTION		"Name of the foreign system."
		::=	{ hicomForeignSysEntry 3 }

	hicomForSysNetId	OBJECT-TYPE
		SYNTAX		OCTET STRING  (SIZE (0..32))
		MAX-ACCESS 	read-create
		STATUS		current
		DESCRIPTION		"Identifier of the network to which
					the foreign system belongs."
		::=	{ hicomForeignSysEntry 4 }

	hicomForSysSubNetId	OBJECT-TYPE
		SYNTAX		OCTET STRING  (SIZE (0..64))
		MAX-ACCESS 	read-create
		STATUS		current
		DESCRIPTION		"Identifier of the sub network to 
					which the foreign system belongs."
		::=	{ hicomForeignSysEntry 5 }

	hicomForSysProvNetId	OBJECT-TYPE
		SYNTAX		OCTET STRING  (SIZE (0..32))
		MAX-ACCESS 	read-create
		STATUS		current
		DESCRIPTION		"Net identifier of the provider 
					network the foreign system 
					belongs to."
		::=	{ hicomForeignSysEntry 6 }

	hicomForSysProvSubNetId	OBJECT-TYPE
		SYNTAX		OCTET STRING   (SIZE (0..64))
		MAX-ACCESS 	read-create
		STATUS		current
		DESCRIPTION		"Subnet identifier of the provider 
					network the foreign system belongs to."
		::=	{ hicomForeignSysEntry 7 }

	hicomForSysRowStat      OBJECT-TYPE
		SYNTAX		RowStatus
		MAX-ACCESS	read-create
		STATUS		current
		DESCRIPTION
				    "Setting a non-existing RowStat 
				     variable to 'createAndGo', creates a new
				     row. If creation was successful, the row
				     gets the status 'active'. Variables of
				     an 'active' row can be read and modified.
				     Setting RowStat to 'destroy' effects 
				     the deletion of the row."
		::= { hicomForeignSysEntry 8 }

hicomSystemGroup OBJECT-GROUP
	OBJECTS	{ 
			hicomNumHicoms, 
			hicomSysPabxId, hicomSysConNo,hicomSysEstabl,
			hicomSysPosNo, hicomSysMnemonic, hicomSysCustName,
			hicomSysCbCode, hicomSysTelNo, hicomSysCutOver,
			hicomSysClnr,hicomSysPabxNo,
			hicomSysLocation, hicomSysRemark, hicomSysSwLic,
			hicomSysSysType, hicomSysApsPa, hicomSysTimeStamp, 
			hicomSysDescription, hicomSysVersion,
            hicomSysCustomerSpecific, hicomSysStreetAddress,
			hicomSysLineType, hicomSysProduct, hicomSysCustomerContact,
            hicomSysServiceDistrict,
			hicomSysCustomerContract, hicomSysTimeOfLastFm, 
			hicomSysHicomSwVersion, hicomSysEndWarranty,
		    hicomSysBatteryType, hicomSysBatteryCapac,
            hicomSysInterface,hicomSysSystemRoomTel,
		
-- unity start
			hicomSysNoType           ,
			hicomSysCustServer       ,
			hicomSysCustNoid         ,
  			hicomSysNoName           ,
			hicomSysRemarkCd         ,
			hicomSysHSystemRelease   ,
			hicomSysHcmAmolang       ,
			hicomSysRemarkCon        ,
			hicomSysIpAddress        ,
  			hicomSysRemarkCom        ,
  			hicomSysMsvProgNum       ,
  			hicomSysMsvRegNum        ,
  			hicomSysHcEquipNr1       ,
  			hicomSysHcEquipNr2       ,
  			hicomSysDaUrl            ,
			hicomSysHcmCorrState     ,
-- unity end
			hicomSysNodeNo, hicomSysLang,
			hicomSysMgrNetId, hicomSysMgrSubNetId, 
			hicomSysMgrPhysNetId, hicomSysMgrFlags,
			hicomSysDiscTimeOutEvnt, hicomSysDiscAgedData,
			hicomSysDiscComType,hicomSysAgentFlags, 
			
			hicomSystemChanges, 
			hicomSysSubagentLastMsgNo, hicomSysSubagentLastMsgText,
			hicomForSysName, hicomForSysNetId, hicomForSysSubNetId,
			hicomForSysProvNetId, hicomForSysProvSubNetId,
			hicomForSysRowStat
		}
	STATUS current
	DESCRIPTION
		"Conformance statement of the hicomSystemGroup."
	::=	{ hicomSysTree 1 }

-- Traps

-- internal Message, Warning and Error

internalMessageSystemSubagent	NOTIFICATION-TYPE
	OBJECTS	{ hicomSysSubagentLastMsgNo, hicomSysSubagentLastMsgText }
	STATUS	current
	DESCRIPTION	"An internalMessage trap contains an informational
			 message generated by the subagent."
	::=	{ hicomSystemTraps 0 }

internalWarningSystemSubagent	NOTIFICATION-TYPE
	OBJECTS	{ hicomSysSubagentLastMsgNo, hicomSysSubagentLastMsgText }
	STATUS	current
	DESCRIPTION	"An internalWarning trap contains a warning message
			 generated by a subagent."
	::=	{ hicomSystemTraps 1 }

internalErrorSystemSubagent NOTIFICATION-TYPE
	OBJECTS	{ hicomSysSubagentLastMsgNo, hicomSysSubagentLastMsgText }
	STATUS	current
	DESCRIPTION	"An internalError trap contains an error message
			 generated by a subagent. 
			 After issuing this trap, the agent terminates."
	::=	{ hicomSystemTraps 2 }

-- network configuration traps:
addHicom NOTIFICATION-TYPE
	OBJECTS	{ hicomSysPabxId, hicomSysMnemonic }
	STATUS	current
	DESCRIPTION	"An addHicom trap signifies that a new
			hicom has been added to network."
	::=	{ hicomSystemTraps 10 }

deleteHicom	NOTIFICATION-TYPE
	OBJECTS	{ hicomSysPabxId, hicomSysMnemonic }
	STATUS	current
	DESCRIPTION	"A deleteHicom trap signifies that a
				hicom has been removed from the network."
	::=	{ hicomSystemTraps 11 }

changeConfig NOTIFICATION-TYPE
	OBJECTS		{ hicomSysPabxId, hicomSysMnemonic }
	STATUS		deprecated
	DESCRIPTION	"A changeConfig trap indicates that some change
				other than adding or removing a Hicom has been
				made to the network."
	::=	{ hicomSystemTraps 12 }


-- BEGIN BLOCK alarm

-- The hicomAlarms group provides hicom alarm information

-- the hicomAlTable

hicomAlarmsChanges	OBJECT-TYPE
	SYNTAX		Counter32
	MAX-ACCESS	read-only
	STATUS		current
	DESCRIPTION	"Is incremented when an alarm SET or RESET trap
			has been sent by the agent."
	::=	{ hicomAlarms 1 }


hicomAlTable	OBJECT-TYPE
	SYNTAX		SEQUENCE OF	HicomAlEntry
	MAX-ACCESS	not-accessible
	STATUS		current
	DESCRIPTION	"The table of all Hicom alarms."
	::=	{ hicomAlarms 2 }

	hicomAlEntry	OBJECT-TYPE
		SYNTAX		HicomAlEntry
		MAX-ACCESS	not-accessible
		STATUS		current
		DESCRIPTION	"Each entry describes a	Hicom alarm in detail."
		INDEX 		{ hicomAlFilter, hicomAlStatus, hicomAlPabxId, 
				hicomAlGroup, hicomAlSubId, hicomAlPriority, 
				hicomAlAbsMod }
		::=	{ hicomAlTable 1 }

	HicomAlEntry ::=
		SEQUENCE {
			hicomAlFilter	        AlarmFilterStates,
			hicomAlStatus           INTEGER,
			hicomAlPabxId	        Integer32,
			hicomAlGroup	        Integer32,
			hicomAlSubId	        Integer32,
			hicomAlPriority	        AlarmPriorities,
			hicomAlAbsMod	        DisplayString,
			hicomAlTimDat	        Integer32,
			hicomAlName	            DisplayString,
			hicomAlReset	        INTEGER,
			hicomAlTimOldDat	    Integer32,
			hicomAlArrivalTimDat	Integer32,
			hicomAlLocation         DisplayString
		}

	hicomAlFilter		OBJECT-TYPE
		SYNTAX		AlarmFilterStates
		MAX-ACCESS	read-only
		STATUS		current
		DESCRIPTION	"Alarm filter status."
		::=	{ hicomAlEntry 1 }

	hicomAlStatus		OBJECT-TYPE
		SYNTAX		INTEGER { reset (1), set (2) }
		MAX-ACCESS	read-only
		STATUS		current
		DESCRIPTION	"Status of an alarm."
		::=	{ hicomAlEntry 2 }

	hicomAlPabxId	OBJECT-TYPE
		SYNTAX		Integer32 (1..2147483647)
		MAX-ACCESS	read-only
		STATUS		current
		DESCRIPTION	"Unique identifier of a Hicom system."
		::=	{ hicomAlEntry 3 }

	hicomAlGroup	OBJECT-TYPE
		SYNTAX		Integer32  (1..7)
		MAX-ACCESS	read-only
		STATUS		current
		DESCRIPTION	"Group identifier of a Hicom alarm."
		::=	{ hicomAlEntry 4 }

	hicomAlSubId	OBJECT-TYPE
		SYNTAX		Integer32 (0..10000)
		MAX-ACCESS	read-only
		STATUS		current
		DESCRIPTION	"Sub-identifier of a Hicom alarm within its
				group."
		::=	{ hicomAlEntry 5 }

	hicomAlPriority		OBJECT-TYPE
		SYNTAX 		AlarmPriorities
		MAX-ACCESS 	read-only
		STATUS 		current
		DESCRIPTION	"Priority of a Hicom alarm."
		::=	{ hicomAlEntry 6 }

	hicomAlAbsMod		OBJECT-TYPE
		SYNTAX		DisplayString
		MAX-ACCESS 	read-only
		STATUS		current
		DESCRIPTION	"Hicom module detecting the Hicom alarm."
		::=	{ hicomAlEntry 7 }

	hicomAlTimDat		OBJECT-TYPE
		SYNTAX		Integer32
		MAX-ACCESS read-only
		STATUS		current
		DESCRIPTION		"Date and time of the Hicom alarm. "
		::=	{ hicomAlEntry 8 }

	hicomAlName	OBJECT-TYPE
		SYNTAX		DisplayString
		MAX-ACCESS	read-only
		STATUS		current
		DESCRIPTION		"Name of the Hicom alarm."
		::=	{ hicomAlEntry 9 }

	hicomAlReset	OBJECT-TYPE
		SYNTAX		INTEGER {
						init (1), error (2), busy (3),
						finok (4), finerr (5)
					}
		MAX-ACCESS	read-write
		STATUS		current
		DESCRIPTION	"This variable can be set to reset a Hicom alarm."
		DEFVAL 		{ init }
		::= { hicomAlEntry 10 }

-- TEST new UNITY MIB

	hicomAlTimOldDat		OBJECT-TYPE
		SYNTAX		Integer32
		MAX-ACCESS read-only
		STATUS		current
		DESCRIPTION		"Date and time of the previous set of this Hicom alarm. "
		::=	{ hicomAlEntry 11 }

	hicomAlArrivalTimDat		OBJECT-TYPE
		SYNTAX		Integer32
		MAX-ACCESS read-only
		STATUS		current
		DESCRIPTION		"Unity A&S Date and time of the arrival of this Hicom alarm. "
		::=	{ hicomAlEntry 12 }
	hicomAlLocation                OBJECT-TYPE
                SYNTAX           DisplayString
                MAX-ACCESS       read-only
                STATUS           current
                DESCRIPTION      "Encoded list of LTUs used for location of the alarm. "
                ::=	{ hicomAlEntry 13 }

-- TEST END new UNITY MIB



hicomAlFiltConfTable	OBJECT-TYPE
	SYNTAX		SEQUENCE OF	HicomAlFiltConfEntry
	MAX-ACCESS	not-accessible
	STATUS		current
	DESCRIPTION	"The table of configured Hicom alarm filters."
	::=	{ hicomAlarms 3 }

	hicomAlFiltConfEntry	OBJECT-TYPE
		SYNTAX		HicomAlFiltConfEntry
		MAX-ACCESS	not-accessible
		STATUS		current
		DESCRIPTION	"Each entry specifies a	filter for a 
				certain type of Hicom alarm."
		INDEX 		{ hicomAlFiltConfPabxId, hicomAlFiltConfGroup, 
				hicomAlFiltConfSubId, hicomAlFiltConfPriority }
		::=	{ hicomAlFiltConfTable 1 }

	HicomAlFiltConfEntry ::=
		SEQUENCE {
			hicomAlFiltConfPabxId	Integer32,
			hicomAlFiltConfGroup	Integer32,
			hicomAlFiltConfSubId	Integer32,
			hicomAlFiltConfPriority	AlarmPriorities,
			hicomAlFiltConfSwitch	AlarmFilterStates,
			hicomAlFiltConfRowStat  RowStatus
		}

	hicomAlFiltConfPabxId	OBJECT-TYPE
		SYNTAX		Integer32 (1..2147483647)
		MAX-ACCESS	not-accessible
		STATUS		current
		DESCRIPTION	"Unique identifier of a Hicom system."
		::=	{ hicomAlFiltConfEntry 1 }

	hicomAlFiltConfGroup	OBJECT-TYPE
		SYNTAX		Integer32 (1..7)
		MAX-ACCESS	not-accessible
		STATUS		current
		DESCRIPTION	"Group identifier of a Hicom alarm."
		::=	{ hicomAlFiltConfEntry 2 }

	hicomAlFiltConfSubId	OBJECT-TYPE
		SYNTAX		Integer32 (0..10000)
		MAX-ACCESS	not-accessible
		STATUS		current
		DESCRIPTION	"Sub-identifier of a Hicom alarm within
				its group."
		::=	{ hicomAlFiltConfEntry 3 }

	hicomAlFiltConfPriority		OBJECT-TYPE
		SYNTAX 		AlarmPriorities
		MAX-ACCESS 	not-accessible
		STATUS 		current
		DESCRIPTION	"Priority of a Hicom alarm."
		::=	{ hicomAlFiltConfEntry 4 }

	hicomAlFiltConfSwitch	OBJECT-TYPE
		SYNTAX 		AlarmFilterStates
		MAX-ACCESS 	read-create
		STATUS 		current
		DESCRIPTION	"Specifies whether filtering for this alarm 
				is switched ON or OFF. If set to ON, no trap 
				will be generated in case the alarm is being 
				SET or RESET."
		::=	{ hicomAlFiltConfEntry 5 }

	hicomAlFiltConfRowStat  OBJECT-TYPE
		SYNTAX		RowStatus
		MAX-ACCESS	read-create
		STATUS		current
		DESCRIPTION
				    "Setting a non-existing RowStat
				     variable to 'createAndGo', creates a new
				     row. If creation was successful, the row
				     gets the status 'active'. Variables of
				     an 'active' row can be read and modified.
				     Setting RowStat to 'destroy' effects 
				     the deletion of the row."
		::= { hicomAlFiltConfEntry 6}

hicomAlarmSubagentLastMsgNo	OBJECT-TYPE
	SYNTAX		Integer32
	MAX-ACCESS	read-only
	STATUS		current
	DESCRIPTION	"The last message, warning or error number 
				issued by the Alarm subagent."
	::=	{ hicomAlarms 4 }

hicomAlarmSubagentLastMsgText	OBJECT-TYPE
	SYNTAX		DisplayString
	MAX-ACCESS	read-only
	STATUS		current
	DESCRIPTION	"The last message, warning or error text
				issued by the Alarm subagent."
	::=	{ hicomAlarms 5 }


-- TEST NEW AlMirrorUpload table

hicomAlMirrorUploadTable    OBJECT-TYPE
    SYNTAX      SEQUENCE OF HicomAlMirrorUploadEntry
    MAX-ACCESS  not-accessible
    STATUS      current
    DESCRIPTION "The table to start an Alarm Upload "
    ::= { hicomAlarms 6 }

    hicomAlMirrorUploadEntry    OBJECT-TYPE
        SYNTAX      HicomAlMirrorUploadEntry
        MAX-ACCESS  not-accessible
        STATUS      current
        DESCRIPTION "Each entry describes a Hicom alarm in detail."
        INDEX  { hicomAlMirrorUploadPabxId }
        ::= { hicomAlMirrorUploadTable 1 }

    HicomAlMirrorUploadEntry ::=
        SEQUENCE {
            hicomAlMirrorUploadPabxId        Integer32,
            hicomAlMirrorUploadMnemonic      DisplayString,
            hicomAlMirrorUploadState         INTEGER,
            hicomAlMirrorUploadStartTimDat   DisplayString,
            hicomAlMirrorUploadErrorTimDat   DisplayString
        }

    hicomAlMirrorUploadPabxId   OBJECT-TYPE
        SYNTAX      Integer32 (1..2147483647)
        MAX-ACCESS  read-only
        STATUS      current
        DESCRIPTION "Unique identifier of a Hicom system."
        ::= { hicomAlMirrorUploadEntry 1 }

    hicomAlMirrorUploadMnemonic   OBJECT-TYPE
        SYNTAX      DisplayString
        MAX-ACCESS  read-only
        STATUS      current
        DESCRIPTION "Mnemonic name of the Hicom system."
        ::= { hicomAlMirrorUploadEntry 2 }

    hicomAlMirrorUploadState   OBJECT-TYPE
        SYNTAX       INTEGER { done (1), error (2), busy (3) }
        MAX-ACCESS  read-write
        STATUS      current
        DESCRIPTION "Status of the AlarmMirror upload
                     done (1), error (2), busy (3)"
        ::= { hicomAlMirrorUploadEntry 3 }

    hicomAlMirrorUploadStartTimDat   OBJECT-TYPE
        SYNTAX      DisplayString
        MAX-ACCESS  read-only
        STATUS      current
        DESCRIPTION "Last successful initiation of an AlarmMirror upload."
        ::= { hicomAlMirrorUploadEntry 4 }

    hicomAlMirrorUploadErrorTimDat   OBJECT-TYPE
        SYNTAX      DisplayString
        MAX-ACCESS  read-only
        STATUS      current
        DESCRIPTION "Last unsuccessful initiation of an AlarmMirror upload."
        ::= { hicomAlMirrorUploadEntry 5 }

    
-- TEST ENDE NEW AlMirrorUpload table


-- conformance statement

hicomAlarmsGroup OBJECT-GROUP
	OBJECTS	{
			hicomAlPabxId, hicomAlGroup, hicomAlSubId,
			hicomAlPriority, hicomAlAbsMod, 
			hicomAlStatus, hicomAlTimDat, hicomAlName, 
			hicomAlReset, 
            hicomAlTimOldDat,
            hicomAlArrivalTimDat,
            hicomAlFilter,
			hicomAlarmsChanges, 
			hicomAlFiltConfSwitch, hicomAlFiltConfRowStat,
			hicomAlarmSubagentLastMsgNo, 
			hicomAlarmSubagentLastMsgText
		}
	STATUS current
	DESCRIPTION
		"Conformance statement of the hicomAlarmsGroup."
	::=	{ hicomAlarmTree 1 }

hicomAlMirrorUploadGroup OBJECT-GROUP
    OBJECTS {
			hicomAlMirrorUploadPabxId,
            hicomAlMirrorUploadMnemonic,
            hicomAlMirrorUploadState ,
            hicomAlMirrorUploadStartTimDat ,
            hicomAlMirrorUploadErrorTimDat 
        }
    STATUS current
    DESCRIPTION
        "Conformance statement of the hicomAlMirrorUploadGroup."
    ::= { hicomAlarmTree 2 }


-- Trap Variables

	hicomAlTrpSysPabxId		OBJECT-TYPE
		SYNTAX		Integer32
		MAX-ACCESS	read-only
		STATUS		current
		DESCRIPTION	"Unique identifier of a Hicom system."
		::=	{ hicomAlarmTrapVariables 1 }

	hicomAlTrpSysMnemonic	OBJECT-TYPE
		SYNTAX		DisplayString
		MAX-ACCESS 	read-only
		STATUS		current
		DESCRIPTION	"Mnemonic name of the Hicom system."
		::=	{ hicomAlarmTrapVariables 2 }

-- Traps 

-- internal Message, Warning and Error

internalMessageAlarmSubagent	NOTIFICATION-TYPE
	OBJECTS	{ hicomAlarmSubagentLastMsgNo, hicomAlarmSubagentLastMsgText }
	STATUS	current
	DESCRIPTION	"An internalMessage trap contains an informational
			 message generated by the subagent."
	::=	{ hicomAlarmTraps 0 }

internalWarningAlarmSubagent	NOTIFICATION-TYPE
	OBJECTS	{ hicomAlarmSubagentLastMsgNo , hicomAlarmSubagentLastMsgText }
	STATUS	current
	DESCRIPTION	"An internalWarning trap contains a warning message
			 generated by a subagent."
	::=	{ hicomAlarmTraps  1 }

internalErrorAlarmSubagent NOTIFICATION-TYPE
	OBJECTS	{ hicomAlarmSubagentLastMsgNo, hicomAlarmSubagentLastMsgText }
	STATUS	current
	DESCRIPTION	"An internalError trap contains an error message
			 generated by a subagent. 
			 After issuing this trap, the agent terminates."
	::=	{ hicomAlarmTraps 2 }

-- alarm reset failure:
hicomAlResetInitFailed	NOTIFICATION-TYPE
	OBJECTS		{ hicomAlTrpSysPabxId, hicomAlTrpSysMnemonic, hicomAlReset }
	STATUS		current
	DESCRIPTION	"A hicomAlResetInitFailed trap signifies that
				the initialization of an alarm reset has failed."
	::=	{ hicomAlarmTraps 20 }

-- alarm upload Mirror failure:
hicomAlUploadMirrorFailed	NOTIFICATION-TYPE
	OBJECTS		{ hicomAlTrpSysPabxId, hicomAlTrpSysMnemonic, hicomAlMirrorUploadErrorTimDat }
	STATUS		current
	DESCRIPTION	"A hicomAlUploadMirrorFailed trap signifies that
				the initialization of an alarm reset has failed."
	::=	{ hicomAlarmTraps 22 }

-- Major Alarms

hicomAlarmOnMajor NOTIFICATION-TYPE
	OBJECTS	{ hicomAlTrpSysPabxId, hicomAlTrpSysMnemonic, hicomAlGroup,
			hicomAlSubId, hicomAlPriority, hicomAlAbsMod,
			hicomAlStatus, hicomAlTimDat, hicomAlName, hicomAlLocation }
	STATUS	current
	DESCRIPTION
		"A hicomAlarmOnMajor trap is sent when a major alarm is set."
	::=	{ hicomAlarmTraps 30 }

hicomAlarmOffMajor NOTIFICATION-TYPE
	OBJECTS	{ hicomAlTrpSysPabxId, hicomAlTrpSysMnemonic, hicomAlGroup,
		hicomAlSubId, hicomAlPriority, hicomAlAbsMod,
		hicomAlStatus, hicomAlTimDat, hicomAlName }
	STATUS	current
	DESCRIPTION	
		"A hicomAlarmOffMajor trap is sent when a major alarm is reset."
	::=	{ hicomAlarmTraps 31 }

-- Minor Alarms

hicomAlarmOnMinor NOTIFICATION-TYPE
	OBJECTS	{ hicomAlTrpSysPabxId, hicomAlTrpSysMnemonic, hicomAlGroup,
		hicomAlSubId, hicomAlPriority, hicomAlAbsMod,
		hicomAlStatus, hicomAlTimDat, hicomAlName, hicomAlLocation }
	STATUS	current
	DESCRIPTION
		"A hicomAlarmOnMinor trap is sent when a minor alarm is set."
	::=	{ hicomAlarmTraps 32 }

hicomAlarmOffMinor NOTIFICATION-TYPE
	OBJECTS	{ hicomAlTrpSysPabxId, hicomAlTrpSysMnemonic, hicomAlGroup,
		hicomAlSubId, hicomAlPriority, hicomAlAbsMod,
		hicomAlStatus, hicomAlTimDat, hicomAlName }
	STATUS	current
	DESCRIPTION
		"A hicomAlarmOffMinor trap is sent when a major alarm is reset."
	::=	{ hicomAlarmTraps 33 }

-- Device Alarms

hicomAlarmOnDevice NOTIFICATION-TYPE
	OBJECTS	{ hicomAlTrpSysPabxId, hicomAlTrpSysMnemonic, hicomAlGroup,
		hicomAlSubId, hicomAlPriority, hicomAlAbsMod,
		hicomAlStatus, hicomAlTimDat, hicomAlName }
	STATUS	current
	DESCRIPTION
		"A hicomAlarmOnDevice trap is sent when a device alarm is set."
	::=	{ hicomAlarmTraps 34 }

hicomAlarmOffDevice	NOTIFICATION-TYPE
	OBJECTS	{ hicomAlTrpSysPabxId, hicomAlTrpSysMnemonic, hicomAlGroup,
		hicomAlSubId, hicomAlPriority, hicomAlAbsMod,
		hicomAlStatus, hicomAlTimDat, hicomAlName }
	STATUS	current
	DESCRIPTION
		"A hicomAlarmOffDevice trap is sent when a device alarm is reset."
	::=	{ hicomAlarmTraps 35 }

-- Alarm on new LTU
hicomAlarmLocationChange  NOTIFICATION-TYPE
	OBJECTS	{ hicomAlTrpSysPabxId, hicomAlTrpSysMnemonic, hicomAlGroup,
		hicomAlSubId, hicomAlPriority, hicomAlAbsMod,
		hicomAlStatus, hicomAlTimDat, hicomAlName, hicomAlLocation }
	STATUS	current
	DESCRIPTION
		"A hicomAlarmLocationChange trap is sent when a hicomAlLocation is changed."
	::=	{ hicomAlarmTraps 36 }

-- BEGIN BLOCK error

-- The hicomErrors MIB subtree provides the errors of the hicom network
-- The hicomAlConfig MIB subtree provides the hicom alarm configuration
-- The MIB subtree consists of the following groups:

hicomAlConfig			OBJECT IDENTIFIER ::= { hicomAlConf 1 }
hicomErrAlConfInfo		OBJECT IDENTIFIER ::= {	hicomAlConf 2 }
-- BEGIN BLOCK discov
hicomAlConfDiscovery	OBJECT IDENTIFIER ::= { hicomAlConf 3 }
-- BEGIN BLOCK error

-- the hicomErrors group

-- the hicomErrorTable

hicomErrorTable	OBJECT-TYPE
	SYNTAX		SEQUENCE	OF HicomErrorEntry
	MAX-ACCESS not-accessible
	STATUS		current
	DESCRIPTION		"The table of Hicom errors."
	::=	{ hicomErrors 1 }

	hicomErrorEntry	OBJECT-TYPE
		SYNTAX		HicomErrorEntry
		MAX-ACCESS not-accessible
		STATUS		current
		DESCRIPTION		"Each entry describes a Hicom error."
		INDEX	{ hicomErrorPabxId,
			hicomErrorAlGroup,
			hicomErrorAlSubId,
			hicomErrorSerialNo }
		::=	{ hicomErrorTable 1 }

	HicomErrorEntry	::=	SEQUENCE {
			hicomErrorPabxId		Integer32,
			hicomErrorAlGroup 		Integer32,
			hicomErrorAlSubId 		Integer32,
			hicomErrorSerialNo		Integer32,
			hicomErrorMsgId			DisplayString,
			hicomErrorPriority		DisplayString,
			hicomErrorAction		DisplayString,
			hicomErrorAbsMod		DisplayString,
			hicomErrorEvent			DisplayString,
			hicomErrorSubevent		DisplayString,
			hicomErrorCardRef		DisplayString,
			hicomErrorBoardVersion		DisplayString,
			hicomErrorFwType 		DisplayString,
			hicomErrorTimDat 		Integer32,
			hicomErrorOrigText 		DisplayString
		}

	hicomErrorPabxId	OBJECT-TYPE
		SYNTAX		Integer32 (1..2147483647)
		MAX-ACCESS	read-only
		STATUS		current
		DESCRIPTION	"Internal identifier of a Hicom system."
		::=	{ hicomErrorEntry 1 }

	hicomErrorAlGroup		OBJECT-TYPE
		SYNTAX		Integer32  (1..7)
		MAX-ACCESS	read-only
		STATUS		current
		DESCRIPTION	"Hicom alarm group this error belongs to."
		::=	{ hicomErrorEntry 2 }

	hicomErrorAlSubId		OBJECT-TYPE
		SYNTAX		Integer32 (0..10000)
		MAX-ACCESS	read-only
		STATUS		current
		DESCRIPTION	"Hicom alarm number within the hicomErrorAlGroup
					this error belongs to."
		::=	{ hicomErrorEntry 3 }

	hicomErrorSerialNo OBJECT-TYPE
		SYNTAX		Integer32 (1..2147483647)
		MAX-ACCESS	read-only
		STATUS		current
		DESCRIPTION	"Internal serial number of a Hicom error."
		::=	{ hicomErrorEntry 4 }

	hicomErrorMsgId		OBJECT-TYPE
		SYNTAX		DisplayString
		MAX-ACCESS	read-only
		STATUS		current
		DESCRIPTION	"Identifier of the Hicom error."
		::=	{ hicomErrorEntry 5 }

	hicomErrorPriority		OBJECT-TYPE
		SYNTAX		DisplayString
		MAX-ACCESS	read-only
		STATUS		current
		DESCRIPTION	"Priority of the Hicom error."
		::=	{ hicomErrorEntry 6 }

	hicomErrorAction		OBJECT-TYPE
		SYNTAX		DisplayString
		MAX-ACCESS	read-only
		STATUS		current
		DESCRIPTION	"Required Hicom system action."
		::=	{ hicomErrorEntry 7 }

	hicomErrorAbsMod		OBJECT-TYPE
		SYNTAX		DisplayString
		MAX-ACCESS	read-only
		STATUS		current
		DESCRIPTION	"Hicom module detecting the error."
		::=	{ hicomErrorEntry 8 }

	hicomErrorEvent	OBJECT-TYPE
		SYNTAX		DisplayString
		MAX-ACCESS	read-only
		STATUS		current
		DESCRIPTION	"Description of the Hicom error."
		::=	{ hicomErrorEntry 9 }

	hicomErrorSubevent		OBJECT-TYPE
		SYNTAX		DisplayString
		MAX-ACCESS	read-only
		STATUS		current
		DESCRIPTION	"Subdescription of the Hicom error."
		::=	{ hicomErrorEntry 10 }

	hicomErrorCardRef		OBJECT-TYPE
		SYNTAX		DisplayString
		MAX-ACCESS	read-only
		STATUS		current
		DESCRIPTION	"Reference to a Hicom board."
		::=	{ hicomErrorEntry 11 }

	hicomErrorBoardVersion	OBJECT-TYPE
		SYNTAX		DisplayString
		MAX-ACCESS	read-only
		STATUS		current
		DESCRIPTION	"Version of that board. "
		::=	{ hicomErrorEntry 12 }

	hicomErrorFwType	OBJECT-TYPE
		SYNTAX		DisplayString
		MAX-ACCESS	read-only
		STATUS		current
		DESCRIPTION	"Firmware of that board."
		::=	{ hicomErrorEntry 13 }

	hicomErrorTimDat	OBJECT-TYPE
		SYNTAX		Integer32
		MAX-ACCESS	read-only
		STATUS		current
		DESCRIPTION	"Date and time of the Hicom error."
		::=	{ hicomErrorEntry 14 }

	hicomErrorOrigText	OBJECT-TYPE
		SYNTAX		DisplayString
		MAX-ACCESS	read-only
		STATUS		current
		DESCRIPTION	"Original message text of the Hicom error."
		::=	{ hicomErrorEntry 15 }


-- the hicomAlConfTable

hicomAlConfTable OBJECT-TYPE
	SYNTAX		SEQUENCE OF HicomAlConfEntry
	MAX-ACCESS	not-accessible
	STATUS		current
	DESCRIPTION	"The table of the Hicom alarm configuration."
	::=	{ hicomAlConfig 1 }

	hicomAlConfEntry		OBJECT-TYPE
		SYNTAX		HicomAlConfEntry
		MAX-ACCESS	not-accessible
		STATUS		current
		DESCRIPTION	"Each entry describes the configuration of a Hicom alarm."
		INDEX	{ hicomAlConfPabxId, hicomAlConfAlGroup, hicomAlConfAlSubId }
		::=	{ hicomAlConfTable 1 }

	HicomAlConfEntry ::=
		SEQUENCE {
			hicomAlConfPabxId		Integer32,
			hicomAlConfAlGroup		Integer32,
			hicomAlConfAlSubId		Integer32,
			hicomAlConfName			DisplayString,
			hicomAlConfThreshold1		Integer32,
			hicomAlConfThreshold2		Integer32,
			hicomAlConfTime1		Integer32,
			hicomAlConfTime2		Integer32,
			hicomAlConfTimeH		Integer32,
			hicomAlConfBase 		Integer32
		}

	hicomAlConfPabxId OBJECT-TYPE
		SYNTAX		Integer32 (1..2147483647)
		MAX-ACCESS	read-only
		STATUS		current
		DESCRIPTION	"Unique identifier of the Hicom system."
		::=	{ hicomAlConfEntry 1 }

	hicomAlConfAlGroup OBJECT-TYPE
		SYNTAX		Integer32 (1..7)
		MAX-ACCESS	read-only
		STATUS		current
		DESCRIPTION	"Group identifier of a Hicom alarm."
		::=	{ hicomAlConfEntry 2 }

	hicomAlConfAlSubId OBJECT-TYPE
		SYNTAX		Integer32 (0..10000)
		MAX-ACCESS	read-only
		STATUS		current
		DESCRIPTION	"Internal group identifier of a Hicom alarm."
		::=	{ hicomAlConfEntry 3 }

	hicomAlConfName	OBJECT-TYPE
		SYNTAX		DisplayString
		MAX-ACCESS	read-only
		STATUS		current
		DESCRIPTION	"Name of the Hicom alarm."
		::=	{ hicomAlConfEntry 4 }

	hicomAlConfThreshold1 OBJECT-TYPE
		SYNTAX		Integer32
		MAX-ACCESS	read-only
		STATUS		current
		DESCRIPTION	"Threshold 'minor' related Hicom errors."
	::=	{ hicomAlConfEntry 5 }

	hicomAlConfThreshold2 OBJECT-TYPE
		SYNTAX		Integer32
		MAX-ACCESS	read-only
		STATUS		current
		DESCRIPTION	"Threshold 'major' for related Hicom errors."
	::=	{ hicomAlConfEntry 6 }

	hicomAlConfTime1 OBJECT-TYPE
		SYNTAX		Integer32
		MAX-ACCESS	read-only
		STATUS		current
		DESCRIPTION	"Interval for the minor threshold."
	::=	{ hicomAlConfEntry 7 }

	hicomAlConfTime2 OBJECT-TYPE
		SYNTAX		Integer32
		MAX-ACCESS	read-only
		STATUS		current
		DESCRIPTION	"Interval for the major threshold."
	::=	{ hicomAlConfEntry 8 }

	hicomAlConfTimeH OBJECT-TYPE
		SYNTAX		Integer32
		MAX-ACCESS	read-only
		STATUS		current
		DESCRIPTION	"Threshold interval for device alarms.
				 Unit of Threshold is hours."
	::=	{ hicomAlConfEntry 9 }

	hicomAlConfBase	OBJECT-TYPE
		SYNTAX		Integer32
		MAX-ACCESS	read-only
		STATUS		current
		DESCRIPTION	"Base value for thresholds in percent."
	::=	{ hicomAlConfEntry 10 }

-- the hicomAlConfPersonTable

hicomAlConfPersonTable OBJECT-TYPE
	SYNTAX		SEQUENCE OF HicomAlConfPersonEntry
	MAX-ACCESS	not-accessible
	STATUS		current
	DESCRIPTION	"The table for the alarm configuration of
				personal (VIP) Hicom alarms."
	::=	{ hicomAlConfig 2 }

	hicomAlConfPersonEntry		OBJECT-TYPE
		SYNTAX		HicomAlConfPersonEntry
		MAX-ACCESS	not-accessible
		STATUS		current
		DESCRIPTION	"Each entry contains an extension number
					for which a VIP alarm is configured."
		INDEX	{ hicomAlConfPersonPabxId,
			hicomAlConfPersonAlGroup,
			hicomAlConfPersonAlSubId,
			hicomAlConfPersonExtNo
		}
		::=	{ hicomAlConfPersonTable 1 }

	HicomAlConfPersonEntry ::=
		SEQUENCE {
			hicomAlConfPersonPabxId 	Integer32,
			hicomAlConfPersonAlGroup	Integer32,
			hicomAlConfPersonAlSubId	Integer32,
			hicomAlConfPersonExtNo	 	DisplayString
		}

	hicomAlConfPersonPabxId	OBJECT-TYPE
		SYNTAX		Integer32 (1..2147483647)
		MAX-ACCESS	read-only
		STATUS		current
		DESCRIPTION	"Unique identifier of the Hicom system."
		::=	{ hicomAlConfPersonEntry 1 }

	hicomAlConfPersonAlGroup OBJECT-TYPE
		SYNTAX		Integer32 (1..7)
		MAX-ACCESS	read-only
		STATUS		current
		DESCRIPTION	"Group identifier of the Hicom alarm."
		::=	{ hicomAlConfPersonEntry 2 }

	hicomAlConfPersonAlSubId OBJECT-TYPE
		SYNTAX		Integer32 (0..10000)
		MAX-ACCESS	read-only
		STATUS		current
		DESCRIPTION	"Internal group identifier of the Hicom alarm."
		::=	{ hicomAlConfPersonEntry 3 }

	hicomAlConfPersonExtNo	OBJECT-TYPE
		SYNTAX		DisplayString
		MAX-ACCESS	read-only
		STATUS		current
		DESCRIPTION	"Extension number."
		::=	{ hicomAlConfPersonEntry 4 }

-- the hicomAlConfTargetTable

hicomAlConfTargetTable OBJECT-TYPE
	SYNTAX		SEQUENCE OF HicomAlConfTargetEntry
	MAX-ACCESS	not-accessible
	STATUS		current
	DESCRIPTION	"The table of the alarm configuration of Hicom target alarms."
	::=	{ hicomAlConfig 3 }

	hicomAlConfTargetEntry		OBJECT-TYPE
		SYNTAX		HicomAlConfTargetEntry
		MAX-ACCESS	not-accessible
		STATUS		current
		DESCRIPTION	"Each entry describes a trunk for which a
					target alarm is configured."
		INDEX	{ 
			hicomAlConfTargetPabxId,
			hicomAlConfTargetAlGroup,
			hicomAlConfTargetAlSubId,
			hicomAlConfTargetLtg,
			hicomAlConfTargetLtu,
			hicomAlConfTargetSlot,
			hicomAlConfTargetTrunkNo
		}
		::=	{ hicomAlConfTargetTable 1 }

	HicomAlConfTargetEntry ::=
		SEQUENCE {
			hicomAlConfTargetPabxId 	Integer32,
			hicomAlConfTargetAlGroup	Integer32,
			hicomAlConfTargetAlSubId	Integer32,
			hicomAlConfTargetLtg		Integer32,
			hicomAlConfTargetLtu		Integer32,
			hicomAlConfTargetSlot		Integer32,
			hicomAlConfTargetTrunkNo	Integer32
		}

	hicomAlConfTargetPabxId	OBJECT-TYPE
		SYNTAX		Integer32 (1..2147483647)
		MAX-ACCESS	read-only
		STATUS		current
		DESCRIPTION	"Unique identifier of the Hicom system."
		::=	{ hicomAlConfTargetEntry 1 }

	hicomAlConfTargetAlGroup OBJECT-TYPE
		SYNTAX		Integer32 (1..7)
		MAX-ACCESS	read-only
		STATUS		current
		DESCRIPTION	"Group identifier of the Hicom alarm."
		::=	{ hicomAlConfTargetEntry 2 }

	hicomAlConfTargetAlSubId OBJECT-TYPE
		SYNTAX		Integer32 (0..10000)
		MAX-ACCESS	read-only
		STATUS		current
		DESCRIPTION	"Internal group identifier of the Hicom alarm."
		::=	{ hicomAlConfTargetEntry 3 }

	hicomAlConfTargetLtg	OBJECT-TYPE
		SYNTAX		Integer32 (1)
		MAX-ACCESS	read-only
		STATUS		current
		DESCRIPTION	"Line Trunk Group of the trunk."
		::=	{ hicomAlConfTargetEntry 4 }

	hicomAlConfTargetLtu	OBJECT-TYPE
		SYNTAX		Integer32 (1..99)
		MAX-ACCESS	read-only
		STATUS		current
		DESCRIPTION	"Line Trunk Unit of the trunk."
		::=	{ hicomAlConfTargetEntry 5 }

	hicomAlConfTargetSlot	OBJECT-TYPE
		SYNTAX		Integer32 (1 .. 121)
		MAX-ACCESS	read-only
		STATUS		current
		DESCRIPTION	"Slot of the trunk."
		::=	{ hicomAlConfTargetEntry 6 }

	hicomAlConfTargetTrunkNo	OBJECT-TYPE
		SYNTAX		Integer32 (1..2147483647)
		MAX-ACCESS	read-only
		STATUS		current
		DESCRIPTION	"Trunk number."
		::=	{ hicomAlConfTargetEntry 7 }

-- the hicomErrAlConfInfo group

hicomErrAlConfSubagentLastMsgNo	OBJECT-TYPE
	SYNTAX		Integer32
	MAX-ACCESS	read-only
	STATUS		current
	DESCRIPTION	"The last message, warning or error number
				issued by the Error/Alarm config subagent."
	::=	{ hicomErrAlConfInfo 1 }

hicomErrAlConfSubagentLastMsgText	OBJECT-TYPE
	SYNTAX		DisplayString
	MAX-ACCESS	read-only
	STATUS		current
	DESCRIPTION	"The last message, warning or error text
				issued by the Error/Alarm config subagent."
	::=	{ hicomErrAlConfInfo 2 }

hicomErrAlConfResultData	OBJECT-TYPE
	SYNTAX		Integer32
	MAX-ACCESS	read-write
	STATUS		current
	DESCRIPTION	"Is used for agent internal communication.
			 Contains the PabxId of a Hicom for which
			 the last discovery process was conveyed.
			 Is SET by the discovery agent and
			 indicates the availability of new discovered data.
			 The new data is to be incorporated by the subagent
			 into the subagent's data base."
	::=	{ hicomErrAlConfInfo 3 }


-- BEGIN BLOCK discov
-- the hicomAlConfDiscovery group

-- the hicomAlConfChanges counter
hicomAlConfChanges		OBJECT-TYPE
	SYNTAX		Counter32
	MAX-ACCESS	read-only
	STATUS		current
	DESCRIPTION	"Indicates changes in the hicomAlConfig group."
	::=	{ hicomAlConfDiscovery 1 }

-- the hicomAlConfDiscov table

hicomAlConfDiscovTable	OBJECT-TYPE
	SYNTAX	SEQUENCE OF HicomAlConfDiscovEntry
	MAX-ACCESS		not-accessible
	STATUS	current
	DESCRIPTION	"This table contains information about the alarm
				configuration discoveries for each managed Hicom."
	::=	{ hicomAlConfDiscovery 2 }

	hicomAlConfDiscovEntry	OBJECT-TYPE
		SYNTAX		HicomAlConfDiscovEntry
		MAX-ACCESS	not-accessible
		STATUS		current
		DESCRIPTION	"Each entry describes the alarm configuration 
					discovery for a specific hicom."
		INDEX	{ hicomAlConfDiscovPabxId }
		::=	{ hicomAlConfDiscovTable 1 }

	HicomAlConfDiscovEntry ::=
		SEQUENCE {
			hicomAlConfDiscovPabxId		Integer32,
			hicomAlConfDiscovPabxMnemonic	DisplayString,
			hicomAlConfDiscovStatus		DiscoveryStates,
			hicomAlConfDiscovMode		DiscoveryModes,
			hicomAlConfDiscovTimDat		DisplayString,
			hicomAlConfDiscovErrTimDat	DisplayString
		}

	hicomAlConfDiscovPabxId	OBJECT-TYPE
		SYNTAX		Integer32 (1..2147483647)
		MAX-ACCESS	read-only
		STATUS		current
		DESCRIPTION	"Unique identifier of the Hicom being discovered."
		::=	{ hicomAlConfDiscovEntry 1 }

	hicomAlConfDiscovPabxMnemonic	OBJECT-TYPE
		SYNTAX	DisplayString
		MAX-ACCESS	read-only
		STATUS		current
		DESCRIPTION	"Name of the Hicom."
		::=	{ hicomAlConfDiscovEntry 2 }

	hicomAlConfDiscovStatus	OBJECT-TYPE
		SYNTAX		DiscoveryStates
		MAX-ACCESS	read-write
		STATUS		current
		DESCRIPTION	"Status of the alarm configuration discovery process."
		::=	{ hicomAlConfDiscovEntry 3 }

	hicomAlConfDiscovMode	OBJECT-TYPE
		SYNTAX		DiscoveryModes
		MAX-ACCESS	read-write
		STATUS		current
		DESCRIPTION	"Mode of the alarm configuration discovery process."
		::=	{ hicomAlConfDiscovEntry 4 }

	hicomAlConfDiscovTimDat	OBJECT-TYPE
		SYNTAX		DisplayString
		MAX-ACCESS	read-only
		STATUS		current
		DESCRIPTION	"Date and time of the last successful discovery."
		::=	{ hicomAlConfDiscovEntry 5 }

	hicomAlConfDiscovErrTimDat	OBJECT-TYPE
		SYNTAX		DisplayString
		MAX-ACCESS	read-only
		STATUS		current
		DESCRIPTION	"Date and time of the last failed discovery."
		::=	{ hicomAlConfDiscovEntry 6 }


-- BEGIN BLOCK error
-- conformance information

-- units of conformance

hicomErrorGroup OBJECT-GROUP
	OBJECTS {
		hicomErrorPabxId, hicomErrorSerialNo,
		hicomErrorMsgId, hicomErrorPriority,
		hicomErrorAction, hicomErrorAbsMod,
		hicomErrorEvent, hicomErrorSubevent,
		hicomErrorCardRef, hicomErrorBoardVersion,
		hicomErrorFwType, hicomErrorTimDat,
		hicomErrorAlGroup, hicomErrorAlSubId,
		hicomErrorOrigText
	}
	STATUS	current
	DESCRIPTION "Conformance statement for hicomErrorGroup."
	::= { hicomErrorTree 1 }

hicomAlConfigGroup	OBJECT-GROUP
	OBJECTS { hicomAlConfPabxId, hicomAlConfAlGroup, hicomAlConfAlSubId,
			hicomAlConfName, hicomAlConfThreshold1, hicomAlConfThreshold2,
			hicomAlConfTime1, hicomAlConfTime2, hicomAlConfTimeH,
			hicomAlConfBase, hicomAlConfTargetPabxId,
			hicomAlConfTargetAlGroup, hicomAlConfTargetAlSubId,
			hicomAlConfTargetLtg, hicomAlConfTargetLtu,
			hicomAlConfTargetSlot, hicomAlConfTargetTrunkNo,
			hicomAlConfPersonPabxId, hicomAlConfPersonAlGroup,
			hicomAlConfPersonAlSubId, hicomAlConfPersonExtNo
		}
	STATUS	current
	DESCRIPTION "Conformance statement for hicomAlConfigGroup."
	::= { hicomAlConfTree 1 }

hicomErrAlConfInfoGroup OBJECT-GROUP
	OBJECTS { hicomErrAlConfSubagentLastMsgNo,
		hicomErrAlConfSubagentLastMsgText,
		hicomErrAlConfResultData
		}
	STATUS		current
	DESCRIPTION "Conformance statement for hicomErrAlConfInfoGroup."
	::= { hicomAlConfTree 2 }

-- BEGIN BLOCK discov
hicomAlConfDiscoveryGroup OBJECT-GROUP
	OBJECTS {
		hicomAlConfChanges,
		hicomAlConfDiscovPabxId,
		hicomAlConfDiscovPabxMnemonic,
		hicomAlConfDiscovStatus,
		hicomAlConfDiscovMode,
		hicomAlConfDiscovTimDat,
		hicomAlConfDiscovErrTimDat
		}
	STATUS	current
	DESCRIPTION "Conformance statement for hicomAlConfDiscoveryGroup. "
	::= { hicomAlConfTree 3 }

-- BEGIN BLOCK error

-- Traps / Notifications
-- Trap Variables

	hicomErrTrpPabxId	OBJECT-TYPE
		SYNTAX		Integer32
		MAX-ACCESS	read-only
		STATUS		current
		DESCRIPTION	"Unique identifier of a Hicom system."
		::=	{ hicomErrorTrapVariables 1 }

	hicomErrTrpMnemonic	OBJECT-TYPE
		SYNTAX		DisplayString
		MAX-ACCESS 	read-only
		STATUS		current
		DESCRIPTION	"Mnemonic name of the Hicom system."
		::=	{ hicomErrorTrapVariables 2 }

-- Agent internal messages, warnings and errors

internalMessageErrAlConfSubagent NOTIFICATION-TYPE
	OBJECTS	{ hicomErrAlConfSubagentLastMsgNo,
		hicomErrAlConfSubagentLastMsgText }
	STATUS	current
	DESCRIPTION	"An internalMessage trap contains an informational
			 message generated by the subagent."
	::=	{ hicomErrorTraps 0 }

internalWarningErrAlConfSubagent NOTIFICATION-TYPE
	OBJECTS	{ hicomErrAlConfSubagentLastMsgNo,
		hicomErrAlConfSubagentLastMsgText }
	STATUS	current
	DESCRIPTION	"An internalWarning trap contains a warning message
			 generated by a subagent."
	::=	{ hicomErrorTraps 1 }

internalErrorErrAlConfSubagent NOTIFICATION-TYPE
	OBJECTS	{ hicomErrAlConfSubagentLastMsgNo,
			hicomErrAlConfSubagentLastMsgText }
	STATUS	current
	DESCRIPTION	"An internalError trap contains an error message
			 generated by a subagent. 
			 After issuing this trap, the agent terminates."
	::=	{ hicomErrorTraps 2 }

-- Hicom related error messages

hicomErrorMsg NOTIFICATION-TYPE
	OBJECTS { hicomErrorPabxId, hicomErrorAlGroup, hicomErrorAlSubId,
		  hicomErrorSerialNo, hicomErrorMsgId, hicomErrorPriority,
		  hicomErrorAction, hicomErrorAbsMod, hicomErrorEvent,
		  hicomErrorSubevent, hicomErrorCardRef, hicomErrorBoardVersion,
		  hicomErrorFwType, hicomErrorTimDat,hicomErrTrpMnemonic 
		}
	STATUS  current
	DESCRIPTION     "A Hicom error message trap contains information 
			 extracted from a Hicom error message"
	 ::=     { hicomErrorTraps 20 }

-- alarm configuration discovery successfully terminated
hicomAlConfDiscovSucc	NOTIFICATION-TYPE
	OBJECTS	{ hicomErrTrpPabxId, hicomErrTrpMnemonic}
	STATUS	current
	DESCRIPTION	"A hicomAlConfDiscovSucc trap indicates the
				successful termination of a discovery process.
				hicomAlConfDiscovPabxId indicates the Pbx involved."
	::=	{ hicomErrorTraps 10 }

-- alarm configuration discovery unsuccessfully terminated

hicomAlConfDiscovErr	NOTIFICATION-TYPE
	OBJECTS	{ hicomErrTrpPabxId, hicomErrTrpMnemonic}
	STATUS	current
	DESCRIPTION	"A hicomAlConfDiscovErr trap signifies the
				unsuccessful termination of a discovery process.
				hicomAlConfDiscovPabxId indicates the Pbx involved."
	::=	{ hicomErrorTraps 11 }

-- alarm configuration discovery is busy

hicomAlConfDiscovBusy	NOTIFICATION-TYPE
	OBJECTS	{ hicomErrTrpPabxId, hicomErrTrpMnemonic}
	STATUS	current
	DESCRIPTION	"A hicomAlConfDiscovBusy trap signifies 
				that a alarm conf discovery process is running.
				hicomAlConfDiscovPabxId indicates the Pbx involved."
	::=	{ hicomErrorTraps 19 }

-- BEGIN BLOCK soft

-- The hicomSoft MIB subtree provides information about software patches

hicomSoftAps	OBJECT IDENTIFIER ::= { hicomSoft 1 }
hicomSoftInfo	OBJECT IDENTIFIER ::= { hicomSoft 2 }
-- BEGIN BLOCK discov
hicomSoftDiscovery	OBJECT IDENTIFIER ::= { hicomSoft 3 }
-- BEGIN BLOCK soft

-- the Aps software table

hicomSoftApsTable		OBJECT-TYPE
	SYNTAX		SEQUENCE OF HicomSoftApsEntry
	MAX-ACCESS	not-accessible
	STATUS		current
	DESCRIPTION	"The table of installed Hicom software systems."
	::=	{ hicomSoftAps 1 }

	hicomSoftApsEntry		OBJECT-TYPE
		SYNTAX		HicomSoftApsEntry
		MAX-ACCESS	not-accessible
		STATUS		current
		DESCRIPTION	"Each entry describes a Hicom software system."
		INDEX	{ hicomSoftApsPabxId, hicomSoftApsID }
		::=	{ hicomSoftApsTable 1 }

	HicomSoftApsEntry ::=
		SEQUENCE {
			hicomSoftApsPabxId		Integer32,
			hicomSoftApsID			OCTET STRING,
			hicomSoftApsPartNo		DisplayString
		}

	hicomSoftApsPabxId		OBJECT-TYPE
		SYNTAX		Integer32 (1..2147483647)
		MAX-ACCESS	read-only
		STATUS		current
		DESCRIPTION	"Unique identifier of the Hicom system."
		::=	{ hicomSoftApsEntry 1 }

	hicomSoftApsID		OBJECT-TYPE
		SYNTAX		OCTET STRING (SIZE (0..64))
		MAX-ACCESS	read-only
		STATUS		current
		DESCRIPTION	"Identifier of the software package."
		::=	{ hicomSoftApsEntry 2 }

	hicomSoftApsPartNo	OBJECT-TYPE
		SYNTAX		DisplayString
		MAX-ACCESS	read-only
		STATUS		current
		DESCRIPTION	"Siemens part number of the software package."
		::=	{ hicomSoftApsEntry 3 }

-- the software patch table

hicomSoftPatchTable		OBJECT-TYPE
	SYNTAX		SEQUENCE OF HicomSoftPatchEntry
	MAX-ACCESS	not-accessible
	STATUS		current
	DESCRIPTION	"The table of installed Hicom software patches."
	::=	{ hicomSoftAps 2 }

	hicomSoftPatchEntry		OBJECT-TYPE
		SYNTAX		HicomSoftPatchEntry
		MAX-ACCESS	not-accessible
		STATUS		current
		DESCRIPTION	"Each entry describes a software patch."
		INDEX		{ hicomSoftPatchPabxId, hicomSoftPatchNo }
		::=	{ hicomSoftPatchTable 1 }

	HicomSoftPatchEntry	::=
		SEQUENCE {
			hicomSoftPatchPabxId	Integer32,
			hicomSoftPatchNo		OCTET STRING,
			hicomSoftPatchHWMod		DisplayString,
			hicomSoftPatchActType	DisplayString,
			hicomSoftPatchGroup	DisplayString
		}

	hicomSoftPatchPabxId	OBJECT-TYPE
		SYNTAX		Integer32 (1..2147483647)
		MAX-ACCESS	read-only
		STATUS		current
		DESCRIPTION	"Unique identifier of the Hicom system."
		::=	{ hicomSoftPatchEntry 1 }

	hicomSoftPatchNo		OBJECT-TYPE
		SYNTAX		OCTET STRING (SIZE (0..64))
		MAX-ACCESS	read-only
		STATUS		current
		DESCRIPTION	"Identifier of the software patch."
		::=	{ hicomSoftPatchEntry 2 }

	hicomSoftPatchHWMod		OBJECT-TYPE
		SYNTAX		DisplayString
		MAX-ACCESS	read-only
		STATUS		current
		DESCRIPTION	"Identification of a hardware module the patch is for."
		::=	{ hicomSoftPatchEntry 3 }

	hicomSoftPatchActType		OBJECT-TYPE
		SYNTAX		DisplayString
		MAX-ACCESS	read-only
		STATUS		current
		DESCRIPTION	"Activation state of patch."
		::=	{ hicomSoftPatchEntry 4 }

	hicomSoftPatchGroup		OBJECT-TYPE
		SYNTAX		DisplayString
		MAX-ACCESS	read-only
		STATUS		current
		DESCRIPTION	"Group identifier of a patch."
		::=	{ hicomSoftPatchEntry 5 }

-- The hicomSWInfo group

hicomSoftSubagentLastMsgNo OBJECT-TYPE
	SYNTAX		Integer32
	MAX-ACCESS	read-only
	STATUS		current
	DESCRIPTION	"The last message, warning or error number 
				issued by the Software subagent."
	::=	{ hicomSoftInfo 1 }

hicomSoftSubagentLastMsgText	OBJECT-TYPE
	SYNTAX		OCTET STRING
	MAX-ACCESS	read-only
	STATUS		current
	DESCRIPTION	"The last message, warning or error text
				issued by the Software subagent."
	::=	{ hicomSoftInfo 2 }

hicomSoftResultData	OBJECT-TYPE
	SYNTAX		Integer32
	MAX-ACCESS	read-write
	STATUS		current
	DESCRIPTION	"Is used for agent internal communication.
			 Contains the PabxId of a Hicom for which
			 the last discovery process was conveyed.
			 Is SET by the discovery agent and
			 indicates the availability of new discovered data.
			 The new data is to be incorporated by the subagent
			 into the subagent's data base."
	::=	{ hicomSoftInfo 3 }

-- BEGIN BLOCK discov
hicomSoftChanges		OBJECT-TYPE
	SYNTAX		Counter32
	MAX-ACCESS	read-only
	STATUS		current
	DESCRIPTION	"Indicates changes in the hicomSoft group."
	::=	{ hicomSoftDiscovery 1 }

-- the hicomSoftDiscov table

hicomSoftDiscovTable	OBJECT-TYPE
	SYNTAX	SEQUENCE OF HicomSoftDiscovEntry
	MAX-ACCESS		not-accessible
	STATUS	current
	DESCRIPTION	"This table contains information about the software
				discoveries for each managed Hicom."
	::=	{ hicomSoftDiscovery 2 }

	hicomSoftDiscovEntry	OBJECT-TYPE
		SYNTAX		HicomSoftDiscovEntry
		MAX-ACCESS	not-accessible
		STATUS		current
		DESCRIPTION	"Each entry describes the software 
					discovery for a specific hicom."
		INDEX	{ hicomSoftDiscovPabxId }
		::=	{ hicomSoftDiscovTable 1 }

	HicomSoftDiscovEntry ::=
		SEQUENCE {
			hicomSoftDiscovPabxId		Integer32,
			hicomSoftDiscovPabxMnemonic	DisplayString,
			hicomSoftDiscovStatus		DiscoveryStates,
			hicomSoftDiscovMode		DiscoveryModes,
			hicomSoftDiscovTimDat		DisplayString,
			hicomSoftDiscovErrTimDat	DisplayString
		}

	hicomSoftDiscovPabxId	OBJECT-TYPE
		SYNTAX		Integer32  (1..2147483647)
		MAX-ACCESS	read-only
		STATUS		current
		DESCRIPTION	"Unique identifier of the Hicom being discovered."
		::=	{ hicomSoftDiscovEntry 1 }

	hicomSoftDiscovPabxMnemonic	OBJECT-TYPE
		SYNTAX	DisplayString
		MAX-ACCESS	read-only
		STATUS		current
		DESCRIPTION	"Name of the Hicom."
		::=	{ hicomSoftDiscovEntry 2 }

	hicomSoftDiscovStatus	OBJECT-TYPE
		SYNTAX		DiscoveryStates
		MAX-ACCESS	read-write
		STATUS		current
		DESCRIPTION	"Status of the software discovery process."
		::=	{ hicomSoftDiscovEntry 3 }

	hicomSoftDiscovMode	OBJECT-TYPE
		SYNTAX		DiscoveryModes
		MAX-ACCESS	read-write
		STATUS		current
		DESCRIPTION	"Mode of the software discovery process."
		::=	{ hicomSoftDiscovEntry 4 }

	hicomSoftDiscovTimDat	OBJECT-TYPE
		SYNTAX		DisplayString
		MAX-ACCESS	read-only
		STATUS		current
		DESCRIPTION	"Date and time of the last successful software discovery."
		::=	{ hicomSoftDiscovEntry 5 }

	hicomSoftDiscovErrTimDat	OBJECT-TYPE
		SYNTAX		DisplayString
		MAX-ACCESS	read-only
		STATUS		current
		DESCRIPTION	"Date and time of the last failed software discovery."
		::=	{ hicomSoftDiscovEntry 6 }

-- conformance information

-- units of conformance
-- BEGIN BLOCK soft
hicomSoftGroup		OBJECT-GROUP
	OBJECTS	{ hicomSoftApsPabxId, hicomSoftApsID, hicomSoftPatchNo,
			hicomSoftApsPartNo, hicomSoftPatchHWMod, hicomSoftPatchActType,
			hicomSoftPatchGroup, hicomSoftPatchPabxId }
	STATUS		current
	DESCRIPTION	"Conformance statement for hicomSoftGroup."
	::=	{ hicomSoftTree 1 }

hicomSoftInfoGroup	OBJECT-GROUP
	OBJECTS	{
		hicomSoftSubagentLastMsgNo,
		hicomSoftSubagentLastMsgText,
		hicomSoftResultData
	}
	STATUS		current
	DESCRIPTION	"Conformance statement for hicomSoftInfoGroup."
	::=	{ hicomSoftTree 2 }

-- BEGIN BLOCK discov
hicomSoftDiscoveryGroup	OBJECT-GROUP
	OBJECTS {
		hicomSoftChanges,
		hicomSoftDiscovPabxId,
		hicomSoftDiscovPabxMnemonic,
		hicomSoftDiscovStatus,
		hicomSoftDiscovMode,
		hicomSoftDiscovTimDat,
		hicomSoftDiscovErrTimDat
	}
	STATUS	current
	DESCRIPTION	"Conformance statement for hicomSoftDiscoveryGroup."
	::= { hicomSoftTree 3 }

-- BEGIN BLOCK soft

-- Traps / Notifications

-- Trap Variables

	hicomSWTrpPabxId	OBJECT-TYPE
		SYNTAX		Integer32
		MAX-ACCESS	read-only
		STATUS		current
		DESCRIPTION	"Unique identifier of a Hicom system."
		::=	{ hicomSWTrapVariables 1 }

	hicomSWTrpPabxMnemonic OBJECT-TYPE
		SYNTAX		DisplayString
		MAX-ACCESS 	read-only
		STATUS		current
		DESCRIPTION	"Mnemonic name of the Hicom system."
		::=	{ hicomSWTrapVariables 2 }

-- Message Traps
internalMessageSWSubagent NOTIFICATION-TYPE
	OBJECTS	{ hicomSoftSubagentLastMsgNo, hicomSoftSubagentLastMsgText }
	STATUS	current
	DESCRIPTION	"An internalMessage trap contains an informational
			 message generated by the subagent."
	::=	{ hicomSWTraps 0 }

-- Warning Traps

internalWarningSWSubagent NOTIFICATION-TYPE
	OBJECTS	{ hicomSoftSubagentLastMsgNo, hicomSoftSubagentLastMsgText }
	STATUS	current
	DESCRIPTION	"An internalWarning trap contains a warning message
			 generated by a subagent."
	::=	{ hicomSWTraps 1 }

-- Error Traps

internalErrorSWSubagent	NOTIFICATION-TYPE
	OBJECTS	{ hicomSoftSubagentLastMsgNo, hicomSoftSubagentLastMsgText }
	STATUS	current
	DESCRIPTION	"An internalError trap contains an error message
			 generated by a subagent. 
			 After issuing this trap, the agent terminates."
	::=	{ hicomSWTraps 2 }

-- software discovery successfully terminated

hicomSoftDiscovSucc	NOTIFICATION-TYPE
	OBJECTS	{ hicomSWTrpPabxId, hicomSWTrpPabxMnemonic }
	STATUS	current
	DESCRIPTION	"A hicomSoftDiscovSucc trap indicates the
				successful termination of a discovery process.
				hicomSoftDiscovPabxId indicates the Pbx involved."
	::=	{ hicomSWTraps 10 }

-- software discovery unsuccessfully terminated

hicomSoftDiscovErr	NOTIFICATION-TYPE
	OBJECTS	{ hicomSWTrpPabxId, hicomSWTrpPabxMnemonic}
	STATUS	current
	DESCRIPTION	"A hicomSoftDiscovErr trap signifies the
				unsuccessful termination of a discovery process.
				hicomSoftDiscovPabxId indicates the Pbx involved."
	::=	{ hicomSWTraps 11 }

-- software discovery is busy

hicomSoftDiscovBusy	NOTIFICATION-TYPE
	OBJECTS	{ hicomSWTrpPabxId, hicomSWTrpPabxMnemonic}
	STATUS	current
	DESCRIPTION	"A hicomSoftDiscovBusy trap signifies
				that a sw discovery process is running.
				hicomSoftDiscovPabxId indicates the Pbx involved."
	::=	{ hicomSWTraps 19 }


-- BEGIN BLOCK hard

-- The hicomHard MIB subtree provides an inventory of hardware components of a
-- hicom network. The MIB subtree falls into the following groups:

hicomCabinets			OBJECT IDENTIFIER ::= {	hicomHard 1 }
hicomPeripherals		OBJECT IDENTIFIER ::= {	hicomHard 2 }
hicomBoards			OBJECT IDENTIFIER ::= {	hicomHard 3 }
hicomHWInfo			OBJECT IDENTIFIER ::= {	hicomHard 4 }

-- BEGIN BLOCK discov
hicomHWDiscovery		OBJECT IDENTIFIER ::= {	hicomHard 5 }

-- BEGIN BLOCK hard

-- The hicomCabinets group provides information on installed cabinets
-- The cabinet table

hicomCabTable	OBJECT-TYPE
	SYNTAX		SEQUENCE OF HicomCabEntry
	MAX-ACCESS	not-accessible
	STATUS		current
	DESCRIPTION		"The table of installed hicom cabinets."
	::=	{ hicomCabinets 1 }

	hicomCabEntry		OBJECT-TYPE
		SYNTAX		HicomCabEntry
		MAX-ACCESS	not-accessible
		STATUS		current
		DESCRIPTION	"Each entry describes a hicom cabinet. "
		INDEX		{ hicomCabPabxId, hicomCabAddr }
		::=	{ hicomCabTable 1 }

	HicomCabEntry ::=
		SEQUENCE {
			hicomCabPabxId		Integer32,
			hicomCabAddr		OCTET STRING,
			hicomCabType		DisplayString,
			hicomCabPartNo		DisplayString,
			hicomCabNumShelves	Integer32
		}

	hicomCabPabxId		OBJECT-TYPE
		SYNTAX		Integer32 (1..2147483647)
		MAX-ACCESS	read-only
		STATUS		current
		DESCRIPTION	"Unique identifier of the Hicom to which 
					the cabinet belongs."
		::=	{ hicomCabEntry 1 }

	hicomCabAddr	OBJECT-TYPE
		SYNTAX		OCTET STRING (SIZE (0..64))
		MAX-ACCESS	read-only
		STATUS		current
		DESCRIPTION	"Unique identifier of the cabinet within the Hicom."
		::=	{ hicomCabEntry 2 }

	hicomCabType	OBJECT-TYPE
		SYNTAX		DisplayString
		MAX-ACCESS	read-only
		STATUS		current
		DESCRIPTION	"Short name of cabinet type."
		::=	{ hicomCabEntry 3 }

	hicomCabPartNo	OBJECT-TYPE
		SYNTAX		DisplayString
		MAX-ACCESS	read-only
		STATUS		current
		DESCRIPTION	"Siemens part number of the cabinet."
		::=	{ hicomCabEntry 4 }

	hicomCabNumShelves	OBJECT-TYPE
		SYNTAX		Integer32
		MAX-ACCESS	read-only
		STATUS		current
		DESCRIPTION	"The number of shelves in a cabinet."
		::=	{ hicomCabEntry 5 }

-- The frame table

hicomFrameTable		OBJECT-TYPE
	SYNTAX		SEQUENCE OF HicomFrameEntry
	MAX-ACCESS	not-accessible
	STATUS		current
	DESCRIPTION	"The table of installed Hicom frames."
	::=	{ hicomCabinets 2 }

	hicomFrameEntry		OBJECT-TYPE
		SYNTAX		HicomFrameEntry
		MAX-ACCESS	not-accessible
		STATUS		current
		DESCRIPTION	"Each entry describes one Hicom frame. "
		INDEX		{ hicomFramePabxId, hicomFrameCabAddr, hicomFrameMntLevel }
		::=	{ hicomFrameTable 1 }

	HicomFrameEntry	::=
		SEQUENCE {
			hicomFramePabxId	Integer32,
			hicomFrameCabAddr	OCTET STRING,
			hicomFrameMntLevel	Integer32,
			hicomFrameType		DisplayString,
			hicomFramePartNo	DisplayString,
			hicomFramePID1		DisplayString,
			hicomFramePID2		DisplayString,
			hicomFramePID3		DisplayString,
			hicomFrameLTU		Integer32,
			hicomFrameIpAddr	DisplayString
		}

	hicomFramePabxId	OBJECT-TYPE
		SYNTAX		Integer32 (1..2147483647)
		MAX-ACCESS	read-only
		STATUS		current
		DESCRIPTION	"Unique identifier of the Hicom to which a frame belongs."
		::=	{ hicomFrameEntry 1 }

	hicomFrameCabAddr	OBJECT-TYPE
		SYNTAX		OCTET STRING (SIZE (0..64))
		MAX-ACCESS	read-only
		STATUS		current
		DESCRIPTION	"Identifier of the cabinet to which a frame belongs."
		::=	{ hicomFrameEntry 2 }

	hicomFrameMntLevel	OBJECT-TYPE
		SYNTAX		Integer32 (0..2147483647)
		MAX-ACCESS	read-only
		STATUS		current
		DESCRIPTION	"Mounting level of the frame in a cabinet. "
		::=	{ hicomFrameEntry 3 }

	hicomFrameType		OBJECT-TYPE
		SYNTAX		DisplayString
		MAX-ACCESS	read-only
		STATUS		current
		DESCRIPTION	"Short name of frame type."
		::=	{ hicomFrameEntry 4 }

	hicomFramePartNo	OBJECT-TYPE
		SYNTAX		DisplayString
		MAX-ACCESS	read-only
		STATUS		current
		DESCRIPTION	"Siemens part number for this frame type."
		::=	{ hicomFrameEntry 5 }

	hicomFramePID1		OBJECT-TYPE
		SYNTAX		DisplayString
		MAX-ACCESS	read-only
		STATUS		current
		DESCRIPTION	"Processor identification - control part A."
		::=	{ hicomFrameEntry 6 }

	hicomFramePID2		OBJECT-TYPE
		SYNTAX		DisplayString
		MAX-ACCESS	read-only
		STATUS		current
		DESCRIPTION	"Processor identification - control part B."
		::=	{ hicomFrameEntry 7 }

	hicomFramePID3		OBJECT-TYPE
		SYNTAX		DisplayString
		MAX-ACCESS	read-only
		STATUS		current
		DESCRIPTION	"Processor identification. "
		::=	{ hicomFrameEntry 8 }

	hicomFrameLTU		OBJECT-TYPE
		SYNTAX		Integer32 (1..99)
		MAX-ACCESS	read-only
		STATUS		current
		DESCRIPTION	"If the shelf houses a LTU, this is the LTU's number."
		::=	{ hicomFrameEntry 9 }

	hicomFrameIpAddr	OBJECT-TYPE
		SYNTAX		DisplayString
		MAX-ACCESS	read-only
		STATUS		current
		DESCRIPTION	"IP-Adress related to a Local Sysytem (LS). "
		::=	{ hicomFrameEntry 10 }


-- hicomPeripherals group

-- The hicom peripherals table, contains information on installed peripherals

hicomPeriphTable	OBJECT-TYPE
	SYNTAX		SEQUENCE OF HicomPeriphEntry
	MAX-ACCESS	not-accessible
	STATUS		current
	DESCRIPTION	"The table of installed devices: disks, tapes etc."
	::=	{ hicomPeripherals 1 }

	hicomPeriphEntry	OBJECT-TYPE
		SYNTAX		HicomPeriphEntry
		MAX-ACCESS	not-accessible
		STATUS		current
		DESCRIPTION	"Each entry describes a device."
		INDEX		{ hicomPeriphPabxId, hicomPeriphContrID, hicomPeriphModule }
		::=	{ hicomPeriphTable 1 }

	HicomPeriphEntry ::=
		SEQUENCE {
			hicomPeriphPabxId	Integer32,
			hicomPeriphContrID	Integer32,
			hicomPeriphModule	OCTET STRING,
			hicomPeriphType		DisplayString,
			hicomPeriphSSNo		DisplayString,
			hicomPeriphSize		Integer32,
			hicomPeriphGran		Integer32
		}

	hicomPeriphPabxId	OBJECT-TYPE
		SYNTAX		Integer32 (1..2147483647)
		MAX-ACCESS	read-only
		STATUS		current
		DESCRIPTION	"Unique identifier of the Hicom to which the
					peripheral device belongs."
		::=	{ hicomPeriphEntry 1 }

	hicomPeriphContrID	OBJECT-TYPE
		SYNTAX		Integer32 (0..2147483647)
		MAX-ACCESS	read-only
		STATUS		current
		DESCRIPTION	"Identifier of the controller the device is connected to."
		::=	{ hicomPeriphEntry 2 }

	hicomPeriphModule	OBJECT-TYPE
		SYNTAX		OCTET STRING  (SIZE (0..64))
		MAX-ACCESS	read-only
		STATUS		current
		DESCRIPTION	"Identifier of the related sever module:
					A1, C1, V1-V3 or T1-T3. "
		::=	{ hicomPeriphEntry 3 }

	hicomPeriphType		OBJECT-TYPE
		SYNTAX		DisplayString
		MAX-ACCESS	read-only
		STATUS		current
		DESCRIPTION	"Abbreviation of the device type: HD, FT, CT ..."
		::=	{ hicomPeriphEntry 4 }

	hicomPeriphSSNo		OBJECT-TYPE
		SYNTAX		DisplayString
		MAX-ACCESS	read-only
		STATUS		current
		DESCRIPTION	"Product identification."
		::=	{ hicomPeriphEntry 5 }

	hicomPeriphSize		OBJECT-TYPE
		SYNTAX		Integer32 (0..2147483647)
		MAX-ACCESS	read-only
		STATUS		current
		DESCRIPTION	"Capacity (MB) of the storage medium."
		::=	{ hicomPeriphEntry 6 }

	hicomPeriphGran		OBJECT-TYPE
		SYNTAX		Integer32 (0..2147483647)
		MAX-ACCESS	read-only
		STATUS		current
		DESCRIPTION	"Sector size of the medium."
		::=	{ hicomPeriphEntry 7 }

-- The hicomBoards group

-- The CDSMTable, describes hicom server module related boards which are
-- currently installed
-- The contents are derived from the Hicom AMO ABFR-CDSM

hicomCDSMTable		OBJECT-TYPE
	SYNTAX		SEQUENCE OF HicomCDSMEntry
	MAX-ACCESS	not-accessible
	STATUS		current
	DESCRIPTION	"The table of hicom CDSM boards."
	::=	{ hicomBoards 1 }

	hicomCDSMEntry		OBJECT-TYPE
		SYNTAX		HicomCDSMEntry
		MAX-ACCESS	not-accessible
		STATUS		current
		DESCRIPTION	"Each entry describes one hardware board."
		INDEX		{ hicomCDSMPabxId, hicomCDSMCabAddr, hicomCDSMMntLevel,
					hicomCDSMSlotAddr}
		::=	{ hicomCDSMTable 1 }

	HicomCDSMEntry ::=
		SEQUENCE {
			hicomCDSMPabxId		Integer32,
			hicomCDSMCabAddr	OCTET STRING,
			hicomCDSMMntLevel	Integer32,
			hicomCDSMSlotAddr	Integer32,
			hicomCDSMPartNo		DisplayString,
			hicomCDSMCode		DisplayString,
			hicomCDSMVers		Integer32,
			hicomCDSMFirmware	DisplayString
		}

	hicomCDSMPabxId		OBJECT-TYPE
		SYNTAX		Integer32 (1..2147483647)
		MAX-ACCESS	read-only
		STATUS		current
		DESCRIPTION	"Identifier of the Hicom to which the Board belongs."
		::=	{ hicomCDSMEntry 1 }

	hicomCDSMCabAddr		OBJECT-TYPE
		SYNTAX		OCTET STRING (SIZE (0..64))
		MAX-ACCESS	read-only
		STATUS		current
		DESCRIPTION	"Identifier of the cabinet to which the board belongs."
		::=	{ hicomCDSMEntry 2 }

	hicomCDSMMntLevel	OBJECT-TYPE
		SYNTAX		Integer32 (0..2147483647)
		MAX-ACCESS	read-only
		STATUS		current
		DESCRIPTION	"Mounting level of the frame containing the board. "
		::=	{ hicomCDSMEntry 3 }

	hicomCDSMSlotAddr	OBJECT-TYPE
		SYNTAX		Integer32 (0..2147483647)
		MAX-ACCESS	read-only
		STATUS		current
		DESCRIPTION	"Slot address for the board within its frame."
		::=	{ hicomCDSMEntry 4 }

	hicomCDSMPartNo		OBJECT-TYPE
		SYNTAX		DisplayString
		MAX-ACCESS	read-only
		STATUS		current
		DESCRIPTION	"Siemens part number of the installed board."
		::=	{ hicomCDSMEntry 5 }

	hicomCDSMCode	OBJECT-TYPE
		SYNTAX		DisplayString
		MAX-ACCESS	read-only
		STATUS		current
		DESCRIPTION	"Short name of the board."
		::=	{ hicomCDSMEntry 6 }

	hicomCDSMVers	OBJECT-TYPE
		SYNTAX		Integer32 (0..2147483647)
		MAX-ACCESS	read-only
		STATUS		current
		DESCRIPTION	"Version number of the board."
		::=	{ hicomCDSMEntry 7 }

	hicomCDSMFirmware	OBJECT-TYPE
		SYNTAX		DisplayString
		MAX-ACCESS	read-only
		STATUS		current
		DESCRIPTION	"Firmware version installed on the board."
		::=	{ hicomCDSMEntry 8 }

-- The CDSUTable, describes hicom SWU-CC related boards which are
-- currently installed
-- The contents are derived from the Hicom AMO ABFR-CDSU

hicomCDSUTable		OBJECT-TYPE
	SYNTAX		SEQUENCE OF HicomCDSUEntry
	MAX-ACCESS	not-accessible
	STATUS		current
	DESCRIPTION	"The table of hicom CDSU boards."
	::=	{ hicomBoards 2 }

	hicomCDSUEntry		OBJECT-TYPE
		SYNTAX		HicomCDSUEntry
		MAX-ACCESS	not-accessible
		STATUS		current
		DESCRIPTION	"Each entry describes one CDSU Board."
		INDEX	{ hicomCDSUPabxId, hicomCDSUCabAddr, hicomCDSUMntLevel,
				hicomCDSUSlotAddr}
		::=	{ hicomCDSUTable 1 }

	HicomCDSUEntry ::=
		SEQUENCE {
			hicomCDSUPabxId		Integer32,
			hicomCDSUCabAddr	OCTET STRING,
			hicomCDSUMntLevel	Integer32,
			hicomCDSUSlotAddr	Integer32,
			hicomCDSUPartNo		DisplayString,
			hicomCDSUCode		DisplayString,
			hicomCDSUVers		Integer32,
			hicomCDSUFirmware	DisplayString
		}

	hicomCDSUPabxId		OBJECT-TYPE
		SYNTAX		Integer32 (1..2147483647)
		MAX-ACCESS	read-only
		STATUS		current
		DESCRIPTION	"The identifier of the Hicom to which the board belongs."
		::=	{ hicomCDSUEntry 1 }

	hicomCDSUCabAddr	OBJECT-TYPE
		SYNTAX		OCTET STRING (SIZE(0..64))
		MAX-ACCESS	read-only
		STATUS		current
		DESCRIPTION	"Identifier of the cabinet to which the board belongs."
		::=	{ hicomCDSUEntry 2 }

	hicomCDSUMntLevel	OBJECT-TYPE
		SYNTAX		Integer32 (0..2147483647)
		MAX-ACCESS	read-only
		STATUS		current
		DESCRIPTION	"Mounting level of the frame containing the board. "
		::=	{ hicomCDSUEntry 3 }

	hicomCDSUSlotAddr	OBJECT-TYPE
		SYNTAX		Integer32 (0..121)
		MAX-ACCESS	read-only
		STATUS		current
		DESCRIPTION	"Slot address for the board within its frame."
		::=	{ hicomCDSUEntry 4 }

	hicomCDSUPartNo		OBJECT-TYPE
		SYNTAX		DisplayString
		MAX-ACCESS	read-only
		STATUS		current
		DESCRIPTION	"Siemens part number of the installed board."
		::=	{ hicomCDSUEntry 5 }

	hicomCDSUCode	OBJECT-TYPE
		SYNTAX		DisplayString
		MAX-ACCESS	read-only
		STATUS		current
		DESCRIPTION	"Short name of the board."
		::=	{ hicomCDSUEntry 6 }

	hicomCDSUVers		OBJECT-TYPE
		SYNTAX		Integer32
		MAX-ACCESS	read-only
		STATUS		current
		DESCRIPTION	"Version number of the board."
		::=	{ hicomCDSUEntry 7 }

	hicomCDSUFirmware	OBJECT-TYPE
		SYNTAX		DisplayString
		MAX-ACCESS	read-only
		STATUS		current
		DESCRIPTION	"Firmware version installed on the board."
		::=	{ hicomCDSUEntry 8 }

-- The BCSMTable, describes service module related boards for line control/	line bus control
-- Shows configured board type and actual installed board type
-- The contents are derived from the Hicom AMO ABFR-BCSM

hicomBCSMTable	OBJECT-TYPE
	SYNTAX		SEQUENCE OF HicomBCSMEntry
	MAX-ACCESS	not-accessible
	STATUS		current
	DESCRIPTION	"The table of hicom BCSM boards."
	::=	{ hicomBoards 3 }

	hicomBCSMEntry		OBJECT-TYPE
		SYNTAX		HicomBCSMEntry
		MAX-ACCESS	not-accessible
		STATUS		current
		DESCRIPTION	"Each entry describes one HW board."
		INDEX		{ hicomBCSMPabxId, hicomBCSMMod, hicomBCSMSlotAddr}
		::=	{ hicomBCSMTable 1 }

	HicomBCSMEntry ::=
		SEQUENCE {
			hicomBCSMPabxId		Integer32,
			hicomBCSMMod		OCTET STRING,
			hicomBCSMSlotAddr	Integer32,
			hicomBCSMConfBoard	DisplayString,
			hicomBCSMCode		DisplayString,
			hicomBCSMInstBoard	DisplayString,
			hicomBCSMVers		Integer32,
			hicomBCSMFirmware	DisplayString,
			hicomBCSMStatus		DisplayString
		}

	hicomBCSMPabxId		OBJECT-TYPE
		SYNTAX		Integer32 (1..2147483647)
		MAX-ACCESS	read-only
		STATUS		current
		DESCRIPTION	"The identifier of the Hicom to which the board belongs."
		::=	{ hicomBCSMEntry 1 }

	hicomBCSMMod	OBJECT-TYPE
		SYNTAX		OCTET STRING (SIZE (0..64))
		MAX-ACCESS	read-only
		STATUS		current
		DESCRIPTION	"Identifier of the module to which the board belongs."
		::=	{ hicomBCSMEntry 2 }

	hicomBCSMSlotAddr	OBJECT-TYPE
		SYNTAX		Integer32 (0..121)
		MAX-ACCESS	read-only
		STATUS		current
		DESCRIPTION	"Address of slot containing the board. "
		::=	{ hicomBCSMEntry 3 }

	hicomBCSMConfBoard	OBJECT-TYPE
		SYNTAX		DisplayString
		MAX-ACCESS	read-only
		STATUS		current
		DESCRIPTION	"Siemens part number of the configured board."
		::=	{ hicomBCSMEntry 4 }

	hicomBCSMCode		OBJECT-TYPE
		SYNTAX		DisplayString
		MAX-ACCESS	read-only
		STATUS		current
		DESCRIPTION	"Short name of the board."
		::=	{ hicomBCSMEntry 5 }

	hicomBCSMInstBoard OBJECT-TYPE
		SYNTAX		DisplayString
		MAX-ACCESS	read-only
		STATUS		current
		DESCRIPTION	"Siemens part number of the installed board.
					This information may in fact differ from that in
					hicomBCSMConfBoard."
		::=	{ hicomBCSMEntry 6 }

	hicomBCSMVers		OBJECT-TYPE
		SYNTAX		Integer32 (0..2147483647)
		MAX-ACCESS	read-only
		STATUS		current
		DESCRIPTION	"Version number of the board."
		::=	{ hicomBCSMEntry 7 }

	hicomBCSMFirmware	OBJECT-TYPE
		SYNTAX		DisplayString
		MAX-ACCESS	read-only
		STATUS		current
		DESCRIPTION	"Firmware version installed on the board."
		::=	{ hicomBCSMEntry 8 }

	hicomBCSMStatus		OBJECT-TYPE
		SYNTAX		DisplayString
		MAX-ACCESS	read-only
		STATUS		current
		DESCRIPTION	"State of the board: INS, READY ..."
		::=	{ hicomBCSMEntry 9 }

-- The BCSUTable describes	LTG/LTU	related boards
-- Shows configured board type and actually installed board type
-- The contents are derived from the Hicom AMO ABFR-BCSU

hicomBCSUTable		OBJECT-TYPE
	SYNTAX		SEQUENCE OF HicomBCSUEntry
	MAX-ACCESS	not-accessible
	STATUS		current
	DESCRIPTION	"The table of hicom BCSU boards."
	::=	{ hicomBoards 4 }

	hicomBCSUEntry		OBJECT-TYPE
		SYNTAX		HicomBCSUEntry
		MAX-ACCESS	not-accessible
		STATUS		current
		DESCRIPTION	"Each entry describes one HW board."
		INDEX		{ hicomBCSUPabxId, hicomBCSULTG, hicomBCSULTU,
					hicomBCSUSlotAddr}
		::=	{ hicomBCSUTable 1 }

	HicomBCSUEntry ::=
		SEQUENCE {
			hicomBCSUPabxId		Integer32,
			hicomBCSULTG		Integer32,
			hicomBCSULTU		Integer32,
			hicomBCSUSlotAddr	Integer32,
			hicomBCSUConfBoard	DisplayString,
			hicomBCSUCode		DisplayString,
			hicomBCSUInstBoard	DisplayString,
			hicomBCSUVers		Integer32,
			hicomBCSUFirmware	DisplayString,
			hicomBCSUStatus		DisplayString
		}

	hicomBCSUPabxId		OBJECT-TYPE
		SYNTAX		Integer32 (1..2147483647)
		MAX-ACCESS	read-only
		STATUS		current
		DESCRIPTION	"The identifier of the Hicom to which the board belongs."
		::=	{ hicomBCSUEntry 1 }

	hicomBCSULTG	OBJECT-TYPE
		SYNTAX		Integer32 (1)
		MAX-ACCESS	read-only
		STATUS		current
		DESCRIPTION	"Identifier of the LTG to which the LTU belongs."
		::=	{ hicomBCSUEntry 2 }

	hicomBCSULTU	OBJECT-TYPE
		SYNTAX		Integer32 (1..99)
		MAX-ACCESS	read-only
		STATUS		current
		DESCRIPTION	"Identifier of the LTU to which the board belongs. "
		::=	{ hicomBCSUEntry 3 }

	hicomBCSUSlotAddr	OBJECT-TYPE
		SYNTAX		Integer32 (1..121)
		MAX-ACCESS	read-only
		STATUS		current
		DESCRIPTION	"Address of slot containing the board."
		::=	{ hicomBCSUEntry 4 }

	hicomBCSUConfBoard	OBJECT-TYPE
		SYNTAX		DisplayString
		MAX-ACCESS	read-only
		STATUS		current
		DESCRIPTION	"Siemens part number of the configured board."
		::=	{ hicomBCSUEntry 5 }

	hicomBCSUCode	OBJECT-TYPE
		SYNTAX		DisplayString
		MAX-ACCESS	read-only
		STATUS		current
		DESCRIPTION	"Short name of the board."
		::=	{ hicomBCSUEntry 6 }

	hicomBCSUInstBoard OBJECT-TYPE
		SYNTAX		DisplayString
		MAX-ACCESS	read-only
		STATUS		current
		DESCRIPTION	"Siemens part number of the installed board.
					This information may in fact differ from that in
					hicomBCSMConfBoard."
		::=	{ hicomBCSUEntry 7 }

	hicomBCSUVers		OBJECT-TYPE
		SYNTAX		Integer32
		MAX-ACCESS	read-only
		STATUS		current
		DESCRIPTION	"Version number of the board."
		::=	{ hicomBCSUEntry 8 }

	hicomBCSUFirmware	OBJECT-TYPE
		SYNTAX		DisplayString
		MAX-ACCESS	read-only
		STATUS		current
		DESCRIPTION	"Firmware version installed on the board."
		::=	{ hicomBCSUEntry 9 }

	hicomBCSUStatus		OBJECT-TYPE
		SYNTAX		DisplayString
		MAX-ACCESS	read-only
		STATUS		current
		DESCRIPTION	"State of the board: INS, READY ..."
		::=	{ hicomBCSUEntry 10 }

-- The hicomHWDiscovery group

-- The hicomHWChanges counter

-- BEGIN BLOCK discov
hicomHWChanges		OBJECT-TYPE
	SYNTAX		Counter32
	MAX-ACCESS	read-only
	STATUS		current
	DESCRIPTION	"Indicates the number of finished hardware discoveries -
				corresponds to the number of hicomHWDiscovXXX traps sent out."
		::=	{ hicomHWDiscovery 1 }

-- The hicomHWDiscovTable table

hicomHWDiscovTable	OBJECT-TYPE
	SYNTAX		SEQUENCE OF HicomHWDiscovEntry
	MAX-ACCESS	not-accessible
	STATUS		current
	DESCRIPTION	"The table describing the status concerning
				discovery of HW information."
	::=	{ hicomHWDiscovery 2 }

	hicomHWDiscovEntry	OBJECT-TYPE
		SYNTAX		HicomHWDiscovEntry
		MAX-ACCESS	not-accessible
		STATUS		current
		DESCRIPTION	"Each entry describes the status of the discovery process
					for a specific hicom."
		INDEX		{ hicomHWDiscovPabxId }
		::=	{ hicomHWDiscovTable 1 }

	HicomHWDiscovEntry ::=
		SEQUENCE {
			hicomHWDiscovPabxId	Integer32,
			hicomHWDiscovPabxMnemonic	DisplayString,
			hicomHWDiscovStatus	DiscoveryStates,
			hicomHWDiscovMode	DiscoveryModes,
			hicomHWDiscovTimDat	DisplayString,
			hicomHWDiscovErrTimDat  DisplayString
		}

	hicomHWDiscovPabxId	OBJECT-TYPE
		SYNTAX	Integer32 (1..2147483647)
		MAX-ACCESS		read-only
		STATUS	current
		DESCRIPTION		"Unique identifier of the Hicom being discovered."
		::=	{ hicomHWDiscovEntry 1 }

	hicomHWDiscovPabxMnemonic	OBJECT-TYPE
		SYNTAX	DisplayString
		MAX-ACCESS		read-only
		STATUS	current
		DESCRIPTION		"Name of the Hicom system. "
		::=	{ hicomHWDiscovEntry 2 }

	hicomHWDiscovStatus	OBJECT-TYPE
		SYNTAX		DiscoveryStates
		MAX-ACCESS	read-write
		STATUS		current
		DESCRIPTION	"Status of HW discovery process.
				A Manager may initiate a discovery by setting
				this variable to value busy.
				The other values are set by the agent.	"
		::=	{ hicomHWDiscovEntry 3 }

	hicomHWDiscovMode	OBJECT-TYPE
		SYNTAX		DiscoveryModes
		MAX-ACCESS	read-write
		STATUS		current
		DESCRIPTION	"Mode of discovery process."
		::=	{ hicomHWDiscovEntry 4 }

	hicomHWDiscovTimDat	OBJECT-TYPE
		SYNTAX	DisplayString
		MAX-ACCESS		read-only
		STATUS	current
		DESCRIPTION		"Date and time (year, month, day, hour, minute, second)
				the last successful discovery action was performed for the	Hicom."
		::=	{ hicomHWDiscovEntry 5 }

	hicomHWDiscovErrTimDat OBJECT-TYPE
		SYNTAX	DisplayString
		MAX-ACCESS		read-only
		STATUS	current
		DESCRIPTION		"Date and time (year, month, day, hour, minute, second)
				the last failed discovery action was performed for the	Hicom."
		::=	{ hicomHWDiscovEntry 6 }

-- BEGIN BLOCK hard
-- The hicomHWInfo group

	hicomHardSubagentLastMsgNo	OBJECT-TYPE
		SYNTAX		Integer32
		MAX-ACCESS	read-only
		STATUS		current
		DESCRIPTION	"The last message, warning or error number 
					issued by the Hardware subagent."
		::=	{ hicomHWInfo 1 }

	hicomHardSubagentLastMsgText	OBJECT-TYPE
		SYNTAX		OCTET STRING
		MAX-ACCESS	read-only
		STATUS		current
		DESCRIPTION	"The last message, warning or error text
					issued by the Hardware subagent."
		::=	{ hicomHWInfo 2 }

	hicomHardSubagentResultData	OBJECT-TYPE
	        SYNTAX		Integer32
	        MAX-ACCESS	read-write
	        STATUS		current
	        DESCRIPTION	"Is used for agent internal communication.
			 Contains the PabxId of a Hicom for which
			 the last discovery process was conveyed.
			 Is SET by the discovery agent and
			 indicates the availability of new discovered data.
			 The new data is to be incorporated by the subagent
			 into the subagent's data base."
		::=	{ hicomHWInfo 3 }


-- Conformance information

-- Units of conformance

	hicomCabinetsGroup		OBJECT-GROUP
		OBJECTS	{ hicomCabPabxId, hicomCabAddr, hicomCabType,
				hicomCabPartNo, hicomCabNumShelves,
				hicomFramePabxId, hicomFrameCabAddr, hicomFrameMntLevel,
				hicomFrameType, hicomFramePartNo, hicomFramePID1,
				hicomFramePID2, hicomFramePID3, hicomFrameLTU,
                hicomFrameIpAddr
			}
		STATUS		current
		DESCRIPTION	"Conformance statement for hicomCabinetsGroup."
		::=	{ hicomHardTree 1 }

	hicomPeriperalsGroup	OBJECT-GROUP
		OBJECTS	{
				hicomPeriphPabxId, hicomPeriphContrID, hicomPeriphModule,
				hicomPeriphType, hicomPeriphSSNo, hicomPeriphSize,
				hicomPeriphGran
			}
		STATUS		current
		DESCRIPTION	"Conformance statement for hicomPeriperalsGroup."
		::=	{ hicomHardTree 2 }

	hicomBoardsGroup	OBJECT-GROUP
		OBJECTS	{
				hicomCDSMPabxId, hicomCDSMCabAddr, hicomCDSMMntLevel,
				hicomCDSMSlotAddr, hicomCDSMPartNo, hicomCDSMCode,
				hicomCDSMVers, hicomCDSMFirmware,
				hicomCDSUPabxId, hicomCDSUCabAddr, hicomCDSUMntLevel,
				hicomCDSUSlotAddr, hicomCDSUPartNo, hicomCDSUCode,
				hicomCDSUVers, hicomCDSUFirmware,
				hicomBCSMPabxId, hicomBCSMMod, hicomBCSMSlotAddr,
				hicomBCSMConfBoard, hicomBCSMCode, hicomBCSMInstBoard,
				hicomBCSMVers, hicomBCSMFirmware, hicomBCSMStatus,
				hicomBCSUPabxId, hicomBCSULTG, hicomBCSULTU,
				hicomBCSUSlotAddr, hicomBCSUConfBoard, hicomBCSUCode,
				hicomBCSUInstBoard, hicomBCSUVers, hicomBCSUFirmware,
				hicomBCSUStatus
			}
		STATUS		current
		DESCRIPTION	"Conformance statement for hicomBoardsGroup."
		::=	{ hicomHardTree 3 }

	hicomHWInfoGroup		OBJECT-GROUP
		OBJECTS	{
				hicomHardSubagentLastMsgNo,
				hicomHardSubagentLastMsgText,
				hicomHardSubagentResultData
			}
		STATUS		current
		DESCRIPTION	"Conformance statement for hicomHWInfoGroup."
		::=	{ hicomHardTree 4 }

-- BEGIN BLOCK discov
	hicomHWDiscoveryGroup	OBJECT-GROUP
		OBJECTS	{
			hicomHWChanges,
			hicomHWDiscovPabxId,
			hicomHWDiscovPabxMnemonic,
			hicomHWDiscovStatus,
			hicomHWDiscovMode,
			hicomHWDiscovTimDat,
			hicomHWDiscovErrTimDat
		}
		STATUS		current
		DESCRIPTION	"Conformance statement for hicomHWDiscoveryGroup. "
		::=	{ hicomHardTree 5 }
-- BEGIN BLOCK hard
-- Traps / Notifications

-- Trap Variables

	hicomHWTrpPabxId	OBJECT-TYPE
		SYNTAX		Integer32
		MAX-ACCESS	read-only
		STATUS		current
		DESCRIPTION	"Unique identifier of a Hicom system."
		::=	{ hicomHWTrapVariables 1 }

	hicomHWTrpPabxMnemonic	OBJECT-TYPE
		SYNTAX		DisplayString
		MAX-ACCESS 	read-only
		STATUS		current
		DESCRIPTION	"Mnemonic name of the Hicom system."
		::=	{ hicomHWTrapVariables 2 }

-- Message Traps

internalMessageHWSubagent NOTIFICATION-TYPE
	OBJECTS	{ hicomHardSubagentLastMsgNo,
		hicomHardSubagentLastMsgText }
	STATUS	current
	DESCRIPTION	"An internalMessage trap contains an informational
			 message generated by the subagent."
	::=	{ hicomHWTraps 0 }

-- Warning Traps

internalWarningHWSubagent NOTIFICATION-TYPE
	OBJECTS	{ hicomHardSubagentLastMsgNo,
		hicomHardSubagentLastMsgText }
	STATUS	current
	DESCRIPTION	"An internalWarning trap contains a warning message
			 generated by a subagent."
	::=	{ hicomHWTraps 1 }

-- Error Traps

internalErrorHWSubagent	NOTIFICATION-TYPE
	OBJECTS	{ hicomHardSubagentLastMsgNo,
		hicomHardSubagentLastMsgText }
	STATUS	current
	DESCRIPTION	"An internalError trap contains an error message
			 generated by a subagent.
			 After issuing this trap, the agent terminates."
	::=	{ hicomHWTraps 2 }

-- HW discovery successfully terminated
hicomHWDiscovSucc	NOTIFICATION-TYPE
	OBJECTS	{ hicomHWTrpPabxId, hicomHWTrpPabxMnemonic }
	STATUS	current
	DESCRIPTION		"A hicomHWDiscovSucc trap signifies the
			successful termination of a discovery request / process.
			hicomHWDiscovPabxId: indicates the	Pbx involved."
	::=	{ hicomHWTraps 10 }

-- HW discovery unsuccessfully terminated

hicomHWDiscovErr	NOTIFICATION-TYPE
	OBJECTS	{ hicomHWTrpPabxId, hicomHWTrpPabxMnemonic }
	STATUS	current
	DESCRIPTION		"A hicomHWDiscovErr trap signifies the
			unsuccessful termination of a discovery request / process.
			hicomHWDiscovPabxId: indicates the	Pbx involved."
	::=	{ hicomHWTraps 11 }


-- HW discovery process is busy

hicomHWDiscovBusy	NOTIFICATION-TYPE
	OBJECTS	{ hicomHWTrpPabxId, hicomHWTrpPabxMnemonic }
	STATUS	current
	DESCRIPTION		"A hicomHWDiscovBusy trap signifies
			that a hw discovery process is running.
			hicomHWDiscovPabxId: indicates the	Pbx involved."
	::=	{ hicomHWTraps 19 }



-- BEGIN BLOCK topo

-- The hicomTopo MIB subtree components
-- The MIB subtree falls into the following groups:

hicomTrunkGrp		OBJECT IDENTIFIER ::= {	hicomTopo 1 }
hicomTrunk			OBJECT IDENTIFIER ::= { hicomTopo 2 }
hicomTopoInfo		OBJECT IDENTIFIER ::= {	hicomTopo 3 }

-- BEGIN BLOCK discov
hicomTopoDiscovery	OBJECT IDENTIFIER ::= {	hicomTopo 4 }

-- BEGIN BLOCK topo
hicomKntop			OBJECT IDENTIFIER ::= { hicomTopo 5 }

TrunkTypes ::= INTEGER { undef(1), analog(2), digital(3), special(4) }

-- The hicomTrunkGrp group

-- The TrunkGrp table

	hicomTrunkGrpTable	OBJECT-TYPE
		SYNTAX	SEQUENCE OF HicomTrunkGrpEntry
		MAX-ACCESS	not-accessible
		STATUS	current
		DESCRIPTION		"The table of trunk groups."
		::=	{ hicomTrunkGrp 1 }

	hicomTrunkGrpEntry	OBJECT-TYPE
		SYNTAX	HicomTrunkGrpEntry
		MAX-ACCESS		not-accessible
		STATUS	current
		DESCRIPTION		"Each entry describes a Hicom trunk group. "
		INDEX	{ hicomTrunkGrpPabxId, hicomTrunkGrpNo }
		::=	{ hicomTrunkGrpTable 1 }

	HicomTrunkGrpEntry ::=
		SEQUENCE {
			hicomTrunkGrpPabxId		Integer32,
			hicomTrunkGrpNo			Integer32,
			hicomTrunkGrpNNodeNo		Integer32,
			hicomTrunkGrpVNodeNo		Integer32,
			hicomTrunkGrpTrunkType		TrunkTypes,
			hicomTrunkGrpMaxNo		Integer32,
			hicomTrunkGrpName		DisplayString,
			hicomTrunkGrpDevice		DisplayString,
			hicomTrunkGrpAlarms		OCTET STRING
		}

	hicomTrunkGrpPabxId		OBJECT-TYPE
		SYNTAX	Integer32 (1..2147483647)
		MAX-ACCESS		read-only
		STATUS	current
		DESCRIPTION		"Unique identifier of the Hicom system."
		::=	{ hicomTrunkGrpEntry 1 }

	hicomTrunkGrpNo		OBJECT-TYPE
		SYNTAX		Integer32 (0..2147483647)
		MAX-ACCESS	read-only
		STATUS		current
		DESCRIPTION		"Identifier Trunk Group."
		::=	{ hicomTrunkGrpEntry 2 }

	hicomTrunkGrpNNodeNo	OBJECT-TYPE
		SYNTAX		Integer32
		MAX-ACCESS	read-write
		STATUS		current
		DESCRIPTION		"Number of neighbour node.	Value to be delivered by manager."
		DEFVAL		{ 0 }
		::=	{ hicomTrunkGrpEntry 3 }

	hicomTrunkGrpVNodeNo	OBJECT-TYPE
		SYNTAX		Integer32
		MAX-ACCESS	read-only
		STATUS		current
		DESCRIPTION		"Derived from source SNodeNo of trunk table."
			DEFVAL		{ 0 }
		::=	{ hicomTrunkGrpEntry 4 }

	hicomTrunkGrpTrunkType	OBJECT-TYPE
		SYNTAX		TrunkTypes
		MAX-ACCESS	read-only
		STATUS		current
		DESCRIPTION	"Type of the trunk group."
		::=	{ hicomTrunkGrpEntry 5 }

	hicomTrunkGrpMaxNo OBJECT-TYPE
		SYNTAX		Integer32
		MAX-ACCESS	read-only
		STATUS		current
		DESCRIPTION		"The maximum number of trunks a trunk groupp may contain."
		::=	{ hicomTrunkGrpEntry 6 }

	hicomTrunkGrpName	OBJECT-TYPE
		SYNTAX		DisplayString
		MAX-ACCESS	read-only
		STATUS		current
		DESCRIPTION		"Name of the trunk group. "
		::=	{ hicomTrunkGrpEntry 7 }

	hicomTrunkGrpDevice	OBJECT-TYPE
		SYNTAX	DisplayString
		MAX-ACCESS		read-only
		STATUS	current
		DESCRIPTION		"Type of device."
		::= { hicomTrunkGrpEntry 8 }

	hicomTrunkGrpAlarms	OBJECT-TYPE
		SYNTAX		OCTET STRING
		MAX-ACCESS	read-only
		STATUS		current
		DESCRIPTION		"Octet string contains configured AlSubIds (0 up to 519)
				of related Pabx and trunkgroup.
				The hicomTrunkGrpAlarms string is 65 octets long.
				AlSubId '0' is set, if (hicomTrunkGrpAlarms[0] AND 0x01)
				evaluates to true.
				AlSubId '7' is set, if (hicomTrunkGrpAlarms[0] AND 0x80)
				evaluates to true.
				AlSubId '8' is set, if (hicomTrunkGrpAlarms[1] AND 0x01)
				evaluates to true etc."
		::=	{ hicomTrunkGrpEntry 9 }

-- The hicomTrunk group

-- The Trunk Table

	hicomTrunkTable		OBJECT-TYPE
		SYNTAX	SEQUENCE OF HicomTrunkEntry
		MAX-ACCESS		not-accessible
		STATUS	current
		DESCRIPTION		"The table of trunks."
		::=	{ hicomTrunk 1 }

	hicomTrunkEntry		OBJECT-TYPE
		SYNTAX	HicomTrunkEntry
		MAX-ACCESS		not-accessible
		STATUS	current
		DESCRIPTION		"Each entry describes a Hicom trunk."
		INDEX	{ hicomTrunkPabxId, hicomTrunkType, hicomTrunkTrunkGrpNo,
		hicomTrunkLtg, hicomTrunkLtu, hicomTrunkSlot, hicomTrunkNo,
		hicomTrunkChannelGrp}
		::=	{ hicomTrunkTable 1 }

	HicomTrunkEntry	::=
		SEQUENCE {
			hicomTrunkPabxId	Integer32,
			hicomTrunkType		TrunkTypes,
			hicomTrunkTrunkGrpNo	Integer32,
			hicomTrunkLtg		Integer32,
			hicomTrunkLtu		Integer32,
			hicomTrunkSlot		Integer32,
			hicomTrunkNo		Integer32,
			hicomTrunkChannelGrp	Integer32,
			hicomTrunkSNodeNo	Integer32,
			hicomTrunkStatOp	INTEGER,
			hicomTrunkAlSubId	Integer32,
			hicomTrunkChannels	OCTET STRING,
			hicomTrunkDevice	DisplayString,
			hicomTrunkName		DisplayString
		}

	hicomTrunkPabxId	OBJECT-TYPE
		SYNTAX	Integer32 (1..2147483647)
		MAX-ACCESS		read-only
		STATUS	current
		DESCRIPTION		"Identifier of the Hicom."
		::=	{ hicomTrunkEntry 1 }

	hicomTrunkType		OBJECT-TYPE
		SYNTAX		TrunkTypes
		MAX-ACCESS	read-only
		STATUS		current
		DESCRIPTION	"Type of trunk."
		::=	{ hicomTrunkEntry 2 }

	hicomTrunkTrunkGrpNo	OBJECT-TYPE
		SYNTAX			Integer32 (0..2147483647)
		MAX-ACCESS		read-only
		STATUS			current
		DESCRIPTION	"Identifier of the related Trunk Group."
		::=	{ hicomTrunkEntry 3 }

	hicomTrunkLtg	OBJECT-TYPE
		SYNTAX			Integer32  (1)
		MAX-ACCESS		read-only
		STATUS			current
		DESCRIPTION	"Identifier of the related line trunk group."
		::=	{ hicomTrunkEntry 4 }

	hicomTrunkLtu		OBJECT-TYPE
		SYNTAX			Integer32 (1..99)
		MAX-ACCESS		read-only
		STATUS			current
		DESCRIPTION	"Identifier of the related line trunk unit."
		::=	{ hicomTrunkEntry 5 }

	hicomTrunkSlot		OBJECT-TYPE
		SYNTAX			Integer32 (0..121)
		MAX-ACCESS		read-only
		STATUS			current
		DESCRIPTION	"Identification of slot within a frame."
		::=	{ hicomTrunkEntry 6 }

	hicomTrunkNo		OBJECT-TYPE
		SYNTAX			Integer32 (0..2147483647)
		MAX-ACCESS		read-only
		STATUS			current
		DESCRIPTION	"Number of trunk within a trunk group. "
		::=	{ hicomTrunkEntry 7 }

	hicomTrunkChannelGrp OBJECT-TYPE
		SYNTAX			Integer32 (0..2147483647)
		MAX-ACCESS		read-only
		STATUS			current
		DESCRIPTION	"Identification of an aggregate of	B-channels. "
		::=	{ hicomTrunkEntry 8 }

	hicomTrunkSNodeNo	OBJECT-TYPE
		SYNTAX			Integer32
		MAX-ACCESS		read-only
		STATUS			current
		DESCRIPTION	"Virtual number of the source node of a connection."
		::=	{ hicomTrunkEntry 9 }

	hicomTrunkStatOp	OBJECT-TYPE
		SYNTAX		INTEGER { no(1), yes(2) }
		MAX-ACCESS	read-only
		STATUS		current
		DESCRIPTION	"The operational state of a trunk."
		::=	{ hicomTrunkEntry 10 }

	hicomTrunkAlSubId	OBJECT-TYPE
		SYNTAX		Integer32
		MAX-ACCESS	read-only
		STATUS		current
		DESCRIPTION	"Assigned alarm referring to a specific target."
		::=	{ hicomTrunkEntry 11 }

	hicomTrunkChannels OBJECT-TYPE
		SYNTAX			OCTET	STRING
		MAX-ACCESS		read-only
		STATUS			current
		DESCRIPTION	"List of chanels in a trunk group. Base64 coded."
		::=	{ hicomTrunkEntry 12 }

	hicomTrunkDevice	OBJECT-TYPE
		SYNTAX			DisplayString
		MAX-ACCESS		read-only
		STATUS			current
		DESCRIPTION	"Type of device / connection."
		::=	{ hicomTrunkEntry 13 }

	hicomTrunkName		OBJECT-TYPE
		SYNTAX			DisplayString
		MAX-ACCESS		read-only
		STATUS			current
		DESCRIPTION	"Name of the trunk."
		::=	{ hicomTrunkEntry 14 }

-- The hicomKntop Table

    hicomKntopTable  OBJECT-TYPE
        SYNTAX  SEQUENCE OF HicomKntopEntry
        MAX-ACCESS  not-accessible
        STATUS  current
        DESCRIPTION     "The table of kntop."
        ::= { hicomKntop 1 }

    hicomKntopEntry  OBJECT-TYPE
        SYNTAX  HicomKntopEntry
        MAX-ACCESS      not-accessible
        STATUS  current
        DESCRIPTION     "Each entry describes a connection between two Hicoms."
        INDEX   { hicomKntopPabxId,hicomKntopLtg,hicomKntopLtu,
                  hicomKntopSlot,hicomKntopSatznr,hicomKntopBKanalGrp,hicomKntopPNodeIndex }
        ::= { hicomKntopTable 1 }

    HicomKntopEntry ::=
        SEQUENCE {
            hicomKntopPabxId     	Integer32,
            hicomKntopLtg        	Integer32,
            hicomKntopLtu        	Integer32,
            hicomKntopSlot        	Integer32,
            hicomKntopSatznr        Integer32,
            hicomKntopBKanalGrp     Integer32,
            hicomKntopPNodeIndex  	Integer32,
            hicomKntopPLtg        	Integer32,
            hicomKntopPLtu        	Integer32,
            hicomKntopPSlot        	Integer32,
            hicomKntopPSatznr       Integer32,
            hicomKntopPBKanalGrp    Integer32,
            hicomKntopPNodeNo       Integer32,
            hicomKntopBunr          Integer32
        }

	hicomKntopPabxId    OBJECT-TYPE
        SYNTAX  Integer32 (1..2147483647)
        MAX-ACCESS      read-only
        STATUS  current
        DESCRIPTION     "Identifier of the Hicom."
        ::= { hicomKntopEntry 1 }

    hicomKntopLtg   OBJECT-TYPE
        SYNTAX          Integer32 (1)
        MAX-ACCESS      read-only
        STATUS          current
        DESCRIPTION "Identifier of the related line trunk group."
        ::= { hicomKntopEntry 2 }

    hicomKntopLtu       OBJECT-TYPE
        SYNTAX          Integer32 (1..99)
        MAX-ACCESS      read-only
        STATUS          current
        DESCRIPTION "Identifier of the related line trunk unit."
        ::= { hicomKntopEntry 3 }

    hicomKntopSlot      OBJECT-TYPE
        SYNTAX          Integer32 (0..121)
        MAX-ACCESS      read-only
        STATUS          current
        DESCRIPTION "Identification of slot within a frame."
        ::= { hicomKntopEntry 4 }

    hicomKntopSatznr   OBJECT-TYPE
        SYNTAX          Integer32 (0..2147483647)
        MAX-ACCESS      read-only
        STATUS          current
        DESCRIPTION "Number of trunk within a trunk group. "
        ::= { hicomKntopEntry 5 }

    hicomKntopBKanalGrp OBJECT-TYPE
        SYNTAX          Integer32 (0..2147483647)
        MAX-ACCESS      read-only
        STATUS          current
        DESCRIPTION "Identification of an aggregate of  B-channels. "
        ::= { hicomKntopEntry 6 }

    hicomKntopPNodeIndex OBJECT-TYPE
        SYNTAX          Integer32 (0..2147483647)
        MAX-ACCESS      read-only
        STATUS          current
        DESCRIPTION "Entry Index of the Partner Node."
        ::= { hicomKntopEntry 7 }

    hicomKntopPLtg   OBJECT-TYPE
        SYNTAX          Integer32
        MAX-ACCESS      read-only
        STATUS          current
        DESCRIPTION "Target Identifier of the related line trunk group."
        ::= { hicomKntopEntry 8 }

    hicomKntopPLtu       OBJECT-TYPE
        SYNTAX          Integer32
        MAX-ACCESS      read-only
        STATUS          current
        DESCRIPTION "Target Identifier of the related line trunk unit."
        ::= { hicomKntopEntry 9 }

    hicomKntopPSlot      OBJECT-TYPE
        SYNTAX          Integer32
        MAX-ACCESS      read-only
        STATUS          current
        DESCRIPTION "Target Identification of slot within a frame."
        ::= { hicomKntopEntry 10 }

    hicomKntopPSatznr   OBJECT-TYPE
        SYNTAX          Integer32
        MAX-ACCESS      read-only
        STATUS          current
        DESCRIPTION "Target Number of trunk within a trunk group. "
        ::= { hicomKntopEntry 11 }

    hicomKntopPBKanalGrp OBJECT-TYPE
        SYNTAX          Integer32
        MAX-ACCESS      read-only
        STATUS          current
        DESCRIPTION "Target Identification of an aggregate of  B-channels. "
        ::= { hicomKntopEntry 12 }

    hicomKntopPNodeNo   OBJECT-TYPE
        SYNTAX          Integer32
        MAX-ACCESS      read-only
        STATUS          current
        DESCRIPTION "Node number of the target node of the connection."
        ::= { hicomKntopEntry 13 }

    hicomKntopBunr   OBJECT-TYPE
        SYNTAX          Integer32
        MAX-ACCESS      read-only
        STATUS          current
        DESCRIPTION "Buendelnumber of the PEN"
        ::= { hicomKntopEntry 14 }





-- BEGIN BLOCK discov
-- The hicomTopoDiscovery group

-- The hicomTopoChanges counter

	hicomTopoChanges	OBJECT-TYPE
		SYNTAX	Counter32
		MAX-ACCESS		read-only
		STATUS	current
		DESCRIPTION		"Indicates number of hardware discoveries -
				corresponds to	TopoDiscovery traps sent out."
		::=	{ hicomTopoDiscovery 1 }

-- The hicomTopoDiscovTable table

	hicomTopoDiscovTable	OBJECT-TYPE
		SYNTAX	SEQUENCE OF HicomTopoDiscovEntry
		MAX-ACCESS		not-accessible
		STATUS	current
		DESCRIPTION		"The table describing the status
				concerning discovery of topology information."
		::=	{ hicomTopoDiscovery 2 }

	hicomTopoDiscovEntry	OBJECT-TYPE
		SYNTAX	HicomTopoDiscovEntry
		MAX-ACCESS		not-accessible
		STATUS	current
		DESCRIPTION		"An entry in the hicomTopoDiscovTable.
				Each entry describes the status of the
				discovery process for a specific hicom."
		INDEX	{ hicomTopoDiscovPabxId }
		::=	{ hicomTopoDiscovTable 1 }

	HicomTopoDiscovEntry ::=
		SEQUENCE {
			hicomTopoDiscovPabxId		Integer32,
			hicomTopoDiscovPabxMnemonic	DisplayString,
			hicomTopoDiscovStatus		DiscoveryStates,
			hicomTopoDiscovMode		DiscoveryModes,
			hicomTopoDiscovTimDat		DisplayString,
			hicomTopoDiscovErrTimDat	DisplayString
		}

	hicomTopoDiscovPabxId OBJECT-TYPE
		SYNTAX	Integer32 (1..2147483647)
		MAX-ACCESS		read-only
		STATUS	current
		DESCRIPTION		"Unique identifier of the Hicom being discovered."
		::=	{ hicomTopoDiscovEntry 1 }

	hicomTopoDiscovPabxMnemonic OBJECT-TYPE
		SYNTAX	DisplayString
		MAX-ACCESS		read-only
		STATUS	current
		DESCRIPTION		"Name of the Hicom system. "
		::=	{ hicomTopoDiscovEntry 2 }

	hicomTopoDiscovStatus OBJECT-TYPE
		SYNTAX		DiscoveryStates
		MAX-ACCESS	read-write
		STATUS		current
		DESCRIPTION	"Status of Topo discovery process.
				A manager initiates discovery by setting
				the variable to 'busy'.
				The agent will set the other values."
		::=	{ hicomTopoDiscovEntry 3 }

	hicomTopoDiscovMode OBJECT-TYPE
		SYNTAX		DiscoveryModes
		MAX-ACCESS	read-write
		STATUS		current
		DESCRIPTION	"Mode of discovery process."
		::=	{ hicomTopoDiscovEntry 4 }

	hicomTopoDiscovTimDat OBJECT-TYPE
		SYNTAX	DisplayString
		MAX-ACCESS		read-only
		STATUS	current
		DESCRIPTION		"Date and time (year, month, day, hour, minute, second)
				the last successful discovery action was performed for the Hicom."
		::=	{ hicomTopoDiscovEntry 5 }

	hicomTopoDiscovErrTimDat OBJECT-TYPE
		SYNTAX	DisplayString
		MAX-ACCESS		read-only
		STATUS	current
		DESCRIPTION		"Date and time (year, month, day, hour, minute, second)
				the last failed discovery action was performed for the	Hicom."
		::=	{ hicomTopoDiscovEntry 6 }

-- BEGIN BLOCK topo

-- The hicomTopoInfo group

	hicomTopoSubagentLastMsgNo	OBJECT-TYPE
		SYNTAX		Integer32
		MAX-ACCESS	read-only
		STATUS		current
		DESCRIPTION	"The last message, warning or error number 
					issued by the Topology subagent."
	::=	{ hicomTopoInfo 1 }

	hicomTopoSubagentLastMsgText	OBJECT-TYPE
		SYNTAX		OCTET STRING
		MAX-ACCESS	read-only
		STATUS		current
		DESCRIPTION	"The last message, warning or error text
					issued by the Topology subagent."
	::=	{ hicomTopoInfo 2 }

	hicomTopoSubagentResultData	OBJECT-TYPE
	        SYNTAX		Integer32
	        MAX-ACCESS	read-write
	        STATUS		current
	        DESCRIPTION	"Is used for agent internal communication.
			 Contains the PabxId of a Hicom for which
			 the last discovery process was conveyed.
			 Is SET by the discovery agent and
			 indicates the availability of new discovered data.
			 The new data is to be incorporated by the subagent
			 into the subagent's data base."
		::=	{ hicomTopoInfo 3 }

-- Conformance information

-- Units of conformance

	hicomTrunkGrpGroup		OBJECT-GROUP
		OBJECTS	{ hicomTrunkGrpPabxId, hicomTrunkGrpTrunkType,
				hicomTrunkGrpNo, hicomTrunkGrpName,
				hicomTrunkGrpMaxNo, hicomTrunkGrpDevice,
				hicomTrunkGrpNNodeNo, hicomTrunkGrpVNodeNo,
				hicomTrunkGrpAlarms
		}
		STATUS		current
		DESCRIPTION	"Conformance statement for hicomTrunkGrpGroup."
		::=	{ hicomTopoTree 1 }

	hicomTrunkGroup	OBJECT-GROUP
		OBJECTS	{
				hicomTrunkPabxId, hicomTrunkType, hicomTrunkTrunkGrpNo,
				hicomTrunkLtg, hicomTrunkLtu, hicomTrunkSlot,
				hicomTrunkNo, hicomTrunkChannelGrp, hicomTrunkChannels,
				hicomTrunkDevice, hicomTrunkName, hicomTrunkStatOp,
				hicomTrunkSNodeNo, hicomTrunkAlSubId
		}
		STATUS		current
		DESCRIPTION	"Conformance statement for hicomTrunkGroup."
		::=	{ hicomTopoTree 2 }


	hicomTopoInfoGroup	OBJECT-GROUP
		OBJECTS	{
				hicomTopoSubagentLastMsgNo,
				hicomTopoSubagentLastMsgText,
				hicomTopoSubagentResultData
		}
		STATUS		current
		DESCRIPTION	"Conformance statement for hicomTopoInfoGroup."
		::=	{ hicomTopoTree 3 }

-- BEGIN BLOCK discov

	hicomTopoDiscoveryGroup		OBJECT-GROUP
		OBJECTS	{
			hicomTopoChanges,
			hicomTopoDiscovPabxId,
			hicomTopoDiscovPabxMnemonic,
			hicomTopoDiscovStatus,
			hicomTopoDiscovMode,
			hicomTopoDiscovTimDat,
			hicomTopoDiscovErrTimDat
		}
		STATUS		current
		DESCRIPTION	"Conformance statement for 
				hicomTopoDiscoveryGroup."
		::=	{ hicomTopoTree 4 }



-- BEGIN BLOCK topo

    hicomKntopGroup  OBJECT-GROUP
        OBJECTS {
			hicomKntopPabxId,
            hicomKntopLtg,
            hicomKntopLtu,
            hicomKntopSlot,
            hicomKntopSatznr,
            hicomKntopBKanalGrp,
            hicomKntopPNodeIndex,
            hicomKntopPLtg,
            hicomKntopPLtu,
            hicomKntopPSlot,
            hicomKntopPSatznr,
            hicomKntopPBKanalGrp,
            hicomKntopPNodeNo,
            hicomKntopBunr
	    }
        STATUS      current
        DESCRIPTION "Conformance statement for hicomKntopTable."
        ::= { hicomTopoTree 5 }

-- Traps / Notifications

-- Trap Variables

	hicomTopoTrpPabxId	OBJECT-TYPE
		SYNTAX		Integer32
		MAX-ACCESS	read-only
		STATUS		current
		DESCRIPTION	"Unique identifier of a Hicom system."
		::=	{ hicomTopoTrapVariables 1 }

	hicomTopoTrpPabxMnemonic OBJECT-TYPE
		SYNTAX		DisplayString
		MAX-ACCESS 	read-only
		STATUS		current
		DESCRIPTION	"Mnemonic name of the Hicom system."
		::=	{ hicomTopoTrapVariables 2 }


-- Message Traps

internalMessageTopoSubagent	NOTIFICATION-TYPE
	OBJECTS	{ hicomTopoSubagentLastMsgNo,
		hicomTopoSubagentLastMsgText }
	STATUS	current
	DESCRIPTION	"An internalMessage trap contains an informational
			 message generated by the subagent."
	::=	{ hicomTopoTraps 0 }

-- Warning Traps

internalWarningTopoSubagent	NOTIFICATION-TYPE
	OBJECTS	{ hicomTopoSubagentLastMsgNo,
		hicomTopoSubagentLastMsgText }
	STATUS	current
	DESCRIPTION	"An internalWarning trap contains a warning message
			 generated by a subagent."
	::=	{ hicomTopoTraps 1 }

-- Error Traps

internalErrorTopoSubagent NOTIFICATION-TYPE
	OBJECTS	{ hicomTopoSubagentLastMsgNo,
		hicomTopoSubagentLastMsgText }
	STATUS	current
	DESCRIPTION	"An internalError trap contains an error message
			 generated by a subagent. 
			 After issuing this trap, the agent terminates."
	::=	{ hicomTopoTraps 2 }


-- Topo discovery successfully terminated

hicomTopoDiscovSucc		NOTIFICATION-TYPE
	OBJECTS	{ hicomTopoTrpPabxId, hicomTopoTrpPabxMnemonic }
	STATUS	current
	DESCRIPTION
		"A hicomTopoDiscovSucc trap signifies the
		successful termination of a discovery process.
		hicomTopoDiscovPabxId: indicates the Pbx involved."
	::=	{ hicomTopoTraps 10 }

-- Topo discovery unsuccessfully terminated

hicomTopoDiscovErr		NOTIFICATION-TYPE
	OBJECTS		{ hicomTopoTrpPabxId, hicomTopoTrpPabxMnemonic }
	STATUS		current
	DESCRIPTION
		"A hicomTopoDiscovErr trap signifies the
		unsuccessful termination of a discovery process.
		hicomTopoDiscovPabxId: indicates the Pbx involved."
	::=	{ hicomTopoTraps 11 }


-- Topo discovery process is busy

hicomTopoDiscovBusy		NOTIFICATION-TYPE
	OBJECTS		{ hicomTopoTrpPabxId, hicomTopoTrpPabxMnemonic }
	STATUS		current
	DESCRIPTION
		"A hicomTopoDiscovBusy trap signifies 
		that a topo discovery process is running.
		hicomTopoDiscovPabxId: indicates the Pbx involved."
	::=	{ hicomTopoTraps 19 }



-- BEGIN BLOCK sql

hicomSQLsessionIdGenerator	OBJECT-TYPE
	SYNTAX		TestAndIncr
	MAX-ACCESS	read-write
	STATUS		current
	DESCRIPTION	"hicomSQLsessionIdGenerator is used to create and assign
			unique SQL session identifiers to concurrent manager 
			applications.
			hicomSQLsessionIdGenerator shall be used in accordance 
			to the semantics of TestAndIncr specified in Textual 
			Conventions (RFC1903).
			
			A GET on hicomSQLsessionIdGenerator returns a new SQL 
			session ID.  This value shall be confirmed/claimed by 
			a manager application by setting the 
			hicomSQLsessionIdGenerator variable to the value which 
			was returned by the previous GET. 
			If the SET on hicomSQLsessionIdGenerator succeeds 
			(error status 'noError' is returned), the SQL session 
			ID value is uniquely assigned to the requesting manager
			application. Further, the agent did create a 
			corresponding entry in the hicomSQLsessionTable having 
			hicomSQLsessionId set to the SQL session ID value used 
			with the SET.

			If the SET on hicomSQLsessionIdGenerator fails (error 
			status 'inconsistenValue' is returned) the same value 
			was read by another manager and this one just claimed 
			his SQL session ID by performing successfully a SET.
			In this case no entry is created in the 
			hicomSQLsessionTable.
			To get and claim a unique SQL session ID, the manager 
			application has to redo the GET and SET operation 
			cycle on hicomSQLsessionIdGenerator.
			
			NOTE: using this and other hicomSQL objects is reserved
			for Siemens internal use ONLY. No documentation on this
			interface is available for customers."
	::= { hicomSQL 1 }

hicomSQLsessionTable	OBJECT-TYPE
	SYNTAX		SEQUENCE OF HicomSQLsessionEntry
	MAX-ACCESS	not-accessible
	STATUS		current
	DESCRIPTION	"This table describes all currently active SQL sessions.
			An entry is generated after a new session ID is read 
			and claimed by a manager application (see 
			hicomSQLsessionIdGenerator).
			An entry is deleted from the table when its timeout 
			(see hicomSQLsessionTimeout) - which is restarted with 
			each access on hicomSQLresultData - expires.
			The state of a new created entry initially is idle(1). 
			The manager must then SET hicomSQLsessionStatement and
			hicomSQLsessionWhereClause, optionally may set 
			hicomSQLsessionTimeout, and then SET hicomSQLsessionState 
			to run(2). The completion of a session will be 
			indicated to the manager via a hicomSQLsessionFinished 
			trap."
	::=	{ hicomSQL 2 }

	hicomSQLsessionEntry	OBJECT-TYPE
		SYNTAX		HicomSQLsessionEntry
		MAX-ACCESS	not-accessible
		STATUS		current
		DESCRIPTION	"An entry in the hicomSQLsessionTable."
		INDEX		{ hicomSQLsessionId }
		::=	{ hicomSQLsessionTable 1 }

	HicomSQLsessionEntry ::=
		SEQUENCE {
			hicomSQLsessionId		Integer32,
			hicomSQLsessionState		INTEGER,
			hicomSQLsessionStatement	Integer32,
			hicomSQLsessionWhereClause	DisplayString,
			hicomSQLsessionTimeout		INTEGER,
			hicomSQLsessionResultSize	Integer32,
			hicomSQLsessionResultNoLines	Integer32
		}

	hicomSQLsessionId OBJECT-TYPE
		SYNTAX		Integer32 (1..2147483647)
		MAX-ACCESS	read-only
		STATUS		current
		DESCRIPTION	"Unique identifier of the SQL session."
		::=	{ hicomSQLsessionEntry 1 }

	hicomSQLsessionState OBJECT-TYPE
		SYNTAX		INTEGER { idle(1), run(2), error(4), valid(5) }
		MAX-ACCESS	read-write
		STATUS		current
		DESCRIPTION	"Indicates current state of the SQL session:
				idle: entry/session has been created by the 
				     agent and has to be initialized by 
				     the manager.
				run: to be set by the manager to initiate the 
				     execution of the SQL query.
				error: execution of the SQL query resulted in 
				     an error
				valid: execution of the SQL query was 
				     successful.
				Transitions:
				idle -> run -> {valid, error}
				"
		::= { hicomSQLsessionEntry 2 }

	hicomSQLsessionStatement OBJECT-TYPE
		SYNTAX		Integer32
		MAX-ACCESS	read-write
		STATUS		current
		DESCRIPTION	"Selects the predefined SQL statement for 
				this session."
		::= { hicomSQLsessionEntry 3 }

	hicomSQLsessionWhereClause OBJECT-TYPE
		SYNTAX		DisplayString
		MAX-ACCESS	read-write
		STATUS		current
		DESCRIPTION	"The WHERE clause to be used for this 
				SQL statement."
		::= { hicomSQLsessionEntry 4 }

	hicomSQLsessionTimeout OBJECT-TYPE
		SYNTAX		INTEGER (10..86400)
		UNITS		"seconds"
		MAX-ACCESS	read-write
		STATUS		current
		DESCRIPTION	"Maximum time interval between any two 
				succeeding retrievals to the result data of 
				the session. If no access is made to the 
				to the result data of the session within
				SQLsessionTimeout, the session and the related 
				result data will be erased.
				SQLSessionTimeout is  messured in seconds."
		DEFVAL		{ 30 }
		::= { hicomSQLsessionEntry 5 }

	hicomSQLsessionResultSize OBJECT-TYPE
		SYNTAX		Integer32
		MAX-ACCESS	read-only
		STATUS		current
		DESCRIPTION	"The result of a SQL query is stored in result 
				file. hicomSQLsessionResultSize specifies the 
				size in number of octets of the result file."
		DEFVAL		{ 0 }
		::= { hicomSQLsessionEntry 6 }

	hicomSQLsessionResultNoLines OBJECT-TYPE
		SYNTAX		Integer32
		MAX-ACCESS	read-only
		STATUS		current
		DESCRIPTION	"The result of a SQL query is stored in result 
				file. hicomSQLsessionResultNoLines specifies 
				the number of lines in the result file."
		DEFVAL		{ 0 }
		::= { hicomSQLsessionEntry 7 }

hicomSQLresultTable	OBJECT-TYPE
	SYNTAX		SEQUENCE OF HicomSQLresultEntry
	MAX-ACCESS	not-accessible
	STATUS		current
	DESCRIPTION	"This table contains the results of finished 
			SQL sessions."
	::=	{ hicomSQL 3 }

	hicomSQLresultEntry	OBJECT-TYPE
		SYNTAX		HicomSQLresultEntry
		MAX-ACCESS	not-accessible
		STATUS		current
		DESCRIPTION	"An entry in the hicomSQLresultTable."
		INDEX		{ hicomSQLresultId, hicomSQLresultBlockNo}
		::=	{ hicomSQLresultTable 1 }

	HicomSQLresultEntry ::=
		SEQUENCE {
			hicomSQLresultId		Integer32,
			hicomSQLresultBlockNo		Integer32,
			hicomSQLresultData		DisplayString
		}

	hicomSQLresultId OBJECT-TYPE
		SYNTAX		Integer32 (1..2147483647)
		MAX-ACCESS	read-only
		STATUS		current
		DESCRIPTION	"Session ID to which these results belong."
		::= { hicomSQLresultEntry 1 }

	hicomSQLresultBlockNo OBJECT-TYPE
		SYNTAX		Integer32 (0..2147483647)
		MAX-ACCESS	read-only
		STATUS		current
		DESCRIPTION	"Identifier of the data block to be returned
				from the result file. The result file is
				logically segmented in blocks of 256 octets.
				Data from the result file is read by GET in
				block units. Each GET will return one block
				specified by BlockNo.  A GET on BlockNo '0'
				will return octet 0 to 255 of the result file
				and a GET on BlockNo '1' octet 256 to 511 etc.
				If the first or last block is smaller then 256
				octets, then a corresponding smaller
				hicomSQLresultData block will be returned."
		::= { hicomSQLresultEntry 2 }


	hicomSQLresultData OBJECT-TYPE
		SYNTAX		DisplayString
		MAX-ACCESS	read-only
		STATUS		current
		DESCRIPTION	"Requested block of result data."
		::= { hicomSQLresultEntry 3 }

hicomSQLinfo OBJECT IDENTIFIER ::= { hicomSQL 4 }

	hicomSQLSubagentLastMsgNo	OBJECT-TYPE
		SYNTAX		Integer32
		MAX-ACCESS	read-only
		STATUS		current
		DESCRIPTION	"The last message, warning or error number 
					issued by the SQL subagent."
	::=	{ hicomSQLinfo 1 }

	hicomSQLSubagentLastMsgText	OBJECT-TYPE
		SYNTAX		OCTET STRING
		MAX-ACCESS	read-only
		STATUS		current
		DESCRIPTION	"The last message, warning or error text
					issued by the SQL subagent."
	::=	{ hicomSQLinfo 2 }


-- conformance information
-- units of conformance

hicomSQLsessionGroup	OBJECT-GROUP
	OBJECTS	{
		hicomSQLsessionIdGenerator,
		hicomSQLsessionId,
		hicomSQLsessionState,
		hicomSQLsessionResultSize,
		hicomSQLsessionResultNoLines,
		hicomSQLsessionTimeout,
		hicomSQLsessionStatement,
		hicomSQLsessionWhereClause
	}
	STATUS		current
	DESCRIPTION	"Conformance statement for hicomSQLsessionGroup."
	::=	{ hicomSQLtree 1 }

hicomSQLresultGroup	OBJECT-GROUP
	OBJECTS	{
		hicomSQLresultId,
		hicomSQLresultBlockNo,
		hicomSQLresultData
	}
	STATUS		current
	DESCRIPTION	"Conformance statement for hicomSQLresultGroup."
	::=	{ hicomSQLtree 2 }

hicomSQLinfoGroup	OBJECT-GROUP
	OBJECTS	{
		hicomSQLSubagentLastMsgNo,
		hicomSQLSubagentLastMsgText
	}
	STATUS		current
	DESCRIPTION	"Conformance statement for hicomSQLinfoGroup."
	::=	{ hicomSQLtree 3 }

-- Traps sql agent

internalMessageSQLSubagent	NOTIFICATION-TYPE
	OBJECTS		{ hicomSQLSubagentLastMsgNo, hicomSQLSubagentLastMsgText }
	STATUS		current
	DESCRIPTION	"An internalMessage trap contains an informational
			 message generated by the subagent."
	::=	{ hicomSQLTraps 0 }

internalWarningSQLSubagent	NOTIFICATION-TYPE
	OBJECTS		{ hicomSQLSubagentLastMsgNo, hicomSQLSubagentLastMsgText }
	STATUS		current
	DESCRIPTION	"An internalWarning trap contains a warning message
			 generated by a subagent."
	::=	{ hicomSQLTraps 1 }

internalErrorSQLSubagent	NOTIFICATION-TYPE
	OBJECTS		{ hicomSQLSubagentLastMsgNo, hicomSQLSubagentLastMsgText }
	STATUS		current
	DESCRIPTION	"An internalError trap contains an error message
			 generated by a subagent. 
			 After issuing this trap, the agent terminates."
	::=	{ hicomSQLTraps 2 }

hicomSQLsessionFinished		NOTIFICATION-TYPE
	OBJECTS		{ hicomSQLsessionId, 
				hicomSQLsessionState,
				hicomSQLsessionResultSize,
				hicomSQLsessionResultNoLines }
	STATUS		current
	DESCRIPTION
		"A hicomSQLsessionFinished trap indicates the completion of
		an SQL query. If hicomSQLsessionState indicates an error in
		the query, hicomSQLsessionResultLines will contain the SQL
		error code instead of the number of resulting lines. In this
		case, no entry in the hicomSQLresultTable will be created."
	::=	{ hicomSQLTraps 20 }


-- BEGIN BLOCK discov

hicomDiscovTable	OBJECT-TYPE
	SYNTAX		SEQUENCE OF HicomDiscovEntry
	MAX-ACCESS	not-accessible
	STATUS		current
	DESCRIPTION	"This table contains information about the master
			discoveries for each managed Hicom. Starting a master
			discoveries will lead to the individual discoveries 
			being started. 
			The termination of these discoveries will be
			signalled through their respective traps."
	::=	{ hicomDiscov 1 }

	hicomDiscovEntry	OBJECT-TYPE
		SYNTAX		HicomDiscovEntry
		MAX-ACCESS	not-accessible
		STATUS		current
		DESCRIPTION	"Each entry describes the master discovery for 
					a specific hicom."
		INDEX	{ hicomDiscovPabxId }
		::=	{ hicomDiscovTable 1 }

	HicomDiscovEntry ::=
		SEQUENCE {
			hicomDiscovPabxId		Integer32,
			hicomDiscovPabxMnemonic		DisplayString,
			hicomDiscovStatus		DiscoveryStates,
			hicomDiscovMode			DiscoveryModes,
			hicomDiscovTimDat		DisplayString,
			hicomDiscovErrTimDat		DisplayString
		}

	hicomDiscovPabxId	OBJECT-TYPE
		SYNTAX		Integer32 (1..2147483647)
		MAX-ACCESS	read-only
		STATUS		current
		DESCRIPTION	"Unique identifier of the Hicom being discovered."
		::=	{ hicomDiscovEntry 1 }

	hicomDiscovPabxMnemonic	OBJECT-TYPE
		SYNTAX	DisplayString
		MAX-ACCESS	read-only
		STATUS		current
		DESCRIPTION	"Name of the Hicom."
		::=	{ hicomDiscovEntry 2 }

	hicomDiscovStatus	OBJECT-TYPE
		SYNTAX		DiscoveryStates
		MAX-ACCESS	read-write
		STATUS		current
		DESCRIPTION	"Status of master discovery process."
		::=	{ hicomDiscovEntry 3 }

	hicomDiscovMode		OBJECT-TYPE
		SYNTAX		DiscoveryModes
		MAX-ACCESS	read-write
		STATUS		current
		DESCRIPTION	"Mode of master discovery process."
		::=	{ hicomDiscovEntry 4 }

	hicomDiscovTimDat	OBJECT-TYPE
		SYNTAX		DisplayString
		MAX-ACCESS	read-only
		STATUS		current
		DESCRIPTION	"Date and time of the last successful discovery."
		::=	{ hicomDiscovEntry 5 }

	hicomDiscovErrTimDat	OBJECT-TYPE
		SYNTAX		DisplayString
		MAX-ACCESS	read-only
		STATUS		current
		DESCRIPTION	"Date and time of the last failed discovery."
		::=	{ hicomDiscovEntry 6 }

hicomDiscInfo OBJECT IDENTIFIER ::= { hicomDiscov 2 }

	hicomDiscSubagentLastMsgNo	OBJECT-TYPE
		SYNTAX		Integer32
		MAX-ACCESS	read-only
		STATUS		current
		DESCRIPTION	"The last message, warning or error number 
					issued by the discovery subagent."
	::=	{ hicomDiscInfo 1 }

	hicomDiscSubagentLastMsgText	OBJECT-TYPE
		SYNTAX		OCTET STRING
		MAX-ACCESS	read-only
		STATUS		current
		DESCRIPTION	"The last message, warning or error text
					issued by the discovery subagent."
	::=	{ hicomDiscInfo 2 }


hicomDiscovGroup	OBJECT-GROUP
	OBJECTS	{
		hicomDiscovPabxId,
		hicomDiscovPabxMnemonic,
		hicomDiscovStatus,
		hicomDiscovMode,
		hicomDiscovTimDat,
		hicomDiscovErrTimDat
	}
	STATUS		current
	DESCRIPTION	"Conformance statement for hicomDiscovGroup."
	::=	{ hicomDiscovTree 1 }

hicomDiscInfoGroup	OBJECT-GROUP
	OBJECTS	{
		hicomDiscSubagentLastMsgNo,
		hicomDiscSubagentLastMsgText
	}
	STATUS		current
	DESCRIPTION	"Conformance statement for hicomDiscinfoGroup."
	::=	{ hicomDiscovTree 2 }


-- Trap Variables

	hicomEDTrpPabxId	OBJECT-TYPE
		SYNTAX		Integer32
		MAX-ACCESS	read-only
		STATUS		current
		DESCRIPTION	"Unique identifier of a Hicom system."
		::=	{ hicomDiscTrapVariables 1 }

	hicomEDTrpPabxMnemonic OBJECT-TYPE
		SYNTAX		DisplayString
		MAX-ACCESS 	read-only
		STATUS		current
		DESCRIPTION	"Mnemonic name of the Hicom system."
		::=	{ hicomDiscTrapVariables 2 }

-- Traps discovery agent

internalMessageDiscSubagent	NOTIFICATION-TYPE
	OBJECTS		{ hicomDiscSubagentLastMsgNo, 
			  hicomDiscSubagentLastMsgText }
	STATUS		current
	DESCRIPTION	"An internalMessage trap contains an informational
			 message generated by the subagent."
	::=	{ hicomDiscTraps 0 }

internalWarningDiscSubagent	NOTIFICATION-TYPE
	OBJECTS		{ hicomDiscSubagentLastMsgNo, 
			  hicomDiscSubagentLastMsgText }
	STATUS		current
	DESCRIPTION	"An internalWarning trap contains a warning message
			 generated by a subagent."
	::=	{ hicomDiscTraps 1 }

internalErrorDiscSubagent	NOTIFICATION-TYPE
	OBJECTS		{ hicomDiscSubagentLastMsgNo, 
			  hicomDiscSubagentLastMsgText }
	STATUS		current
	DESCRIPTION	"An internalError trap contains an error message
			 generated by a subagent. 
			 After issuing this trap, the agent terminates."
	::=	{ hicomDiscTraps 2 }

-- error message deletion successfully terminated

hicomErrDeleteSucc	NOTIFICATION-TYPE
	OBJECTS	{ hicomEDTrpPabxId, hicomEDTrpPabxMnemonic }
	STATUS	current
	DESCRIPTION	"A hicomErrDeleteSucc trap indicates the
				successful termination of an Error Message Delete  process.
				hicomErrDeletePabxId indicates the Pbx involved."
	::=	{ hicomDiscTraps 10 }

-- error message deletion unsuccessfully terminated

hicomErrDeleteErr	NOTIFICATION-TYPE
	OBJECTS	{ hicomEDTrpPabxId, hicomEDTrpPabxMnemonic}
	STATUS	current
	DESCRIPTION	"A hicomErrDeleteErr trap signifies the
				unsuccessful termination of an Error Message Delete process.
				hicomErrDeletePabxId indicates the Pbx involved."
	::=	{ hicomDiscTraps 11 }

-- error message deletion is busy

hicomErrDeleteBusy	NOTIFICATION-TYPE
	OBJECTS	{ hicomEDTrpPabxId, hicomEDTrpPabxMnemonic}
	STATUS	current
	DESCRIPTION	"A hicomErrDeleteBusy trap signifies
				that an Error Message Delete process is running.
				hicomErrDeletePabxId indicates the Pbx involved."
	::=	{ hicomDiscTraps 19 }

-- BEGIN BLOCK hipathmgragt

procadmin OBJECT IDENTIFIER ::= { hipath4000Supervisor 1 }

	processNumber		OBJECT-TYPE
		SYNTAX		Integer32
		MAX-ACCESS	read-only
		STATUS		current
		DESCRIPTION	"The number of processes observed by
	  			procadmin."
	::= { procadmin 1 }

	processTable OBJECT-TYPE
		SYNTAX		SEQUENCE OF ProcessEntry
		MAX-ACCESS	not-accessible
		STATUS		current
 		DESCRIPTION	"A list of processes observed by procadmin.
				The number of entries is given by
				the value processNumber."
	::= { procadmin 2 }

	refreshProcessList OBJECT-TYPE
		SYNTAX		INTEGER {
					off ( 0 ),
					on  ( 1 )
					}
		MAX-ACCESS	read-write
		STATUS		current
		DESCRIPTION	"Reinitialize actual list of daemons shown
				by procadmin.The value of processNumber
				can be changed."
	::= { procadmin 3 }

	processEntry OBJECT-TYPE
		SYNTAX		ProcessEntry
		MAX-ACCESS	not-accessible
		STATUS		current
		DESCRIPTION	"An process entry containing info about
				particular process controled by procadmin."
		INDEX		{ processIndex }
	::= { processTable 1 }

	ProcessEntry ::= SEQUENCE {
		processIndex		Integer32,
		processDescr		DisplayString,
		processStatus		INTEGER,
		processStartDate	DisplayString,
		processRegGroup		DisplayString,
		processID		Integer32
	}

	processIndex OBJECT-TYPE
		SYNTAX		Integer32 (1..65534)
		MAX-ACCESS	read-only
		STATUS		current
		DESCRIPTION	"A unique value for each process.
				Its value ranges between 1 and the value of
				processNumber. The value for each process
				must remain constant at least from one
				re-initialization of the process entity's
				to the next re-initialization."
	::= { processEntry 1 }

	processDescr OBJECT-TYPE
		SYNTAX		DisplayString (SIZE(0..255))
		MAX-ACCESS	read-only
		STATUS		current
		DESCRIPTION	"A textual string containing information about
				the process. This string should include the name
				of the process shown by procadmin"
	::= { processEntry 2 }

	processStatus OBJECT-TYPE
		SYNTAX		INTEGER {
					active( 1 ),
					inactive( 2 ),
					registered( 3 ),
					starting( 4 ),
					startupDeferred( 5 ),
					startupTimeOut( 6 )
				}
		MAX-ACCESS	read-only
		STATUS		current
		DESCRIPTION	"The actual status of the process shown
				by procadmin."
	::= { processEntry 3 }

	processStartDate OBJECT-TYPE
		SYNTAX		DisplayString (SIZE(0..255))
		MAX-ACCESS	read-only
		STATUS		current
		DESCRIPTION	"The actual Date and time when the process
				was started."
	::= { processEntry 4 }

	processRegGroup OBJECT-TYPE
		SYNTAX		DisplayString (SIZE(0..255))
		MAX-ACCESS	read-only
		STATUS		current
		DESCRIPTION	"The registration group of the process"
	::= { processEntry 5 }

	processID OBJECT-TYPE
		SYNTAX		Integer32
		MAX-ACCESS	read-only
		STATUS		current
		DESCRIPTION	"ID of the procces provided by operating
				system - PID. If the process is not running
				the PID is 0"
	::= { processEntry 6 }

--=========================================================================
--The SNMP MIB table for disk partition filesystem monitoring
--=========================================================================
diskFileSys OBJECT IDENTIFIER ::= { hipath4000Supervisor 2 }

	numberOfPartition OBJECT-TYPE
		SYNTAX		Integer32
		MAX-ACCESS	read-only
		STATUS		current
		DESCRIPTION	"The number of file system partition
				gathered from command df -k."
	::= { diskFileSys 1 }


	fileSysTable OBJECT-TYPE
		SYNTAX		SEQUENCE OF DiskPartitionEntry
		MAX-ACCESS	not-accessible
		STATUS		current
		DESCRIPTION	"The table of disk partition filesystem 
				monitoring."
	::= { diskFileSys 2 }

	refreshVolumeList OBJECT-TYPE
		SYNTAX		INTEGER{
					off ( 0 ),
					on  ( 1 )
				}
		MAX-ACCESS	read-write
		STATUS		current
		DESCRIPTION	"Reinitialize actual list of volumes
				in fileSysTable. After reinitialization
				the value of partitionNumber can be changed."
	::= { diskFileSys 3 }

	diskPartitionEntry OBJECT-TYPE
		SYNTAX		DiskPartitionEntry
		MAX-ACCESS	not-accessible
		STATUS		current
		DESCRIPTION	"The information about the partition
				on the disk filesystem."
		INDEX		{ volumeIndex }
	::= { fileSysTable 1 }

	DiskPartitionEntry ::= SEQUENCE {
		volumeIndex		Integer32,
		diskPartitionName	DisplayString,
		diskPartitionDataBlocs	DisplayString,
		diskPartitionUsed	DisplayString,
		diskPartitionAvailable	DisplayString,
		diskPartitionUsePercent	DisplayString,
		diskSaturationThreshold	Integer32
	}

	volumeIndex OBJECT-TYPE
		SYNTAX		Integer32 (1..255)
		MAX-ACCESS	read-only
		STATUS		current
		DESCRIPTION	"A unique value for each volume. Its value 
				ranges between 1 and the value of 
				partitionNumber. The value for each volume 
				must remain constant at least from one 
				re-initialization of the volumes entity's 
				to the next re-initialization. Reinitialization
				can be done by setting 1 on refreshVolumeList."
	::= { diskPartitionEntry 1 }

	diskPartitionName OBJECT-TYPE
		SYNTAX		DisplayString
		MAX-ACCESS	read-only
		STATUS		current
		DESCRIPTION	"Name of the partition."
	::= { diskPartitionEntry 2 }

	diskPartitionDataBlocs OBJECT-TYPE
		SYNTAX		DisplayString
		MAX-ACCESS	read-only
		STATUS		current
		DESCRIPTION	"Size of the partition in kilo bytes."
	::= { diskPartitionEntry 3 }

	diskPartitionUsed OBJECT-TYPE
		SYNTAX		DisplayString
		MAX-ACCESS	read-only
		STATUS		current
		DESCRIPTION	"The fill space on disk partition in kilo bytes."
	::= { diskPartitionEntry 4 }

	diskPartitionAvailable OBJECT-TYPE
		SYNTAX		DisplayString
		MAX-ACCESS	read-only
		STATUS		current
		DESCRIPTION	"The available space on disk partition in kilo bytes."
	::= { diskPartitionEntry 5 }

	diskPartitionUsePercent OBJECT-TYPE
		SYNTAX		DisplayString
		MAX-ACCESS	read-only
		STATUS		current
		DESCRIPTION	"The percentage free space on disk partition."
	::= { diskPartitionEntry 6 }

	diskSaturationThreshold OBJECT-TYPE
		SYNTAX		INTEGER (0..100)
		MAX-ACCESS	read-write
		STATUS		current
		DESCRIPTION	"The threshold value for alarm monitoring of
				the saturation of partial harddisk volume
				in percentage. Set this value to 0 to
				deactivate disk saturation threshold monitoring."
	::= { diskPartitionEntry 7 }

--=========================================================================
--The SNMP MIB table for running snmp agents
--=========================================================================
hiPathSubagents OBJECT IDENTIFIER ::= { hipath4000Supervisor 3 }

	agentTable OBJECT-TYPE
		SYNTAX		SEQUENCE OF AgentEntry
		MAX-ACCESS	not-accessible
		STATUS		current
		DESCRIPTION	"A list of SNMP subagents."
	::= { hiPathSubagents 1 }

	agentEntry OBJECT-TYPE
		SYNTAX		AgentEntry
		MAX-ACCESS	not-accessible
		STATUS		current
		DESCRIPTION	"An SNMP agent entry containing info
				about status of particular Agent"
		INDEX		{ agentIndex }
	::= { agentTable 1 }

	AgentEntry ::= SEQUENCE {
			agentIndex	INTEGER,
			agentStatus	INTEGER,
			agentPID	Integer32
	}

	agentIndex OBJECT-TYPE
		SYNTAX	INTEGER {
				systemagt( 1 ),
				alarmagt( 2 ),
				erroragt( 3 ),
				softagt( 4 ),
				hardagt( 5 ),
				topoagt( 6 ),
				sqlagt( 7 ),
				disagt( 8 ),
				portagt( 9 ),
				mib2agt ( 10 )
			}
		MAX-ACCESS	read-only
		STATUS		current
		DESCRIPTION	"A unique value for each subagent."
	::= { agentEntry 1 }

	agentStatus OBJECT-TYPE
		SYNTAX	INTEGER {
				running( 1 ),
				stopped( 2 ),
				restart( 3 )
			}
		MAX-ACCESS	read-write
		STATUS		current
		DESCRIPTION	"A status of particular subagent.
				Can be used for stopping/starting subagent.
				Beteween the agents are stop/start dependences:
				1. In case of restart systemagt, the agents softagt,
				   alarmagt, hardagt, topoagt, erroragt, disagt are
				   also automatically restarted
				2. In case of restart softagt, topoagt, hardagt
				    or erroragt the disagt is also automatically 
				    restarted"

	::= { agentEntry 2 }

	agentPID OBJECT-TYPE
		SYNTAX		Integer32
		MAX-ACCESS	read-only
		STATUS		current
		DESCRIPTION	"Process ID of the particular subagent."
	::= { agentEntry 3 }

 --=========================================================================
 --The SNMP MIB table for PM, LogM db threshold management
 --=========================================================================
dbThreshold OBJECT IDENTIFIER ::= { hipath4000Supervisor 4 }

logmDatabase OBJECT IDENTIFIER ::= { dbThreshold 1 }

	activityThreshold OBJECT-TYPE
		SYNTAX		Integer32
		MAX-ACCESS	read-write
		STATUS		current
		DESCRIPTION	"Threshold set on activity table of LogM 
				database."
		::= { logmDatabase 1 }

	errorThreshold OBJECT-TYPE
		SYNTAX		Integer32
		MAX-ACCESS	read-write
		STATUS		current
		DESCRIPTION	"Threshold set on error table of LogM 
				database."
	::= { logmDatabase 2 }

	activityCount OBJECT-TYPE
		SYNTAX		Integer32
		MAX-ACCESS	read-only
		STATUS		current
		DESCRIPTION	"Number of entries in activity table of LogM
				database."
	::= { logmDatabase 3 }

	errorCount OBJECT-TYPE
		SYNTAX		Integer32
		MAX-ACCESS	read-only
		STATUS		current
		DESCRIPTION	"Number of entries in error table of LogM
				database."
	::= { logmDatabase 4 }

pmDatabase OBJECT IDENTIFIER ::= { dbThreshold 2 }

	pmDBThreshold OBJECT-TYPE
		SYNTAX		Integer32
		MAX-ACCESS	read-write
		STATUS		current
		DESCRIPTION	"Threshold set on error table of LogM
				database."
	::= { pmDatabase 1 }

 --=========================================================================
 --The SNMP MIB for lmt management
 --=========================================================================
lmt OBJECT IDENTIFIER ::= { hipath4000Supervisor 5 }

	numberOfAdminGroups OBJECT-TYPE
		SYNTAX		Integer32
		MAX-ACCESS	read-only
		STATUS		current
		DESCRIPTION	"Number of the Admin Groups managed by LMT."
	::= { lmt 1 }

	adminGroupTable OBJECT-TYPE
		SYNTAX		SEQUENCE OF AdminGroupEntry
		MAX-ACCESS	not-accessible
		STATUS		current
		DESCRIPTION 	"A list of administration groups managed by LMT."
	::= { lmt 2 }

	refreshAdminGroupsList OBJECT-TYPE
		SYNTAX		INTEGER{
					off ( 0 ),
					on  ( 1 )
				}
		MAX-ACCESS	read-write
		STATUS		current
		DESCRIPTION	"Refresh list of the Admin Groups
				managed by LMT."
	::= { lmt 3 }

	adminGroupEntry OBJECT-TYPE
		SYNTAX		AdminGroupEntry
		MAX-ACCESS	not-accessible
		STATUS		current
		DESCRIPTION	"Contains info about the particular
				administration group."
		INDEX		{ adminGroupID }
	::= { adminGroupTable 1 }

	AdminGroupEntry ::= SEQUENCE {
		adminGroupID Integer32,
		numberOfHicoms Integer32,
		standbyHicoms Integer32,
		resolvedHicoms Integer32,
		licenseReduction INTEGER
	}

	adminGroupID OBJECT-TYPE
		SYNTAX		Integer32 (0..255)
		MAX-ACCESS	read-only
		STATUS		current
		DESCRIPTION	"A unique ID for each admin group. Its value
				ranges between 0 and the value of
				numberOfAdminGroups. The value for each
				admin group must remain constant at
				least from one re-initialization of the group
				entity's to the next re-initialization.
				Reinitialization can be done by setting 1 on
				refreshAdminGroupsList."
	::= { adminGroupEntry 1 }

	numberOfHicoms OBJECT-TYPE
		SYNTAX		Integer32
		MAX-ACCESS	read-only
		STATUS		current
		DESCRIPTION	"Number of hicoms in particular admin group."
	::= { adminGroupEntry 2 }

	standbyHicoms OBJECT-TYPE
		SYNTAX		Integer32
		MAX-ACCESS	read-only
		STATUS		current
		DESCRIPTION	"Number of standby hicoms in particular 
				admin group."
	::= { adminGroupEntry 3 }

	resolvedHicoms OBJECT-TYPE
		SYNTAX		Integer32
		MAX-ACCESS	read-only
		STATUS		current
		DESCRIPTION	"Number of resolved hicoms in particular 
				admin group."
	::= { adminGroupEntry 4 }

	licenseReduction OBJECT-TYPE
		SYNTAX		INTEGER (1..100)
		MAX-ACCESS	read-only
		STATUS		current
		DESCRIPTION	"License reduction done by LMT in percentage."
	::= { adminGroupEntry 5 }

 --=========================================================================
 --The SNMP MIB for COL backup management
 --=========================================================================
backupApp OBJECT IDENTIFIER ::= { hipath4000Supervisor 6 }

	colBackup OBJECT-TYPE
		SYNTAX		INTEGER {
					activated( 1 ),
					deactivated( 2 )
					}
		MAX-ACCESS	read-write
		STATUS		current
		DESCRIPTION	"Status of backup AScol component.
				You can activate it or deactivate it."
	::= { backupApp 1 }

 --=========================================================================
 --The SNMP MIB table for dipasBatch management
 --=========================================================================
dipasBatch OBJECT IDENTIFIER ::= { hipath4000Supervisor 7 }

	onlineRepeatCount OBJECT-TYPE
		SYNTAX		Integer32
		MAX-ACCESS	read-write
		STATUS		current
		DESCRIPTION	"Repeat count for online batch processing
				(FAMOS connection)."
	::= { dipasBatch 1 }

	onlineRepeatInt OBJECT-TYPE
		SYNTAX		Integer32
		MAX-ACCESS	read-write
		STATUS		current
		DESCRIPTION	"Repeat interval in minutes for online
				batch processing (FAMOS connection)."
	::= { dipasBatch 2 }

	offlineRepeatCount OBJECT-TYPE
		SYNTAX		Integer32
		MAX-ACCESS	read-write
		STATUS		current
		DESCRIPTION	"Repeat count for offline batch processing
				(file transfer)."
	::= { dipasBatch 3 }

	offlineRepeatInt OBJECT-TYPE
		SYNTAX		Integer32
		MAX-ACCESS	read-write
		STATUS		current
		DESCRIPTION	"Repeat interval in minutes for offline
				batch processing (file transfer)."
	::= { dipasBatch 4 }


hipath4000SupervisorInfo OBJECT IDENTIFIER ::= { hipath4000Supervisor 8 }

-- hipath4000Supervisor subagent Trap Variables
	hipath4000SupervisorTrpUserName OBJECT-TYPE
		SYNTAX		DisplayString
		MAX-ACCESS	read-only
		STATUS		current
		DESCRIPTION	"User account name."
	::= { hipath4000SupervisorTrapVariables 1 }

	hipath4000SupervisorSubagentLastMsgNo OBJECT-TYPE
		SYNTAX		Integer32
		MAX-ACCESS	read-only
		STATUS		current
		DESCRIPTION	"The last message, warning or error number
				issued by the Manager subagent."
	::= { hipath4000SupervisorInfo 1 }

	hipath4000SupervisorSubagentLastMsgText    OBJECT-TYPE
		SYNTAX		DisplayString
		MAX-ACCESS	read-only
		STATUS		current
		DESCRIPTION	"The last message, warning or error text
				issued by the Manager subagent."
	::= { hipath4000SupervisorInfo 2 }

-- conformance information
-- units of conformance

hipath4000SupervisorProcadminGroup	OBJECT-GROUP
		OBJECTS {
			processNumber,
			processIndex,
			processDescr,
			processStatus,
			processStartDate,
			processRegGroup,
			processID,
			refreshProcessList
		}
		STATUS		current
		DESCRIPTION	"Conformance statement for hipath4000SupervisorProcadminGroup"
	::= { hipath4000SupervisorTree 1 }

hipath4000SupervisorFilesystemGroup    OBJECT-GROUP
		OBJECTS {
			numberOfPartition,
      volumeIndex,
			diskPartitionName,
			diskPartitionDataBlocs,
			diskPartitionUsed,
			diskPartitionAvailable,
			diskPartitionUsePercent,
      refreshVolumeList
		}
		STATUS		current
		DESCRIPTION	"Conformance statement for hipath4000SupervisorFilesystemGroup"
	::= { hipath4000SupervisorTree 2 }

hipath4000SupervisorSubagentsGroup    OBJECT-GROUP
		OBJECTS {
			agentIndex,
			agentStatus,
			agentPID
		}
		STATUS		current
		DESCRIPTION	"Conformance statement for hipath4000SupervisorSubagentsGroup"
	::= { hipath4000SupervisorTree 3 }

hipath4000SupervisorDatabaseGroup    OBJECT-GROUP
		OBJECTS {
			activityCount,
			errorCount,
                        activityThreshold,
			errorThreshold,
			pmDBThreshold
		}
		STATUS		current
		DESCRIPTION	"Conformance statement for hipath4000SupervisorDatabaseGroup"
	::= { hipath4000SupervisorTree 4 }

hipath4000SupervisorLMTGroup    OBJECT-GROUP
		OBJECTS {
                         numberOfAdminGroups,
                         adminGroupID,
                         numberOfHicoms,
                         standbyHicoms,
                         resolvedHicoms,
                         licenseReduction,
                         refreshAdminGroupsList
		}
		STATUS		current
		DESCRIPTION	"Conformance statement for hipath4000SupervisorLMTGroup"
	::= { hipath4000SupervisorTree 5 }

hipath4000SupervisorCOLGroup    OBJECT-GROUP
		OBJECTS {
			colBackup
		}
		STATUS		current
		DESCRIPTION	"Conformance statement for hipath4000SupervisorCOLGroup"
	::= { hipath4000SupervisorTree 6 }

hipath4000SupervisorBatchGroup    OBJECT-GROUP
		OBJECTS {
			onlineRepeatCount,
			onlineRepeatInt,
			offlineRepeatCount,
			offlineRepeatInt
		}
		STATUS		current
		DESCRIPTION	"Conformance statement for hipath4000SupervisorBatchGroup"
	::= { hipath4000SupervisorTree 7 }

hipath4000SupervisorInfoGroup    OBJECT-GROUP
		OBJECTS {
			hipath4000SupervisorSubagentLastMsgNo,
			hipath4000SupervisorSubagentLastMsgText
		}
		STATUS		current
		DESCRIPTION	"Conformance statement for hipath4000SupervisorInfoGroup"
	::= { hipath4000SupervisorTree 8 }

-- hipath4000Supervisor agent Traps

internalMessageManagerSubagent NOTIFICATION-TYPE
	OBJECTS		{ hipath4000SupervisorSubagentLastMsgNo, hipath4000SupervisorSubagentLastMsgText }
	STATUS		current
	DESCRIPTION	"An internalMessage trap contains an informational
			message generated by the subagent."
	::= { hipath4000SupervisorTraps 0 }

internalWarningManagerSubagent NOTIFICATION-TYPE
	OBJECTS		{ hipath4000SupervisorSubagentLastMsgNo, hipath4000SupervisorSubagentLastMsgText }
	STATUS		current
	DESCRIPTION	"An internalWarning trap contains a warning message
			generated by a subagent."
	::= { hipath4000SupervisorTraps 1 }

internalErrorManagerSubagent NOTIFICATION-TYPE
	OBJECTS		{ hipath4000SupervisorSubagentLastMsgNo, hipath4000SupervisorSubagentLastMsgText }
	STATUS		current
	DESCRIPTION	"An internalError trap contains an error message
			generated by a subagent.
			After issuing this trap, the agent terminates."
	::= { hipath4000SupervisorTraps 2 }

hipath4000SupervisorAcountLocked NOTIFICATION-TYPE
	OBJECTS		{ hipath4000SupervisorTrpUserName }
	STATUS		current
	DESCRIPTION	"A hipath4000SupervisorAcountLocked trap is sent 
			when account of some user is locked."
	::= { hipath4000SupervisorTraps 3 }

hipath4000SupervisorFileSysTableReinit NOTIFICATION-TYPE
	STATUS		current
	DESCRIPTION	"An inform trap is sent when the fileSysTable
			is reinitialized."
	::= { hipath4000SupervisorTraps 4 }

hipath4000SupervisorProcessTableReinit NOTIFICATION-TYPE
	STATUS		current
	DESCRIPTION	"An inform trap is sent when the processTable 
			is reinitialized."
	::= { hipath4000SupervisorTraps 5 }

hipath4000SupervisorAdminGroupTableReinit NOTIFICATION-TYPE
	STATUS  	current
	DESCRIPTION	"An inform trap is sent when the adminGroupTable 
			is reinitialized."
	::= { hipath4000SupervisorTraps 6 }

-- BEGIN BLOCK common



systemRebootTime OBJECT-TYPE
		SYNTAX		DisplayString
		MAX-ACCESS	read-only
		STATUS		current
		DESCRIPTION	"Last reboot time of the host operating system."
	::= { commonManagement 1 }

systemVersion OBJECT-TYPE
		SYNTAX		DisplayString (SIZE(0..255))
		MAX-ACCESS	read-only
		STATUS		current
		DESCRIPTION	"Textual string containing kernel version of the host operating system."
	::= { commonManagement 2 }

systemCPU OBJECT-TYPE
		SYNTAX		Integer32
		MAX-ACCESS	read-only
		STATUS		current
		DESCRIPTION	"CPU usage of the host system."
	::= { commonManagement 3 }

systemTime OBJECT-TYPE
                SYNTAX          DisplayString
                MAX-ACCESS      read-only
                STATUS          current
                DESCRIPTION     "Actual OS time."
        ::= { commonManagement 4 }

systemMemory OBJECT IDENTIFIER ::= { commonManagement 5 }

systemPhysicalMemoryTotal OBJECT-TYPE
		SYNTAX		Integer32
		MAX-ACCESS	read-only
		STATUS		current
		DESCRIPTION	"Amount of total physical memory of the host operating system."
	::= { systemMemory 1 }

systemPhysicalMemoryUsed OBJECT-TYPE
		SYNTAX		Integer32
		MAX-ACCESS	read-only
		STATUS		current
		DESCRIPTION	"Amount of used physical memory of the host operating system."
	::= { systemMemory 2 }

systemSwapMemoryTotal OBJECT-TYPE
		SYNTAX		Integer32
		MAX-ACCESS	read-only
		STATUS		current
		DESCRIPTION	"Amount of total swap memory of the host operating system."
	::= { systemMemory 3 }

systemSwapMemoryUsed OBJECT-TYPE
		SYNTAX		Integer32
		MAX-ACCESS	read-only
		STATUS		current
		DESCRIPTION	"Amount of used swap memory of the host operating system."
	::= { systemMemory 4 }

commonDiscovery OBJECT IDENTIFIER ::= { commonManagement 10 }

commonDiscoveryDateTime	OBJECT-TYPE
		SYNTAX		DisplayString
		MAX-ACCESS	read-only
		STATUS		current
		DESCRIPTION	"Date and time of the last successful discovery."
		::=	{ commonDiscovery 1 }

commonDiscoveryStatus OBJECT-TYPE
		SYNTAX		INTEGER {
					done( 1 ),
					error ( 2 ),
					busy ( 3 )
					}
		MAX-ACCESS	read-write
		STATUS		current
		DESCRIPTION	"Setting to 'busy' reinitialize all common managent data.
                                 Whenever the re-initialization is finished the status is 'done'"
	::= { commonDiscovery 2 }


subSystems OBJECT IDENTIFIER ::= { commonManagement 20 }

subSystemState OBJECT IDENTIFIER ::= { subSystems 1 }

	subSystemNumber		OBJECT-TYPE
		SYNTAX		Integer32
		MAX-ACCESS	read-only
		STATUS		current
		DESCRIPTION	"Number of subsystems or virtual machines installed and running on the host system."
	::= { subSystemState 1 }

	subSystemTable OBJECT-TYPE
		SYNTAX		SEQUENCE OF MachineTableEntry
		MAX-ACCESS	not-accessible
		STATUS		current
 		DESCRIPTION	"List of subsystems or virtual machines managed by the host system.
				 Number of entries is given by the subSystemNumber value."
	::= { subSystemState 2 }

	subSystemTableEntry OBJECT-TYPE
		SYNTAX		MachineTableEntry
		MAX-ACCESS	not-accessible
		STATUS		current
		DESCRIPTION	"Subsystem table entry containing info about
				particular subsystem or virtual machine running on the host system."
		INDEX		{ subSystemIndex }
	::= { subSystemTable 1 }

	MachineTableEntry ::= SEQUENCE {
		subSystemIndex		Integer32,
		subSystemName     	DisplayString,
		subSystemStatus		INTEGER,
		subSystemRebootTime		DisplayString
	}

	subSystemIndex OBJECT-TYPE
		SYNTAX		Integer32 (1..10)
		MAX-ACCESS	read-only
		STATUS		current
		DESCRIPTION	"Unique value for each subsystem or virtual machine.
				Its value ranges between 1 and the value of
				subSystemNumber. The value for each machine
				remains constant at least from one
				re-initialization of the subSystem entity's
				to the next re-initialization."
	::= { subSystemTableEntry 1 }

	subSystemName OBJECT-TYPE
		SYNTAX		DisplayString (SIZE(0..255))
		MAX-ACCESS	read-only
		STATUS		current
		DESCRIPTION	"Textual string containing name of the subsystem or virtual machine installed on the host system.
				 Example values: ADP, CCA, CCB, CSTA, Assistant, Manager, Platform, HiPathFM, SoftGate ..."
	::= { subSystemTableEntry 2 }

	subSystemStatus OBJECT-TYPE
		SYNTAX		INTEGER {
					green( 1 ),
					yellow( 2 ),
					red( 3 )
				}
		MAX-ACCESS	read-only
		STATUS		current
		DESCRIPTION	"Health status of the subsytem or virtual machine from the global point of view."
	::= { subSystemTableEntry 3 }

	subSystemRebootTime OBJECT-TYPE
		SYNTAX		DisplayString (SIZE(0..255))
		MAX-ACCESS	read-only
		STATUS		current
		DESCRIPTION	"Last reboot time of the subsystem or virtual machine."
	::= { subSystemTableEntry 4 }

--- Information about the software versions for products installed on the system

versionInfo OBJECT IDENTIFIER ::= { subSystems 2 }

	productNumber		OBJECT-TYPE
		SYNTAX		Integer32
		MAX-ACCESS	read-only
		STATUS		current
		DESCRIPTION	"Number of products installed on the host system."
	::= { versionInfo 1 }

	productVersionTable OBJECT-TYPE
		SYNTAX		SEQUENCE OF ProductVersionEntry
		MAX-ACCESS	not-accessible
		STATUS		current
 		DESCRIPTION	"List of the products running on the host system.
				The number of products is given by
				the productNumber value."
	::= { versionInfo 2 }

	productVersionEntry OBJECT-TYPE
		SYNTAX		ProductVersionEntry
		MAX-ACCESS	not-accessible
		STATUS		current
		DESCRIPTION	"Product version entry containing info about
				particular product running on the host system."
		INDEX		{ productIndex }
	::= { productVersionTable 1 }

	ProductVersionEntry ::= SEQUENCE {
		productIndex		Integer32,
		productName     	DisplayString,
		productDescription      DisplayString,
		productVersion		DisplayString
	}

	productIndex OBJECT-TYPE
		SYNTAX		Integer32 (1..2147483647)
		MAX-ACCESS	read-only
		STATUS		current
		DESCRIPTION	"Unique value for each product installed on the host system.
				Its value ranges between 1 and the value of
				productNumber. The value for each product
				remains constant at least from one
				re-initialization of the product entity's
				to the next re-initialization."
	::= { productVersionEntry 1 }

	productName OBJECT-TYPE
		SYNTAX		DisplayString (SIZE(0..255))
		MAX-ACCESS	read-only
		STATUS		current
		DESCRIPTION	"Textual string containing identifier of software product.
				 Example values: RMX, Assistant, CSTA, SoftGate, Manager, HiPathFM ..."
	::= { productVersionEntry 2 }

	productDescription OBJECT-TYPE
		SYNTAX		DisplayString (SIZE(0..255))
		MAX-ACCESS	read-only
		STATUS		current
		DESCRIPTION	"Textual string containing description of the software product."
	::= { productVersionEntry 3 }

	productVersion OBJECT-TYPE
		SYNTAX		DisplayString (SIZE(0..255))
		MAX-ACCESS	read-only
		STATUS		current
		DESCRIPTION	"The version of the software product."
	::= { productVersionEntry 4 }

--- license information for the products running on the system

licenseInfo                       OBJECT IDENTIFIER ::= { subSystems 3 }

        globalLicenseStatus OBJECT-TYPE
		SYNTAX		INTEGER {
		                     gp ( 0 ),
		                     ok ( 1 ),
		                     error ( 2 )
                                }
		MAX-ACCESS	read-only
		STATUS		current
		DESCRIPTION	"The license sumarization for the whole system.
				 Possible values:
				 gp ... in case of some of the product installed on the system is running in the grace period.
				 ok ... all the products installed on the system have valid license.
				 error ... some of the products has invalid license stuff."
	::= { licenseInfo 1 }

        licenseNumber		OBJECT-TYPE
		SYNTAX		Integer32
		MAX-ACCESS	read-only
		STATUS		current
		DESCRIPTION	"Number of the license types used by the host system and its subsystems."
	::= { licenseInfo 2 }

	licenseTable OBJECT-TYPE
		SYNTAX		SEQUENCE OF LicenseEntry
		MAX-ACCESS	not-accessible
		STATUS		current
 		DESCRIPTION	"List of the license types used by the host system and its subsystems.
				 Number is given by the licenseNumber value."
	::= { licenseInfo 3 }

	licenseEntry OBJECT-TYPE
		SYNTAX		LicenseEntry
		MAX-ACCESS	not-accessible
		STATUS		current
		DESCRIPTION	"License entry containing info about
				 particular licenses used by the host system and its subsystems."
		INDEX		{ licenseIndex }
	::= { licenseTable 1 }

	LicenseEntry ::= SEQUENCE {
		licenseIndex		Integer32,
		licenseName     	DisplayString,
                licenseValidity         Integer32,
                licenseGracePeriod      INTEGER
	}

	licenseIndex OBJECT-TYPE
		SYNTAX		Integer32 (1..2147483647)
		MAX-ACCESS	read-only
		STATUS		current
		DESCRIPTION	"Unique value for each license type.
				Its value ranges between 1 and the value of
				licenseNumber. The value for each license
				remains constant at least from one
				re-initialization of the license entity's
				to the next re-initialization."
	::= { licenseEntry 1 }

	licenseName OBJECT-TYPE
		SYNTAX		DisplayString (SIZE(0..255))
		MAX-ACCESS	read-only
		STATUS		current
		DESCRIPTION	"Textual string containing name of the license."
	::= { licenseEntry 2 }

	licenseValidity OBJECT-TYPE
                SYNTAX		Integer32
		MAX-ACCESS	read-only
		STATUS		current
		DESCRIPTION	"Value containing validity of the license in days.
				 In case of the value is -1, the license is valid forever.
				 In case of the value is 0, the license expired."
	::= { licenseEntry 3 }

	licenseGracePeriod OBJECT-TYPE
                SYNTAX		INTEGER {
                                         yes ( 1 ),
                                         no  ( 2 )
                                }
		MAX-ACCESS	read-only
		STATUS		current
		DESCRIPTION	"yes ... in case of the license is a grace period license.
				 no  ... in case of the license is a customer license."
	::= { licenseEntry 4 }

configurationManagement           OBJECT IDENTIFIER ::= { commonManagement 30 }

dataSynchronization               OBJECT IDENTIFIER ::= { configurationManagement 1 }

----
--dbsync table
	dbsyncTypeNumber         OBJECT-TYPE
		SYNTAX          Integer32
		MAX-ACCESS      read-only
		STATUS          current
		DESCRIPTION     "Number of the database synchronization types used on the system."
	::= { dataSynchronization 1 }

	dbsyncTable OBJECT-TYPE
		SYNTAX          SEQUENCE OF DbsyncEntry
		MAX-ACCESS      not-accessible
		STATUS          current
		DESCRIPTION     "List of the database synchronization types on the system.
				 The number is given by the value dbsyncTypeNumber."
	::= { dataSynchronization 2 }

	dbsyncEntry OBJECT-TYPE
		SYNTAX          DbsyncEntry
		MAX-ACCESS      not-accessible
		STATUS          current
		DESCRIPTION     "Dbsync entry contaning info about
				 last database synchronization executed on the sytem."
		INDEX           { dbsyncIndex }
	::= { dbsyncTable 1 }

        DbsyncEntry ::= SEQUENCE {
                dbsyncIndex             Integer32,
                dbsyncType              DisplayString,
		dbsyncDescription	DisplayString,
                dbsyncState             INTEGER
        }

	dbsyncIndex OBJECT-TYPE
		SYNTAX          Integer32 (1..2147483647)
		MAX-ACCESS      read-only
		STATUS          current
		DESCRIPTION     "Unique value for each synchronization type.
				 Its value ranges between 1 and the value of
				 dbsyncTypeNumber. The value for each synchronization type
				 remains constant."
	::= { dbsyncEntry 1 }

        dbsyncType OBJECT-TYPE
                SYNTAX          DisplayString (SIZE(0..255))
                MAX-ACCESS      read-only
                STATUS          current
                DESCRIPTION     "Textual string containing name of the synchronization type.
				 Example values: Upload, HIM SWU,  ..."
        ::= { dbsyncEntry 2 }

	dbsyncDescription OBJECT-TYPE
		SYNTAX	DisplayString (SIZE(0..255))
		MAX-ACCESS	read-only
		STATUS		current
		DESCRIPTION	"Textual string containing description of the synchronization type."
	::= { dbsyncEntry 3 }

        dbsyncState OBJECT-TYPE
		SYNTAX		INTEGER {
					ok( 1 ),
					failed ( 2 ),
					unknown ( 3 )
				}
		MAX-ACCESS	read-only
		STATUS		current
		DESCRIPTION	"Global status od the synchronization of given type." 
	::= { dbsyncEntry 4 }

backupManagement OBJECT IDENTIFIER ::= { commonManagement 40 }
        apeSync  OBJECT-TYPE
		SYNTAX		INTEGER {
					notSync ( 0 ),
					ok( 1 ),
					failed ( 2 ),
					unknown ( 3 )
				}
		MAX-ACCESS	read-only
		STATUS		current
		DESCRIPTION	"Status of the synchronization with the AP emergency systems.
				 ok ... last AP backup was successful and all APE systems successfully restored this backup set.
				 not_sync ... AP backup has not yet finished or APE systems haven't finished restoring of backup set yet.
				 failed ... AP backup failed or restore on any APE systems failed.
				 unknown ... Agent was not able to read the status of the APE synchronization."
	::= { backupManagement 1 }

backup OBJECT IDENTIFIER ::= { backupManagement 2 }
       backupTypeNumber		OBJECT-TYPE
		SYNTAX		Integer32
		MAX-ACCESS	read-only
		STATUS		current
		DESCRIPTION	"Number of the backup types used on the system."
	::= { backup 1 }

	backupTable OBJECT-TYPE
		SYNTAX		SEQUENCE OF BackupEntry
		MAX-ACCESS	not-accessible
		STATUS		current
 		DESCRIPTION	"List of the backup types executed on the system.
				The number of backup types is given by
				the value backupTypeNumber."
	::= { backup 2 }

	backupEntry OBJECT-TYPE
		SYNTAX		BackupEntry
		MAX-ACCESS	not-accessible
		STATUS		current
		DESCRIPTION	"Backup entry contaning info about
				last backup executed on the sytem."
		INDEX		{ backupIndex }
	::= { backupTable 1 }

	BackupEntry ::= SEQUENCE {
		backupIndex		Integer32,
		backupType        	DisplayString,
                backupDateTime        	DisplayString,
		backupState             INTEGER
	}

	backupIndex OBJECT-TYPE
		SYNTAX		Integer32 (1..2147483647)
		MAX-ACCESS	read-only
		STATUS		current
		DESCRIPTION	"Unique value for each backup type.
				Its value ranges between 1 and the value of
				backupNumber. The value for each backup type
				remains constant at least from one
				re-initialization of the backup entity's
				to the next re-initialization."
	::= { backupEntry 1 }

	backupType OBJECT-TYPE
		SYNTAX		DisplayString (SIZE(0..255))
		MAX-ACCESS	read-only
		STATUS		current
		DESCRIPTION	"Textual string containing identifier for type of the backup.
				 Example values: Data, Logical, ..."
	::= { backupEntry 2 }

	backupDateTime OBJECT-TYPE
		SYNTAX		DisplayString (SIZE(0..255))
		MAX-ACCESS	read-only
		STATUS		current
		DESCRIPTION	"The time of the latest executed backup of particular type."
	::= { backupEntry 3 }

	backupState  OBJECT-TYPE
		SYNTAX		INTEGER {
					ok( 1 ),
					failed ( 2 ),
					unknown ( 3 )
				}
		MAX-ACCESS	read-only
		STATUS		current
		DESCRIPTION	"The status of the latest executed backup of the particular type."
	::= { backupEntry 4 }

--========= NOTIFICATIONS ======================

notificationMessages     OBJECT IDENTIFIER ::= { commonManagement 90 }

syslogMessages    OBJECT IDENTIFIER ::= { notificationMessages 1 }

logmMessages OBJECT IDENTIFIER  ::= { notificationMessages 2 }

-- syslogTrapMessage variables --

syslogSeverity    OBJECT-TYPE
                  SYNTAX     INTEGER {
                                     emerg(1),
                                     alert(2),
                                     crit(3),
                                     err(4),
                                     warning(5),
                                     notice(6),
                                     info(7),
                                     debug(8)
                             }
                  MAX-ACCESS read-only
                  STATUS     current
                  DESCRIPTION       "Severity of syslog message."
::= { syslogMessages 1 }

syslogFacility    OBJECT-TYPE
                  SYNTAX     INTEGER {
                                     kern(1),
                                     user(2),
                                     mail(3),
                                     daemon(4),
                                     auth(5),
                                     syslog(6),
                                     lpr(7),
                                     news(8),
                                     uucp(9),
                                     cron(10),
                                     authpriv(11),
                                     ftp(12),
                                     local0(17),
                                     local1(18),
                                     local2(19),
                                     local3(20),
                                     local4(21),
                                     local5(22),
                                     local6(23),
                                     local7(24)
                                     }
                        MAX-ACCESS   read-only
                        STATUS       current
                        DESCRIPTION  "Facility of syslog message."
::= { syslogMessages 2 }

syslogMessageName    OBJECT-TYPE
                     SYNTAX     DisplayString
                     MAX-ACCESS     read-only
                     STATUS     current
                     DESCRIPTION         "Name identifier of the message. ( e.g. LOGIN_FAILED )"
::= { syslogMessages 3 }

syslogMessageText    OBJECT-TYPE
                     SYNTAX     DisplayString
                     MAX-ACCESS     read-only
                     STATUS     current
                     DESCRIPTION         "The text of the message. ( e.g. Login for user xxx failed) "
::= { syslogMessages 4 }

syslogMessageDateTime  OBJECT-TYPE
                       SYNTAX     DisplayString (SIZE (1..32))
                       MAX-ACCESS read-only
                       STATUS     current
                       DESCRIPTION       "The date and time when this message was generated in seconds since 1.1.1970."
::= { syslogMessages 5 }

syslogHostIDType     OBJECT-TYPE
                     SYNTAX     INTEGER {
                                     ipAddress(1),
                                     hostName(2),
                                     other(3)
                                     }
                     MAX-ACCESS     read-only
                     STATUS     current
                     DESCRIPTION         "Type of the host identifier"
::= { syslogMessages 6 }

syslogHostID         OBJECT-TYPE
                     SYNTAX     DisplayString
                     MAX-ACCESS     read-only
                     STATUS     current
                     DESCRIPTION       "Identifier for host generating syslog message.
                                       It can be IPaddress, hostName or some other string
                                       based on the syslogHostIDType."
::= { syslogMessages 7 }

syslogSubsytemID     OBJECT-TYPE
                     SYNTAX     DisplayString
                     MAX-ACCESS     read-only
                     STATUS     current
                     DESCRIPTION       "Identifier for subsystem on the host generating syslog message."
::= { syslogMessages 8 }

syslogUserName       OBJECT-TYPE
                     SYNTAX     DisplayString
                     MAX-ACCESS     read-only
                     STATUS     current
                     DESCRIPTION       "Name of the user who caused generating of the message ( may be empty )"
::= {syslogMessages 9 }

-- syslog trap message  --

syslogMessage   NOTIFICATION-TYPE
                OBJECTS { syslogSeverity,
                        syslogFacility,
                        syslogMessageName,
                        syslogMessageText,
                        syslogMessageDateTime,
                        syslogHostIDType,
                        syslogHostID,
                        syslogSubsytemID,
                        syslogUserName
                        }
                STATUS    current
                DESCRIPTION      "Notification send when syslog message is generated."
::= {  syslogMessages 10 }

-- logmMessage variables --

logmUserName       OBJECT-TYPE
                   SYNTAX     DisplayString
                   MAX-ACCESS     read-only
                   STATUS     current
                   DESCRIPTION       "Name of the user who caused generating of the message ( may be empty )."
::= {logmMessages 1 }

logmPlatformID    OBJECT-TYPE
                  SYNTAX     DisplayString
                  MAX-ACCESS     read-only
                  STATUS     current
                  DESCRIPTION       "ID of the platform which generates the message (usually an IP address)."
::= {logmMessages 2 }

logmSupplierID    OBJECT-TYPE
                  SYNTAX     DisplayString
                  MAX-ACCESS     read-only
                  STATUS     current
                  DESCRIPTION       "ID of the supplier (subsystem) which generates the message."
::= {logmMessages 3 }

logmSupplierTS    OBJECT-TYPE
                  SYNTAX     DisplayString
                  MAX-ACCESS     read-only
                  STATUS     current
                  DESCRIPTION       "Date/Time string in format YYYY-MM-DD HH:MM:SS.XXX
                                     referencing time when the message was produced by supplier."
::= {logmMessages 4 }

logmMessageCategory OBJECT-TYPE
                    SYNTAX     INTEGER {
                                     userAdd(1),
                                     userLogon(20),
                                     userLogoff(21),
                                     logonRejected(22),
                                     noPrivilege(23),
                                     information(46),
                                     inconsistency(56),
                                     security(61)
                                     }
                     MAX-ACCESS     read-only
                     STATUS     current
                     DESCRIPTION         "Category of the message - definition list is
                                          comming from system internal Logging Management."
::= { logmMessages 5 }

logmErrorSeverity   OBJECT-TYPE
                    SYNTAX     INTEGER {
                                       serious(10),
                                       caution(11),
                                       info(12),
                                       notApplicable(13)
                                     }
                     MAX-ACCESS     read-only
                     STATUS     current
                     DESCRIPTION         "Severity of the error message - definition list is
                                          comming from system internal Logging Management."
::= { logmMessages 6 }

logmMessageDescr   OBJECT-TYPE
                   SYNTAX     DisplayString
                   MAX-ACCESS     read-only
                   STATUS     current
                   DESCRIPTION       "Short textual description of the message."
::= {logmMessages 7 }

logmMessageDetails OBJECT-TYPE
                   SYNTAX     DisplayString
                   MAX-ACCESS     read-only
                   STATUS     current
                   DESCRIPTION       "Detailed description of the message (may be empty)"
::= {logmMessages 8 }

activityEvent NOTIFICATION-TYPE
              OBJECTS { logmUserName,
                        logmPlatformID,
                        logmSupplierID,
                        logmSupplierTS,
                        logmMessageCategory,
                        logmMessageDescr,
                        logmMessageDetails
              }
              STATUS  current
              DESCRIPTION    "Activity event produced by internal Logging Management of managed system"
::= { logmMessages 100 }

errorEvent NOTIFICATION-TYPE
           OBJECTS { logmUserName,
                     logmPlatformID,
                     logmSupplierID,
                     logmSupplierTS,
                     logmMessageCategory,
                     logmErrorSeverity,
                     logmMessageDescr,
                     logmMessageDetails
           }
           STATUS  current
           DESCRIPTION    "Error event produced by internal Logging Management of managed system"
::= { logmMessages 200 }


END
