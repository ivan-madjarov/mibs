EXTREME-OSPFV3-MIB DEFINITIONS ::= BEGIN

    IMPORTS
            MODULE-IDENTITY, OBJECT-TYPE, NOTIFICATION-TYPE, mib-2,
            Counter32, Gauge32, Integer32, Unsigned32
                    FROM SNMPv2-SMI
            TEXTUAL-CONVENTION, TruthValue, StorageType, RowStatus
                    FROM SNMPv2-TC
            MODULE-COMPLIANCE, OBJECT-GROUP, NOTIFICATION-GROUP
                    FROM SNMPv2-CONF
            InterfaceIndex
                    FROM IF-MIB
            InetAddressType, InetAddress, InetAddressPrefixLength,
            InetAddressIPv6
                    FROM INET-ADDRESS-MIB
            Metric, BigMetric, Status,
            HelloRange, DesignatedRouterPriority
                    FROM OSPF-MIB
            extremeAgent            FROM EXTREME-BASE-MIB;

    extremeOspfv3MIB MODULE-IDENTITY


            LAST-UPDATED "200505021200Z"
            ORGANIZATION "IETF OSPF Working Group"
            CONTACT-INFO
                "WG E-Mail: ospf@peach.ease.lsoft.com
                 WG Chairs: acee@cisco.com
                            dube.rohit@gmail.com

                 Dan Joyal
                 Nortel Networks
                 600 Technology Park Drive
                 Billerica, MA  01821, USA
                 djoyal@nortel.com

                 Vishwas Manral
                 SiNett Corporation
                 2/1, First Floor
                 Embassy Icon Annex
                 Infantry Road
                 Bangalore 560001
                 vishwas@sinett.com"

             DESCRIPTION
                 "The MIB module to describe OSPF version 3.

                  Copyright (C) The Internet Society (2005).
                  This version of this MIB module is part of
                  RFC XXXX;  see the RFC itself for full legal
                  notices."

             REVISION "200512281200Z"
             DESCRIPTION -- RFC Editor assigns RFC xxxx
                 "Initial version, published as RFC xxxx"

--      DESCRIPTION
--        This MIB module is based on Internet Draft draft-ietf-ospf-ospfv3-mib-10.txt.
--        In this initial version, extreme keyword is prepended before every
--        Textual Convention; A subset of notifications from RFC5643 are also included.

             ::= { extremeAgent 50 }

    -- Texual conventions

    ExtremeOspfv3UpToRefreshIntervalTc ::= TEXTUAL-CONVENTION
             DISPLAY-HINT "d"
             STATUS        current
             DESCRIPTION
                "The values one might be able to configure for
                variables bounded by the Refresh Interval"
             SYNTAX      Integer32 (1..1800)

    ExtremeOspfv3DeadIntRangeTc ::= TEXTUAL-CONVENTION
             DISPLAY-HINT "d"
             STATUS        current
             DESCRIPTION
                "The range, in seconds, of dead interval value."
             SYNTAX      Integer32 (1..'FFFF'h)

    ExtremeOspfv3RouterIdTc ::= TEXTUAL-CONVENTION


             DISPLAY-HINT "d"
             STATUS      current
             DESCRIPTION
                "A 32-bit, unsigned integer uniquely identifying the
                router in the Autonomous System. To ensure uniqueness,
                this may default to the value of one of the router's
                IPv4 host addresses if IPv4 is configured on the
                router."
             SYNTAX      Unsigned32 (0..'FFFFFFFF'h)

    ExtremeOspfv3AreaIdTc ::= TEXTUAL-CONVENTION
             DISPLAY-HINT "d"
             STATUS      current
             DESCRIPTION
                "An OSPFv3 Area Identifier"
             SYNTAX      Unsigned32 (0..'FFFFFFFF'h)

    ExtremeOspfv3IfInstIdTc ::= TEXTUAL-CONVENTION
             DISPLAY-HINT "d"
             STATUS      current
             DESCRIPTION
                "An OSPFv3 interface instance ID"
             SYNTAX      Integer32 (0..255)


    -- Top-level structure of MIB
    extremeOspfv3Notifications  OBJECT IDENTIFIER ::= { extremeOspfv3MIB 0 }
    extremeOspfv3Objects        OBJECT IDENTIFIER ::= { extremeOspfv3MIB 1 }
    extremeOspfv3Conformance    OBJECT IDENTIFIER ::= { extremeOspfv3MIB 2 }

    -- OSPFv3 General Variables

    -- These parameters apply globally to the Router's
    -- OSPFv3 Process.

    extremeOspfv3GeneralGroup OBJECT IDENTIFIER ::= { extremeOspfv3Objects 1 }

    extremeOspfv3RouterId OBJECT-TYPE
            SYNTAX         ExtremeOspfv3RouterIdTc
            MAX-ACCESS     read-write
            STATUS         current
            DESCRIPTION
                "A 32-bit integer uniquely identifying the
                router in the Autonomous System. To ensure
                uniqueness, this may default to the value of
                one of the router's IPv4 host addresses,
                represented as a 32-bit unsigned integer,
                if IPv4 is configured on the router."
            ::= { extremeOspfv3GeneralGroup 1 }

    extremeOspfv3AdminStat OBJECT-TYPE
            SYNTAX          Status
            MAX-ACCESS      read-write
            STATUS          current


            DESCRIPTION
                "The administrative status of OSPFv3 in the
                router. The value 'enabled' denotes that the
                OSPFv3 Process is active on at least one
                interface; 'disabled' disables it on all
                interfaces."
            ::= { extremeOspfv3GeneralGroup 2 }

    extremeOspfv3VersionNumber OBJECT-TYPE
            SYNTAX          INTEGER { version3 (3) }
            MAX-ACCESS      read-only
            STATUS          current
            DESCRIPTION
                "The version number of OSPF for IPv6 is 3."
            ::= { extremeOspfv3GeneralGroup 3 }

    extremeOspfv3AreaBdrRtrStatus OBJECT-TYPE
            SYNTAX          TruthValue
            MAX-ACCESS      read-only
            STATUS          current
            DESCRIPTION
                "A flag to note whether this router is an area
                border router."
            REFERENCE
                "OSPF Version 2, Section 3 Splitting the AS into
                Areas"
            ::= { extremeOspfv3GeneralGroup 4 }

    extremeOspfv3ASBdrRtrStatus OBJECT-TYPE
            SYNTAX          TruthValue
            MAX-ACCESS      read-write
            STATUS          current
            DESCRIPTION
                "A flag to note whether this router is
                configured as an Autonomous System border router."
            REFERENCE
                "OSPF Version 2, Section 3.3 Classification of
                routers"
            ::= { extremeOspfv3GeneralGroup 5 }

    extremeOspfv3AsScopeLsaCount OBJECT-TYPE
            SYNTAX          Gauge32
            MAX-ACCESS      read-only
            STATUS          current
            DESCRIPTION
                "The number of AS-Scope (e.g. AS-External) link state
                advertisements in the link state database."
            ::= { extremeOspfv3GeneralGroup 6 }

    extremeOspfv3AsScopeLsaCksumSum OBJECT-TYPE
            SYNTAX          Integer32
            MAX-ACCESS      read-only
            STATUS          current


            DESCRIPTION
                "The 32-bit unsigned sum of the LS checksums of
                the AS-scoped link state advertisements
                contained in the link state database. This sum
                can be  used  to determine if there has been a
                change in a router's link state database, and
                to compare the link state database of two
                routers."
            ::= { extremeOspfv3GeneralGroup 7 }

    extremeOspfv3OriginateNewLsas OBJECT-TYPE
            SYNTAX          Counter32
            MAX-ACCESS      read-only
            STATUS          current
            DESCRIPTION
                "The number of new link-state advertisements
                that have been originated.  This number is
                incremented each time the router originates a new
                LSA."
            ::= { extremeOspfv3GeneralGroup 8 }

    extremeOspfv3RxNewLsas OBJECT-TYPE
            SYNTAX          Counter32
            MAX-ACCESS      read-only
            STATUS          current
            DESCRIPTION
                "The number of link state advertisements
                received determined to be new instantiations.
                This number does not include newer
                instantiations of self-originated link state
                advertisements."
            ::= { extremeOspfv3GeneralGroup 9 }

    extremeOspfv3ExtLsaCount OBJECT-TYPE
            SYNTAX          Gauge32
            MAX-ACCESS      read-only
            STATUS          current
            DESCRIPTION
                "The number of External(LS type 0x4005) in the
                link state database"
            ::= { extremeOspfv3GeneralGroup 10 }


    extremeOspfv3ExtAreaLsdbLimit OBJECT-TYPE
            SYNTAX          Integer32 (-1..'7FFFFFFF'h)
            MAX-ACCESS      read-write
            STATUS          current
            DESCRIPTION
                "The maximum number of non-default
                AS-external-LSAs entries that can be stored in the
                link state database. If the value is -1, then
                there is no limit.



                When the number of non-default AS-external-LSAs
                in a router's link-state database reaches
                extremeOspfv3ExtAreaLsdbLimit, the router enters Overflow
                state. The router never holds more than
                extremeOspfv3ExtAreaLsdbLimit non-default AS-external-LSAs
                in its database. OspfExtAreaLsdbLimit MUST be set
                identically in all routers attached to the OSPFv3
                backbone and/or any regular OSPFv3 area. (i.e.,
                OSPFv3 stub areas and NSSAs are excluded)."
            ::= { extremeOspfv3GeneralGroup 11 }

    extremeOspfv3MulticastExtensions OBJECT-TYPE
            SYNTAX          BITS {
                                     intraAreaMulticast(0),
                                     interAreaMulticast(1),
                                     interAsMulticast(2)
                                 }

            MAX-ACCESS      read-write
            STATUS          current
            DESCRIPTION
                "A Bit Mask indicating whether the router is
                forwarding IPv6 multicast datagrams based on
                the algorithms defined in the  Multicast
                Extensions to OSPF.

                If intraAreaMulticast set, indicates that the router
                can forward IPv6 multicast datagrams in the router's
                directly attached areas (called intra-area
                multicast routing).

                If interAreaMulticast set, indicates that the router
                can forward IPv6 multicast datagrams between OSPFv3
                areas (called inter-area multicast routing).

                If interAsMulticast set, indicates that the router can
                forward  IPv6  multicast datagrams between
                Autonomous Systems (called inter-AS multicast
                routing).

                Only certain combinations of bit settings are
                allowed, namely:
                        - All bits cleared (no multicasting)
                        - intraAreaMulticast only,
                        - intraAreaMulticast and interAreaMulticast,
                        - intraAreaMulticast and interAsMulticast
                        - intraAreaMulticast, interAreaMulticast and
                                interAsMulticast
                By default, all bits are cleared."
            ::= { extremeOspfv3GeneralGroup 12 }

    extremeOspfv3ExitOverflowInterval OBJECT-TYPE
            SYNTAX          Unsigned32


            UNITS           "seconds"
            MAX-ACCESS      read-write
            STATUS          current
            DESCRIPTION
                "The number of seconds that, after entering
                Overflow State, a router will attempt to leave
                Overflow State. This allows the router to again
                originate non-default, AS-External-LSAs. When
                set to 0, the router will not leave Overflow
                State until restarted."
            ::= { extremeOspfv3GeneralGroup 13 }

    extremeOspfv3DemandExtensions OBJECT-TYPE
            SYNTAX         TruthValue
            MAX-ACCESS     read-write
            STATUS         current
            DESCRIPTION
                "The router's support for demand routing."
            REFERENCE
                "OSPF Version 2, Appendix on Demand Routing"
            ::= { extremeOspfv3GeneralGroup 14 }

    extremeOspfv3ReferenceBandwidth OBJECT-TYPE
           SYNTAX       Unsigned32
           MAX-ACCESS   read-write
           STATUS       current
           DESCRIPTION
              "Reference bandwidth in kilobits/second for
              calculating default interface metrics. The
              default value is 100,000 KBPS (100 MBPS)"
        ::= { extremeOspfv3GeneralGroup 15 }

    extremeOspfv3RestartSupport OBJECT-TYPE
           SYNTAX       INTEGER { none (1),
                                  plannedOnly (2),
                                  plannedAndUnplanned (3)
                             }
           MAX-ACCESS   read-write
           STATUS       current
           DESCRIPTION
              "The router's support for OSPF Graceful restart.
              Options include: no restart support, only planned
              restarts or both planned and unplanned restarts."
           ::= { extremeOspfv3GeneralGroup 16 }

    extremeOspfv3RestartInterval OBJECT-TYPE
           SYNTAX       ExtremeOspfv3UpToRefreshIntervalTc
           UNITS        "seconds"
           MAX-ACCESS   read-write
           STATUS       current
           DESCRIPTION
              "Configured OSPF Graceful restart timeout interval."
           ::= { extremeOspfv3GeneralGroup 17 }



    extremeOspfv3RestartStatus OBJECT-TYPE
           SYNTAX       INTEGER { notRestarting (1),
                                  plannedRestart (2),
                                  unplannedRestart (3)
                                }
           MAX-ACCESS   read-only
           STATUS       current
           DESCRIPTION
              "The current status of OSPF Graceful restart capability."
           ::= { extremeOspfv3GeneralGroup 18 }

    extremeOspfv3RestartAge OBJECT-TYPE
           SYNTAX       ExtremeOspfv3UpToRefreshIntervalTc
           UNITS        "seconds"
           MAX-ACCESS   read-only
           STATUS       current
           DESCRIPTION
              "Remaining time in current OSPF Graceful restart
              interval."
           ::= { extremeOspfv3GeneralGroup 19 }

    extremeOspfv3RestartExitRc OBJECT-TYPE
           SYNTAX       INTEGER { none (1),
                                  inProgress (2),
                                  completed (3),
                                  timedOut (4),
                                  topologyChanged (5)
                                }
           MAX-ACCESS   read-only
           STATUS       current
           DESCRIPTION
              "Describes the outcome of the last attempt at a
              Graceful restart.

              none:............no restart has yet been attempted.
              inProgress:......a restart attempt is currently underway.
              completed:.......the last restart completed successfully.
              timedOut:........the last restart timed out.
              topologyChanged:.the last restart was aborted due to
                               a topology change."
        ::= { extremeOspfv3GeneralGroup 20 }

    extremeOspfv3NotificationEnable OBJECT-TYPE
           SYNTAX TruthValue
           MAX-ACCESS read-write
           STATUS current
           DESCRIPTION
               "This object provides a coarse level of control
                over the generation of OSPFv3 notifications.

                If this object is set to true (1), then it enables
                the generation of OSPFv3 notifications.  If it is
                set to false (2), these notifications are not
                generated.

                This object is persistent, and when written, the
                entity SHOULD save the change to non-volatile
                storage."
       ::= { extremeOspfv3GeneralGroup 21 }



    -- The OSPFv3 Area Data Structure contains information
    -- regarding the various areas. The interfaces and
    -- virtual links are configured as part of these areas.
    -- Area 0, by definition, is the Backbone Area

    extremeOspfv3AreaTable OBJECT-TYPE
            SYNTAX          SEQUENCE OF ExtremeOspfv3AreaEntry
            MAX-ACCESS      not-accessible
            STATUS          current


            DESCRIPTION
                "Information describing the configured
                parameters and cumulative statistics of the router's
                attached areas."
            REFERENCE
                "OSPF Version 2, Section 6 The Area Data
                Structure"
            ::= { extremeOspfv3Objects 2 }

    extremeOspfv3AreaEntry OBJECT-TYPE
            SYNTAX          ExtremeOspfv3AreaEntry
            MAX-ACCESS      not-accessible
            STATUS          current
            DESCRIPTION
                "Information describing the configured
                parameters and cumulative statistics of one of the
                router's attached areas."
            INDEX           { extremeOspfv3AreaId }
            ::= { extremeOspfv3AreaTable 1 }

    ExtremeOspfv3AreaEntry ::= SEQUENCE {
            extremeOspfv3AreaId
                    ExtremeOspfv3AreaIdTc,
            extremeOspfv3ImportAsExtern
                    INTEGER,
            extremeOspfv3AreaSpfRuns
                    Counter32,
            extremeOspfv3AreaBdrRtrCount
                    Gauge32,
            extremeOspfv3AreaAsBdrRtrCount
                    Gauge32,
            extremeOspfv3AreaScopeLsaCount
                    Gauge32,
            extremeOspfv3AreaScopeLsaCksumSum
                    Integer32,
            extremeOspfv3AreaSummary
                    INTEGER,
            extremeOspfv3AreaStatus
                    RowStatus,
            extremeOspfv3StubMetric
                    BigMetric,
            extremeOspfv3AreaNssaTranslatorRole
                    INTEGER,
            extremeOspfv3AreaNssaTranslatorState
                    INTEGER,
            extremeOspfv3AreaNssaTranslatorStabInt
                    Unsigned32,
            extremeOspfv3AreaNssaTranslatorEvents
                    Counter32,
            extremeOspfv3AreaStubMetricType
                    INTEGER
            }



    extremeOspfv3AreaId OBJECT-TYPE
            SYNTAX          ExtremeOspfv3AreaIdTc
            MAX-ACCESS      not-accessible
            STATUS          current
            DESCRIPTION
                "A 32-bit integer uniquely identifying an area.
                Area ID 0 is used for the OSPFv3 backbone."
            REFERENCE
                "OSPF Version 2, Appendix C.2 Area parameters"
            ::= { extremeOspfv3AreaEntry 1 }

    extremeOspfv3ImportAsExtern OBJECT-TYPE
            SYNTAX          INTEGER {
                            importExternal(1),   -- normal area
                            importNoExternal(2), -- stub area
                            importNssa(3)        -- not-so-stubby-area
                            }
            MAX-ACCESS      read-create
            STATUS          current
            DESCRIPTION
                "Indicates whether an area is a Stub area, NSSA, or
                standard area. AS-scope LSAs are not imported into Stub
                Areas or NSSAs. NSSAs import AS-External data as NSSA
                LSAs which have Area-scope"
            REFERENCE
                "OSPF Version 2, Appendix C.2 Area parameters"
            DEFVAL { importExternal }
            ::= { extremeOspfv3AreaEntry 2 }

    extremeOspfv3AreaSpfRuns OBJECT-TYPE
            SYNTAX          Counter32
            MAX-ACCESS      read-only
            STATUS          current
            DESCRIPTION
                "The number of times that the intra-area route
                table has  been  calculated  using this area's
                link state database. This is typically done
                using Dijkstra's algorithm."
            ::= { extremeOspfv3AreaEntry 3 }

    extremeOspfv3AreaBdrRtrCount OBJECT-TYPE
            SYNTAX          Gauge32
            MAX-ACCESS      read-only
            STATUS          current
            DESCRIPTION
                "The total number of area border routers
                reachable within this area. This is initially zero,
                and is calculated in each SPF Pass."
            ::= { extremeOspfv3AreaEntry 4 }

    extremeOspfv3AreaAsBdrRtrCount OBJECT-TYPE
            SYNTAX          Gauge32
            MAX-ACCESS      read-only


            STATUS          current
            DESCRIPTION
                "The total number of Autonomous System border
                routers reachable within this area. This is
                initially zero, and is calculated in each SPF
                Pass."
            ::= { extremeOspfv3AreaEntry 5 }

    extremeOspfv3AreaScopeLsaCount OBJECT-TYPE
            SYNTAX          Gauge32
            MAX-ACCESS      read-only
            STATUS          current
            DESCRIPTION
                "The total number of Area-Scope link state
                advertisements in  this  area's link state
                database."
            ::= { extremeOspfv3AreaEntry 6 }

    extremeOspfv3AreaScopeLsaCksumSum OBJECT-TYPE
            SYNTAX          Integer32
            MAX-ACCESS      read-only
            STATUS          current
            DESCRIPTION
                "The 32-bit unsigned sum of the Area-Scope link state
                advertisements' LS checksums contained in this
                area's link state database. The sum can be used
                to determine if there has been a change in a
                router's link state database, and to compare the
                link-state database of two routers."
            ::= { extremeOspfv3AreaEntry 7 }

    extremeOspfv3AreaSummary OBJECT-TYPE
            SYNTAX          INTEGER {
                            noAreaSummary(1),
                            sendAreaSummary(2)
                            }
            MAX-ACCESS      read-create
            STATUS          current
            DESCRIPTION

                "The variable ospfAreaSummary controls the im-
                port of summary LSAs into stub and NSSA areas.
                It has no effect on other areas.

                If it is noAreaSummary, the router will not
                originate summary LSAs into the stub or NSSA area.
                It will rely entirely on its default route.

                If it is sendAreaSummary, the router will both
                summarize and propagate summary LSAs."
             DEFVAL { noAreaSummary }
            ::= { extremeOspfv3AreaEntry 8 }



    extremeOspfv3AreaStatus OBJECT-TYPE
            SYNTAX          RowStatus
            MAX-ACCESS      read-create
            STATUS          current
            DESCRIPTION
                "This variable controls the status of the
                entry. The use of RowStatus is covered in more detail
                in [6]."
            ::= { extremeOspfv3AreaEntry 9 }

    extremeOspfv3StubMetric OBJECT-TYPE
            SYNTAX          BigMetric
            MAX-ACCESS      read-create
            STATUS          current
            DESCRIPTION
                "The metric value advertised for the default route
                 into Stub and NSSA areas."
            ::= { extremeOspfv3AreaEntry 10 }

    extremeOspfv3AreaNssaTranslatorRole OBJECT-TYPE
            SYNTAX          INTEGER { always(1), candidate(2) }
            MAX-ACCESS      read-create
            STATUS          current
            DESCRIPTION
                "Indicates an NSSA Border router's ability to
                perform NSSA translation of NSSA-LSAs into
                AS-External-LSAs."
            DEFVAL { candidate }
            ::= { extremeOspfv3AreaEntry 11 }

    extremeOspfv3AreaNssaTranslatorState OBJECT-TYPE
            SYNTAX          INTEGER {
                            enabled(1),
                            elected(2),
                            disabled(3)
                            }
            MAX-ACCESS      read-only
            STATUS          current
            DESCRIPTION
                "Indicates if and how an NSSA Border router is
                 performing NSSA translation of NSSA-LSAs into
                AS-External-LSAǳ. When this object is set to enabled,
                the NSSA Border router's extremeOspfv3AreaNssTranslatorRole
                has been set to always. When this object is set to
                elected, a candidate NSSA Border router is translating
                NSSA-LSAǳ into AS-External-LSAǳ. When this object is
                set to disabled, a candidate NSSA Border router is NOT
                translating NSSA-LSAǳ into AS-External-LSAǳ."
            ::= { extremeOspfv3AreaEntry 12 }

    extremeOspfv3AreaNssaTranslatorStabInt OBJECT-TYPE
            SYNTAX          Unsigned32
            UNITS           "seconds"


            MAX-ACCESS      read-create
            STATUS          current
            DESCRIPTION
                "The number of seconds after an elected translator
                determines its services are no longer required, that
                it should continue to perform its translation duties."
            DEFVAL { 40 }
            ::= { extremeOspfv3AreaEntry 13 }

    extremeOspfv3AreaNssaTranslatorEvents OBJECT-TYPE
            SYNTAX          Counter32
            MAX-ACCESS      read-only
            STATUS          current
            DESCRIPTION
                "Indicates the number of Translator State changes
                that have occurred since the last boot-up."
            ::= { extremeOspfv3AreaEntry 14 }

    extremeOspfv3AreaStubMetricType OBJECT-TYPE
            SYNTAX       INTEGER {
                            extremeOspfv3Metric (1),   -- OSPF Metric
                            comparableCost (2), -- external type 1
                            nonComparable (3)   -- external type 2
                            }
            MAX-ACCESS   read-create
            STATUS       current
            DESCRIPTION
               "This variable displays the type of metric
               advertised as a default route."
            DEFVAL { extremeOspfv3Metric }
            ::= { extremeOspfv3AreaEntry 15 }

    -- OSPFv3 AS-Scope Link State Database

    -- The Link State Database contains the AS-Scope Link State
    -- Advertisements from throughout the areas that the
    -- device is attached to.

    extremeOspfv3AsLsdbTable OBJECT-TYPE
            SYNTAX          SEQUENCE OF ExtremeOspfv3AsLsdbEntry
            MAX-ACCESS      not-accessible
            STATUS          current
            DESCRIPTION
                "The OSPFv3 Process's AS-Scope Link State Database."
            ::= { extremeOspfv3Objects 3 }

    extremeOspfv3AsLsdbEntry OBJECT-TYPE
            SYNTAX          ExtremeOspfv3AsLsdbEntry
            MAX-ACCESS      not-accessible
            STATUS          current
            DESCRIPTION
                "A single AS-Scope Link State Advertisement."
            INDEX           { extremeOspfv3AsLsdbType,


                              extremeOspfv3AsLsdbRouterId,
                              extremeOspfv3AsLsdbLsid }
            ::= { extremeOspfv3AsLsdbTable 1 }

    ExtremeOspfv3AsLsdbEntry ::= SEQUENCE {
            extremeOspfv3AsLsdbType
                    Unsigned32,
            extremeOspfv3AsLsdbRouterId
                    ExtremeOspfv3RouterIdTc,
            extremeOspfv3AsLsdbLsid
                    Unsigned32,
            extremeOspfv3AsLsdbSequence
                    Integer32,
            extremeOspfv3AsLsdbAge
                    Integer32,
            extremeOspfv3AsLsdbChecksum
                    Integer32,
            extremeOspfv3AsLsdbAdvertisement
                    OCTET STRING,
            extremeOspfv3AsLsdbTypeKnown
                    TruthValue
            }

    extremeOspfv3AsLsdbType OBJECT-TYPE
            SYNTAX          Unsigned32(0..'FFFFFFFF'h)
            MAX-ACCESS      not-accessible
            STATUS          current
            DESCRIPTION
                "The type of the link state advertisement.
                Each link state type has a separate
                advertisement format. AS-Scope LSAs not recognized
                by the router may be stored in the database."
            ::= { extremeOspfv3AsLsdbEntry 1 }

    extremeOspfv3AsLsdbRouterId OBJECT-TYPE
            SYNTAX          ExtremeOspfv3RouterIdTc
            MAX-ACCESS      not-accessible
            STATUS          current
            DESCRIPTION
                "The 32 bit number that uniquely identifies the
                originating router in the Autonomous System."
            REFERENCE
                "OSPF Version 2, Appendix C.1 Global parameters"
            ::= { extremeOspfv3AsLsdbEntry 2 }

    extremeOspfv3AsLsdbLsid OBJECT-TYPE
            SYNTAX          Unsigned32
            MAX-ACCESS      not-accessible
            STATUS          current
            DESCRIPTION
                "The Link State ID is an LS Type Specific field
                containing a unique identifier;
                it identifies the piece of the  routing  domain


                that is being described by the advertisement.
                In contrast to OSPFv2, the LSID has no
                addressing semantics."
            ::= { extremeOspfv3AsLsdbEntry 3 }

    -- Note that the OSPF Sequence Number is a 32 bit signed
    -- integer.  It starts with the value '80000001'h,
    -- or -'7FFFFFFF'h, and increments until '7FFFFFFF'h
    -- Thus, a typical sequence number will be very negative.

    extremeOspfv3AsLsdbSequence OBJECT-TYPE
            SYNTAX          Integer32
            MAX-ACCESS      read-only
            STATUS          current
            DESCRIPTION
                "The sequence number field is a signed 32-bit
                integer. It is used to detect old and duplicate
                link state advertisements. The space of
                sequence numbers is linearly ordered. The
                larger the sequence number the more recent the
                advertisement."
            REFERENCE
                "OSPF Version  2,  Section  12.1.6  LS  sequence
                number"
            ::= { extremeOspfv3AsLsdbEntry 4 }

    extremeOspfv3AsLsdbAge OBJECT-TYPE
            SYNTAX          Integer32 -- Should be 0..MaxAge
                                      -- unless DoNotAge bit is set
            UNITS           "seconds"
            MAX-ACCESS      read-only
            STATUS          current
            DESCRIPTION
                "This field is the age of the link state
                advertisement in seconds."
            REFERENCE
                "OSPF Version 2, Section 12.1.1 LS age"
            ::= { extremeOspfv3AsLsdbEntry 5 }

    extremeOspfv3AsLsdbChecksum OBJECT-TYPE
            SYNTAX          Integer32
            MAX-ACCESS      read-only
            STATUS          current
            DESCRIPTION
                "This field is the checksum of the complete
                contents of the advertisement, excepting the
                age field. The age field is excepted so that
                an advertisement's age can be incremented
                without updating the checksum. The checksum
                used is the same that is used for ISO
                connectionless datagrams; it is commonly referred
                to as the Fletcher checksum."
            REFERENCE


                "OSPF Version 2, Section 12.1.7 LS checksum"
            ::= { extremeOspfv3AsLsdbEntry 6 }

    extremeOspfv3AsLsdbAdvertisement OBJECT-TYPE
            SYNTAX          OCTET STRING (SIZE (1..65535))
            MAX-ACCESS      read-only
            STATUS          current
            DESCRIPTION
                "The entire Link State Advertisement, including
                its header."
            ::= { extremeOspfv3AsLsdbEntry 7 }

    extremeOspfv3AsLsdbTypeKnown OBJECT-TYPE
            SYNTAX          TruthValue
            MAX-ACCESS      read-only
            STATUS          current
            DESCRIPTION
                "Indicates whether the LSA type is recognized by
                this Router."
            ::= { extremeOspfv3AsLsdbEntry 8 }


    -- OSPFv3 Area-Scope Link State Database

    -- The Link State Database contains the Area-Scope Link State
    -- Advertisements from throughout the area that the
    -- device is attached to.

    extremeOspfv3AreaLsdbTable OBJECT-TYPE
            SYNTAX          SEQUENCE OF ExtremeOspfv3AreaLsdbEntry
            MAX-ACCESS      not-accessible
            STATUS          current
            DESCRIPTION
                "The OSPFv3 Process's Area-Scope Link State Database."
            ::= { extremeOspfv3Objects 4 }

    extremeOspfv3AreaLsdbEntry OBJECT-TYPE
            SYNTAX          ExtremeOspfv3AreaLsdbEntry
            MAX-ACCESS      not-accessible
            STATUS          current
            DESCRIPTION
                "A single Area-Scope Link State Advertisement."
            INDEX           { extremeOspfv3AreaLsdbAreaId,
                              extremeOspfv3AreaLsdbType,
                              extremeOspfv3AreaLsdbRouterId,
                              extremeOspfv3AreaLsdbLsid }
            ::= { extremeOspfv3AreaLsdbTable 1 }

    ExtremeOspfv3AreaLsdbEntry ::= SEQUENCE {
            extremeOspfv3AreaLsdbAreaId
                    ExtremeOspfv3AreaIdTc,
            extremeOspfv3AreaLsdbType
                    Unsigned32,


            extremeOspfv3AreaLsdbRouterId
                    ExtremeOspfv3RouterIdTc,
            extremeOspfv3AreaLsdbLsid
                    Unsigned32,
            extremeOspfv3AreaLsdbSequence
                    Integer32,
            extremeOspfv3AreaLsdbAge
                    Integer32,
            extremeOspfv3AreaLsdbChecksum
                    Integer32,
            extremeOspfv3AreaLsdbAdvertisement
                    OCTET STRING,
            extremeOspfv3AreaLsdbTypeKnown
                    TruthValue
            }

    extremeOspfv3AreaLsdbAreaId OBJECT-TYPE
            SYNTAX          ExtremeOspfv3AreaIdTc
            MAX-ACCESS      not-accessible
            STATUS          current
            DESCRIPTION
                "The 32-bit identifier of the Area from which the
                LSA was received."
            REFERENCE
                "OSPF Version 2, Appendix C.2 Area parameters"
            ::= { extremeOspfv3AreaLsdbEntry 1 }

    extremeOspfv3AreaLsdbType OBJECT-TYPE
            SYNTAX          Unsigned32(0..'FFFFFFFF'h)
            MAX-ACCESS      not-accessible
            STATUS          current
            DESCRIPTION
                "The type of the link state advertisement.
                Each link state type has a separate
                advertisement format. Area-Scope LSAs unrecognized
                by the router are also stored in this database."
            ::= { extremeOspfv3AreaLsdbEntry 2 }

    extremeOspfv3AreaLsdbRouterId OBJECT-TYPE
            SYNTAX          ExtremeOspfv3RouterIdTc
            MAX-ACCESS      not-accessible
            STATUS          current
            DESCRIPTION
                "The 32-bit number that uniquely identifies the
                originating router in the Autonomous System."
            REFERENCE
                "OSPF Version 2, Appendix C.1 Global parameters"
            ::= { extremeOspfv3AreaLsdbEntry 3 }

    extremeOspfv3AreaLsdbLsid OBJECT-TYPE
            SYNTAX          Unsigned32
            MAX-ACCESS      not-accessible
            STATUS          current


            DESCRIPTION
                "The Link State ID is an LS Type Specific field
                containing a unique identifier;
                it identifies the piece of the  routing  domain
                that is being described by the advertisement.
                In contrast to OSPFv2, the LSID has no
                addressing semantics."
            ::= { extremeOspfv3AreaLsdbEntry 4 }

    -- Note that the OSPF Sequence Number is a 32 bit signed
    -- integer.  It starts with the value '80000001'h,
    -- or -'7FFFFFFF'h, and increments until '7FFFFFFF'h
    -- Thus, a typical sequence number will be very negative.

    extremeOspfv3AreaLsdbSequence OBJECT-TYPE
            SYNTAX          Integer32
            MAX-ACCESS      read-only
            STATUS          current
            DESCRIPTION
                "The sequence number field is a  signed  32-bit
                integer.   It  is used to detect old and dupli-
                cate link state advertisements.  The  space  of
                sequence  numbers  is  linearly  ordered.   The
                larger the sequence number the more recent  the
                advertisement."
            REFERENCE
                "OSPF Version  2,  Section  12.1.6  LS  sequence
                number"
            ::= { extremeOspfv3AreaLsdbEntry 5 }

    extremeOspfv3AreaLsdbAge OBJECT-TYPE
            SYNTAX          Integer32 -- Should be 0..MaxAge
                                      -- unless DoNotAge bit is set
            UNITS           "seconds"
            MAX-ACCESS      read-only
            STATUS          current
            DESCRIPTION
                "This field is the age of the link state
                advertisement in seconds."
            REFERENCE
                "OSPF Version 2, Section 12.1.1 LS age"
            ::= { extremeOspfv3AreaLsdbEntry 6 }

    extremeOspfv3AreaLsdbChecksum OBJECT-TYPE
            SYNTAX          Integer32
            MAX-ACCESS      read-only
            STATUS          current
            DESCRIPTION
                "This field is the checksum of the complete
                contents of the advertisement, excepting the
                age field. The age field is excepted so that
                an advertisement's age can be incremented
                without updating the checksum. The checksum


                used is the same that is used for ISO
                connectionless datagrams; it is commonly referred
                to as the Fletcher checksum."
            REFERENCE
                "OSPF Version 2, Section 12.1.7 LS checksum"
            ::= { extremeOspfv3AreaLsdbEntry 7 }

    extremeOspfv3AreaLsdbAdvertisement OBJECT-TYPE
            SYNTAX          OCTET STRING (SIZE (1..65535))
            MAX-ACCESS      read-only
            STATUS          current
            DESCRIPTION
                "The entire Link State Advertisement, including
                its header."
            ::= { extremeOspfv3AreaLsdbEntry 8 }

    extremeOspfv3AreaLsdbTypeKnown OBJECT-TYPE
            SYNTAX          TruthValue
            MAX-ACCESS      read-only
            STATUS          current
            DESCRIPTION
                "Indicates whether the LSA type is recognized
                by this Router."
            ::= { extremeOspfv3AreaLsdbEntry 9 }

    -- OSPFv3 Link-Scope Link State Database

    -- The Link State Database contains the Link-Scope Link State
    -- Advertisements from the links that the
    -- device is attached to.

    extremeOspfv3LinkLsdbTable OBJECT-TYPE
            SYNTAX          SEQUENCE OF ExtremeOspfv3LinkLsdbEntry
            MAX-ACCESS      not-accessible
            STATUS          current
            DESCRIPTION
                "The OSPFv3 Process's Link-Scope Link State Database."
            ::= { extremeOspfv3Objects 5 }

    extremeOspfv3LinkLsdbEntry OBJECT-TYPE
            SYNTAX          ExtremeOspfv3LinkLsdbEntry
            MAX-ACCESS      not-accessible
            STATUS          current
            DESCRIPTION
                "A single Link-Scope Link State Advertisement."
            INDEX           { extremeOspfv3LinkLsdbIfIndex,
                              extremeOspfv3LinkLsdbIfInstId,
                              extremeOspfv3LinkLsdbType,
                              extremeOspfv3LinkLsdbRouterId,
                              extremeOspfv3LinkLsdbLsid }
            ::= { extremeOspfv3LinkLsdbTable 1 }

    ExtremeOspfv3LinkLsdbEntry ::= SEQUENCE {


            extremeOspfv3LinkLsdbIfIndex
                    InterfaceIndex,
            extremeOspfv3LinkLsdbIfInstId
                    ExtremeOspfv3IfInstIdTc,
            extremeOspfv3LinkLsdbType
                    Unsigned32,
            extremeOspfv3LinkLsdbRouterId
                    ExtremeOspfv3RouterIdTc,
            extremeOspfv3LinkLsdbLsid
                    Unsigned32,
            extremeOspfv3LinkLsdbSequence
                    Integer32,
            extremeOspfv3LinkLsdbAge
                    Integer32,
            extremeOspfv3LinkLsdbChecksum
                    Integer32,
            extremeOspfv3LinkLsdbAdvertisement
                    OCTET STRING,
            extremeOspfv3LinkLsdbTypeKnown
                    TruthValue
            }

    extremeOspfv3LinkLsdbIfIndex OBJECT-TYPE
            SYNTAX         InterfaceIndex
            MAX-ACCESS     not-accessible
            STATUS         current
            DESCRIPTION
                "The identifier of the link from which the LSA
                was received."
            ::= { extremeOspfv3LinkLsdbEntry 1 }

    extremeOspfv3LinkLsdbIfInstId OBJECT-TYPE
            SYNTAX         ExtremeOspfv3IfInstIdTc
            MAX-ACCESS     not-accessible
            STATUS         current
            DESCRIPTION
                "The identifier of the interface instance from
                which the LSA was received."
            ::= { extremeOspfv3LinkLsdbEntry 2 }

    extremeOspfv3LinkLsdbType OBJECT-TYPE
            SYNTAX          Unsigned32(0..'FFFFFFFF'h)
            MAX-ACCESS      not-accessible
            STATUS          current
            DESCRIPTION
                "The type of the link state advertisement.
                Each link state type has a separate
                advertisement format. Link-Scope LSAs unrecognized
                by the router are also stored in this database."
            ::= { extremeOspfv3LinkLsdbEntry 3 }

    extremeOspfv3LinkLsdbRouterId OBJECT-TYPE
            SYNTAX          ExtremeOspfv3RouterIdTc


            MAX-ACCESS      not-accessible
            STATUS          current
            DESCRIPTION
                "The 32 bit number that uniquely identifies the
                originating router in the Autonomous System."
            REFERENCE
                "OSPF Version 2, Appendix C.1 Global parameters"
            ::= { extremeOspfv3LinkLsdbEntry 4 }

    extremeOspfv3LinkLsdbLsid OBJECT-TYPE
            SYNTAX        Unsigned32
            MAX-ACCESS    not-accessible
            STATUS        current
            DESCRIPTION
                "The Link State ID is an LS Type Specific field
                containing a unique identifier;
                it identifies the piece of the  routing  domain
                that is being described by the advertisement.
                In contrast to OSPFv2, the LSID has no
                addressing semantics."
            ::= { extremeOspfv3LinkLsdbEntry 5 }

    -- Note that the OSPF Sequence Number is a 32 bit signed
    -- integer.  It starts with the value '80000001'h,
    -- or -'7FFFFFFF'h, and increments until '7FFFFFFF'h
    -- Thus, a typical sequence number will be very negative.

    extremeOspfv3LinkLsdbSequence OBJECT-TYPE
            SYNTAX          Integer32
            MAX-ACCESS      read-only
            STATUS          current
            DESCRIPTION
                "The sequence number field is a signed 32-bit
                integer. It is used to detect old and duplicate
                link state advertisements. The space of
                sequence numbers is linearly ordered. The
                larger the sequence number the more recent the
                advertisement."
            REFERENCE
                "OSPF Version  2,  Section  12.1.6  LS  sequence
                number"
            ::= { extremeOspfv3LinkLsdbEntry 6 }

    extremeOspfv3LinkLsdbAge OBJECT-TYPE
            SYNTAX          Integer32 -- Should be 0..MaxAge
                                      -- unless DoNotAge bit is set
            UNITS           "seconds"
            MAX-ACCESS      read-only
            STATUS          current
            DESCRIPTION
                "This field is the age of the link state
                advertisement in seconds."
            REFERENCE


                "OSPF Version 2, Section 12.1.1 LS age"
            ::= { extremeOspfv3LinkLsdbEntry 7 }

    extremeOspfv3LinkLsdbChecksum OBJECT-TYPE
            SYNTAX          Integer32
            MAX-ACCESS      read-only
            STATUS          current
            DESCRIPTION
                "This field is the checksum of the complete
                contents of the advertisement, excepting the
                age field. The age field is excepted so that
                an advertisement's age can be incremented
                without updating the  checksum. The checksum
                used is the same that is used for ISO
                connectionless datagrams; it is commonly
                referred to as the Fletcher checksum."
            REFERENCE
                "OSPF Version 2, Section 12.1.7 LS checksum"
            ::= { extremeOspfv3LinkLsdbEntry 8 }

    extremeOspfv3LinkLsdbAdvertisement OBJECT-TYPE
            SYNTAX          OCTET STRING (SIZE (1..65535))
            MAX-ACCESS      read-only
            STATUS          current
            DESCRIPTION
                "The entire Link State Advertisement, including
                its header."
            ::= { extremeOspfv3LinkLsdbEntry 9 }

    extremeOspfv3LinkLsdbTypeKnown OBJECT-TYPE
            SYNTAX          TruthValue
            MAX-ACCESS      read-only
            STATUS          current
            DESCRIPTION
                "Indicates whether the LSA type is recognized by this
                 Router."
            ::= { extremeOspfv3LinkLsdbEntry 10 }


    -- OSPF Host Table

    -- The Host/Metric Table indicates what hosts are directly
    -- attached to the Router, and what metrics and types of
    -- service should be advertised for them.

    extremeOspfv3HostTable OBJECT-TYPE
            SYNTAX          SEQUENCE OF ExtremeOspfv3HostEntry
            MAX-ACCESS      not-accessible
            STATUS          current
            DESCRIPTION
                "The list of Hosts, and their metrics, that the
                router will advertise as host routes."
            REFERENCE


                "OSPF Version 2, Appendix C.6  Host route
                parameters"
            ::= { extremeOspfv3Objects 6 }

    extremeOspfv3HostEntry OBJECT-TYPE
            SYNTAX          ExtremeOspfv3HostEntry
            MAX-ACCESS      not-accessible
            STATUS          current
            DESCRIPTION
                "A metric to be advertised when a given host is
                reachable."
            INDEX           { extremeOspfv3HostAddressType,
                              extremeOspfv3HostAddress }
            ::= { extremeOspfv3HostTable 1 }

    ExtremeOspfv3HostEntry ::= SEQUENCE {
            extremeOspfv3HostAddressType
                    InetAddressType,
            extremeOspfv3HostAddress
                    InetAddress,
            extremeOspfv3HostMetric
                    Metric,
            extremeOspfv3HostStatus
                    RowStatus,
            extremeOspfv3HostAreaID
                    ExtremeOspfv3AreaIdTc
            }

    extremeOspfv3HostAddressType OBJECT-TYPE
            SYNTAX          InetAddressType
            MAX-ACCESS      not-accessible
            STATUS          current
            DESCRIPTION
                "The address type of extremeOspfv3HostAddress. Only IPv6
                addresses without zone index are expected."
            REFERENCE
                "OSPF Version 2, Appendix C.6 Host route
                parameters"
            ::= { extremeOspfv3HostEntry 1 }


    extremeOspfv3HostAddress OBJECT-TYPE
            SYNTAX          InetAddress (SIZE (16))
            MAX-ACCESS      not-accessible
            STATUS          current
            DESCRIPTION
                "The IPv6 Address of the Host. Must be a Global
                 address."
            REFERENCE
                "OSPF Version 2, Appendix C.6 Host route
                parameters"
            ::= { extremeOspfv3HostEntry 2 }



    extremeOspfv3HostMetric OBJECT-TYPE
            SYNTAX          Metric
            MAX-ACCESS      read-create
            STATUS          current
            DESCRIPTION
                "The Metric to be advertised."
            REFERENCE
                "OSPF Version 2, Appendix C.6 Host route
                parameters"
            ::= { extremeOspfv3HostEntry 3 }

    extremeOspfv3HostStatus OBJECT-TYPE
            SYNTAX          RowStatus
            MAX-ACCESS      read-create
            STATUS          current
            DESCRIPTION
                "This variable controls the status of the
                entry. The use of RowStatus is covered in
                more detail in [6]."
            ::= { extremeOspfv3HostEntry 4 }

    extremeOspfv3HostAreaID OBJECT-TYPE
            SYNTAX          ExtremeOspfv3AreaIdTc
            MAX-ACCESS      read-create
            STATUS          current
            DESCRIPTION
                "The Area the Host Entry is to be found within.
                By default, the area that a subsuming OSPFv3
                interface is in, or Area 0"
            REFERENCE
                "OSPF Version 2, Appendix C.2 Area parameters"
            ::= { extremeOspfv3HostEntry 5 }

    -- OSPFv3 Interface Table

    extremeOspfv3IfTable OBJECT-TYPE
            SYNTAX          SEQUENCE OF ExtremeOspfv3IfEntry
            MAX-ACCESS      not-accessible
            STATUS          current
            DESCRIPTION
                "The OSPFv3 Interface Table describes the
                interfaces from the viewpoint of OSPFv3."
            REFERENCE
                "OSPF Version 2, Appendix C.3 Router interface
                parameters"
            ::= { extremeOspfv3Objects 7 }

    extremeOspfv3IfEntry OBJECT-TYPE
            SYNTAX          ExtremeOspfv3IfEntry
            MAX-ACCESS      not-accessible
            STATUS          current
            DESCRIPTION
                "The OSPFv3 Interface Entry describes one


                interface from the viewpoint of OSPFv3."
            INDEX           { extremeOspfv3IfIndex,
                              extremeOspfv3IfInstId }
            ::= { extremeOspfv3IfTable 1 }


    ExtremeOspfv3IfEntry ::= SEQUENCE {
            extremeOspfv3IfIndex
                    InterfaceIndex,
            extremeOspfv3IfInstId
                    ExtremeOspfv3IfInstIdTc,
            extremeOspfv3IfAreaId
                    ExtremeOspfv3AreaIdTc,
            extremeOspfv3IfType
                    INTEGER,
            extremeOspfv3IfAdminStat
                    Status,
            extremeOspfv3IfRtrPriority
                    DesignatedRouterPriority,
            extremeOspfv3IfTransitDelay
                    ExtremeOspfv3UpToRefreshIntervalTc,
            extremeOspfv3IfRetransInterval
                    ExtremeOspfv3UpToRefreshIntervalTc,
            extremeOspfv3IfHelloInterval
                    HelloRange,
            extremeOspfv3IfRtrDeadInterval
                     ExtremeOspfv3DeadIntRangeTc,
            extremeOspfv3IfPollInterval
                    Unsigned32,
            extremeOspfv3IfState
                    INTEGER,
            extremeOspfv3IfDesignatedRouter
                    ExtremeOspfv3RouterIdTc,
            extremeOspfv3IfBackupDesignatedRouter
                    ExtremeOspfv3RouterIdTc,
            extremeOspfv3IfEvents
                    Counter32,
            extremeOspfv3IfStatus
                    RowStatus,
            extremeOspfv3IfMulticastForwarding
                    INTEGER,
            extremeOspfv3IfDemand
                    TruthValue,
            extremeOspfv3IfMetricValue
                    Metric,
            extremeOspfv3IfLinkScopeLsaCount
                    Gauge32,
            extremeOspfv3IfLinkLsaCksumSum
                    Integer32,
            extremeOspfv3IfDemandNbrProbe
                    TruthValue,
            extremeOspfv3IfDemandNbrProbeRetxLimit
                    Unsigned32,


            extremeOspfv3IfDemandNbrProbeInterval
                    Unsigned32
            }

    extremeOspfv3IfIndex OBJECT-TYPE
            SYNTAX          InterfaceIndex
            MAX-ACCESS      not-accessible
            STATUS          current
            DESCRIPTION
                "The interface index of this OSPFv3 interface.
                 It corresponds to the interface index of the
                 IPv6 interface on which OSPFv3 is configured."
            ::= { extremeOspfv3IfEntry 1 }

    extremeOspfv3IfInstId OBJECT-TYPE
            SYNTAX          ExtremeOspfv3IfInstIdTc
            MAX-ACCESS      not-accessible
            STATUS          current
            DESCRIPTION
                "Enables multiple interface instances of OSPFv3
                to be run over a single link. Each protocol
                instance would be assigned a separate ID. This ID
                has local link significance only."
            ::= { extremeOspfv3IfEntry 2 }

    extremeOspfv3IfAreaId OBJECT-TYPE
            SYNTAX          ExtremeOspfv3AreaIdTc
            MAX-ACCESS      read-create
            STATUS          current
            DESCRIPTION
                "A 32-bit integer uniquely identifying the area
                to which the interface connects. Area ID
                0 is used for the OSPFv3 backbone."
            DEFVAL          { 0 }
            ::= { extremeOspfv3IfEntry 3 }

    extremeOspfv3IfType OBJECT-TYPE
            SYNTAX          INTEGER {
                            broadcast(1),
                            nbma(2),
                            pointToPoint(3),
                            pointToMultipoint(5)
                            }
            MAX-ACCESS      read-create
            STATUS          current
            DESCRIPTION
                "The OSPFv3 interface type."
            ::= { extremeOspfv3IfEntry 4 }

    extremeOspfv3IfAdminStat OBJECT-TYPE
            SYNTAX          Status
            MAX-ACCESS      read-create
            STATUS          current


            DESCRIPTION
                "The OSPFv3 interface's administrative status.
                The value formed on the interface, and the
                interface will be advertised as an internal route
                to some area. The value 'disabled' denotes
                that the interface is external to OSPFv3."
            DEFVAL          { enabled }
            ::= { extremeOspfv3IfEntry 5 }

    extremeOspfv3IfRtrPriority OBJECT-TYPE
            SYNTAX          DesignatedRouterPriority
            MAX-ACCESS      read-create
            STATUS          current
            DESCRIPTION
                "The priority of this interface. Used in
                multi-access networks, this field is used in
                the designated router election algorithm. The
                value 0 signifies that the router is not
                eligible to become the designated router on this
                particular network. In the event of a tie in
                this value, routers will use their Router ID as
                a tie breaker."
            DEFVAL          { 1 }
            ::= { extremeOspfv3IfEntry 6 }

    extremeOspfv3IfTransitDelay OBJECT-TYPE
            SYNTAX          ExtremeOspfv3UpToRefreshIntervalTc
            UNITS           "seconds"
            MAX-ACCESS      read-create
            STATUS          current
            DESCRIPTION
                "The estimated number of seconds it takes to
                transmit a link state update packet over this
                interface."
            DEFVAL          { 1 }
            ::= { extremeOspfv3IfEntry 7 }

    extremeOspfv3IfRetransInterval OBJECT-TYPE
            SYNTAX          ExtremeOspfv3UpToRefreshIntervalTc
            UNITS           "seconds"
            MAX-ACCESS      read-create
            STATUS          current
            DESCRIPTION
                "The number of seconds between link state
                advertisement retransmissions, for adjacencies
                belonging to this interface. This value is
                also used when retransmitting database
                description and link state request packets."
            DEFVAL          { 5 }
            ::= { extremeOspfv3IfEntry 8 }

    extremeOspfv3IfHelloInterval OBJECT-TYPE
            SYNTAX          HelloRange


            UNITS           "seconds"
            MAX-ACCESS      read-create
            STATUS          current
            DESCRIPTION
                "The length of time, in seconds, between the
                Hello packets that the router sends on the
                interface. This value must be the same for all
                routers attached to a common network."
            DEFVAL          { 10 }
            ::= { extremeOspfv3IfEntry 9 }

    extremeOspfv3IfRtrDeadInterval OBJECT-TYPE
            SYNTAX          ExtremeOspfv3DeadIntRangeTc
            UNITS           "seconds"
            MAX-ACCESS      read-create
            STATUS          current
            DESCRIPTION
                "The number of seconds that a router's Hello
                packets have not been seen before its
                neighbors declare the router down on the interface.
                This should be some multiple of the Hello interval.
                This value must be the same for all routers attached
                to a common network."
            DEFVAL          { 40 }
            ::= { extremeOspfv3IfEntry 10 }

    extremeOspfv3IfPollInterval OBJECT-TYPE
            SYNTAX          Unsigned32
            UNITS           "seconds"
            MAX-ACCESS      read-create
            STATUS          current
            DESCRIPTION
                "The larger time interval, in seconds, between
                the Hello packets sent to an inactive
                non-broadcast multi-access neighbor."
            DEFVAL          { 120 }
            ::= { extremeOspfv3IfEntry 11 }

    extremeOspfv3IfState OBJECT-TYPE
            SYNTAX          INTEGER {
                            down(1),
                            loopback(2),
                            waiting(3),
                            pointToPoint(4),
                            designatedRouter(5),
                            backupDesignatedRouter(6),
                            otherDesignatedRouter(7)
                            }
            MAX-ACCESS      read-only
            STATUS          current
            DESCRIPTION
                "The OSPFv3 Interface State."
            ::= { extremeOspfv3IfEntry 12 }



    extremeOspfv3IfDesignatedRouter OBJECT-TYPE
            SYNTAX          ExtremeOspfv3RouterIdTc
            MAX-ACCESS      read-only
            STATUS          current
            DESCRIPTION
                "The Router ID of the Designated Router."
            ::= { extremeOspfv3IfEntry 13 }

    extremeOspfv3IfBackupDesignatedRouter OBJECT-TYPE
            SYNTAX          ExtremeOspfv3RouterIdTc
            MAX-ACCESS      read-only
            STATUS          current
            DESCRIPTION
                "The Router ID of the Backup Designated
                Router."
            ::= { extremeOspfv3IfEntry 14 }

    extremeOspfv3IfEvents OBJECT-TYPE
            SYNTAX          Counter32
            MAX-ACCESS      read-only
            STATUS          current
            DESCRIPTION
                "The number of times this OSPF interface has
                changed its state, or an error has occurred."
            ::= { extremeOspfv3IfEntry 15 }

     extremeOspfv3IfStatus OBJECT-TYPE
            SYNTAX          RowStatus
            MAX-ACCESS      read-create
            STATUS          current
            DESCRIPTION
                "This variable controls the status of the
                entry. The use of RowStatus is covered in more
                detail in [6]."
            ::= { extremeOspfv3IfEntry 16 }

    extremeOspfv3IfMulticastForwarding OBJECT-TYPE
            SYNTAX          INTEGER {
                            blocked(1),   -- no multicast forwarding
                            multicast(2), -- using multicast address
                            unicast(3)    -- to each OSPFv3 neighbor
                            }
            MAX-ACCESS      read-create
            STATUS          current
            DESCRIPTION
                "The way multicasts should forwarded on this
                interface; not forwarded, forwarded as data
                link multicasts, or forwarded as data link
                unicasts. Data link multicasting is not
                meaningful on point to point and NBMA interfaces,
                and setting extremeOspfv3MulticastForwarding to 0
                effectively disables all multicast forwarding."


            DEFVAL { blocked }
            ::= { extremeOspfv3IfEntry 17 }

    extremeOspfv3IfDemand OBJECT-TYPE
            SYNTAX          TruthValue
            MAX-ACCESS      read-create
            STATUS          current
            DESCRIPTION
                "Indicates whether Demand OSPFv3 procedures
                (hello suppression to FULL neighbors and
                setting the DoNotAge flag on propagated LSAs)
                should be performed on this interface."
            DEFVAL { false }
            ::= { extremeOspfv3IfEntry 18 }

    extremeOspfv3IfMetricValue OBJECT-TYPE
            SYNTAX          Metric
            MAX-ACCESS      read-create
            STATUS          current
            DESCRIPTION
                "The metric assigned to this interface.
                 The default value of the Metric is
                Reference Bandwidth / ifSpeed. The value of the
                reference bandwidth is configured by the
                extremeOspfv3ReferenceBandwidth object."
            ::= { extremeOspfv3IfEntry 19 }

     extremeOspfv3IfLinkScopeLsaCount OBJECT-TYPE
            SYNTAX          Gauge32
            MAX-ACCESS      read-only
            STATUS          current
            DESCRIPTION
                "The total number of Link-Scope link state
                advertisements in  this  link's link state
                database."
            ::= { extremeOspfv3IfEntry 20 }

     extremeOspfv3IfLinkLsaCksumSum OBJECT-TYPE
            SYNTAX          Integer32
            MAX-ACCESS      read-only
            STATUS          current
            DESCRIPTION
                "The 32-bit unsigned sum of the Link-Scope link state
                advertisements' LS checksums contained in this
                link's link state database. The sum can be used
                to determine if  there has been a change in a
                router's link state database, and to compare the
                link state database of two routers."
            ::= { extremeOspfv3IfEntry 21 }

    extremeOspfv3IfDemandNbrProbe OBJECT-TYPE
            SYNTAX          TruthValue
            MAX-ACCESS      read-create


            STATUS          current
            DESCRIPTION
                   "Indicates whether or not neighbor probing is
                   enabled to determine whether or not the neighbor
                   is inactive. Neighbor probing is disabled by
                   default."
            DEFVAL { false }
            ::= { extremeOspfv3IfEntry 22 }

   extremeOspfv3IfDemandNbrProbeRetxLimit OBJECT-TYPE
           SYNTAX       Unsigned32
           UNITS        "seconds"
           MAX-ACCESS   read-create
           STATUS       current
           DESCRIPTION
              "The number of consecutive LSA retransmissions before
              the neighbor is deemed inactive and the neighbor
              adjacency is brought down."
           DEFVAL          { 10 }
           ::= { extremeOspfv3IfEntry 23}


   extremeOspfv3IfDemandNbrProbeInterval OBJECT-TYPE
           SYNTAX       Unsigned32
           UNITS        "seconds"
           MAX-ACCESS   read-create
           STATUS       current
           DESCRIPTION
              "Defines how often the neighbor will be probed."
           DEFVAL          { 120 }
           ::= { extremeOspfv3IfEntry 24 }


    -- OSPFv3 Virtual Interface Table

    -- The Virtual Interface Table describes the virtual
    -- links that the OSPFv3 Process is configured to
    -- carry on.

    extremeOspfv3VirtIfTable OBJECT-TYPE
            SYNTAX          SEQUENCE OF ExtremeOspfv3VirtIfEntry
            MAX-ACCESS      not-accessible
            STATUS          current
            DESCRIPTION
                "Information about this router's virtual
                interfaces."
            REFERENCE
                "OSPF Version 2, Appendix C.4 Virtual link
                parameters"
            ::= { extremeOspfv3Objects 8 }

    extremeOspfv3VirtIfEntry OBJECT-TYPE
            SYNTAX          ExtremeOspfv3VirtIfEntry


            MAX-ACCESS      not-accessible
            STATUS          current
            DESCRIPTION
                "Information about a single Virtual Interface."
            INDEX           { extremeOspfv3VirtIfAreaId,
                              extremeOspfv3VirtIfNeighbor }
            ::= { extremeOspfv3VirtIfTable 1 }

    ExtremeOspfv3VirtIfEntry ::= SEQUENCE {
            extremeOspfv3VirtIfAreaId
                    ExtremeOspfv3AreaIdTc,
            extremeOspfv3VirtIfNeighbor
                    ExtremeOspfv3RouterIdTc,
            extremeOspfv3VirtIfIndex
                    InterfaceIndex,
            extremeOspfv3VirtIfInstId
                    ExtremeOspfv3IfInstIdTc,
            extremeOspfv3VirtIfTransitDelay
                    ExtremeOspfv3UpToRefreshIntervalTc,
            extremeOspfv3VirtIfRetransInterval
                    ExtremeOspfv3UpToRefreshIntervalTc,
            extremeOspfv3VirtIfHelloInterval
                    HelloRange,
            extremeOspfv3VirtIfRtrDeadInterval
                    ExtremeOspfv3DeadIntRangeTc,
            extremeOspfv3VirtIfState
                    INTEGER,
            extremeOspfv3VirtIfEvents
                    Counter32,
            extremeOspfv3VirtIfStatus
                    RowStatus,
            extremeOspfv3VirtIfLinkScopeLsaCount
                    Gauge32,
            extremeOspfv3VirtIfLinkLsaCksumSum
                    Integer32
            }

    extremeOspfv3VirtIfAreaId OBJECT-TYPE
            SYNTAX          ExtremeOspfv3AreaIdTc
            MAX-ACCESS      not-accessible
            STATUS          current
            DESCRIPTION
                "The Transit Area that the Virtual Link
                traverses. By definition, this is not
                Area 0"
            ::= { extremeOspfv3VirtIfEntry 1 }

    extremeOspfv3VirtIfNeighbor OBJECT-TYPE
            SYNTAX          ExtremeOspfv3RouterIdTc
            MAX-ACCESS      not-accessible
            STATUS          current
            DESCRIPTION
                "The Router ID of the Virtual Neighbor."


            ::= { extremeOspfv3VirtIfEntry 2 }

    extremeOspfv3VirtIfIndex OBJECT-TYPE
            SYNTAX          InterfaceIndex
            MAX-ACCESS      read-create
            STATUS          current
            DESCRIPTION
                "The interface index assigned to this OSPFv3 virtual
                interface. It is advertised in Hello's sent over
                the virtal link and in the router's router-LSAs."
            ::= { extremeOspfv3VirtIfEntry 3 }

    extremeOspfv3VirtIfInstId OBJECT-TYPE
            SYNTAX          ExtremeOspfv3IfInstIdTc
            MAX-ACCESS      read-create
            STATUS          current
            DESCRIPTION
                "Specifies the interface instance ID to be used
                for the virtual interface. This ID has local link
                significance only."
            DEFVAL          { 0 }
            ::= { extremeOspfv3VirtIfEntry 4 }

    extremeOspfv3VirtIfTransitDelay OBJECT-TYPE
            SYNTAX          ExtremeOspfv3UpToRefreshIntervalTc
            UNITS           "seconds"
            MAX-ACCESS      read-create
            STATUS          current
            DESCRIPTION
                "The estimated number of seconds it takes to
                transmit a link state update packet over this
                interface."
            DEFVAL          { 1 }
            ::= { extremeOspfv3VirtIfEntry 5 }

    extremeOspfv3VirtIfRetransInterval OBJECT-TYPE
            SYNTAX          ExtremeOspfv3UpToRefreshIntervalTc
            UNITS           "seconds"
            MAX-ACCESS      read-create
            STATUS          current
            DESCRIPTION
                "The number of seconds between link state
                advertisement retransmissions, for adjacencies
                belonging to this  interface. This value is
                also used when retransmitting database
                description and link state request packets. This
                value should be well over the expected
                round-trip time."
            DEFVAL          { 5 }
            ::= { extremeOspfv3VirtIfEntry 6 }

    extremeOspfv3VirtIfHelloInterval OBJECT-TYPE
            SYNTAX          HelloRange


            UNITS           "seconds"
            MAX-ACCESS      read-create
            STATUS          current
            DESCRIPTION
                "The length of time, in seconds, between the
                Hello packets that the router sends on the
                interface.  This value must be the same for the
                virtual neighbor."
            DEFVAL          { 10 }
            ::= { extremeOspfv3VirtIfEntry 7 }

    extremeOspfv3VirtIfRtrDeadInterval OBJECT-TYPE
            SYNTAX          ExtremeOspfv3DeadIntRangeTc
            UNITS           "seconds"
            MAX-ACCESS      read-create
            STATUS          current
            DESCRIPTION
                "The number of seconds that a router's Hello
                packets have not been seen before its
                neighbors declare the router down. This should
                be some multiple of the Hello interval. This
                value must be the same for the virtual
                neighbor."
            DEFVAL          { 60 }
            ::= { extremeOspfv3VirtIfEntry 8 }

    extremeOspfv3VirtIfState OBJECT-TYPE
            SYNTAX          INTEGER {
                            down(1),
                            pointToPoint(4)
                            }
            MAX-ACCESS      read-only
            STATUS          current
            DESCRIPTION
                "OSPF virtual interface states. The same encoding
                as the ospfV3IfTable is used."
            ::= { extremeOspfv3VirtIfEntry 9 }

    extremeOspfv3VirtIfEvents OBJECT-TYPE
            SYNTAX          Counter32
            MAX-ACCESS      read-only
            STATUS          current
            DESCRIPTION
                "The number of state changes or error events on
                this Virtual Link"
            ::= { extremeOspfv3VirtIfEntry 10 }

    extremeOspfv3VirtIfStatus OBJECT-TYPE
            SYNTAX          RowStatus
            MAX-ACCESS      read-create
            STATUS          current
            DESCRIPTION
                "This variable controls the status of the entry.


                The use of RowStatus is covered in more detail
                in [6]."
            ::= { extremeOspfv3VirtIfEntry 11 }

    extremeOspfv3VirtIfLinkScopeLsaCount OBJECT-TYPE
            SYNTAX          Gauge32
            MAX-ACCESS      read-only
            STATUS          current
            DESCRIPTION
                "The total number of Link-Scope link state
                advertisements in  this  virtual link's link state
                database."
            ::= { extremeOspfv3VirtIfEntry 12 }

    extremeOspfv3VirtIfLinkLsaCksumSum OBJECT-TYPE
            SYNTAX          Integer32
            MAX-ACCESS      read-only
            STATUS          current
            DESCRIPTION
                "The 32-bit unsigned sum of the Link-Scope link-state
                advertisements'  LS  checksums  contained in this
                virtual link's link-state database.  The sum can be used
                to determine if  there  has been  a  change  in a
                router's link state database, and to compare the
                link state database of two routers."
            ::= { extremeOspfv3VirtIfEntry 13 }


    -- OSPFv3 Neighbor Table

    -- The OSPFv3 Neighbor Table describes all neighbors in
    -- the locality of the subject router.

    extremeOspfv3NbrTable OBJECT-TYPE
            SYNTAX          SEQUENCE OF ExtremeOspfv3NbrEntry
            MAX-ACCESS      not-accessible
            STATUS          current
            DESCRIPTION
                "A table of non-virtual neighbor information."
            REFERENCE
                "OSPF Version 2, Section 10 The Neighbor Data
                Structure"
            ::= { extremeOspfv3Objects 9 }

    extremeOspfv3NbrEntry OBJECT-TYPE
            SYNTAX          ExtremeOspfv3NbrEntry
            MAX-ACCESS      not-accessible
            STATUS          current
            DESCRIPTION
                "The information regarding a single neighbor."
            REFERENCE
                "OSPF Version 2, Section 10 The Neighbor Data
                Structure"


            INDEX           { extremeOspfv3NbrIfIndex,
                              extremeOspfv3NbrIfInstId,
                              extremeOspfv3NbrRtrId }
            ::= { extremeOspfv3NbrTable 1 }

    ExtremeOspfv3NbrEntry ::= SEQUENCE {
            extremeOspfv3NbrIfIndex
                    InterfaceIndex,
            extremeOspfv3NbrIfInstId
                    ExtremeOspfv3IfInstIdTc,
            extremeOspfv3NbrRtrId
                    ExtremeOspfv3RouterIdTc,
            extremeOspfv3NbrAddressType
                    InetAddressType,
            extremeOspfv3NbrAddress
                    InetAddress,
            extremeOspfv3NbrOptions
                    Integer32,
            extremeOspfv3NbrPriority
                    DesignatedRouterPriority,
            extremeOspfv3NbrState
                    INTEGER,
            extremeOspfv3NbrEvents
                    Counter32,
            extremeOspfv3NbrLsRetransQLen
                    Gauge32,
            extremeOspfv3NbrHelloSuppressed
                    TruthValue,
            extremeOspfv3NbrIfId
                    InterfaceIndex,
            extremeOspfv3NbrRestartHelperStatus
                    INTEGER,
            extremeOspfv3NbrRestartHelperAge
                    ExtremeOspfv3UpToRefreshIntervalTc,
            extremeOspfv3NbrRestartHelperExitRc
                    INTEGER
            }

    extremeOspfv3NbrIfIndex OBJECT-TYPE
            SYNTAX          InterfaceIndex
            MAX-ACCESS      not-accessible
            STATUS          current
            DESCRIPTION
                "The local link ID of the link over which the
                 neighbor can be reached."
            ::= { extremeOspfv3NbrEntry 1 }

    extremeOspfv3NbrIfInstId OBJECT-TYPE
            SYNTAX          ExtremeOspfv3IfInstIdTc
            MAX-ACCESS      not-accessible
            STATUS          current
            DESCRIPTION
                "Interface instance over which the neighbor


                can be reached. This ID has local link
                significance only."
            ::= { extremeOspfv3NbrEntry 2 }

    extremeOspfv3NbrRtrId OBJECT-TYPE
            SYNTAX          ExtremeOspfv3RouterIdTc
            MAX-ACCESS      not-accessible
            STATUS          current
            DESCRIPTION
               "A 32-bit integer uniquely identifying the neighboring
               router in the Autonomous System."
            ::= { extremeOspfv3NbrEntry 3 }

    extremeOspfv3NbrAddressType OBJECT-TYPE
            SYNTAX          InetAddressType
            MAX-ACCESS      read-only
            STATUS          current
            DESCRIPTION
                "The address type of extremeOspfv3NbrAddress. Only IPv6
                addresses without zone index are expected."
            ::= { extremeOspfv3NbrEntry 4 }

    extremeOspfv3NbrAddress OBJECT-TYPE
            SYNTAX          InetAddress (SIZE (16))
            MAX-ACCESS      read-only
            STATUS          current
            DESCRIPTION
                "The IPv6 address of the neighbor associated with
                the local link."
            ::= { extremeOspfv3NbrEntry 5 }

    extremeOspfv3NbrOptions OBJECT-TYPE
            SYNTAX          Integer32
            MAX-ACCESS      read-only
            STATUS          current
            DESCRIPTION
                "A Bit Mask corresponding to the neighbor's
                options field."
            REFERENCE
                "OSPF Version 3, Appendix A.2 the Options field"
            ::= { extremeOspfv3NbrEntry 6 }

    extremeOspfv3NbrPriority OBJECT-TYPE
            SYNTAX          DesignatedRouterPriority
            MAX-ACCESS      read-only
            STATUS          current
            DESCRIPTION
                "The priority of this neighbor in the designated
                router election algorithm. The value 0 signifies
                that the neighbor is not eligible to become the
                designated router on this particular network."
            ::= { extremeOspfv3NbrEntry 7 }



    extremeOspfv3NbrState OBJECT-TYPE
            SYNTAX          INTEGER {
                            down(1),
                            attempt(2),
                            init(3),
                            twoWay(4),
                            exchangeStart(5),
                            exchange(6),
                            loading(7),
                            full(8)
                            }
            MAX-ACCESS      read-only
            STATUS          current
            DESCRIPTION
                "The State of the relationship with this
                Neighbor."
            REFERENCE
                "OSPF Version 2, Section 10.1 Neighbor States"
            ::= { extremeOspfv3NbrEntry 8 }

    extremeOspfv3NbrEvents OBJECT-TYPE
            SYNTAX          Counter32
            MAX-ACCESS      read-only
            STATUS          current
            DESCRIPTION
                "The number of times this neighbor relationship
                has changed state, or an error has occurred."
            ::= { extremeOspfv3NbrEntry 9 }

    extremeOspfv3NbrLsRetransQLen OBJECT-TYPE
            SYNTAX          Gauge32
            MAX-ACCESS      read-only
            STATUS          current
            DESCRIPTION
                "The current length of the retransmission
                queue."
            ::= { extremeOspfv3NbrEntry 10 }

    extremeOspfv3NbrHelloSuppressed OBJECT-TYPE
            SYNTAX          TruthValue
            MAX-ACCESS      read-only
            STATUS          current
            DESCRIPTION
                "Indicates whether Hellos are being suppressed
                to the neighbor"
            ::= { extremeOspfv3NbrEntry 11 }

    extremeOspfv3NbrIfId OBJECT-TYPE
            SYNTAX          InterfaceIndex
            MAX-ACCESS      read-only
            STATUS          current
            DESCRIPTION
                "The interface ID that the neighbor advertises


                in its Hello Packets on this link, that is, the
                neighbor's local interface index."
            ::= { extremeOspfv3NbrEntry 12 }

    extremeOspfv3NbrRestartHelperStatus OBJECT-TYPE
           SYNTAX       INTEGER { notHelping (1),
                                  helping (2)
                                }
           MAX-ACCESS   read-only
           STATUS       current
           DESCRIPTION
              "Indicates whether the router is acting
              as a Graceful restart helper for the neighbor."
              ::= { extremeOspfv3NbrEntry 13 }

    extremeOspfv3NbrRestartHelperAge OBJECT-TYPE
           SYNTAX       ExtremeOspfv3UpToRefreshIntervalTc
           UNITS        "seconds"
           MAX-ACCESS   read-only
           STATUS       current
           DESCRIPTION
              "Remaining time in current OSPF Graceful restart
              interval, if the router is acting as a restart
              helper for the neighbor."
           ::= { extremeOspfv3NbrEntry 14 }

    extremeOspfv3NbrRestartHelperExitRc OBJECT-TYPE
           SYNTAX       INTEGER { none (1),
                                  inProgress (2),
                                  completed (3),
                                  timedOut (4),
                                  topologyChanged (5)
                                }
           MAX-ACCESS   read-only
           STATUS       current
           DESCRIPTION
              "Describes the outcome of the last attempt at acting
              as a Graceful restart helper for the neighbor.

              none:............no restart has yet been attempted.
              inProgress:......a restart attempt is currently underway.
              completed:.......the last restart completed successfully.
              timedOut:........the last restart timed out.
              topologyChanged:.the last restart was aborted due to
                               a topology change."
        ::= { extremeOspfv3NbrEntry 15 }


    -- OSPFv3 Configured Neighbor Table

    -- The OSPFv3 Configured Neighbor Table describes all configured
    -- neighbors and neighbors dynamically discovered by
    -- lower-level protocols such as Inverse Neighbor Discovery.



    extremeOspfv3CfgNbrTable OBJECT-TYPE
            SYNTAX          SEQUENCE OF ExtremeOspfv3CfgNbrEntry
            MAX-ACCESS      not-accessible
            STATUS          current
            DESCRIPTION
                "A table of configured non-virtual neighbor
                information and neighbors dynamically discovered
                by lower-level protocols such as Inverse Neighbor
                Discovery."
            REFERENCE
                "OSPF Version 2, Section 10 The Neighbor Data
                Structure"
            ::= { extremeOspfv3Objects 10 }

    extremeOspfv3CfgNbrEntry OBJECT-TYPE
            SYNTAX          ExtremeOspfv3CfgNbrEntry
            MAX-ACCESS      not-accessible
            STATUS          current
            DESCRIPTION
                "The information regarding a single configured
                neighbor or neighbor discovered by lower-level
                protocols such as Inverse Neighbor Discovery."
            REFERENCE
                "OSPF Version 2, Section 10 The Neighbor Data
                Structure"
            INDEX           { extremeOspfv3CfgNbrIfIndex,
                              extremeOspfv3CfgNbrIfInstId,
                              extremeOspfv3CfgNbrAddressType,
                              extremeOspfv3CfgNbrAddress }
            ::= { extremeOspfv3CfgNbrTable 1 }

    ExtremeOspfv3CfgNbrEntry ::= SEQUENCE {
            extremeOspfv3CfgNbrIfIndex
                    InterfaceIndex,
            extremeOspfv3CfgNbrIfInstId
                    ExtremeOspfv3IfInstIdTc,
            extremeOspfv3CfgNbrAddressType
                    InetAddressType,
            extremeOspfv3CfgNbrAddress
                    InetAddress,
            extremeOspfv3CfgNbrPriority
                    DesignatedRouterPriority,
            extremeOspfv3CfgNbrRtrId
                    ExtremeOspfv3RouterIdTc,
            extremeOspfv3CfgNbrState
                    INTEGER,
            extremeOspfv3CfgNbrStorageType
                    StorageType,
            extremeOspfv3CfgNbrStatus
                    RowStatus
            }



    extremeOspfv3CfgNbrIfIndex OBJECT-TYPE
            SYNTAX          InterfaceIndex
            MAX-ACCESS      not-accessible
            STATUS          current
            DESCRIPTION
                "The local link ID of the link over which the
                 neighbor can be reached."
            ::= { extremeOspfv3CfgNbrEntry 1 }

    extremeOspfv3CfgNbrIfInstId OBJECT-TYPE
            SYNTAX          ExtremeOspfv3IfInstIdTc
            MAX-ACCESS      not-accessible
            STATUS          current
            DESCRIPTION
                "Interface instance over which the neighbor
                can be reached. This ID has local link
                significance only."
            ::= { extremeOspfv3CfgNbrEntry 2 }

    extremeOspfv3CfgNbrAddressType OBJECT-TYPE
            SYNTAX          InetAddressType
            MAX-ACCESS      not-accessible
            STATUS          current
            DESCRIPTION
                "The address type of extremeOspfv3NbrAddress. Only IPv6
                addresses without zone index are expected."
            ::= { extremeOspfv3CfgNbrEntry 3 }

    extremeOspfv3CfgNbrAddress OBJECT-TYPE
            SYNTAX          InetAddress (SIZE (16))
            MAX-ACCESS      not-accessible
            STATUS          current
            DESCRIPTION
                "The IPv6 address of the neighbor associated with
                the local link."
            ::= { extremeOspfv3CfgNbrEntry 4 }

    extremeOspfv3CfgNbrPriority OBJECT-TYPE
            SYNTAX          DesignatedRouterPriority
            MAX-ACCESS      read-create
            STATUS          current
            DESCRIPTION
                "The priority of this neighbor in the designated
                router election algorithm. The value 0 signifies
                that the neighbor is not eligible to become the
                designated router on this particular network."
            DEFVAL          { 1 }
            ::= { extremeOspfv3CfgNbrEntry 5 }

    extremeOspfv3CfgNbrRtrId OBJECT-TYPE
            SYNTAX          ExtremeOspfv3RouterIdTc
            MAX-ACCESS      read-only
            STATUS          current


            DESCRIPTION
                "A 32-bit integer uniquely identifying the neighboring
                router in the Autonomous System. A value of 0
                is returned until a Hello is received
                from the configured neighbor."
            ::= { extremeOspfv3CfgNbrEntry 6 }

    extremeOspfv3CfgNbrState OBJECT-TYPE
            SYNTAX          INTEGER {
                            down(1),
                            attempt(2),
                            init(3),
                            twoWay(4),
                            exchangeStart(5),
                            exchange(6),
                            loading(7),
                            full(8)
                            }
            MAX-ACCESS      read-only
            STATUS          current
            DESCRIPTION
                "The State of the relationship with this Neighbor."
            REFERENCE
                "OSPF Version 2, Section 10.1 Neighbor States"
            ::= { extremeOspfv3CfgNbrEntry 7 }

    extremeOspfv3CfgNbrStorageType OBJECT-TYPE
            SYNTAX          StorageType
            MAX-ACCESS      read-create
            STATUS          current
            DESCRIPTION
                "The storage type for this conceptual row.
                Conceptual rows having the value 'permanent' need not
                allow write-access to any columnar objects in the row.
                Manually configured entries will have a storage type
                of nonVolatile while entries dynamically created as a
                result of a lower-level protocol such as Inverse
                Neighbor Discovery will have a storage type of
                volatile."
            DEFVAL          { nonVolatile }
            ::= { extremeOspfv3CfgNbrEntry 8 }

    extremeOspfv3CfgNbrStatus OBJECT-TYPE
            SYNTAX          RowStatus
            MAX-ACCESS      read-create
            STATUS          current
            DESCRIPTION
                "This variable controls the status of the entry.
                The use of RowStatus is covered in more detail
                in [6]."
            ::= { extremeOspfv3CfgNbrEntry 9 }

    -- OSPFv3 Virtual Neighbor Table



    -- This table describes all virtual neighbors.
    -- Since Virtual Links are configured in the
    -- virtual interface table, this table is read-only.

    extremeOspfv3VirtNbrTable OBJECT-TYPE
            SYNTAX          SEQUENCE OF ExtremeOspfv3VirtNbrEntry
            MAX-ACCESS      not-accessible
            STATUS          current
            DESCRIPTION
                "A table of virtual neighbor information."
            REFERENCE
                "OSPF Version 2, Section 15 Virtual Links"
            ::= { extremeOspfv3Objects 11 }

    extremeOspfv3VirtNbrEntry OBJECT-TYPE
            SYNTAX          ExtremeOspfv3VirtNbrEntry
            MAX-ACCESS      not-accessible
            STATUS          current
            DESCRIPTION
                "Virtual neighbor information."
            INDEX           { extremeOspfv3VirtNbrArea,
                              extremeOspfv3VirtNbrRtrId }
            ::= { extremeOspfv3VirtNbrTable 1 }

    ExtremeOspfv3VirtNbrEntry ::= SEQUENCE {
            extremeOspfv3VirtNbrArea
                    ExtremeOspfv3AreaIdTc,
            extremeOspfv3VirtNbrRtrId
                    ExtremeOspfv3RouterIdTc,
            extremeOspfv3VirtNbrIfIndex
                    InterfaceIndex,
            extremeOspfv3VirtNbrIfInstId
                    ExtremeOspfv3IfInstIdTc,
            extremeOspfv3VirtNbrAddressType
                    InetAddressType,
            extremeOspfv3VirtNbrAddress
                    InetAddress,
            extremeOspfv3VirtNbrOptions
                    Integer32,
            extremeOspfv3VirtNbrState
                    INTEGER,
            extremeOspfv3VirtNbrEvents
                    Counter32,
            extremeOspfv3VirtNbrLsRetransQLen
                    Gauge32,
            extremeOspfv3VirtNbrHelloSuppressed
                    TruthValue,
            extremeOspfv3VirtNbrIfId
                    InterfaceIndex,
            extremeOspfv3VirtNbrRestartHelperStatus
                    INTEGER,
            extremeOspfv3VirtNbrRestartHelperAge


                    ExtremeOspfv3UpToRefreshIntervalTc,
            extremeOspfv3VirtNbrRestartHelperExitRc
                    INTEGER
            }

    extremeOspfv3VirtNbrArea OBJECT-TYPE
            SYNTAX          ExtremeOspfv3AreaIdTc
            MAX-ACCESS      not-accessible
            STATUS          current
            DESCRIPTION
                "The Transit Area Identifier."
            ::= { extremeOspfv3VirtNbrEntry 1 }

    extremeOspfv3VirtNbrRtrId OBJECT-TYPE
            SYNTAX          ExtremeOspfv3RouterIdTc
            MAX-ACCESS      not-accessible
            STATUS          current
            DESCRIPTION
                "A 32-bit integer uniquely identifying the
                neighboring router in the Autonomous System."
            ::= { extremeOspfv3VirtNbrEntry 2 }

    extremeOspfv3VirtNbrIfIndex OBJECT-TYPE
            SYNTAX          InterfaceIndex
            MAX-ACCESS      read-only
            STATUS          current
            DESCRIPTION
                "The local interface ID for the virtual link over
                which the neighbor can be reached."
            ::= { extremeOspfv3VirtNbrEntry 3 }

    extremeOspfv3VirtNbrIfInstId OBJECT-TYPE
            SYNTAX          ExtremeOspfv3IfInstIdTc
            MAX-ACCESS      read-only
            STATUS          current
            DESCRIPTION
                "The interface instance for the virtual link over
                which the neighbor can be reached."
            ::= { extremeOspfv3VirtNbrEntry 4 }

    extremeOspfv3VirtNbrAddressType OBJECT-TYPE
            SYNTAX          InetAddressType
            MAX-ACCESS      read-only
            STATUS          current
            DESCRIPTION
                "The address type of extremeOspfv3VirtNbrAddress. Only IPv6
                addresses without zone index are expected."
            ::= { extremeOspfv3VirtNbrEntry 5 }

    extremeOspfv3VirtNbrAddress OBJECT-TYPE
            SYNTAX          InetAddress (SIZE (16))
            MAX-ACCESS      read-only
            STATUS          current


            DESCRIPTION
                "The IPv6 address advertised by this Virtual Neighbor.
                It must be a Global scope address."
            ::= { extremeOspfv3VirtNbrEntry 6 }

    extremeOspfv3VirtNbrOptions OBJECT-TYPE
            SYNTAX          Integer32
            MAX-ACCESS      read-only
            STATUS          current
            DESCRIPTION
                "A Bit Mask corresponding to the neighbor's options
                field."
            REFERENCE
                "OSPF Version 3, Appendix A.2 the Options field"
            ::= { extremeOspfv3VirtNbrEntry 7 }

    extremeOspfv3VirtNbrState OBJECT-TYPE
            SYNTAX          INTEGER {
                            down(1),
                            attempt(2),
                            init(3),
                            twoWay(4),
                            exchangeStart(5),
                            exchange(6),
                            loading(7),
                            full(8)
                            }
            MAX-ACCESS      read-only
            STATUS          current
            DESCRIPTION
                "The state of the Virtual Neighbor Relationship."
            ::= { extremeOspfv3VirtNbrEntry 8 }

    extremeOspfv3VirtNbrEvents OBJECT-TYPE
            SYNTAX          Counter32
            MAX-ACCESS      read-only
            STATUS          current
            DESCRIPTION
                "The number of times this virtual link has
                changed its state, or an error has occurred."
            ::= { extremeOspfv3VirtNbrEntry 9 }

    extremeOspfv3VirtNbrLsRetransQLen OBJECT-TYPE
            SYNTAX          Gauge32
            MAX-ACCESS      read-only
            STATUS          current
            DESCRIPTION
                "The current length of the retransmission
                queue."
            ::= { extremeOspfv3VirtNbrEntry 10 }

    extremeOspfv3VirtNbrHelloSuppressed OBJECT-TYPE
            SYNTAX          TruthValue


            MAX-ACCESS      read-only
            STATUS          current
            DESCRIPTION
                "Indicates whether Hellos are being suppressed
                to the neighbor"
            ::= { extremeOspfv3VirtNbrEntry 11 }

    extremeOspfv3VirtNbrIfId OBJECT-TYPE
            SYNTAX          InterfaceIndex
            MAX-ACCESS      read-only
            STATUS          current
            DESCRIPTION
                "The interface ID that the neighbor advertises
                in its Hello Packets on this virtual link, that is,
                the neighbor's local interface ID."
            ::= { extremeOspfv3VirtNbrEntry 12 }

   extremeOspfv3VirtNbrRestartHelperStatus OBJECT-TYPE
           SYNTAX       INTEGER { notHelping (1),
                                  helping (2)
                                }
           MAX-ACCESS   read-only
           STATUS       current
           DESCRIPTION
              "Indicates whether the router is acting
              as a Graceful restart helper for the neighbor."
              ::= { extremeOspfv3VirtNbrEntry 13 }

    extremeOspfv3VirtNbrRestartHelperAge OBJECT-TYPE
           SYNTAX       ExtremeOspfv3UpToRefreshIntervalTc
           UNITS        "seconds"
           MAX-ACCESS   read-only
           STATUS       current
           DESCRIPTION
              "Remaining time in current OSPF Graceful restart
              interval, if the router is acting as a restart
              helper for the neighbor."
           ::= { extremeOspfv3VirtNbrEntry 14 }

    extremeOspfv3VirtNbrRestartHelperExitRc OBJECT-TYPE
           SYNTAX       INTEGER { none (1),
                                  inProgress (2),
                                  completed (3),
                                  timedOut (4),
                                  topologyChanged (5)
                                }
           MAX-ACCESS   read-only
           STATUS       current
           DESCRIPTION
              "Describes the outcome of the last attempt at acting
               as a Graceful restart helper for the neighbor.

              none:............no restart has yet been attempted.


              inProgress:......a restart attempt is currently underway.
              completed:.......the last restart completed successfully.
              timedOut:........the last restart timed out.
              topologyChanged:.the last restart was aborted due to
                               a topology change."
        ::= { extremeOspfv3VirtNbrEntry 15 }


    --
    -- The OSPFv3 Area Aggregate Table
    --

    extremeOspfv3AreaAggregateTable OBJECT-TYPE
            SYNTAX          SEQUENCE OF ExtremeOspfv3AreaAggregateEntry
            MAX-ACCESS      not-accessible
            STATUS          current
            DESCRIPTION
                "A range of IPv6 prefixes specified by a
                prefix/prefix length pair. Note that if
                ranges are configured such that one range
                subsumes another range the most specific
                match is the preferred one."
            ::= { extremeOspfv3Objects 12 }

    extremeOspfv3AreaAggregateEntry OBJECT-TYPE
            SYNTAX          ExtremeOspfv3AreaAggregateEntry
            MAX-ACCESS      not-accessible
            STATUS          current
            DESCRIPTION
                "A range of IPv6 prefixes specified by a
                prefix/prefix length  pair. Note that if
                ranges are configured such that one range
                subsumes another range the most specific match is
                the preferred one."
            REFERENCE
                "OSPF Version 2, Appendix C.2  Area parameters"
            INDEX           { extremeOspfv3AreaAggregateAreaID,
                              extremeOspfv3AreaAggregateAreaLsdbType,
                              extremeOspfv3AreaAggregatePrefixType,
                              extremeOspfv3AreaAggregatePrefix,
                              extremeOspfv3AreaAggregatePrefixLength }
            ::= { extremeOspfv3AreaAggregateTable 1 }

    ExtremeOspfv3AreaAggregateEntry ::= SEQUENCE {
            extremeOspfv3AreaAggregateAreaID
                    ExtremeOspfv3AreaIdTc,
            extremeOspfv3AreaAggregateAreaLsdbType
                    INTEGER,
            extremeOspfv3AreaAggregatePrefixType
                    InetAddressType,
            extremeOspfv3AreaAggregatePrefix
                    InetAddress,
            extremeOspfv3AreaAggregatePrefixLength


                    InetAddressPrefixLength,
            extremeOspfv3AreaAggregateStatus
                    RowStatus,
            extremeOspfv3AreaAggregateEffect
                    INTEGER,
            extremeOspfv3AreaAggregateRouteTag
                    Integer32
            }

    extremeOspfv3AreaAggregateAreaID OBJECT-TYPE
            SYNTAX          ExtremeOspfv3AreaIdTc
            MAX-ACCESS      not-accessible
            STATUS          current
            DESCRIPTION
                "The Area the Address Aggregate is to be found
                within."
            REFERENCE
                "OSPF Version 2, Appendix C.2 Area parameters"
            ::= { extremeOspfv3AreaAggregateEntry 1 }

    extremeOspfv3AreaAggregateAreaLsdbType OBJECT-TYPE
            SYNTAX          INTEGER {
                            interAreaPrefixLsa(8195), -- 0x2003
                            nssaExternalLsa(8199)     -- 0x2007
                            }
            MAX-ACCESS      not-accessible
            STATUS          current
            DESCRIPTION
                "The type of the Address Aggregate.  This field
                specifies  the  Area Lsdb type that this Address
                Aggregate applies to."
            REFERENCE
                "OSPF Version 2, Appendix A.4.1 The Link State
                Advertisement header"
            ::= { extremeOspfv3AreaAggregateEntry 2 }

    extremeOspfv3AreaAggregatePrefixType OBJECT-TYPE
            SYNTAX          InetAddressType
            MAX-ACCESS      not-accessible
            STATUS          current
            DESCRIPTION
                "The prefix type of extremeOspfv3AreaAggregatePrefix. Only
                IPv6 addresses are expected."
            ::= { extremeOspfv3AreaAggregateEntry 4 }

    extremeOspfv3AreaAggregatePrefix OBJECT-TYPE
            SYNTAX          InetAddress (SIZE (0..16))
            MAX-ACCESS      not-accessible
            STATUS          current
            DESCRIPTION
                "The IPv6 Prefix."
            REFERENCE
                "OSPF Version 2, Appendix C.2 Area parameters"


            ::= { extremeOspfv3AreaAggregateEntry 5 }

    extremeOspfv3AreaAggregatePrefixLength OBJECT-TYPE
            SYNTAX          InetAddressPrefixLength (3..128)
            UNITS           "bits"
            MAX-ACCESS      not-accessible
            STATUS          current
            DESCRIPTION
                "The length of the prefix (in bits). A prefix can
                not be shorter than 3 bits."
            REFERENCE
                "OSPF Version 2, Appendix C.2 Area parameters"
            ::= { extremeOspfv3AreaAggregateEntry 6 }

    extremeOspfv3AreaAggregateStatus OBJECT-TYPE
            SYNTAX          RowStatus
            MAX-ACCESS      read-create
            STATUS          current
            DESCRIPTION
                "This variable controls the status of the entry
                The use of RowStatus is covered in more detail
                in [6]."
            ::= { extremeOspfv3AreaAggregateEntry 7 }

    extremeOspfv3AreaAggregateEffect OBJECT-TYPE
            SYNTAX          INTEGER {
                            advertiseMatching(1),
                            doNotAdvertiseMatching(2)
                            }
            MAX-ACCESS      read-create
            STATUS          current
            DESCRIPTION
                "Prefixes subsumed by ranges either trigger the
                advertisement of the indicated aggregate
                (advertiseMatching), or result in the prefix not
                being advertised at all outside the area."
            DEFVAL          { advertiseMatching }
            ::= { extremeOspfv3AreaAggregateEntry 8 }

    extremeOspfv3AreaAggregateRouteTag OBJECT-TYPE
            SYNTAX          Integer32
            MAX-ACCESS      read-create
            STATUS          current
            DESCRIPTION
                "This tag is advertised only in the summarized
                 As-External LSA when summarizing from NSSA-LSAǳ to
                 AS-External-LSAǳ."
            DEFVAL         { 0 }
            ::= { extremeOspfv3AreaAggregateEntry 9 }

    -- The Ospfv3 Notification Table

    -- The Ospfv3 Notification Table records fields that are
    -- required for notifications.

    extremeOspfv3NotificationEntry OBJECT IDENTIFIER
            ::= { extremeOspfv3Objects 13 }

    extremeOspfv3ConfigErrorType OBJECT-TYPE
        SYNTAX       INTEGER {
                        badVersion(1),
                        areaMismatch(2),
                        unknownNbmaNbr(3), -- Router is DR eligible
                        unknownVirtualNbr(4),
                        helloIntervalMismatch(5),
                        deadIntervalMismatch(6),
                        optionMismatch(7),
                        mtuMismatch(8),
                        duplicateRouterId(9),
                        noError(10) }
        MAX-ACCESS   accessible-for-notify
        STATUS   current
        DESCRIPTION
            "Potential types of configuration conflicts.
            Used by the extremeOspfv3ConfigError and
            extremeOspfv3ConfigVirtError notifications."
        ::= { extremeOspfv3NotificationEntry 1 }








    extremeOspfv3PacketType OBJECT-TYPE
        SYNTAX       INTEGER {
                        hello(1),
                        dbDescript(2),
                        lsReq(3),
                        lsUpdate(4),
                        lsAck(5),
                        nullPacket(6) }
        MAX-ACCESS   accessible-for-notify
        STATUS       current
        DESCRIPTION
            "OSPFv3 packet types."
        ::= { extremeOspfv3NotificationEntry 2 }

    extremeOspfv3PacketSrc  OBJECT-TYPE
        SYNTAX       InetAddressIPv6
        MAX-ACCESS   accessible-for-notify
        STATUS       current
        DESCRIPTION
            "The IPv6 address of an inbound packet that cannot
            be identified by a neighbor instance.

            Only IPv6 addresses without zone index are expected."
        ::= { extremeOspfv3NotificationEntry 3 }

    -- Notification Definitions

    -- The notifications need to be throttled so as to not overwhelm the
    -- management agent in case of rapid changes to the OSPFv3 module.

   extremeOspfv3VirtIfStateChange NOTIFICATION-TYPE
        OBJECTS { extremeOspfv3RouterId,  -- The originator of the notification
                  extremeOspfv3VirtIfState  -- The new state
           }
        STATUS       current
        DESCRIPTION
            "An extremeOspfv3VirtIfStateChange notification signifies that
            there has been a change in the state of an OSPFv3 virtual
            interface.

            This notification should be generated when the interface
            state regresses (e.g., goes from Point-to-Point to Down)
            or progresses to a terminal state (i.e., Point-to-Point)."
        ::= { extremeOspfv3Notifications 1 }

   extremeOspfv3NbrStateChange NOTIFICATION-TYPE
        OBJECTS { extremeOspfv3RouterId, -- The originator of the notification
                  extremeOspfv3NbrState  -- The new state





           }
        STATUS       current
        DESCRIPTION
            "An extremeOspfv3NbrStateChange notification signifies that
            there has been a change in the state of a
            non-virtual OSPFv3 neighbor.  This notification should be
            generated when the neighbor state regresses
            (e.g., goes from Attempt or Full to 1-Way or
            Down) or progresses to a terminal state (e.g.,
            2-Way or Full).  When a neighbor transitions
            from or to Full on non-broadcast multi-access
            and broadcast networks, the notification should be
            generated by the Designated Router.  A Designated
            Router transitioning to Down will be noted by
            ospfIfStateChange."
        ::= { extremeOspfv3Notifications 2 }

   extremeOspfv3VirtNbrStateChange NOTIFICATION-TYPE
        OBJECTS { extremeOspfv3RouterId, -- The originator of the notification
                  extremeOspfv3VirtNbrState  -- The new state
           }
        STATUS       current
        DESCRIPTION
            "An extremeOspfv3VirtNbrStateChange notification signifies
            that there has been a change in the state of an OSPFv3
            virtual neighbor.  This notification should be generated
            when the neighbor state regresses (e.g., goes
            from Attempt or Full to 1-Way or Down) or
            progresses to a terminal state (e.g., Full)."
        ::= { extremeOspfv3Notifications 3 }

   extremeOspfv3IfConfigError NOTIFICATION-TYPE
        OBJECTS { extremeOspfv3RouterId, -- The originator of the notification
           extremeOspfv3IfState,         -- State of the interface
           extremeOspfv3PacketSrc,       -- IPv6 address of source
           extremeOspfv3ConfigErrorType, -- Type of error
           extremeOspfv3PacketType       -- Type of packet
           }
        STATUS       current
        DESCRIPTION
            "An extremeOspfv3IfConfigError notification signifies that a
            packet has been received on a non-virtual
            interface from a router whose configuration
            parameters conflict with this router's
            configuration parameters.  Note that the event
            optionMismatch should cause a notification only if it
            prevents an adjacency from forming."
        ::= { extremeOspfv3Notifications 4 }





   extremeOspfv3VirtIfConfigError NOTIFICATION-TYPE
        OBJECTS { extremeOspfv3RouterId, -- The originator of the notification
           extremeOspfv3VirtIfState,     -- State of the interface
           extremeOspfv3ConfigErrorType, -- Type of error
           extremeOspfv3PacketType
           }
        STATUS       current
        DESCRIPTION
            "An extremeOspfv3VirtIfConfigError notification signifies that a
            packet has been received on a virtual interface
            from a router whose configuration parameters
            conflict with this router's configuration
            parameters.  Note that the event optionMismatch
            should cause a notification only if it prevents an
            adjacency from forming."
        ::= { extremeOspfv3Notifications 5 }

   extremeOspfv3IfStateChange NOTIFICATION-TYPE
        OBJECTS { extremeOspfv3RouterId, -- The originator of the notification
           extremeOspfv3IfState   -- The new state
           }
        STATUS       current
        DESCRIPTION
            "An extremeOspfv3IfStateChange notification signifies that there
            has been a change in the state of a non-virtual
            OSPFv3 interface.  This notification should be generated
            when the interface state regresses (e.g., goes
            from DR to Down) or progresses to a terminal
            state (i.e., Point-to-Point, DR Other, DR, or
            Backup)."
        ::= { extremeOspfv3Notifications 6 }

   extremeOspfv3NssaTranslatorStatusChange NOTIFICATION-TYPE
        OBJECTS { extremeOspfv3RouterId, -- The originator of the notification
           extremeOspfv3AreaNssaTranslatorState  -- new state
           }
        STATUS       current
        DESCRIPTION
            "An extremeOspfv3NssaTranslatorStatusChange notification
            indicates that there has been a change in the router's
            ability to translate OSPFv3 NSSA LSAs into OSPFv3 External
            LSAs.  This notification should be generated when the
            Translator Status transitions from or to any defined
            status on a per-area basis."
        ::= { extremeOspfv3Notifications 7 }

   extremeOspfv3NbrRestartHelperStatusChange NOTIFICATION-TYPE
        OBJECTS { extremeOspfv3RouterId, -- The originator of the notification
                  extremeOspfv3NbrRestartHelperStatus,  -- new status
                  extremeOspfv3NbrRestartHelperAge,
                  extremeOspfv3NbrRestartHelperExitRc
                }
        STATUS       current
        DESCRIPTION
            "An extremeOspfv3NbrRestartHelperStatusChange notification
            signifies that there has been a change in the
            graceful restart helper state for the neighbor.
            This notification should be generated when the
            neighbor restart helper status transitions for a neighbor."
        ::= { extremeOspfv3Notifications 8 }

   extremeOspfv3VirtNbrRestartHelperStatusChange NOTIFICATION-TYPE
        OBJECTS { extremeOspfv3RouterId, -- The originator of the notification
                  extremeOspfv3VirtNbrRestartHelperStatus,  -- new status
                  extremeOspfv3VirtNbrRestartHelperAge,
                  extremeOspfv3VirtNbrRestartHelperExitRc
                }
        STATUS       current
        DESCRIPTION
            "An extremeOspfv3VirtNbrRestartHelperStatusChange
            notification signifies that there has been a
            change in the graceful restart helper state for
            the virtual neighbor.  This notification should be
            generated when the virtual neighbor restart helper status
            transitions for a virtual neighbor."
        ::= { extremeOspfv3Notifications 9 }


    -- conformance information



    extremeOspfv3Groups      OBJECT IDENTIFIER ::= { extremeOspfv3Conformance 1 }
    extremeOspfv3Compliances OBJECT IDENTIFIER ::= { extremeOspfv3Conformance 2 }

    -- compliance statements

    extremeOspfv3Compliance MODULE-COMPLIANCE
            STATUS          current
            DESCRIPTION     "The compliance statement"
            MODULE          -- this module
            MANDATORY-GROUPS {
                            extremeOspfv3BasicGroup,
                            extremeOspfv3AreaGroup,
                            extremeOspfv3IfGroup,
                            extremeOspfv3VirtIfGroup,
                            extremeOspfv3NbrGroup,
                            extremeOspfv3CfgNbrGroup,
                            extremeOspfv3VirtNbrGroup,
                            extremeOspfv3AreaAggregateGroup
                            }

            GROUP           extremeOspfv3AsLsdbGroup
            DESCRIPTION
                "This group is required for OSPFv3 systems that
                display their AS-scope link state database."

            GROUP           extremeOspfv3AreaLsdbGroup
            DESCRIPTION
                "This group is required for OSPFv3 systems that
                display their Area-scope link state database."

            GROUP           extremeOspfv3LinkLsdbGroup
            DESCRIPTION
                "This group is required for OSPFv3 systems that
                display their Link-scope link state database."

            GROUP           extremeOspfv3HostGroup
            DESCRIPTION
                "This group is required for OSPFv3 systems that
                support attached hosts."

            GROUP           extremeOspfv3NotificationObjectGroup
            DESCRIPTION
                "This group is required for OSPFv3 systems that
                support OSPFv3 notifications."

            GROUP           extremeOspfv3NotificationGroup
            DESCRIPTION
                "This group is required for OSPFv3 systems that
                support OSPFv3 notifications."

            OBJECT          extremeOspfv3NbrAddressType
            SYNTAX          InetAddressType { ipv6(2) }
            DESCRIPTION
                "An implementation is only required to support IPv6
                address without zone index."

            OBJECT          extremeOspfv3VirtNbrAddressType
            SYNTAX          InetAddressType { ipv6(2) }
            DESCRIPTION
                "An implementation is only required to support IPv6
                address without zone index."

            ::= { extremeOspfv3Compliances 1 }



    -- units of conformance

    extremeOspfv3BasicGroup OBJECT-GROUP
            OBJECTS         {
                            extremeOspfv3RouterId,
                            extremeOspfv3AdminStat,
                            extremeOspfv3VersionNumber,
                            extremeOspfv3AreaBdrRtrStatus,
                            extremeOspfv3ASBdrRtrStatus,
                            extremeOspfv3AsScopeLsaCount,
                            extremeOspfv3AsScopeLsaCksumSum,
                            extremeOspfv3OriginateNewLsas,
                            extremeOspfv3RxNewLsas,
                            extremeOspfv3ExtLsaCount,
                            extremeOspfv3ExtAreaLsdbLimit,
                            extremeOspfv3MulticastExtensions,
                            extremeOspfv3ExitOverflowInterval,
                            extremeOspfv3DemandExtensions,
                            extremeOspfv3ReferenceBandwidth,
                            extremeOspfv3RestartSupport,
                            extremeOspfv3RestartInterval,
                            extremeOspfv3RestartStatus,
                            extremeOspfv3RestartAge,
                            extremeOspfv3RestartExitRc,
                            extremeOspfv3NotificationEnable
                            }
            STATUS          current
            DESCRIPTION
                "These objects are required for OSPFv3 systems."
            ::= { extremeOspfv3Groups 1 }


    extremeOspfv3AreaGroup OBJECT-GROUP
            OBJECTS         {
                            extremeOspfv3ImportAsExtern,
                            extremeOspfv3AreaSpfRuns,
                            extremeOspfv3AreaBdrRtrCount,
                            extremeOspfv3AreaAsBdrRtrCount,
                            extremeOspfv3AreaScopeLsaCount,
                            extremeOspfv3AreaScopeLsaCksumSum,
                            extremeOspfv3AreaSummary,
                            extremeOspfv3AreaStatus,
                            extremeOspfv3StubMetric,
                            extremeOspfv3AreaNssaTranslatorRole,
                            extremeOspfv3AreaNssaTranslatorState,
                            extremeOspfv3AreaNssaTranslatorStabInt,
                            extremeOspfv3AreaNssaTranslatorEvents,
                            extremeOspfv3AreaStubMetricType
                            }
            STATUS          current
            DESCRIPTION
                "These objects are required for OSPFv3 systems
                supporting areas."


            ::= { extremeOspfv3Groups 2 }

    extremeOspfv3AsLsdbGroup OBJECT-GROUP
            OBJECTS         {
                            extremeOspfv3AsLsdbSequence,
                            extremeOspfv3AsLsdbAge,
                            extremeOspfv3AsLsdbChecksum,
                            extremeOspfv3AsLsdbAdvertisement,
                            extremeOspfv3AsLsdbTypeKnown
                            }
            STATUS          current
            DESCRIPTION
                "These objects are required for OSPFv3 systems
                that display their AS-scope link state database."
            ::= { extremeOspfv3Groups 3 }

    extremeOspfv3AreaLsdbGroup OBJECT-GROUP
            OBJECTS         {
                            extremeOspfv3AreaLsdbSequence,
                            extremeOspfv3AreaLsdbAge,
                            extremeOspfv3AreaLsdbChecksum,
                            extremeOspfv3AreaLsdbAdvertisement,
                            extremeOspfv3AreaLsdbTypeKnown
                            }
            STATUS          current
            DESCRIPTION
                "These objects are required for OSPFv3 systems
                that display their Area-scope link state database."
            ::= { extremeOspfv3Groups 4 }

    extremeOspfv3LinkLsdbGroup OBJECT-GROUP
            OBJECTS         {
                            extremeOspfv3LinkLsdbSequence,
                            extremeOspfv3LinkLsdbAge,
                            extremeOspfv3LinkLsdbChecksum,
                            extremeOspfv3LinkLsdbAdvertisement,
                            extremeOspfv3LinkLsdbTypeKnown
                            }
            STATUS          current
            DESCRIPTION
                "These objects are required for OSPFv3 systems
                that display their Link-scope link state database."
            ::= { extremeOspfv3Groups 5 }

    extremeOspfv3HostGroup OBJECT-GROUP
            OBJECTS         {
                            extremeOspfv3HostMetric,
                            extremeOspfv3HostStatus,
                            extremeOspfv3HostAreaID
                            }
            STATUS          current
            DESCRIPTION
                "These objects are required for OSPFv3 systems


                that support attached hosts."
            ::= { extremeOspfv3Groups 6 }

    extremeOspfv3IfGroup OBJECT-GROUP
            OBJECTS         {
                            extremeOspfv3IfAreaId,
                            extremeOspfv3IfType,
                            extremeOspfv3IfAdminStat,
                            extremeOspfv3IfRtrPriority,
                            extremeOspfv3IfTransitDelay,
                            extremeOspfv3IfRetransInterval,
                            extremeOspfv3IfHelloInterval,
                            extremeOspfv3IfRtrDeadInterval,
                            extremeOspfv3IfPollInterval,
                            extremeOspfv3IfState,
                            extremeOspfv3IfDesignatedRouter,
                            extremeOspfv3IfBackupDesignatedRouter,
                            extremeOspfv3IfEvents,
                            extremeOspfv3IfStatus,
                            extremeOspfv3IfMulticastForwarding,
                            extremeOspfv3IfDemand,
                            extremeOspfv3IfMetricValue,
                            extremeOspfv3IfLinkScopeLsaCount,
                            extremeOspfv3IfLinkLsaCksumSum,
                            extremeOspfv3IfDemandNbrProbe,
                            extremeOspfv3IfDemandNbrProbeRetxLimit,
                            extremeOspfv3IfDemandNbrProbeInterval
                            }
            STATUS          current
            DESCRIPTION
                "These interface objects are required for
                OSPFv3 systems."
            ::= { extremeOspfv3Groups 7 }

    extremeOspfv3VirtIfGroup OBJECT-GROUP
            OBJECTS         {
                            extremeOspfv3VirtIfIndex,
                            extremeOspfv3VirtIfInstId,
                            extremeOspfv3VirtIfTransitDelay,
                            extremeOspfv3VirtIfRetransInterval,
                            extremeOspfv3VirtIfHelloInterval,
                            extremeOspfv3VirtIfRtrDeadInterval,
                            extremeOspfv3VirtIfState,
                            extremeOspfv3VirtIfEvents,
                            extremeOspfv3VirtIfStatus,
                            extremeOspfv3VirtIfLinkScopeLsaCount,
                            extremeOspfv3VirtIfLinkLsaCksumSum
                            }
            STATUS          current
            DESCRIPTION
                "These virtual interface objects are required for
                OSPFv3 systems."
            ::= { extremeOspfv3Groups 8 }



    extremeOspfv3NbrGroup OBJECT-GROUP
            OBJECTS         {
                            extremeOspfv3NbrAddressType,
                            extremeOspfv3NbrAddress,
                            extremeOspfv3NbrOptions,
                            extremeOspfv3NbrPriority,
                            extremeOspfv3NbrState,
                            extremeOspfv3NbrEvents,
                            extremeOspfv3NbrLsRetransQLen,
                            extremeOspfv3NbrHelloSuppressed,
                            extremeOspfv3NbrIfId,
                            extremeOspfv3NbrRestartHelperStatus,
                            extremeOspfv3NbrRestartHelperAge,
                            extremeOspfv3NbrRestartHelperExitRc
                            }
            STATUS          current
            DESCRIPTION
                "These neighbor objects are required for
                OSPFv3 systems."
            ::= { extremeOspfv3Groups 9 }

    extremeOspfv3CfgNbrGroup OBJECT-GROUP
            OBJECTS         {
                            extremeOspfv3CfgNbrPriority,
                            extremeOspfv3CfgNbrRtrId,
                            extremeOspfv3CfgNbrState,
                            extremeOspfv3CfgNbrStorageType,
                            extremeOspfv3CfgNbrStatus
                            }
            STATUS          current
            DESCRIPTION
                "These Configured neighbor objects are required for
                OSPFv3 systems."
            ::= { extremeOspfv3Groups 10 }

    extremeOspfv3VirtNbrGroup OBJECT-GROUP
            OBJECTS         {
                            extremeOspfv3VirtNbrIfIndex,
                            extremeOspfv3VirtNbrIfInstId,
                            extremeOspfv3VirtNbrAddressType,
                            extremeOspfv3VirtNbrAddress,
                            extremeOspfv3VirtNbrOptions,
                            extremeOspfv3VirtNbrState,
                            extremeOspfv3VirtNbrEvents,
                            extremeOspfv3VirtNbrLsRetransQLen,
                            extremeOspfv3VirtNbrHelloSuppressed,
                            extremeOspfv3VirtNbrIfId,
                            extremeOspfv3VirtNbrRestartHelperStatus,
                            extremeOspfv3VirtNbrRestartHelperAge,
                            extremeOspfv3VirtNbrRestartHelperExitRc
                            }
            STATUS          current


            DESCRIPTION
                "These virtual neighbor objects are required for
                OSPFv3 systems."
            ::= { extremeOspfv3Groups 11 }

    extremeOspfv3AreaAggregateGroup OBJECT-GROUP
            OBJECTS         {
                            extremeOspfv3AreaAggregateStatus,
                            extremeOspfv3AreaAggregateEffect,
                            extremeOspfv3AreaAggregateRouteTag
                            }
            STATUS          current
            DESCRIPTION
                "These area aggregate objects are required for
                OSPFv3 systems."
            ::= { extremeOspfv3Groups 12 }

    extremeOspfv3NotificationObjectGroup OBJECT-GROUP
            OBJECTS         {
                            extremeOspfv3ConfigErrorType,
                            extremeOspfv3PacketType,
                            extremeOspfv3PacketSrc
                            }
            STATUS          current
            DESCRIPTION
                "These objects are used to record notification
                parameters."
            ::= { extremeOspfv3Groups 13 }

    extremeOspfv3NotificationGroup NOTIFICATION-GROUP
            NOTIFICATIONS   {
                            extremeOspfv3VirtIfStateChange,
                            extremeOspfv3NbrStateChange,
                            extremeOspfv3VirtNbrStateChange,
                            extremeOspfv3IfConfigError,
                            extremeOspfv3VirtIfConfigError,
                            extremeOspfv3IfStateChange,
                            extremeOspfv3NssaTranslatorStatusChange,
                            extremeOspfv3NbrRestartHelperStatusChange,
                            extremeOspfv3VirtNbrRestartHelperStatusChange
                            }
            STATUS          current
            DESCRIPTION
                "This group is used for OSPFv3 notifications."
            ::= { extremeOspfv3Groups 14 }

    END
