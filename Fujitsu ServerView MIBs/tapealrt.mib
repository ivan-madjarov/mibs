-- *************************************************************************
-- *************************************************************************
-- TapeAlert (1.3.6.1.4.1.11.2.3.9.7.1)
-- Issue: v2.1
-- Date: 16th May 1998
-- Changes from v2.0:
--    Added new flag 19 from v2.1 spec
-- Changes from v1.2:
--    Added new flags for library device support from TapeAlert v2 spec
--    Added new flags for tape drive/autoloader support from v2 spec
--    Updated description for errorTrapNum to reflect library flags 255 offset
--
-- Changes from v1.1:
--    Changed trap definitions for Managewise compilation
-- Changes from v1.0:
--    Minor change to errorDate field making it 14 octets long rather than 7
--
-- Overall MIB Structure
--
--      tapeAlert
--      .1      control
--              .1      revMajor                (used for presence checking)
--              .2      revMinor
--              .3      trapEnable              (optional)
--              .4      autoCleanEnable         (optional)
--              .5      autoCopyEnable          (optional)
--      .2      numDevices
--      .3      {devTable}                      (table of device information)
--              .1      devInfo                 (device information entry in table)
--                      .1      devNum          (index)
--                      .2      tapeAlertCapability
--                      .3      hbaName
--                      .4      hbaNumber
--                      .5      hbaChannel
--                      .6      driveScsiID
--                      .7      driveInquiry
--                      .8      driveFirmware
--                      .9      driveType
--                      .10     driveCompress
--                      .11     currentMedia
--                      .12     driveSerialNum  (optional)
--      .4      numErrors
--      .5      {errorHistoryTable}             (table of error history)
--              .1      errorHistoryEntry       (error entry in table)
--                      .1      errorIndex      (index)
--                      .2      errorHbaNumber
--                      .3      errorHbaChannel
--                      .4      errorDriveScsiID
--                      .5      errorDate
--                      .6      errorTrapNum
--                      .7      errorMedia
-- **************************************************************************
-- **************************************************************************

TapeAlert-MIB DEFINITIONS ::= BEGIN

        IMPORTS
                enterprises    FROM RFC1155-SMI
                OBJECT-TYPE    FROM RFC-1212
                DisplayString  FROM RFC1213-MIB
                TRAP-TYPE      FROM RFC-1215;

                hp             OBJECT IDENTIFIER ::= { enterprises 11 }
                nm             OBJECT IDENTIFIER ::= { hp 2 }
                system         OBJECT IDENTIFIER ::= { nm 3 }
                netPeripheral  OBJECT IDENTIFIER ::= { system 9 }
                netTape        OBJECT IDENTIFIER ::= { netPeripheral 7 }
                tapeAlert      OBJECT IDENTIFIER ::= { netTape 1 }
                control        OBJECT IDENTIFIER ::= { tapeAlert 1 }

-- **************************************************************************
-- control group definitions
-- **************************************************************************

revMajor OBJECT-TYPE
        SYNTAX INTEGER (0..255)
        ACCESS read-only
        STATUS mandatory
        DESCRIPTION
                "The TapeAlert major revision level (left of the decimal).
                Used for presence checking."
        ::= { control 1 }

revMinor OBJECT-TYPE
        SYNTAX INTEGER (0..255)
        ACCESS read-only
        STATUS mandatory
        DESCRIPTION
                "The TapeAlert minor revision level (right of the decimal)."
        ::= { control 2 }

trapEnable OBJECT-TYPE
        SYNTAX INTEGER (0..1)
        ACCESS read-write
        STATUS optional
        DESCRIPTION
                "Indicates whether agent should or should not send TapeAlert traps."
        ::= { control 3 }

autoCleanEnable OBJECT-TYPE
        SYNTAX INTEGER (0..1)
        ACCESS read-write
        STATUS optional
        DESCRIPTION
                "Indicates whether application should or should not perform
                an automatic cleaning operation based on TapeAlert cleaning
                information."
        ::= { control 4 }

autoCopyEnable OBJECT-TYPE
        SYNTAX INTEGER (0..1)
        ACCESS read-write
        STATUS optional
        DESCRIPTION
                "Indicates whether application should or should not perform
                an automatic tape copy or tape discard operation based on
                TapeAlert media information."
        ::= { control 5 }

-- **************************************************************************
-- numDevices definition
-- Total number of tape devices attached to server.
-- **************************************************************************

numDevices OBJECT-TYPE
        SYNTAX INTEGER (0..255)
        ACCESS read-only
        STATUS mandatory
        DESCRIPTION
                "Total number of tape devices attached to server and
                managed by TapeAlert agent. Zero means no devices present."
        ::= { tapeAlert 2 }

-- **************************************************************************
-- devTable definition
-- A table of tape device information, consisting of a list of devInfo
-- entries. The number of entries is given by the value of numDevices.
-- **************************************************************************

devTable OBJECT-TYPE
        SYNTAX SEQUENCE OF DevInfo
        ACCESS not-accessible
        STATUS mandatory
        DESCRIPTION
                "A list of tape device information entries. The number
                of entries is given by the value of numDevices."
        ::= { tapeAlert 3 }

-- **************************************************************************
-- devInfo definition
-- A tape device information entry, containing configuration information for
-- a particular tape device
-- **************************************************************************

devInfo OBJECT-TYPE
        SYNTAX DevInfo
        ACCESS not-accessible
        STATUS mandatory
        DESCRIPTION
                "A tape device information entry, containing configuration
                information for a particular tape device."
        INDEX { devNum }
        ::= { devTable 1 }

DevInfo ::= SEQUENCE
{
        devNum                  INTEGER (0..255),
        tapeAlertCapability     INTEGER (0..1),
        hbaName                 DisplayString,
        hbaNumber               INTEGER (0..255),
        hbaChannel              INTEGER (0..255),
        driveScsiID             INTEGER (0..255),
        driveInquiry            DisplayString,
        driveFirmware           DisplayString,
        driveType               DisplayString,
        driveCompress           INTEGER (0..1),
        currentMedia            DisplayString,
        driveSerialNum          DisplayString
}

devNum OBJECT-TYPE
        SYNTAX INTEGER (0..255)
        ACCESS read-only
        STATUS mandatory
        DESCRIPTION
                "A unique index value for each tape device. Its value ranges
                between 1 and the value of numDevices."
        ::= { devInfo 1 }

tapeAlertCapability OBJECT-TYPE
        SYNTAX INTEGER (0..1)
        ACCESS read-only
        STATUS mandatory
        DESCRIPTION
                "Indicates whether tape device supports TapeAlert, with
                zero indicating not supported and one indicating supported"
        ::= { devInfo 2 }

hbaName OBJECT-TYPE
        SYNTAX DisplayString (SIZE (0..255))
        ACCESS read-only
        STATUS mandatory
        DESCRIPTION
                "Name of SCSI Host Bus Adaptor connected to tape drive,
                for example Adaptec AHA2740AT."
        ::= { devInfo 3 }

hbaNumber OBJECT-TYPE
        SYNTAX INTEGER (0..255)
        ACCESS read-only
        STATUS mandatory
        DESCRIPTION
                "The number of SCSI Host Bus Adaptor connected
                to tape drive, for example 0 is first HBA on the system."
        ::= { devInfo 4 }

hbaChannel OBJECT-TYPE
        SYNTAX INTEGER (0..255)
        ACCESS read-only
        STATUS mandatory
        DESCRIPTION
                "SCSI Channel number of SCSI Host Bus Adaptor connected
                to tape drive, for example 0 is first SCSI channel of HBA."
        ::= { devInfo 5 }

driveScsiID OBJECT-TYPE
        SYNTAX INTEGER (0..255)
        ACCESS read-only
        STATUS mandatory
        DESCRIPTION
                "SCSI ID of Tape Device."
        ::= { devInfo 6 }

driveInquiry OBJECT-TYPE
        SYNTAX DisplayString (SIZE (0..255))
        ACCESS read-only
        STATUS mandatory
        DESCRIPTION
                "SCSI Inquiry data of Tape Device, with vendor ID data
                followed by device ID data."
        ::= { devInfo 7 }

driveFirmware OBJECT-TYPE
        SYNTAX DisplayString (SIZE (0..255))
        ACCESS read-only
        STATUS mandatory
        DESCRIPTION
                "Firmware revision of Tape Device."
        ::= { devInfo 8 }

driveType OBJECT-TYPE
        SYNTAX DisplayString (SIZE (0..255))
        ACCESS read-only
        STATUS mandatory
        DESCRIPTION
                "Device type of Tape Device, for example DDS1"
        ::= { devInfo 9 }

driveCompress OBJECT-TYPE
        SYNTAX INTEGER (0..1)
        ACCESS read-only
        STATUS mandatory
        DESCRIPTION
                "Indicates whether Tape Device supports hardware compression,
                with zero indicating not supported and one indicating supported."
        ::= { devInfo 10 }

currentMedia OBJECT-TYPE
        SYNTAX DisplayString (SIZE (0..255))
        ACCESS read-only
        STATUS mandatory
        DESCRIPTION
                "Software label of current media loaded in drive"
        ::= { devInfo 11 }

driveSerialNum OBJECT-TYPE
        SYNTAX DisplayString (SIZE (0..255))
        ACCESS read-only
        STATUS optional
        DESCRIPTION
                "Hardware Serial Number of Tape Device, if available"
        ::= { devInfo 12 }

-- **************************************************************************
-- numErrors definition
-- Total number of TapeAlert error traps logged by TapeAlert agent since
-- agent was initialised.
-- **************************************************************************

numErrors OBJECT-TYPE
        SYNTAX INTEGER (0..255)
        ACCESS read-only
        STATUS mandatory
        DESCRIPTION
                "Total number of TapeAlert error traps logged by TapeAlert
                agent since agent was initialised. Zero means that no
                TapeAlert trap events occurred since initialisation."
        ::= { tapeAlert 4 }

-- **************************************************************************
-- errorHistoryTable definition
-- This table will provide a historical list of all TapeAlert errors since
-- the TapeAlert agent was initialised. This will provide the ability to show
-- the error history of a specified tape device and identify any trends
-- **************************************************************************

errorHistoryTable OBJECT-TYPE
        SYNTAX SEQUENCE OF ErrorHistoryEntry
        ACCESS not-accessible
        STATUS mandatory
        DESCRIPTION
                "A list of historical error entries for all tape
                devices on the server. The list should contain
                an entry for each TapeAlert trap sent since the
                TapeAlert agent was initialised."
        ::= { tapeAlert 5 }

-- **************************************************************************
-- errorHistoryEntry definition
-- An error entry in the errorHistoryTable, containing information on a
-- historic TapeAlert trap sent by the TapeAlert agent
-- **************************************************************************

errorHistoryEntry OBJECT-TYPE
        SYNTAX ErrorHistoryEntry
        ACCESS not-accessible
        STATUS mandatory
        DESCRIPTION
                "An error entry in the errorHistoryTable, containing
                information on a historic TapeAlert trap sent by the
                TapeAlert agent"
        INDEX { errorIndex }
        ::= { errorHistoryTable 1 }

ErrorHistoryEntry ::= SEQUENCE
{
        errorIndex              INTEGER (0..255),
        errorHbaNumber          INTEGER (0..255),
        errorHbaChannel         INTEGER (0..255),
        errorDriveScsiID        INTEGER (0..255),
        errorDate               OCTET STRING,
        errorTrapNum            INTEGER (1..64),
        errorMedia              DisplayString
}

errorIndex OBJECT-TYPE
        SYNTAX INTEGER (0..255)
        ACCESS read-only
        STATUS mandatory
        DESCRIPTION
                "A unique index value for each error entry. Its value ranges
                between 1 and the value of numErrors."
        ::= { errorHistoryEntry 1 }

errorHbaNumber OBJECT-TYPE
        SYNTAX INTEGER (0..255)
        ACCESS read-only
        STATUS mandatory
        DESCRIPTION
                "The number of SCSI Host Bus Adaptor connected to
                the tape drive that caused this specific TapeAlert
                error, for example 0 is first HBA on the system."
        ::= { errorHistoryEntry 2 }

errorHbaChannel OBJECT-TYPE
        SYNTAX INTEGER (0..255)
        ACCESS read-only
        STATUS mandatory
        DESCRIPTION
                "SCSI channel number of SCSI Host Bus Adaptor connected
                to the tape drive that caused this specific TapeAlert
                error, for example 0 is first SCSI channel of HBA."
        ::= { errorHistoryEntry 3 }

errorDriveScsiID OBJECT-TYPE
        SYNTAX INTEGER (0..255)
        ACCESS read-only
        STATUS mandatory
        DESCRIPTION
                "SCSI of the tape drive that caused this specific TapeAlert
                error, for example 0 is first SCSI channel of HBA."
        ::= { errorHistoryEntry 4 }

errorDate OBJECT-TYPE
        SYNTAX OCTET STRING (SIZE (14))
        ACCESS read-only
        STATUS mandatory
        DESCRIPTION
            "Date and time of the error in yyyymmddHHMMSS format:
             where
              yyyy    year    1980-9999
              mm      month   01-12
              dd      day     01-31
              HH      hour    00-23
              MM      minute  00-59
              SS      second  00-60 (use 60 for leap-second)
             Example  14:35:26 5th Oct 1996 = 19961005143526"
        ::= { errorHistoryEntry 5 }

errorTrapNum OBJECT-TYPE
        SYNTAX INTEGER (1..64)
        ACCESS read-only
        STATUS mandatory
        DESCRIPTION
                "TapeAlert trap number of the error.
                 For tape drive/autoloader traps, range 1-64.
                 For library device traps, range 256-319
                 (Library device traps = TapeAlert flag + 255)"
        ::= { errorHistoryEntry 6 }

errorMedia OBJECT-TYPE
        SYNTAX DisplayString (SIZE (0..255))
        ACCESS read-only
        STATUS mandatory
        DESCRIPTION
                "Software label of the media that was loaded in the
                tape drive at the time of the error."
        ::= { errorHistoryEntry 7 }

-- **************************************************************************
-- Trap Definitions
-- **************************************************************************

tapeAlertTrap1                  TRAP-TYPE
                                ENTERPRISE      tapeAlert
                                VARIABLES       {
                                                hbaNumber,
                                                hbaChannel,
                                                driveScsiID
                                                }
                                DESCRIPTION
                                        "The tape drive is having problems reading data. No
                                        data has been lost, but there has been a reduction
                                        in the performance of the tape."
                                --#TYPE "HP TapeAlert #1"
                                --#SUMMARY "Hba%d:Channel%d:ScsiID%d Tape Device Has Problems Reading Data"
                                --#ARGUMENTS {0,1,2}
                                --#SEVERITY MINOR
                                --#TIMEINDEX 9
                                --#STATE   OPERATIONAL
                                ::= 1

tapeAlertTrap2                  TRAP-TYPE
                                ENTERPRISE      tapeAlert
                                VARIABLES       {
                                                hbaNumber,
                                                hbaChannel,
                                                driveScsiID
                                                }
                                DESCRIPTION
                                        "The tape drive is having problems writing data. No
                                        data has been lost, but there has been a reduction
                                        in the capacity of the tape."
                                --#TYPE "HP TapeAlert #2"
                                --#SUMMARY "Hba%d:Channel%d:ScsiID%d Tape Device Has Problems Writing Data"
                                --#ARGUMENTS {0,1,2}
                                --#SEVERITY MINOR
                                --#TIMEINDEX 9
                                --#STATE   OPERATIONAL
                                ::= 2

tapeAlertTrap3                  TRAP-TYPE
                                ENTERPRISE      tapeAlert
                                VARIABLES       {
                                                hbaNumber,
                                                hbaChannel,
                                                driveScsiID
                                                }
                                DESCRIPTION
                                        "The operation has stopped because an error has
                                        occured while reading or writing data which the
                                        drive cannot correct."
                                --#TYPE "HP TapeAlert #3"
                                --#SUMMARY "Hba%d:Channel%d:ScsiID%d Tape Device Has Detected Read or Write Data Error"
                                --#ARGUMENTS {0,1,2}
                                --#SEVERITY MINOR
                                --#TIMEINDEX 9
                                --#STATE   DEGRADED
                                ::= 3

tapeAlertTrap4                  TRAP-TYPE
                                ENTERPRISE      tapeAlert
                                VARIABLES       {
                                                hbaNumber,
                                                hbaChannel,
                                                driveScsiID,
                                                currentMedia
                                                }
                                DESCRIPTION
                                        "Your data is at risk:
                                        1. Copy any data you require from this tape
                                        2. Do not use this tape again
                                        3. Restart the operation with a different tape"
                                --#TYPE "HP TapeAlert #4"
                                --#SUMMARY "Hba%d:Channel%d:ScsiID%d Tape Device Has Detected Faulty Media [%s]"
                                --#ARGUMENTS {0,1,2,3}
                                --#SEVERITY CRITICAL
                                --#TIMEINDEX 9
                                --#STATE   DEGRADED
                                ::= 4

tapeAlertTrap5                  TRAP-TYPE
                                ENTERPRISE      tapeAlert
                                VARIABLES       {
                                                hbaNumber,
                                                hbaChannel,
                                                driveScsiID
                                                }
                                DESCRIPTION
                                        "The tape is damaged or the drive is faulty.
                                        Call the tape drive supplier helpline."
                                --#TYPE "HP TapeAlert #5"
                                --#SUMMARY "Hba%d:Channel%d:ScsiID%d Tape Device May Have Read Fault - Call Helpline"
                                --#ARGUMENTS {0,1,2}
                                --#SEVERITY CRITICAL
                                --#TIMEINDEX 9
                                --#STATE   DEGRADED
                                ::= 5

tapeAlertTrap6                  TRAP-TYPE
                                ENTERPRISE      tapeAlert
                                VARIABLES       {
                                                hbaNumber,
                                                hbaChannel,
                                                driveScsiID
                                                }
                                DESCRIPTION
                                        "The tape is from a faulty batch or the tape drive
                                        is faulty:
                                        1. Use a good tape to test the drive.
                                        2. If the problem persists, call the tape drive
                                           supplier helpline."
                                --#TYPE "HP TapeAlert #6"
                                --#SUMMARY "Hba%d:Channel%d:ScsiID%d Tape Device May Have Write Fault - Call Helpline"
                                --#ARGUMENTS {0,1,2}
                                --#SEVERITY CRITICAL
                                --#TIMEINDEX 9
                                --#STATE   DEGRADED
                                ::= 6

tapeAlertTrap7                  TRAP-TYPE
                                ENTERPRISE      tapeAlert
                                VARIABLES       {
                                                hbaNumber,
                                                hbaChannel,
                                                driveScsiID,
                                                currentMedia
                                                }
                              DESCRIPTION
                                        "The tape cartridge has reached the end of its
                                        calculated useful life:
                                        1. Copy any data you need to another tape
                                        2. Discard the old tape."
                                --#TYPE "HP TapeAlert #7"
                                --#SUMMARY "Hba%d:Channel%d:ScsiID%d Tape Device Has Detected Worn Out Media [%s]"
                                --#ARGUMENTS {0,1,2,3}
                                --#SEVERITY MINOR
                                --#TIMEINDEX 9
                                --#STATE   OPERATIONAL
                                ::= 7

tapeAlertTrap8                  TRAP-TYPE
                                ENTERPRISE      tapeAlert
                                VARIABLES       {
                                                hbaNumber,
                                                hbaChannel,
                                                driveScsiID
                                                }
                                DESCRIPTION
                                        "The tape cartridge is not data-grade.
                                        Any data you back up to the tape is at risk.
                                        Replace the cartridge with a data-grade tape."
                                --#TYPE "HP TapeAlert #8"
                                --#SUMMARY "Hba%d:Channel%d:ScsiID%d Media Loaded In Tape Device Is Not Data Grade"
                                --#ARGUMENTS {0,1,2}
                                --#SEVERITY MINOR
                                --#TIMEINDEX 9
                                --#STATE   OPERATIONAL
                                ::= 8

tapeAlertTrap9                  TRAP-TYPE
                                ENTERPRISE      tapeAlert
                                VARIABLES       {
                                                hbaNumber,
                                                hbaChannel,
                                                driveScsiID
                                                }
                                DESCRIPTION
                                        "You are trying to write to a write-protected
                                        cartridge. Remove the write-protection or use
                                        another tape."
                                --#TYPE "HP TapeAlert #9"
                                --#SUMMARY "Hba%d:Channel%d:ScsiID%d Tape Device Attempted Backup to Write-Protected Tape"
                                --#ARGUMENTS {0,1,2}
                                --#SEVERITY CRITICAL
                                --#TIMEINDEX 9
                                --#STATE   DEGRADED
                                ::= 9

tapeAlertTrap10                         TRAP-TYPE
                                ENTERPRISE      tapeAlert
                                VARIABLES       {
                                                hbaNumber,
                                                hbaChannel,
                                                driveScsiID
                                                }
                                DESCRIPTION
                                        "You cannot eject the cartridge because the tape
                                        drive is in use. Wait until the operation is
                                        complete before ejecting the cartridge."
                                --#TYPE "HP TapeAlert #10"
                                --#SUMMARY "Hba%d:Channel%d:ScsiID%d Tape Device Eject Attempted When Media Locked"
                                --#ARGUMENTS {0,1,2}
                                --#SEVERITY INFORMATIONAL
                                --#TIMEINDEX 9
                                --#STATE   OPERATIONAL
                                ::= 10

tapeAlertTrap11                 TRAP-TYPE
                                ENTERPRISE      tapeAlert
                                VARIABLES       {
                                                hbaNumber,
                                                hbaChannel,
                                                driveScsiID
                                                }
                                DESCRIPTION
                                        "The tape in the drive is a cleaning cartridge.
                                        If you want to back up or restore, insert a
                                        data-grade tape."
                                --#TYPE "HP TapeAlert #11"
                                --#SUMMARY "Hba%d:Channel%d:ScsiID%d Tape Device Attempted Backup/Restore To Cleaning Tape"
                                --#ARGUMENTS {0,1,2}
                                --#SEVERITY INFORMATIONAL
                                --#TIMEINDEX 9
                                --#STATE   OPERATIONAL
                                ::= 11

tapeAlertTrap12                 TRAP-TYPE
                                ENTERPRISE      tapeAlert
                                VARIABLES       {
                                                hbaNumber,
                                                hbaChannel,
                                                driveScsiID
                                                }
                                DESCRIPTION
                                        "You have tried to load a cartridge of a type
                                        which is not supported by this drive."
                                --#TYPE "HP TapeAlert #12"
                                --#SUMMARY "Hba%d:Channel%d:ScsiID%d Media Loaded In Tape Device Is Unsupported Type"
                                --#ARGUMENTS {0,1,2}
                                --#SEVERITY INFORMATIONAL
                                --#TIMEINDEX 9
                                --#STATE   OPERATIONAL
                                ::= 12

tapeAlertTrap13                 TRAP-TYPE
                                ENTERPRISE      tapeAlert
                                VARIABLES       {
                                                hbaNumber,
                                                hbaChannel,
                                                driveScsiID
                                                }
                                DESCRIPTION
                                        "The operation has failed because the tape in the
                                        drive has snapped:
                                        1. Discard the old tape.
                                        2. Restart the operation with a different tape."
                                --#TYPE "HP TapeAlert #13"
                                --#SUMMARY "Hba%d:Channel%d:ScsiID%d Tape Device Has Detected Snapped Tape"
                                --#ARGUMENTS {0,1,2}
                                --#SEVERITY CRITICAL
                                --#TIMEINDEX 9
                                --#STATE   DEGRADED
                                ::= 13

tapeAlertTrap14                 TRAP-TYPE
                                ENTERPRISE      tapeAlert
                                VARIABLES       {
                                                hbaNumber,
                                                hbaChannel,
                                                driveScsiID
                                                }
                                DESCRIPTION
                                        "The operation has failed because the tape in the
                                        drive has snapped:
                                        1. Do not attempt to extract the tape cartridge.
                                        2. Call the tape drive supplier helpline."
                                --#TYPE "HP TapeAlert #14"
                                --#SUMMARY "Hba%d:Channel%d:ScsiID%d Tape Device Has Detected Snapped Tape"
                                --#ARGUMENTS {0,1,2}
                                --#SEVERITY CRITICAL
                                --#TIMEINDEX 9
                                --#STATE   DEGRADED
                                ::= 14

tapeAlertTrap15                 TRAP-TYPE
                                ENTERPRISE      tapeAlert
                                VARIABLES       {
                                                hbaNumber,
                                                hbaChannel,
                                                driveScsiID,
                                                currentMedia
                                                }
                                DESCRIPTION
                                        "The memory in the tape cartridge has failed, which reduces performance.
                                         Do not use the cartridge for further backup operations."
                                --#TYPE "HP TapeAlert #15"
                                --#SUMMARY "Hba%d:Channel%d:ScsiID%d Tape Device Has Memory Chip in Cartridge Failure [%s]"
                                --#ARGUMENTS {0,1,2,3}
                                --#SEVERITY MINOR
                                --#TIMEINDEX 9
                                --#STATE   DEGRADED
                                ::= 15

tapeAlertTrap16                 TRAP-TYPE
                                ENTERPRISE      tapeAlert
                                VARIABLES       {
                                                hbaNumber,
                                                hbaChannel,
                                                driveScsiID
                                                }
                                DESCRIPTION
                                        "The operation has failed because the tape cartridge was
                                         manually ejected while the tape drive was actively writing
                                         or reading."
                                --#TYPE "HP TapeAlert #16"
                                --#SUMMARY "Hba%d:Channel%d:ScsiID%d Tape Cartridge Ejected While Actively Writing/Reading"
                                --#ARGUMENTS {0,1,2}
                                --#SEVERITY CRITICAL
                                --#TIMEINDEX 9
                                --#STATE   DEGRADED
                                ::= 16

tapeAlertTrap17                 TRAP-TYPE
                                ENTERPRISE      tapeAlert
                                VARIABLES       {
                                                hbaNumber,
                                                hbaChannel,
                                                driveScsiID
                                                }
                                DESCRIPTION
                                        "You have loaded a cartridge of a type that is read-only in this drive.
                                         The cartridge will appear as write-protected"
                                --#TYPE "HP TapeAlert #17"
                                --#SUMMARY "Hba%d:Channel%d:ScsiID%d Tape Device Has Detected Read Only Media"
                                --#ARGUMENTS {0,1,2}
                                --#SEVERITY MINOR
                                --#TIMEINDEX 9
                                --#STATE   OPERATIONAL
                                ::= 17

tapeAlertTrap18                 TRAP-TYPE
                                ENTERPRISE      tapeAlert
                                VARIABLES       {
                                                hbaNumber,
                                                hbaChannel,
                                                driveScsiID
                                                }
                                DESCRIPTION
                                        "The directory on the tape cartridge has been corrupted.
                                         File search performance will be degraded."
                                --#TYPE "HP TapeAlert #18"
                                --#SUMMARY "Hba%d:Channel%d:ScsiID%d Tape Device Has Detected Corrupted Directory On Tape"
                                --#ARGUMENTS {0,1,2}
                                --#SEVERITY MINOR
                                --#TIMEINDEX 9
                                --#STATE   DEGRADED
                                ::= 18

tapeAlertTrap19                 TRAP-TYPE
                                ENTERPRISE      tapeAlert
                                VARIABLES       {
                                                hbaNumber,
                                                hbaChannel,
                                                driveScsiID,
                                                currentMedia
                                                }
                                DESCRIPTION
                                        "The tape cartridge is nearing the end of its useful life.
                                         It is recommended that you:
                                         1. Use another tape cartridge for your next backup.
                                         2. Store this tape cartridge in a safe place in case you
                                            need to restore data from it."
                                --#TYPE "HP TapeAlert #19"
                                --#SUMMARY "Hba%d:Channel%d:ScsiID%d Tape Device Has Detected Worn Out Media [%s]"
                                --#ARGUMENTS {0,1,2,3}
                                --#SEVERITY INFORMATIONAL
                                --#TIMEINDEX 9
                                --#STATE   OPERATIONAL
                                ::= 19


tapeAlertTrap20                 TRAP-TYPE
                                ENTERPRISE      tapeAlert
                                VARIABLES       {
                                                hbaNumber,
                                                hbaChannel,
                                                driveScsiID
                                                }
                                DESCRIPTION
                                        "The tape drive needs cleaning:
                                        1. If the operation has stopped, eject the tape
                                           and clean the drive
                                        2. If the operation has not stopped, wait for it
                                           to finish and then clean the drive.
                                        Check the tape drive users manual for device
                                        specific cleaning instructions."
                                --#TYPE "HP TapeAlert #20"
                                --#SUMMARY "Hba%d:Channel%d:ScsiID%d Tape Device Needs Cleaning"
                                --#ARGUMENTS {0,1,2}
                                --#SEVERITY CRITICAL
                                --#TIMEINDEX 9
                                --#STATE   DEGRADED
                                ::= 20

tapeAlertTrap21                 TRAP-TYPE
                                ENTERPRISE      tapeAlert
                                VARIABLES       {
                                                hbaNumber,
                                                hbaChannel,
                                                driveScsiID
                                                }
                                DESCRIPTION
                                        "The tape drive is due for routine cleaning:
                                        1. Wait for the current operation to finish.
                                        2. Then use a cleaning cartridge.
                                        Check the tape drive users manual for device
                                        specific cleaning instructions."
                                --#TYPE "HP TapeAlert #21"
                                --#SUMMARY "Hba%d:Channel%d:ScsiID%d Tape Device Requests Routine Cleaning"
                                --#ARGUMENTS {0,1,2}
                                --#SEVERITY MINOR
                                --#TIMEINDEX 9
                                --#STATE   OPERATIONAL
                                ::= 21

tapeAlertTrap22                 TRAP-TYPE
                                ENTERPRISE      tapeAlert
                                VARIABLES       {
                                                hbaNumber,
                                                hbaChannel,
                                                driveScsiID
                                                }
                                DESCRIPTION
                                        "The last cleaning cartridge used in the tape
                                        drive has worn out:
                                        1. Discard the worn out cleaning cartridge.
                                        2. Wait for the current operation to finish.
                                        3. Then use a new cleaning cartridge."
                                --#TYPE "HP TapeAlert #22"
                                --#SUMMARY "Hba%d:Channel%d:ScsiID%d Tape Device Has Detected Worn Out Cleaning Cartridge"
                                --#ARGUMENTS {0,1,2}
                                --#SEVERITY CRITICAL
                                --#TIMEINDEX 9
                                --#STATE   DEGRADED
                                ::= 22

tapeAlertTrap23                 TRAP-TYPE
                                ENTERPRISE      tapeAlert
                                VARIABLES       {
                                                hbaNumber,
                                                hbaChannel,
                                                driveScsiID
                                                }
                                DESCRIPTION
                                        "The last cleaning cartridge used in the tape drive was an invalid type:
                                         1. Do not use this cleaning cartridge in this drive.
                                         2. Wait for the current operation to finish.
                                         3. Then use a valid cleaning cartridge."
                                --#TYPE "HP TapeAlert #23"
                                --#SUMMARY "Hba%d:Channel%d:ScsiID%d Tape Device Has Detected Invalid Cleaning Cartridge"
                                --#ARGUMENTS {0,1,2}
                                --#SEVERITY CRITICAL
                                --#TIMEINDEX 9
                                --#STATE   DEGRADED
                                ::= 23

tapeAlertTrap29                 TRAP-TYPE
                                ENTERPRISE      tapeAlert
                                VARIABLES       {
                                                hbaNumber,
                                                hbaChannel,
                                                driveScsiID
                                                }
                                DESCRIPTION
                                        "Preventive maintenance of the tape drive is required.
                                         Check the tape drive users manual for device specific
                                         preventive maintenance tasks or call the tape drive
                                         supplier helpline."
                                --#TYPE "HP TapeAlert #29"
                                --#SUMMARY "Hba%d:Channel%d:ScsiID%d Tape Device Requires Preventative Maintenance"
                                --#ARGUMENTS {0,1,2}
                                --#SEVERITY MINOR
                                --#TIMEINDEX 9
                                --#STATE   DEGRADED
                                ::= 29

tapeAlertTrap30                 TRAP-TYPE
                                ENTERPRISE      tapeAlert
                                VARIABLES       {
                                                hbaNumber,
                                                hbaChannel,
                                                driveScsiID
                                                }
                                DESCRIPTION
                                        "The tape drive has a hardware fault:
                                        1. Eject the tape or magazine.
                                        2. Reset the drive.
                                        3. Restart the operation."
                                --#TYPE "HP TapeAlert #30"
                                --#SUMMARY "Hba%d:Channel%d:ScsiID%d Tape Device Has Hardware Fault - Reset Drive"
                                --#ARGUMENTS {0,1,2}
                                --#SEVERITY CRITICAL
                                --#TIMEINDEX 9
                                --#STATE   DEGRADED
                                ::= 30

tapeAlertTrap31                 TRAP-TYPE
                                ENTERPRISE      tapeAlert
                                VARIABLES       {
                                                hbaNumber,
                                                hbaChannel,
                                                driveScsiID
                                                }
                                DESCRIPTION
                                        "The tape drive has a hardware fault:
                                        1. Turn the tape drive off and then on again.
                                        2. Restart the operation.
                                        3. If the problem persists, call the tape
                                           drive supplier helpline.
                                        Check the tape drive users manual for device specific
                                        instructions on turning the device power on and off."
                                --#TYPE "HP TapeAlert #31"
                                --#SUMMARY "Hba%d:Channel%d:ScsiID%d Tape Device Has Hardware Fault - Call Helpline"
                                --#ARGUMENTS {0,1,2}
                                --#SEVERITY CRITICAL
                                --#TIMEINDEX 9
                                --#STATE   DEGRADED
                                ::= 31

tapeAlertTrap32                 TRAP-TYPE
                                ENTERPRISE      tapeAlert
                                VARIABLES       {
                                                hbaNumber,
                                                hbaChannel,
                                                driveScsiID
                                                }
                                DESCRIPTION
                                        "The tape drive has a problem with the host
                                        interface:
                                        1. Check the cables and cable connections.
                                        2. Restart the operation."
                                --#TYPE "HP TapeAlert #32"
                                --#SUMMARY "Hba%d:Channel%d:ScsiID%d Tape Device Has Host Interface Fault"
                                --#ARGUMENTS {0,1,2}
                                --#SEVERITY MINOR
                                --#TIMEINDEX 9
                                --#STATE   OPERATIONAL
                                ::= 32

tapeAlertTrap33                 TRAP-TYPE
                                ENTERPRISE      tapeAlert
                                VARIABLES       {
                                                hbaNumber,
                                                hbaChannel,
                                                driveScsiID
                                                }
                                DESCRIPTION
                                        "The operation has failed:
                                        1. Eject the tape or magazine.
                                        2. Insert the tape or magazine again.
                                        3. Restart the operation."
                                --#TYPE "HP TapeAlert #33"
                                --#SUMMARY "Hba%d:Channel%d:ScsiID%d Tape Device Has Eject Media Request"
                                --#ARGUMENTS {0,1,2}
                                --#SEVERITY CRITICAL
                                --#TIMEINDEX 9
                                --#STATE   DEGRADED
                                ::= 33

tapeAlertTrap34                 TRAP-TYPE
                                ENTERPRISE      tapeAlert
                                VARIABLES       {
                                                hbaNumber,
                                                hbaChannel,
                                                driveScsiID
                                                }
                                DESCRIPTION
                                        "The firmware download has failed because you
                                        have tried to use the incorrect firmware for
                                        this tape drive.
                                        Obtain the correct firmware and try again."
                                --#TYPE "HP TapeAlert #34"
                                --#SUMMARY "Hba%d:Channel%d:ScsiID%d Tape Device Has Firmware Download Fault"
                                --#ARGUMENTS {0,1,2}
                                --#SEVERITY MINOR
                                --#TIMEINDEX 9
                                --#STATE   OPERATIONAL
                                ::= 34

tapeAlertTrap35                 TRAP-TYPE
                                ENTERPRISE      tapeAlert
                                VARIABLES       {
                                                hbaNumber,
                                                hbaChannel,
                                                driveScsiID
                                                }
                                DESCRIPTION
                                        "Environmental conditions inside the tape drive are
                                         exceeding the humidity specifications"
                                --#TYPE "HP TapeAlert #35"
                                --#SUMMARY "Hba%d:Channel%d:ScsiID%d Tape Device Humidity Specification Exceeded"
                                --#ARGUMENTS {0,1,2}
                                --#SEVERITY MINOR
                                --#TIMEINDEX 9
                                --#STATE   DEGRADED
                                ::= 35

tapeAlertTrap36                 TRAP-TYPE
                                ENTERPRISE      tapeAlert
                                VARIABLES       {
                                                hbaNumber,
                                                hbaChannel,
                                                driveScsiID
                                                }
                                DESCRIPTION
                                        "Environmental conditions inside the tape drive are
                                         exceeding the temperature specifications"
                                --#TYPE "HP TapeAlert #36"
                                --#SUMMARY "Hba%d:Channel%d:ScsiID%d Tape Device Temperature Specification Exceeded"
                                --#ARGUMENTS {0,1,2}
                                --#SEVERITY MINOR
                                --#TIMEINDEX 9
                                --#STATE   DEGRADED
                                ::= 36

tapeAlertTrap37                 TRAP-TYPE
                                ENTERPRISE      tapeAlert
                                VARIABLES       {
                                                hbaNumber,
                                                hbaChannel,
                                                driveScsiID
                                                }
                                DESCRIPTION
                                        "The voltage supply to the tape drive exceeds specifications"
                                --#TYPE "HP TapeAlert #37"
                                --#SUMMARY "Hba%d:Channel%d:ScsiID%d Tape Device Voltage Specification Exceeded"
                                --#ARGUMENTS {0,1,2}
                                --#SEVERITY MINOR
                                --#TIMEINDEX 9
                                --#STATE   DEGRADED
                                ::= 37

tapeAlertTrap38                 TRAP-TYPE
                                ENTERPRISE      tapeAlert
                                VARIABLES       {
                                                hbaNumber,
                                                hbaChannel,
                                                driveScsiID
                                                }
                                DESCRIPTION
                                        "A hardware failure of the tape drive is predicted.
                                        Call the tape drive supplier helpline."
                                --#TYPE "HP TapeAlert #38"
                                --#SUMMARY "Hba%d:Channel%d:ScsiID%d Tape Device Predicted to Fail - Call Helpline"
                                --#ARGUMENTS {0,1,2}
                                --#SEVERITY CRITICAL
                                --#TIMEINDEX 9
                                --#STATE   DEGRADED
                                ::= 38

tapeAlertTrap39                 TRAP-TYPE
                                ENTERPRISE      tapeAlert
                                VARIABLES       {
                                                hbaNumber,
                                                hbaChannel,
                                                driveScsiID
                                                }
                                DESCRIPTION
                                        "The tape drive may have a hardware fault.
                                        Run extended diagnostics to verify and diagnose the problem.
                                        Check the tape drive users manual for device specific
                                        instructions on running extended diagnostic tests."
                                --#TYPE "HP TapeAlert #39"
                                --#SUMMARY "Hba%d:Channel%d:ScsiID%d Tape Device May Have Hardware Fault - Run Diagnostics"
                                --#ARGUMENTS {0,1,2}
                                --#SEVERITY MINOR
                                --#TIMEINDEX 9
                                --#STATE   DEGRADED
                                ::= 39

tapeAlertTrap40                 TRAP-TYPE
                                ENTERPRISE      tapeAlert
                                VARIABLES       {
                                                hbaNumber,
                                                hbaChannel,
                                                driveScsiID
                                                }
                                DESCRIPTION
                                        "The changer mechanism is having difficulty
                                        communicating with the tape drive:
                                        1. Turn the autoloader off then on.
                                        2. Restart the operation.
                                        3. If problem persists, call the tape drive
                                           supplier helpline."
                                --#TYPE "HP TapeAlert #40"
                                --#SUMMARY "Hba%d:Channel%d:ScsiID%d Tape Device Has Autoloader Communications Fault"
                                --#ARGUMENTS {0,1,2}
                                --#SEVERITY CRITICAL
                                --#TIMEINDEX 9
                                --#STATE   DEGRADED
                                ::= 40

tapeAlertTrap41                 TRAP-TYPE
                                ENTERPRISE      tapeAlert
                                VARIABLES       {
                                                hbaNumber,
                                                hbaChannel,
                                                driveScsiID
                                                }
                                DESCRIPTION
                                        "A tape has been left in the autoloader by a
                                        previous hardware fault:
                                        1. Insert an empty magazine to clear the fault.
                                        2. If the fault does not clear, turn the autoloader
                                           off and then on again.
                                        3. If the problem persists, call the tape drive
                                           supplier helpline."
                                --#TYPE "HP TapeAlert #41"
                                --#SUMMARY "Hba%d:Channel%d:ScsiID%d Tape Device Detects Stray Tape In Autoloader"
                                --#ARGUMENTS {0,1,2}
                                --#SEVERITY CRITICAL
                                --#TIMEINDEX 9
                                --#STATE   DEGRADED
                                ::= 41

tapeAlertTrap42                 TRAP-TYPE
                                ENTERPRISE      tapeAlert
                                VARIABLES       {
                                                hbaNumber,
                                                hbaChannel,
                                                driveScsiID
                                                }
                                DESCRIPTION
                                        "There is a problem with the autoloader mechanism."
                                --#TYPE "HP TapeAlert #42"
                                --#SUMMARY "Hba%d:Channel%d:ScsiID%d Tape Device Has Autoloader Mechanism Fault"
                                --#ARGUMENTS {0,1,2}
                                --#SEVERITY MINOR
                                --#TIMEINDEX 9
                                --#STATE   OPERATIONAL
                                ::= 42

tapeAlertTrap43                 TRAP-TYPE
                                ENTERPRISE      tapeAlert
                                VARIABLES       {
                                                hbaNumber,
                                                hbaChannel,
                                                driveScsiID
                                                }
                                DESCRIPTION
                                        "The operation has failed because the autoloader
                                        door is open:
                                        1. Clear any obstructions from the autoloader door.
                                        2. Eject the magazine and then insert it again.
                                        3. If the fault does not clear, turn the autoloader
                                           off and then on again.
                                        4. If the problem persists, call the tape drive
                                           supplier helpline."
                                --#TYPE "HP TapeAlert #43"
                                --#SUMMARY "Hba%d:Channel%d:ScsiID%d Tape Device Has Autoloader Door Open"
                                --#ARGUMENTS {0,1,2}
                                --#SEVERITY CRITICAL
                                --#TIMEINDEX 9
                                --#STATE   DEGRADED
                                ::= 43

tapeAlertTrap44                 TRAP-TYPE
                                ENTERPRISE      tapeAlert
                                VARIABLES       {
                                                hbaNumber,
                                                hbaChannel,
                                                driveScsiID
                                                }
                                DESCRIPTION
                                        "The autoloader has a hardware fault:
                                        1. Turn the autoloader off and then on again.
                                        2. Restart the operation.
                                        3. If the problem persists, call the tape drive supplier helpline.
                                        Check the autoloader users manual for device specific
                                        instructions on turning the device power on and off."
                                --#TYPE "HP TapeAlert #44"
                                --#SUMMARY "Hba%d:Channel%d:ScsiID%d Autoloader Has Hardware Fault - Call Helpline"
                                --#ARGUMENTS {0,1,2}
                                --#SEVERITY CRITICAL
                                --#TIMEINDEX 9
                                --#STATE   DEGRADED
                                ::= 44

tapeAlertTrap45                 TRAP-TYPE
                                ENTERPRISE      tapeAlert
                                VARIABLES       {
                                                hbaNumber,
                                                hbaChannel,
                                                driveScsiID
                                                }
                                DESCRIPTION
                                        "The autoloader cannot operate without the magazine.
                                        1. Insert the magazine into the autoloader
                                        2. Restart the operation."
                                --#TYPE "HP TapeAlert #45"
                                --#SUMMARY "Hba%d:Channel%d:ScsiID%d Autoloader Cannot Operate Without Magazine"
                                --#ARGUMENTS {0,1,2}
                                --#SEVERITY CRITICAL
                                --#TIMEINDEX 9
                                --#STATE   DEGRADED
                                ::= 45

tapeAlertTrap46                 TRAP-TYPE
                                ENTERPRISE      tapeAlert
                                VARIABLES       {
                                                hbaNumber,
                                                hbaChannel,
                                                driveScsiID
                                                }
                                DESCRIPTION
                                        "A hardware failure of the changer mechanism is predicted.
                                        Call the tape drive supplier helpline."
                                --#TYPE "HP TapeAlert #46"
                                --#SUMMARY "Hba%d:Channel%d:ScsiID%d Autoloader Predicted to Fail - Call Helpline"
                                --#ARGUMENTS {0,1,2}
                                --#SEVERITY MINOR
                                --#TIMEINDEX 9
                                --#STATE   DEGRADED
                                ::= 46

tapeAlertTrap256                TRAP-TYPE
                                ENTERPRISE      tapeAlert
                                VARIABLES       {
                                                hbaNumber,
                                                hbaChannel,
                                                driveScsiID
                                                }
                                DESCRIPTION
                                        "The library  mechanism is having difficulty communicating with the drive:
                                        1. Turn the library off then on.
                                        2. Restart the operation.
                                        3. If problem persists, call the library supplier helpline."
                                --#TYPE "HP TapeAlert #256"
                                --#SUMMARY "Hba%d:Channel%d:ScsiID%d Library Has Drive Communications Fault"
                                --#ARGUMENTS {0,1,2}
                                --#SEVERITY CRITICAL
                                --#TIMEINDEX 9
                                --#STATE   DEGRADED
                                ::= 256

tapeAlertTrap257                TRAP-TYPE
                                ENTERPRISE      tapeAlert
                                VARIABLES       {
                                                hbaNumber,
                                                hbaChannel,
                                                driveScsiID
                                                }
                                DESCRIPTION
                                        "There is a problem with the library mechanism.
                                        If problem persists, call the library supplier helpline."
                                --#TYPE "HP TapeAlert #257"
                                --#SUMMARY "Hba%d:Channel%d:ScsiID%d Library Has Changer Mechanism Fault"
                                --#ARGUMENTS {0,1,2}
                                --#SEVERITY MINOR
                                --#TIMEINDEX 9
                                --#STATE   DEGRADED
                                ::= 257

tapeAlertTrap258                TRAP-TYPE
                                ENTERPRISE      tapeAlert
                                VARIABLES       {
                                                hbaNumber,
                                                hbaChannel,
                                                driveScsiID
                                                }
                                DESCRIPTION
                                        "The library has a hardware fault:
                                        1. Reset the library
                                        2. Restart the operation.
                                        Check the library users manual for device specific
                                        instructions on resetting the device."
                                --#TYPE "HP TapeAlert #258"
                                --#SUMMARY "Hba%d:Channel%d:ScsiID%d Library Has Hardware Fault - Reset Library"
                                --#ARGUMENTS {0,1,2}
                                --#SEVERITY CRITICAL
                                --#TIMEINDEX 9
                                --#STATE   DEGRADED
                                ::= 258

tapeAlertTrap259                TRAP-TYPE
                                ENTERPRISE      tapeAlert
                                VARIABLES       {
                                                hbaNumber,
                                                hbaChannel,
                                                driveScsiID
                                                }
                                DESCRIPTION
                                        "The library has a hardware fault:
                                        1. Turn the library off and then on again.
                                        2. Restart the operation.
                                        3. If the problem persists, call the library supplier helpline.
                                        Check the library users manual for device specific
                                        instructions on turning the device power on and off."
                                --#TYPE "HP TapeAlert #259"
                                --#SUMMARY "Hba%d:Channel%d:ScsiID%d Library Has Hardware Fault - Call Helpline"
                                --#ARGUMENTS {0,1,2}
                                --#SEVERITY CRITICAL
                                --#TIMEINDEX 9
                                --#STATE   DEGRADED
                                ::= 259

tapeAlertTrap260                TRAP-TYPE
                                ENTERPRISE      tapeAlert
                                VARIABLES       {
                                                hbaNumber,
                                                hbaChannel,
                                                driveScsiID
                                                }
                                DESCRIPTION
                                        "The library mechanism may have a hardware fault.
                                        Run extended diagnostics to verify and diagnose the problem.
                                        Check the library users manual for device specific
                                        instructions on running extended diagnostic tests."
                                --#TYPE "HP TapeAlert #260"
                                --#SUMMARY "Hba%d:Channel%d:ScsiID%d Library May Have Hardware Fault - Run Diagnostics"
                                --#ARGUMENTS {0,1,2}
                                --#SEVERITY MINOR
                                --#TIMEINDEX 9
                                --#STATE   DEGRADED
                                ::= 260

tapeAlertTrap261                TRAP-TYPE
                                ENTERPRISE      tapeAlert
                                VARIABLES       {
                                                hbaNumber,
                                                hbaChannel,
                                                driveScsiID
                                                }
                                DESCRIPTION
                                        "The library has a problem with the host interface:
                                        1. Check the cables and cable connections.
                                        2. Restart the operation."
                                --#TYPE "HP TapeAlert #261"
                                --#SUMMARY "Hba%d:Channel%d:ScsiID%d Library Has Host Interface Fault"
                                --#ARGUMENTS {0,1,2}
                                --#SEVERITY CRITICAL
                                --#TIMEINDEX 9
                                --#STATE   DEGRADED
                                ::= 261

tapeAlertTrap262                TRAP-TYPE
                                ENTERPRISE      tapeAlert
                                VARIABLES       {
                                                hbaNumber,
                                                hbaChannel,
                                                driveScsiID
                                                }
                                DESCRIPTION
                                        "A hardware failure of the library is predicted.
                                        Call the library supplier helpline."
                                --#TYPE "HP TapeAlert #262"
                                --#SUMMARY "Hba%d:Channel%d:ScsiID%d Library Predicted to Fail - Call Helpline"
                                --#ARGUMENTS {0,1,2}
                                --#SEVERITY MINOR
                                --#TIMEINDEX 9
                                --#STATE   DEGRADED
                                ::= 262

tapeAlertTrap263                TRAP-TYPE
                                ENTERPRISE      tapeAlert
                                VARIABLES       {
                                                hbaNumber,
                                                hbaChannel,
                                                driveScsiID
                                                }
                                DESCRIPTION
                                        "Preventative maintenance of the library is required.
                                        Check the library users manual for device specific
                                        preventative maintenance tasks, or call your library
                                        supplier helpline."
                                --#TYPE "HP TapeAlert #263"
                                --#SUMMARY "Hba%d:Channel%d:ScsiID%d Library Requires Preventative Maintenance"
                                --#ARGUMENTS {0,1,2}
                                --#SEVERITY MINOR
                                --#TIMEINDEX 9
                                --#STATE   DEGRADED
                                ::= 263

tapeAlertTrap264                TRAP-TYPE
                                ENTERPRISE      tapeAlert
                                VARIABLES       {
                                                hbaNumber,
                                                hbaChannel,
                                                driveScsiID
                                                }
                                DESCRIPTION
                                        "General environmental conditions inside the library have
                                        exceeded the humidity specifications."
                                --#TYPE "HP TapeAlert #264"
                                --#SUMMARY "Hba%d:Channel%d:ScsiID%d Library Humidity Specification Exceeded"
                                --#ARGUMENTS {0,1,2}
                                --#SEVERITY CRITICAL
                                --#TIMEINDEX 9
                                --#STATE   DEGRADED
                                ::= 264

tapeAlertTrap265                TRAP-TYPE
                                ENTERPRISE      tapeAlert
                                VARIABLES       {
                                                hbaNumber,
                                                hbaChannel,
                                                driveScsiID
                                                }
                                DESCRIPTION
                                        "General environmental conditions inside the library have
                                        exceeded the temperature specifications.e"
                                --#TYPE "HP TapeAlert #265"
                                --#SUMMARY "Hba%d:Channel%d:ScsiID%d Library Temperature Specification Exceeded"
                                --#ARGUMENTS {0,1,2}
                                --#SEVERITY CRITICAL
                                --#TIMEINDEX 9
                                --#STATE   DEGRADED
                                ::= 265

tapeAlertTrap266                TRAP-TYPE
                                ENTERPRISE      tapeAlert
                                VARIABLES       {
                                                hbaNumber,
                                                hbaChannel,
                                                driveScsiID
                                                }
                                DESCRIPTION
                                        "he voltage supply to the library exceeds specifications.
                                        There is a potential problem with the power supply or failure
                                        of a redundant power supply"
                                --#TYPE "HP TapeAlert #266"
                                --#SUMMARY "Hba%d:Channel%d:ScsiID%d Library Voltage Specification Exceeded"
                                --#ARGUMENTS {0,1,2}
                                --#SEVERITY CRITICAL
                                --#TIMEINDEX 9
                                --#STATE   DEGRADED
                                ::= 266

tapeAlertTrap267                TRAP-TYPE
                                ENTERPRISE      tapeAlert
                                VARIABLES       {
                                                hbaNumber,
                                                hbaChannel,
                                                driveScsiID
                                                }
                                DESCRIPTION
                                        "A cartridge has been left in a drive inside the library by a
                                        previous hardware fault:
                                        1. Insert an empty magazine to clear the fault.
                                        2. If the fault does not clear, turn the library off and then on again.
                                        3. If the problem persists, call the library supplier helpline."
                                --#TYPE "HP TapeAlert #267"
                                --#SUMMARY "Hba%d:Channel%d:ScsiID%d Library Detects Stray Tape In Drive"
                                --#ARGUMENTS {0,1,2}
                                --#SEVERITY CRITICAL
                                --#TIMEINDEX 9
                                --#STATE   DEGRADED
                                ::= 267

tapeAlertTrap268                TRAP-TYPE
                                ENTERPRISE      tapeAlert
                                VARIABLES       {
                                                hbaNumber,
                                                hbaChannel,
                                                driveScsiID
                                                }
                                DESCRIPTION
                                        "There is a potential problem with a drive ejecting cartridges short or
                                        with the library mechanism picking a cartridge from a slot.
                                        1. No action needs to be taken at this time.
                                        2. If the problem persists, call the library supplier helpline."
                                --#TYPE "HP TapeAlert #268"
                                --#SUMMARY "Hba%d:Channel%d:ScsiID%d Library Has Problems Picking Cartridge from Slot"
                                --#ARGUMENTS {0,1,2}
                                --#SEVERITY MINOR
                                --#TIMEINDEX 9
                                --#STATE   DEGRADED
                                ::= 268

tapeAlertTrap269                TRAP-TYPE
                                ENTERPRISE      tapeAlert
                                VARIABLES       {
                                                hbaNumber,
                                                hbaChannel,
                                                driveScsiID
                                                }
                                DESCRIPTION
                                        "There is a potential problem with the library mechanism
                                        placing a cartridge into a slot
                                        1. No action needs to be taken at this time.
                                        2. If the problem persists, call the library supplier helpline."
                                --#TYPE "HP TapeAlert #269"
                                --#SUMMARY "Hba%d:Channel%d:ScsiID%d Library Has Problems Placing Cartridge into Slot"
                                --#ARGUMENTS {0,1,2}
                                --#SEVERITY MINOR
                                --#TIMEINDEX 9
                                --#STATE   DEGRADED
                                ::= 269

tapeAlertTrap270                TRAP-TYPE
                                ENTERPRISE      tapeAlert
                                VARIABLES       {
                                                hbaNumber,
                                                hbaChannel,
                                                driveScsiID
                                                }
                                DESCRIPTION
                                        "There is a potential problem with a drive or the library
                                        mechanism loading cartridges, or an incompatible cartridge."
                                --#TYPE "HP TapeAlert #270"
                                --#SUMMARY "Hba%d:Channel%d:ScsiID%d Library Has Problems Loading Cartridge into Drive"
                                --#ARGUMENTS {0,1,2}
                                --#SEVERITY MINOR
                                --#TIMEINDEX 9
                                --#STATE   DEGRADED
                                ::= 270

tapeAlertTrap271                TRAP-TYPE
                                ENTERPRISE      tapeAlert
                                VARIABLES       {
                                                hbaNumber,
                                                hbaChannel,
                                                driveScsiID
                                                }
                                DESCRIPTION
                                        "The operation has failed because the library door is open:
                                        1. Clear any obstructions from the library door.
                                        2. Close the library door.
                                        3. If the problem persists, call the library supplier helpline."
                                --#TYPE "HP TapeAlert #271"
                                --#SUMMARY "Hba%d:Channel%d:ScsiID%d Library Door is Open"
                                --#ARGUMENTS {0,1,2}
                                --#SEVERITY CRITICAL
                                --#TIMEINDEX 9
                                --#STATE   DEGRADED
                                ::= 271

tapeAlertTrap272                TRAP-TYPE
                                ENTERPRISE      tapeAlert
                                VARIABLES       {
                                                hbaNumber,
                                                hbaChannel,
                                                driveScsiID
                                                }
                                DESCRIPTION
                                        "There is a mechanical problem with the
                                        library media import/export mailslot."
                                --#TYPE "HP TapeAlert #272"
                                --#SUMMARY "Hba%d:Channel%d:ScsiID%d Library Has Mechanical Fault with Mailslot"
                                --#ARGUMENTS {0,1,2}
                                --#SEVERITY CRITICAL
                                --#TIMEINDEX 9
                                --#STATE   DEGRADED
                                ::= 272

tapeAlertTrap273                TRAP-TYPE
                                ENTERPRISE      tapeAlert
                                VARIABLES       {
                                                hbaNumber,
                                                hbaChannel,
                                                driveScsiID
                                                }
                                DESCRIPTION
                                        "The library cannot operate without the magazine.
                                        1. Insert the magazine into the library
                                        2. Restart the operation."
                                --#TYPE "HP TapeAlert #273"
                                --#SUMMARY "Hba%d:Channel%d:ScsiID%d Library Cannot Operate Without Magazine"
                                --#ARGUMENTS {0,1,2}
                                --#SEVERITY CRITICAL
                                --#TIMEINDEX 9
                                --#STATE   DEGRADED
                                ::= 273

tapeAlertTrap274                TRAP-TYPE
                                ENTERPRISE      tapeAlert
                                VARIABLES       {
                                                hbaNumber,
                                                hbaChannel,
                                                driveScsiID
                                                }
                                DESCRIPTION
                                        "Library security has been compromised"
                                --#TYPE "HP TapeAlert #274"
                                --#SUMMARY "Hba%d:Channel%d:ScsiID%d Library Security Has Been Compromised"
                                --#ARGUMENTS {0,1,2}
                                --#SEVERITY MINOR
                                --#TIMEINDEX 9
                                --#STATE   DEGRADED
                                ::= 274

tapeAlertTrap275                TRAP-TYPE
                                ENTERPRISE      tapeAlert
                                VARIABLES       {
                                                hbaNumber,
                                                hbaChannel,
                                                driveScsiID
                                                }
                                DESCRIPTION
                                        "The security mode of the library has been changed.
                                        The library has either been put into secure mode,
                                        or the library has exited the secure mode.
                                        This is for information purposes only. No action is required."
                                --#TYPE "HP TapeAlert #275"
                                --#SUMMARY "Hba%d:Channel%d:ScsiID%d Library Security Mode Changed"
                                --#ARGUMENTS {0,1,2}
                                --#SEVERITY INFORMATIONAL
                                --#TIMEINDEX 9
                                --#STATE   DEGRADED
                                ::= 275

tapeAlertTrap276                TRAP-TYPE
                                ENTERPRISE      tapeAlert
                                VARIABLES       {
                                                hbaNumber,
                                                hbaChannel,
                                                driveScsiID
                                                }
                                DESCRIPTION
                                        "The library has been manually turned offline and is unavailable for use."
                                --#TYPE "HP TapeAlert #276"
                                --#SUMMARY "Hba%d:Channel%d:ScsiID%d Library Manually Turned Offline"
                                --#ARGUMENTS {0,1,2}
                                --#SEVERITY INFORMATIONAL
                                --#TIMEINDEX 9
                                --#STATE   DEGRADED
                                ::= 276

tapeAlertTrap277                TRAP-TYPE
                                ENTERPRISE      tapeAlert
                                VARIABLES       {
                                                hbaNumber,
                                                hbaChannel,
                                                driveScsiID
                                                }
                                DESCRIPTION
                                        "A drive inside the library has been taken offline.
                                        This is for information purposes only. No action is required."
                                --#TYPE "HP TapeAlert #277"
                                --#SUMMARY "Hba%d:Channel%d:ScsiID%d Library Drive Turned Offline"
                                --#ARGUMENTS {0,1,2}
                                --#SEVERITY INFORMATIONAL
                                --#TIMEINDEX 9
                                --#STATE   DEGRADED
                                ::= 277

tapeAlertTrap278                TRAP-TYPE
                                ENTERPRISE      tapeAlert
                                VARIABLES       {
                                                hbaNumber,
                                                hbaChannel,
                                                driveScsiID
                                                }
                                DESCRIPTION
                                        "There is a potential problem with the barcode label or
                                        the scanner hardware in the library mechanism.
                                        1. No action needs to be taken at this time.
                                        2. If the problem persists, call the library supplier helpline."
                                --#TYPE "HP TapeAlert #278"
                                --#SUMMARY "Hba%d:Channel%d:ScsiID%d Library Has Problems Reading Barcode Labels"
                                --#ARGUMENTS {0,1,2}
                                --#SEVERITY MINOR
                                --#TIMEINDEX 9
                                --#STATE   DEGRADED
                                ::= 278

tapeAlertTrap279                TRAP-TYPE
                                ENTERPRISE      tapeAlert
                                VARIABLES       {
                                                hbaNumber,
                                                hbaChannel,
                                                driveScsiID
                                                }
                                DESCRIPTION
                                        "The library has detected a inconsistency in its inventory.
                                        1. Redo the library inventory to correct inconsistency.
                                        2. Restart the operation
                                        Check the applications users manual or the hardware users
                                        manual for specific instructions on redoing the library inventory."
                                --#TYPE "HP TapeAlert #279"
                                --#SUMMARY "Hba%d:Channel%d:ScsiID%d Library Inventory is Inconsistent"
                                --#ARGUMENTS {0,1,2}
                                --#SEVERITY CRITICAL
                                --#TIMEINDEX 9
                                --#STATE   DEGRADED
                                ::= 279

tapeAlertTrap280                TRAP-TYPE
                                ENTERPRISE      tapeAlert
                                VARIABLES       {
                                                hbaNumber,
                                                hbaChannel,
                                                driveScsiID
                                                }
                                DESCRIPTION
                                        "A library operation has been attempted that is invalid at this time."
                                --#TYPE "HP TapeAlert #280"
                                --#SUMMARY "Hba%d:Channel%d:ScsiID%d Invalid Library Operation Attempted"
                                --#ARGUMENTS {0,1,2}
                                --#SEVERITY MINOR
                                --#TIMEINDEX 9
                                --#STATE   DEGRADED
                                ::= 280


END
