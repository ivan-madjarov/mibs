-------------------------------------------------------------------------------
-- Fjdary-E150 MIB definition                                                --
-- for SNMPv1                                                                --
-- All Rights Reserved, Copyright FUJITSU LIMITED 2013-2014.                 --
--                                                                           --
-- Modification History :                                                    --
--  v1.0 Initial version.                                                    --
--  v1.0a DESCRIPTION of fjdaryPfDtCmNasInfo was changed.                    --
--  v2.0 Add fjdarye150StorageClusterEvent,                                  --
--       fjdarye150StorageClusterInformation.                                --
--       Add raid6-fr to fjdaryMgtRaidGrpRaidLevel.                          --
--  v3.0 Add fjdarye150QuotaLimitExceeded,fjdarye150QuotaWarningExceeded,    --
--       fjdarye150QuotaNormal,fjdarye150SnapshotInformation.                --
--       Add fjdaryPfCmNasCoreIOWait,fjdaryPfDtCmNasCoreIOWait,              --
--       fjdaryPfCaPortNas,fjdaryPfDtCaPortNas,                              --
--       fjdaryPfCmNasVol,fjdaryPfDtCmNasVol.                                --
-------------------------------------------------------------------------------
FJDARY-E150 DEFINITIONS ::= BEGIN

IMPORTS
    enterprises,IpAddress
        FROM RFC1155-SMI
    DisplayString
        FROM RFC1213-MIB
    PhysAddress
        FROM RFC1213-MIB
    OBJECT-TYPE
        FROM RFC-1212
    TRAP-TYPE
        FROM RFC-1215;

-- Textual Conventions
FjdaryComponentStatus ::= INTEGER{
    normal(1),      -- Normal state
    alarm(2),       -- Abnormal state
    warning(3),     -- Warning state
    invalid(4),     -- Not installed state
    maintenance(5), -- Maintenance state
    undefined(6)    -- Undefined state
}

-- FUJITSU Specific Object Identifier

fujitsu                      OBJECT IDENTIFIER ::= { enterprises 211 }
product                      OBJECT IDENTIFIER ::= { fujitsu 1 }
storage                      OBJECT IDENTIFIER ::= { product 21 }

-- User Specific Object Identifier(1)

nsp                          OBJECT IDENTIFIER ::= { storage 1 }
fjdarye150                   OBJECT IDENTIFIER ::= { nsp 150 }

--
fjdarySsp                    OBJECT IDENTIFIER ::= { fjdarye150 1 }

--
fjdaryPconfig                OBJECT IDENTIFIER ::= { fjdarye150 2 }
fjdaryCm                     OBJECT IDENTIFIER ::= { fjdaryPconfig 1 }
fjdaryCmcpu                  OBJECT IDENTIFIER ::= { fjdaryPconfig 2 }
fjdaryCa                     OBJECT IDENTIFIER ::= { fjdaryPconfig 3 }
fjdaryCmmemory               OBJECT IDENTIFIER ::= { fjdaryPconfig 4 }
fjdaryBud                    OBJECT IDENTIFIER ::= { fjdaryPconfig 5 }
fjdaryCmfan                  OBJECT IDENTIFIER ::= { fjdaryPconfig 6 }
fjdaryBcu                    OBJECT IDENTIFIER ::= { fjdaryPconfig 7 }
fjdaryBtu                    OBJECT IDENTIFIER ::= { fjdaryPconfig 8 }
fjdaryScu                    OBJECT IDENTIFIER ::= { fjdaryPconfig 9 }
fjdaryCe                     OBJECT IDENTIFIER ::= { fjdaryPconfig 10 }
fjdaryCeinletthml            OBJECT IDENTIFIER ::= { fjdaryPconfig 11 }
fjdaryCethml                 OBJECT IDENTIFIER ::= { fjdaryPconfig 12 }
fjdaryCpsu                   OBJECT IDENTIFIER ::= { fjdaryPconfig 13 }
fjdaryDe                     OBJECT IDENTIFIER ::= { fjdaryPconfig 14 }
fjdaryIom                    OBJECT IDENTIFIER ::= { fjdaryPconfig 15 }
fjdaryPsu                    OBJECT IDENTIFIER ::= { fjdaryPconfig 16 }
fjdaryDeinletthml            OBJECT IDENTIFIER ::= { fjdaryPconfig 17 }
fjdaryDethml                 OBJECT IDENTIFIER ::= { fjdaryPconfig 18 }
fjdaryDisk                   OBJECT IDENTIFIER ::= { fjdaryPconfig 19 }
fjdaryLanport                OBJECT IDENTIFIER ::= { fjdaryPconfig 20 }
fjdaryFem                    OBJECT IDENTIFIER ::= { fjdaryPconfig 21 }
fjdaryPfm                    OBJECT IDENTIFIER ::= { fjdaryPconfig 22 }

--
fjdaryLconfig                OBJECT IDENTIFIER ::= { fjdarye150 3 }
fjdaryCaPort                 OBJECT IDENTIFIER ::= { fjdaryLconfig 1 }
fjdaryOlu                    OBJECT IDENTIFIER ::= { fjdaryLconfig 2 }
fjdarySlu                    OBJECT IDENTIFIER ::= { fjdaryLconfig 3 }
fjdaryRlu                    OBJECT IDENTIFIER ::= { fjdaryLconfig 4 }
fjdaryDlu                    OBJECT IDENTIFIER ::= { fjdaryLconfig 5 }
fjdaryMlu                    OBJECT IDENTIFIER ::= { fjdaryLconfig 6 }
fjdaryOpenmap                OBJECT IDENTIFIER ::= { fjdaryLconfig 7 }
fjdaryLunmap                 OBJECT IDENTIFIER ::= { fjdaryLconfig 8 }
fjdaryAffinityGrp            OBJECT IDENTIFIER ::= { fjdaryLconfig 9 }
fjdaryHostwwn                OBJECT IDENTIFIER ::= { fjdaryLconfig 10 }
fjdaryResetpath              OBJECT IDENTIFIER ::= { fjdaryLconfig 11 }
fjdaryHostiscsi              OBJECT IDENTIFIER ::= { fjdaryLconfig 12 }
fjdaryHostResponse           OBJECT IDENTIFIER ::= { fjdaryLconfig 13 }

--
fjdarySensor                 OBJECT IDENTIFIER ::= { fjdarye150 13 }
fjdaryMachinePower           OBJECT IDENTIFIER ::= { fjdarySensor 1 }
fjdaryEncPower               OBJECT IDENTIFIER ::= { fjdarySensor 2 }
fjdaryMachineTemp            OBJECT IDENTIFIER ::= { fjdarySensor 3 }
fjdaryEncTemp                OBJECT IDENTIFIER ::= { fjdarySensor 4 }

--
fjdaryFirm                   OBJECT IDENTIFIER ::= { fjdarye150 4 }

--
fjdaryPerformance            OBJECT IDENTIFIER ::= { fjdarye150 5 }
fjdaryPfInfo                 OBJECT IDENTIFIER ::= { fjdaryPerformance 1 }
fjdaryPfOlu                  OBJECT IDENTIFIER ::= { fjdaryPerformance 2 }
fjdaryPfDisk                 OBJECT IDENTIFIER ::= { fjdaryPerformance 3 }
fjdaryPfCm                   OBJECT IDENTIFIER ::= { fjdaryPerformance 4 }
fjdaryPfCaPort               OBJECT IDENTIFIER ::= { fjdaryPerformance 5 }
fjdaryPfDtOlu                OBJECT IDENTIFIER ::= { fjdaryPerformance 6 }
fjdaryPfDtDisk               OBJECT IDENTIFIER ::= { fjdaryPerformance 7 }
fjdaryPfDtCm                 OBJECT IDENTIFIER ::= { fjdaryPerformance 8 }
fjdaryPfDtCaPort             OBJECT IDENTIFIER ::= { fjdaryPerformance 9 }
fjdaryPfRaPort               OBJECT IDENTIFIER ::= { fjdaryPerformance 10 }
fjdaryPfDtRaPort             OBJECT IDENTIFIER ::= { fjdaryPerformance 11 }
fjdaryPfPfm                  OBJECT IDENTIFIER ::= { fjdaryPerformance 12 }
fjdaryPfDtPfm                OBJECT IDENTIFIER ::= { fjdaryPerformance 13 }
fjdaryPfCmCore               OBJECT IDENTIFIER ::= { fjdaryPerformance 14 }
fjdaryPfDtCmCore             OBJECT IDENTIFIER ::= { fjdaryPerformance 15 }
fjdaryPfCmNas                OBJECT IDENTIFIER ::= { fjdaryPerformance 16 }
fjdaryPfDtCmNas              OBJECT IDENTIFIER ::= { fjdaryPerformance 17 }
fjdaryPfCmNasCore            OBJECT IDENTIFIER ::= { fjdaryPerformance 18 }
fjdaryPfDtCmNasCore          OBJECT IDENTIFIER ::= { fjdaryPerformance 19 }
fjdaryPfCmNasCoreIOWait      OBJECT IDENTIFIER ::= { fjdaryPerformance 20 }
fjdaryPfDtCmNasCoreIOWait    OBJECT IDENTIFIER ::= { fjdaryPerformance 21 }
fjdaryPfCaPortNas            OBJECT IDENTIFIER ::= { fjdaryPerformance 22 }
fjdaryPfDtCaPortNas          OBJECT IDENTIFIER ::= { fjdaryPerformance 23 }
fjdaryPfCmNasVol             OBJECT IDENTIFIER ::= { fjdaryPerformance 24 }
fjdaryPfDtCmNasVol           OBJECT IDENTIFIER ::= { fjdaryPerformance 25 }

--
fjdaryManagement             OBJECT IDENTIFIER ::= { fjdarye150 14 }
fjdaryMgtMachineInfo         OBJECT IDENTIFIER ::= { fjdaryManagement 1 }
fjdaryMgtOpVolume            OBJECT IDENTIFIER ::= { fjdaryManagement 2 }
fjdaryMgtRaidGrp             OBJECT IDENTIFIER ::= { fjdaryManagement 3 }

--
application                  OBJECT IDENTIFIER ::= { fujitsu 4 }
aplNetwork                   OBJECT IDENTIFIER ::= { application 1 }
aplNetDevice                 OBJECT IDENTIFIER ::= { aplNetwork 1 }
aplNetStorage                OBJECT IDENTIFIER ::= { aplNetDevice 126 }
aplNetNsp                    OBJECT IDENTIFIER ::= { aplNetStorage 1 }
aplNetFjdarye150             OBJECT IDENTIFIER ::= { aplNetNsp 150 }

--***************************************************************************--
--   Unit Status                                                             --
--***************************************************************************--
fjdaryUnitStatus OBJECT-TYPE
    SYNTAX INTEGER {
        unknown(1),
        unused(2),
        ok(3),
        warning(4),
        failed(5)
    }
    ACCESS read-only
    STATUS mandatory
    DESCRIPTION
        "Overall status of this system. Status becomes warning or failed
         when there are broken parts in the system.
         But, it doesn't become warning or failed when maintaining it.
         (In the maintenance work, fjdaryMgtMaintenanceMode is on)"
    ::= { fjdarye150 6 }

--***************************************************************************--
--   Trap Specific Object                                                    --
--***************************************************************************--
fjdaryTrapItemId OBJECT-TYPE
    SYNTAX INTEGER(-2147483648..2147483647)
    ACCESS read-only
    STATUS mandatory
    DESCRIPTION
        "This object is used to store the identification number of parts for
         which maintenance is necessary when trap is transmitted."
    ::= { fjdarye150 7 }

fjdaryTrapSensorInfo OBJECT-TYPE
    SYNTAX INTEGER(-2147483648..2147483647)
    ACCESS read-only
    STATUS mandatory
    DESCRIPTION
        "This object is used to store detail information of sensor when trap is
         transmitted."
    ::= { fjdarye150 8 }

fjdaryTrapMaintenanceInfo OBJECT-TYPE
    SYNTAX INTEGER(-2147483648..2147483647)
    ACCESS read-only
    STATUS mandatory
    DESCRIPTION
        "This object is used to store detail information of maintenance when
         trap is transmitted."
    ::= { fjdarye150 9 }

fjdaryTrapWarningInfo OBJECT-TYPE
    SYNTAX INTEGER(-2147483648..2147483647)
    ACCESS read-only
    STATUS mandatory
    DESCRIPTION
        "This object is used to store detail information of warning when trap
         is transmitted."
    ::= { fjdarye150 10 }

fjdaryTrapMessage OBJECT-TYPE
    SYNTAX DisplayString
    ACCESS read-only
    STATUS mandatory
    DESCRIPTION
        "This object is used to store detail messages when all trap is
         transmitted."
    ::= { fjdarye150 11 }

fjdaryTrapLinkStatusInfo OBJECT-TYPE
    SYNTAX INTEGER {
        linkup(1),
        linkdown(2)
    }
    ACCESS read-only
    STATUS mandatory
    DESCRIPTION
        "This object is used to store detail information of CA port link
         status when trap is transmitted."
    ::= { fjdarye150 15 }

--***************************************************************************--
--   MIB definition Version                                                  --
--***************************************************************************--
fjdaryMIBversion OBJECT-TYPE
    SYNTAX DisplayString
    ACCESS read-only
    STATUS mandatory
    DESCRIPTION
        "This is the version for this MIB.
         This defines a revision of v3.0"
    ::= { fjdarye150 12 }

--***************************************************************************--
--   Subsystem Parameter                                                     --
--***************************************************************************--
fjdarySspMachineId OBJECT-TYPE
    SYNTAX OCTET STRING (SIZE (0..256))
    ACCESS read-only
    STATUS mandatory
    DESCRIPTION
        "This value indicates the identification number of this system.
         ttssssssssssssmmmmmmmmmmmmccssssssssssss
         | |           |           | |
         | |           |           | +-serial number(12byte)
         | |           |           +-check code(2byte)
         | |           +-model name(12byte)
         | +-series name(12byte)
         +-type code(2byte)"
    ::= { fjdarySsp 1 }

fjdarySspConfigDate OBJECT-TYPE
    SYNTAX DisplayString
    ACCESS read-only
    STATUS mandatory
    DESCRIPTION
        "The last date when the configuration was applied.
         yyyymmddHHMMSS
         |   | | | | |
         |   | | | | +-second
         |   | | | +-minute
         |   | | +-hour
         |   | +-day
         |   +-month
         +-year"
    ::= { fjdarySsp 2 }

fjdarySspWwnn OBJECT-TYPE
    SYNTAX OCTET STRING (SIZE (0..256))
    ACCESS read-only
    STATUS mandatory
    DESCRIPTION
        "The value of this object indecates the World Wide Node Name."
    ::= { fjdarySsp 3 }

fjdarySspVenderId OBJECT-TYPE
    SYNTAX OCTET STRING (SIZE (0..256))
    ACCESS read-only
    STATUS mandatory
    DESCRIPTION
        "The value of this object indecates the Vender ID."
    ::= { fjdarySsp 4 }

fjdarySspProductId OBJECT-TYPE
    SYNTAX OCTET STRING (SIZE (0..256))
    ACCESS read-only
    STATUS mandatory
    DESCRIPTION
        "The value of this object indecates the Product ID."
    ::= { fjdarySsp 5 }

fjdarySspBoxId OBJECT-TYPE
    SYNTAX OCTET STRING (SIZE (0..256))
    ACCESS read-only
    STATUS mandatory
    DESCRIPTION
        "This value of a meaning within a user system. An initial value is the
         same as fjdarySspMachineId."
    ::= { fjdarySsp 6 }

fjdarySspMaintenanceServiceLevel OBJECT-TYPE
    SYNTAX INTEGER {
        level1(1),
        level2(2)
    }
    ACCESS read-only
    STATUS mandatory
    DESCRIPTION
        "The value of this object indecates the support level of maintenance
         service. Level2 supports interface that strengthens the security
         level from level1."
    ::= { fjdarySsp 7 }

--***************************************************************************--
--   Physical Component                                                      --
--***************************************************************************--
-------------------------------------------------------------------------------
--   fjdaryCm                                                                --
-------------------------------------------------------------------------------
fjdaryCmCount OBJECT-TYPE
    SYNTAX INTEGER(0..2147483647)
    ACCESS read-only
    STATUS mandatory
    DESCRIPTION
        "The number of CM(controller module)'s informations
         (regardless of their current state) present on this system."
    ::= { fjdaryCm 1 }

fjdaryCmTable OBJECT-TYPE
    SYNTAX SEQUENCE OF FjdaryCmEntry
    ACCESS not-accessible
    STATUS mandatory
    DESCRIPTION
        ""
    ::= { fjdaryCm 2 }

fjdaryCmEntry OBJECT-TYPE
    SYNTAX FjdaryCmEntry
    ACCESS not-accessible
    STATUS mandatory
    DESCRIPTION
        ""
    INDEX { fjdaryCmIndex }
    ::= { fjdaryCmTable 1 }

FjdaryCmEntry ::=
    SEQUENCE{
        fjdaryCmIndex     INTEGER,
        fjdaryCmItemId    INTEGER,
        fjdaryCmStatus    FjdaryComponentStatus,
        fjdaryCmSubStatus FjdaryComponentStatus,
        fjdaryCmModuleId  INTEGER,
        fjdaryCmRole      INTEGER,
        fjdaryCmPartNo    OCTET STRING,
        fjdaryCmSerialNo  OCTET STRING,
        fjdaryCmRevision  OCTET STRING
    }

fjdaryCmIndex OBJECT-TYPE
    SYNTAX INTEGER(0..2147483647)
    ACCESS read-only
    STATUS mandatory
    DESCRIPTION
        "The value of this object uniquely identifies this fjdaryCm entry."
    ::= { fjdaryCmEntry 1 }

fjdaryCmItemId OBJECT-TYPE
    SYNTAX INTEGER(-2147483648..2147483647)
    ACCESS read-only
    STATUS mandatory
    DESCRIPTION
        "The value of this object indicates the identification number
         of this CM.
         the following definition:
           0x0100MM00
                 |
                 +-fjdaryCmModuleId"
    ::= { fjdaryCmEntry 2 }

fjdaryCmStatus OBJECT-TYPE
    SYNTAX FjdaryComponentStatus
    ACCESS read-only
    STATUS mandatory
    DESCRIPTION
        "The value of this object indicates the state of this CM.
         But, it doesn't become warning or alarm when maintaining it.
         (In the maintenance work, fjdaryMgtMaintenanceMode is on)"
    ::= { fjdaryCmEntry 3 }

fjdaryCmSubStatus OBJECT-TYPE
    SYNTAX FjdaryComponentStatus
    ACCESS read-only
    STATUS mandatory
    DESCRIPTION
        "The value of this object indicates the state of this CM.
         It becomes warning and alarm while even maintaining it.
         (In the maintenance work, fjdaryMgtMaintenanceMode is on)"
    ::= { fjdaryCmEntry 4 }

fjdaryCmModuleId OBJECT-TYPE
    SYNTAX INTEGER(-2147483648..2147483647)
    ACCESS read-only
    STATUS mandatory
    DESCRIPTION
        "The value of this object indicates the module indicates of this CM.
         0x10-0x17 shows CM. bit0-2 shows the CM slot number."
    ::= { fjdaryCmEntry 5 }

fjdaryCmRole OBJECT-TYPE
    SYNTAX INTEGER {
        master(1),
        slave(2)
    }
    ACCESS read-only
    STATUS mandatory
    DESCRIPTION
        "The value of this object indicates the role of this CM."
    ::= { fjdaryCmEntry 6 }

fjdaryCmPartNo OBJECT-TYPE
    SYNTAX OCTET STRING (SIZE (0..256))
    ACCESS read-only
    STATUS mandatory
    DESCRIPTION
        "The value of this object indicates the Part No of this CM."
    ::= { fjdaryCmEntry 7 }

fjdaryCmSerialNo OBJECT-TYPE
    SYNTAX OCTET STRING (SIZE (0..256))
    ACCESS read-only
    STATUS mandatory
    DESCRIPTION
        "The value of this object indicates the Serial No of this CM."
    ::= { fjdaryCmEntry 8 }

fjdaryCmRevision OBJECT-TYPE
    SYNTAX OCTET STRING (SIZE (0..256))
    ACCESS read-only
    STATUS mandatory
    DESCRIPTION
        "The value of this object indicates the Revision of this CM."
    ::= { fjdaryCmEntry 9 }

-------------------------------------------------------------------------------
--   fjdaryCmcpu                                                             --
-------------------------------------------------------------------------------
fjdaryCmcpuCount OBJECT-TYPE
    SYNTAX INTEGER(0..2147483647)
    ACCESS read-only
    STATUS mandatory
    DESCRIPTION
        "The number of CM CPU informations
         (regardless of their current state) present on this system."
    ::= { fjdaryCmcpu 1 }

fjdaryCmcpuTable OBJECT-TYPE
    SYNTAX SEQUENCE OF FjdaryCmcpuEntry
    ACCESS not-accessible
    STATUS mandatory
    DESCRIPTION
        ""
    ::= { fjdaryCmcpu 2 }

fjdaryCmcpuEntry OBJECT-TYPE
    SYNTAX FjdaryCmcpuEntry
    ACCESS not-accessible
    STATUS mandatory
    DESCRIPTION
        ""
    INDEX { fjdaryCmcpuIndex }
    ::= { fjdaryCmcpuTable 1 }

FjdaryCmcpuEntry ::=
    SEQUENCE{
        fjdaryCmcpuIndex     INTEGER,
        fjdaryCmcpuItemId    INTEGER,
        fjdaryCmcpuStatus    FjdaryComponentStatus,
        fjdaryCmcpuSubStatus FjdaryComponentStatus,
        fjdaryCmcpuModuleId  INTEGER,
        fjdaryCmcpuRole      INTEGER,
        fjdaryCmcpuClock     INTEGER
    }

fjdaryCmcpuIndex OBJECT-TYPE
    SYNTAX INTEGER(0..2147483647)
    ACCESS read-only
    STATUS mandatory
    DESCRIPTION
        "The value of this object uniquely identifies this fjdaryCmcpu entry."
    ::= { fjdaryCmcpuEntry 1 }

fjdaryCmcpuItemId OBJECT-TYPE
    SYNTAX INTEGER(-2147483648..2147483647)
    ACCESS read-only
    STATUS mandatory
    DESCRIPTION
        "The value of this object indicates the identification number
         of this CM CPU.
         the following definition:
           0x0100MM00
                 |
                 +-fjdaryCmcpuModuleId"
    ::= { fjdaryCmcpuEntry 2 }

fjdaryCmcpuStatus OBJECT-TYPE
    SYNTAX FjdaryComponentStatus
    ACCESS read-only
    STATUS mandatory
    DESCRIPTION
        "The value of this object indicates the state of this CM CPU.
         But, it doesn't become warning or alarm when maintaining it.
         (In the maintenance work, fjdaryMgtMaintenanceMode is on)"
    ::= { fjdaryCmcpuEntry 3 }

fjdaryCmcpuSubStatus OBJECT-TYPE
    SYNTAX FjdaryComponentStatus
    ACCESS read-only
    STATUS mandatory
    DESCRIPTION
        "The value of this object indicates the state of this CM CPU.
         It becomes warning and alarm while even maintaining it.
         (In the maintenance work, fjdaryMgtMaintenanceMode is on)"
    ::= { fjdaryCmcpuEntry 4 }

fjdaryCmcpuModuleId OBJECT-TYPE
    SYNTAX INTEGER(-2147483648..2147483647)
    ACCESS read-only
    STATUS mandatory
    DESCRIPTION
        "The value of this object indicates the module indicates of this
         CM CPU.
         0x10-0x17 shows CM. bit0-2 shows the CM slot number."
    ::= { fjdaryCmcpuEntry 5 }

fjdaryCmcpuRole OBJECT-TYPE
    SYNTAX INTEGER {
        master(1),
        slave(2)
    }
    ACCESS read-only
    STATUS mandatory
    DESCRIPTION
        "The value of this object indicates the role of this CM CPU."
    ::= { fjdaryCmcpuEntry 6 }

fjdaryCmcpuClock OBJECT-TYPE
    SYNTAX INTEGER(-2147483648..2147483647)
    ACCESS read-only
    STATUS mandatory
    DESCRIPTION
        "This shows CPU Clock of CM CPU. The unit is KHz."
    ::= { fjdaryCmcpuEntry 7 }

-------------------------------------------------------------------------------
--   fjdaryCa                                                                --
-------------------------------------------------------------------------------
fjdaryCaCount OBJECT-TYPE
    SYNTAX INTEGER(0..2147483647)
    ACCESS read-only
    STATUS mandatory
    DESCRIPTION
        "The number of CA(channel adapter)'s informations
         (regardless of their current state) present on this system."
    ::= { fjdaryCa 1 }

fjdaryCaTable OBJECT-TYPE
    SYNTAX SEQUENCE OF FjdaryCaEntry
    ACCESS not-accessible
    STATUS mandatory
    DESCRIPTION
        ""
    ::= { fjdaryCa 2 }

fjdaryCaEntry OBJECT-TYPE
    SYNTAX FjdaryCaEntry
    ACCESS not-accessible
    STATUS mandatory
    DESCRIPTION
        ""
    INDEX { fjdaryCaIndex }
    ::= { fjdaryCaTable 1 }

FjdaryCaEntry ::=
    SEQUENCE{
        fjdaryCaIndex     INTEGER,
        fjdaryCaItemId    INTEGER,
        fjdaryCaStatus    FjdaryComponentStatus,
        fjdaryCaSubStatus FjdaryComponentStatus,
        fjdaryCaModuleId  INTEGER,
        fjdaryCaType      INTEGER
    }

fjdaryCaIndex OBJECT-TYPE
    SYNTAX INTEGER(0..2147483647)
    ACCESS read-only
    STATUS mandatory
    DESCRIPTION
        "The value of this object uniquely identifies this fjdaryCa entry."
    ::= { fjdaryCaEntry 1 }

fjdaryCaItemId OBJECT-TYPE
    SYNTAX INTEGER(-2147483648..2147483647)
    ACCESS read-only
    STATUS mandatory
    DESCRIPTION
        "The value of this object indicates the identification number
         of this CA.
         the following definition:
           0x1000MM00
                 |
                 +-fjdaryCaModuleId"
    ::= { fjdaryCaEntry 2 }

fjdaryCaStatus OBJECT-TYPE
    SYNTAX FjdaryComponentStatus
    ACCESS read-only
    STATUS mandatory
    DESCRIPTION
        "The value of this object indicates the state of this CA.
         But, it doesn't become warning or alarm when maintaining it.
         (In the maintenance work, fjdaryMgtMaintenanceMode is on)"
    ::= { fjdaryCaEntry 3 }

fjdaryCaSubStatus OBJECT-TYPE
    SYNTAX FjdaryComponentStatus
    ACCESS read-only
    STATUS mandatory
    DESCRIPTION
        "The value of this object indicates the state of this CA.
         It becomes warning and alarm while even maintaining it.
         (In the maintenance work, fjdaryMgtMaintenanceMode is on)"
    ::= { fjdaryCaEntry 4 }

fjdaryCaModuleId OBJECT-TYPE
    SYNTAX INTEGER(-2147483648..2147483647)
    ACCESS read-only
    STATUS mandatory
    DESCRIPTION
        "The value of this object indicates the module indicates of this CA.
         0x40-0x7F shows CA. bit0-2 shows the CM slot number.
         bit4-5 shows the CA slot number in CM.
         bit3 shows the processor number in CA."
    ::= { fjdaryCaEntry 5 }

fjdaryCaType OBJECT-TYPE
    SYNTAX INTEGER(-2147483648..2147483647)
    ACCESS read-only
    STATUS mandatory
    DESCRIPTION
        "The value of this object indicates the type of this CA."
    ::= { fjdaryCaEntry 6 }

-------------------------------------------------------------------------------
--   fjdaryCmmemory                                                          --
-------------------------------------------------------------------------------
fjdaryCmmemoryCount OBJECT-TYPE
    SYNTAX INTEGER(0..2147483647)
    ACCESS read-only
    STATUS mandatory
    DESCRIPTION
        "The number of CM memory's informations
         (regardless of their current state) present on this system."
    ::= { fjdaryCmmemory 1 }

fjdaryCmmemoryTable OBJECT-TYPE
    SYNTAX SEQUENCE OF FjdaryCmmemoryEntry
    ACCESS not-accessible
    STATUS mandatory
    DESCRIPTION
        ""
    ::= { fjdaryCmmemory 2 }

fjdaryCmmemoryEntry OBJECT-TYPE
    SYNTAX FjdaryCmmemoryEntry
    ACCESS not-accessible
    STATUS mandatory
    DESCRIPTION
        ""
    INDEX { fjdaryCmmemoryIndex }
    ::= { fjdaryCmmemoryTable 1 }

FjdaryCmmemoryEntry ::=
    SEQUENCE{
        fjdaryCmmemoryIndex     INTEGER,
        fjdaryCmmemoryItemId    INTEGER,
        fjdaryCmmemoryStatus    FjdaryComponentStatus,
        fjdaryCmmemorySubStatus FjdaryComponentStatus,
        fjdaryCmmemoryCapacity  INTEGER,
        fjdaryCmmemoryPartNo    OCTET STRING,
        fjdaryCmmemorySerialNo  OCTET STRING
    }

fjdaryCmmemoryIndex OBJECT-TYPE
    SYNTAX INTEGER(0..2147483647)
    ACCESS read-only
    STATUS mandatory
    DESCRIPTION
        "The value of this object uniquely identifies this fjdaryCmmemory
         entry."
    ::= { fjdaryCmmemoryEntry 1 }

fjdaryCmmemoryItemId OBJECT-TYPE
    SYNTAX INTEGER(-2147483648..2147483647)
    ACCESS read-only
    STATUS mandatory
    DESCRIPTION
        "The value of this object indicates the identification number
         of this CM memory.
         the following definition:
           0x0b00MM00
                 |
                 +-fjdaryCmModuleId"
    ::= { fjdaryCmmemoryEntry 2 }

fjdaryCmmemoryStatus OBJECT-TYPE
    SYNTAX FjdaryComponentStatus
    ACCESS read-only
    STATUS mandatory
    DESCRIPTION
        "The value of this object indicates the state of this CM memory.
         But, it doesn't become warning or alarm when maintaining it.
         (In the maintenance work, fjdaryMgtMaintenanceMode is on)"
    ::= { fjdaryCmmemoryEntry 3 }

fjdaryCmmemorySubStatus OBJECT-TYPE
    SYNTAX FjdaryComponentStatus
    ACCESS read-only
    STATUS mandatory
    DESCRIPTION
        "The value of this object indicates the state of this CM memory.
         It becomes warning and alarm while even maintaining it.
         (In the maintenance work, fjdaryMgtMaintenanceMode is on)"
    ::= { fjdaryCmmemoryEntry 4 }

fjdaryCmmemoryCapacity OBJECT-TYPE
    SYNTAX INTEGER(-2147483648..2147483647)
    ACCESS read-only
    STATUS mandatory
    DESCRIPTION
        "The value of this object indicates the capacity of this CM memory.
         The unit is MB."
    ::= { fjdaryCmmemoryEntry 5 }

fjdaryCmmemoryPartNo OBJECT-TYPE
    SYNTAX OCTET STRING (SIZE (0..256))
    ACCESS read-only
    STATUS mandatory
    DESCRIPTION
        "The value of this object indicates the Part No of this CM memory."
    ::= { fjdaryCmmemoryEntry 6 }

fjdaryCmmemorySerialNo OBJECT-TYPE
    SYNTAX OCTET STRING (SIZE (0..256))
    ACCESS read-only
    STATUS mandatory
    DESCRIPTION
        "The value of this object indicates the Serial No of this CM memory."
    ::= { fjdaryCmmemoryEntry 7 }

-------------------------------------------------------------------------------
--   fjdaryBud                                                               --
-------------------------------------------------------------------------------
fjdaryBudCount OBJECT-TYPE
    SYNTAX INTEGER(0..2147483647)
    ACCESS read-only
    STATUS mandatory
    DESCRIPTION
        "The number of BUD's informations
         (regardless of their current state) present on this system."
    ::= { fjdaryBud 1 }

fjdaryBudTable OBJECT-TYPE
    SYNTAX SEQUENCE OF FjdaryBudEntry
    ACCESS not-accessible
    STATUS mandatory
    DESCRIPTION
        ""
    ::= { fjdaryBud 2 }

fjdaryBudEntry OBJECT-TYPE
    SYNTAX FjdaryBudEntry
    ACCESS not-accessible
    STATUS mandatory
    DESCRIPTION
        ""
    INDEX { fjdaryBudIndex }
    ::= { fjdaryBudTable 1 }

FjdaryBudEntry ::=
    SEQUENCE{
        fjdaryBudIndex     INTEGER,
        fjdaryBudItemId    INTEGER,
        fjdaryBudStatus    FjdaryComponentStatus,
        fjdaryBudSubStatus FjdaryComponentStatus
    }

fjdaryBudIndex OBJECT-TYPE
    SYNTAX INTEGER(0..2147483647)
    ACCESS read-only
    STATUS mandatory
    DESCRIPTION
        "The value of this object uniquely identifies this fjdaryBud entry."
    ::= { fjdaryBudEntry 1 }

fjdaryBudItemId OBJECT-TYPE
    SYNTAX INTEGER(-2147483648..2147483647)
    ACCESS read-only
    STATUS mandatory
    DESCRIPTION
        "The value of this object indicates the identification number
         of this BUD.
         the following definition:
           0x0c00MM00
                 |
                 +-fjdaryCmModuleId"
    ::= { fjdaryBudEntry 2 }

fjdaryBudStatus OBJECT-TYPE
    SYNTAX FjdaryComponentStatus
    ACCESS read-only
    STATUS mandatory
    DESCRIPTION
        "The value of this object indicates the state of this BUD.
         But, it doesn't become warning or alarm when maintaining it.
         (In the maintenance work, fjdaryMgtMaintenanceMode is on)"
    ::= { fjdaryBudEntry 3 }

fjdaryBudSubStatus OBJECT-TYPE
    SYNTAX FjdaryComponentStatus
    ACCESS read-only
    STATUS mandatory
    DESCRIPTION
        "The value of this object indicates the state of this BUD.
         It becomes warning and alarm while even maintaining it.
         (In the maintenance work, fjdaryMgtMaintenanceMode is on)"
    ::= { fjdaryBudEntry 4 }

-------------------------------------------------------------------------------
--   fjdaryCmfan                                                             --
-------------------------------------------------------------------------------
fjdaryCmfanCount OBJECT-TYPE
    SYNTAX INTEGER(0..2147483647)
    ACCESS read-only
    STATUS mandatory
    DESCRIPTION
        "The number of CM fan's informations
         (regardless of their current state) present on this system."
    ::= { fjdaryCmfan 1 }

fjdaryCmfanTable OBJECT-TYPE
    SYNTAX SEQUENCE OF FjdaryCmfanEntry
    ACCESS not-accessible
    STATUS mandatory
    DESCRIPTION
        ""
    ::= { fjdaryCmfan 2 }

fjdaryCmfanEntry OBJECT-TYPE
    SYNTAX FjdaryCmfanEntry
    ACCESS not-accessible
    STATUS mandatory
    DESCRIPTION
        ""
    INDEX { fjdaryCmfanIndex }
    ::= { fjdaryCmfanTable 1 }

FjdaryCmfanEntry ::=
    SEQUENCE{
        fjdaryCmfanIndex     INTEGER,
        fjdaryCmfanItemId    INTEGER,
        fjdaryCmfanStatus    FjdaryComponentStatus,
        fjdaryCmfanSubStatus FjdaryComponentStatus
    }

fjdaryCmfanIndex OBJECT-TYPE
    SYNTAX INTEGER(0..2147483647)
    ACCESS read-only
    STATUS mandatory
    DESCRIPTION
        "The value of this object uniquely identifies this fjdaryCmfan entry."
    ::= { fjdaryCmfanEntry 1 }

fjdaryCmfanItemId OBJECT-TYPE
    SYNTAX INTEGER(-2147483648..2147483647)
    ACCESS read-only
    STATUS mandatory
    DESCRIPTION
        "The value of this object indicates the identification number
         of this CM fan.
         the following definition:
           0x0d00MM00
                 |
                 +-fjdaryCmModuleId"
    ::= { fjdaryCmfanEntry 2 }

fjdaryCmfanStatus OBJECT-TYPE
    SYNTAX FjdaryComponentStatus
    ACCESS read-only
    STATUS mandatory
    DESCRIPTION
        "The value of this object indicates the state of this CM fan.
         But, it doesn't become warning or alarm when maintaining it.
         (In the maintenance work, fjdaryMgtMaintenanceMode is on)"
    ::= { fjdaryCmfanEntry 3 }

fjdaryCmfanSubStatus OBJECT-TYPE
    SYNTAX FjdaryComponentStatus
    ACCESS read-only
    STATUS mandatory
    DESCRIPTION
        "The value of this object indicates the state of this CM fan.
         It becomes warning and alarm while even maintaining it.
         (In the maintenance work, fjdaryMgtMaintenanceMode is on)"
    ::= { fjdaryCmfanEntry 4 }

-------------------------------------------------------------------------------
--   fjdaryBcu                                                               --
-------------------------------------------------------------------------------
fjdaryBcuCount OBJECT-TYPE
    SYNTAX INTEGER(0..2147483647)
    ACCESS read-only
    STATUS mandatory
    DESCRIPTION
        "The number of BCU's informations
         (regardless of their current state) present on this system."
    ::= { fjdaryBcu 1 }

fjdaryBcuTable OBJECT-TYPE
    SYNTAX SEQUENCE OF FjdaryBcuEntry
    ACCESS not-accessible
    STATUS mandatory
    DESCRIPTION
        ""
    ::= { fjdaryBcu 2 }

fjdaryBcuEntry OBJECT-TYPE
    SYNTAX FjdaryBcuEntry
    ACCESS not-accessible
    STATUS mandatory
    DESCRIPTION
        ""
    INDEX { fjdaryBcuIndex }
    ::= { fjdaryBcuTable 1 }

FjdaryBcuEntry ::=
    SEQUENCE{
        fjdaryBcuIndex     INTEGER,
        fjdaryBcuItemId    INTEGER,
        fjdaryBcuStatus    FjdaryComponentStatus,
        fjdaryBcuSubStatus FjdaryComponentStatus
    }

fjdaryBcuIndex OBJECT-TYPE
    SYNTAX INTEGER(0..2147483647)
    ACCESS read-only
    STATUS mandatory
    DESCRIPTION
        "The value of this object uniquely identifies this fjdaryBcu entry."
    ::= { fjdaryBcuEntry 1 }

fjdaryBcuItemId OBJECT-TYPE
    SYNTAX INTEGER(-2147483648..2147483647)
    ACCESS read-only
    STATUS mandatory
    DESCRIPTION
        "The value of this object indicates the identification number
         of this BCU.
         the following definition:
           0x7500SS00
                 |
                 +-slot number"
    ::= { fjdaryBcuEntry 2 }

fjdaryBcuStatus OBJECT-TYPE
    SYNTAX FjdaryComponentStatus
    ACCESS read-only
    STATUS mandatory
    DESCRIPTION
        "The value of this object indicates the state of this BCU.
         But, it doesn't become warning or alarm when maintaining it.
         (In the maintenance work, fjdaryMgtMaintenanceMode is on)"
    ::= { fjdaryBcuEntry 3 }

fjdaryBcuSubStatus OBJECT-TYPE
    SYNTAX FjdaryComponentStatus
    ACCESS read-only
    STATUS mandatory
    DESCRIPTION
        "The value of this object indicates the state of this BCU.
         It becomes warning and alarm while even maintaining it.
         (In the maintenance work, fjdaryMgtMaintenanceMode is on)"
    ::= { fjdaryBcuEntry 4 }

-------------------------------------------------------------------------------
--   fjdaryBtu                                                               --
-------------------------------------------------------------------------------
fjdaryBtuCount OBJECT-TYPE
    SYNTAX INTEGER(0..2147483647)
    ACCESS read-only
    STATUS mandatory
    DESCRIPTION
        "The number of BTU's informations
         (regardless of their current state) present on this system."
    ::= { fjdaryBtu 1 }

fjdaryBtuTable OBJECT-TYPE
    SYNTAX SEQUENCE OF FjdaryBtuEntry
    ACCESS not-accessible
    STATUS mandatory
    DESCRIPTION
        ""
    ::= { fjdaryBtu 2 }

fjdaryBtuEntry OBJECT-TYPE
    SYNTAX FjdaryBtuEntry
    ACCESS not-accessible
    STATUS mandatory
    DESCRIPTION
        ""
    INDEX { fjdaryBtuIndex }
    ::= { fjdaryBtuTable 1 }

FjdaryBtuEntry ::=
    SEQUENCE{
        fjdaryBtuIndex     INTEGER,
        fjdaryBtuItemId    INTEGER,
        fjdaryBtuStatus    FjdaryComponentStatus,
        fjdaryBtuSubStatus FjdaryComponentStatus
    }

fjdaryBtuIndex OBJECT-TYPE
    SYNTAX INTEGER(0..2147483647)
    ACCESS read-only
    STATUS mandatory
    DESCRIPTION
        "The value of this object uniquely identifies this fjdaryBtu entry."
    ::= { fjdaryBtuEntry 1 }

fjdaryBtuItemId OBJECT-TYPE
    SYNTAX INTEGER(-2147483648..2147483647)
    ACCESS read-only
    STATUS mandatory
    DESCRIPTION
        "The value of this object indicates the identification number
         of this BTU.
         the following definition:
           0x7600SS00
                 |
                 +-slot number"
    ::= { fjdaryBtuEntry 2 }

fjdaryBtuStatus OBJECT-TYPE
    SYNTAX FjdaryComponentStatus
    ACCESS read-only
    STATUS mandatory
    DESCRIPTION
        "The value of this object indicates the state of this BTU.
         But, it doesn't become warning or alarm when maintaining it.
         (In the maintenance work, fjdaryMgtMaintenanceMode is on)"
    ::= { fjdaryBtuEntry 3 }

fjdaryBtuSubStatus OBJECT-TYPE
    SYNTAX FjdaryComponentStatus
    ACCESS read-only
    STATUS mandatory
    DESCRIPTION
        "The value of this object indicates the state of this BTU.
         It becomes warning and alarm while even maintaining it.
         (In the maintenance work, fjdaryMgtMaintenanceMode is on)"
    ::= { fjdaryBtuEntry 4 }

-------------------------------------------------------------------------------
--   fjdaryScu                                                               --
-------------------------------------------------------------------------------
fjdaryScuCount OBJECT-TYPE
    SYNTAX INTEGER(0..2147483647)
    ACCESS read-only
    STATUS mandatory
    DESCRIPTION
        "The number of SCU's informations
         (regardless of their current state) present on this system."
    ::= { fjdaryScu 1 }

fjdaryScuTable OBJECT-TYPE
    SYNTAX SEQUENCE OF FjdaryScuEntry
    ACCESS not-accessible
    STATUS mandatory
    DESCRIPTION
        ""
    ::= { fjdaryScu 2 }

fjdaryScuEntry OBJECT-TYPE
    SYNTAX FjdaryScuEntry
    ACCESS not-accessible
    STATUS mandatory
    DESCRIPTION
        ""
    INDEX { fjdaryScuIndex }
    ::= { fjdaryScuTable 1 }

FjdaryScuEntry ::=
    SEQUENCE{
        fjdaryScuIndex     INTEGER,
        fjdaryScuItemId    INTEGER,
        fjdaryScuStatus    FjdaryComponentStatus,
        fjdaryScuSubStatus FjdaryComponentStatus,
        fjdaryScuVoltage   INTEGER,
        fjdaryScuPartNo    OCTET STRING,
        fjdaryScuSerialNo  OCTET STRING,
        fjdaryScuRevision  OCTET STRING
    }

fjdaryScuIndex OBJECT-TYPE
    SYNTAX INTEGER(0..2147483647)
    ACCESS read-only
    STATUS mandatory
    DESCRIPTION
        "The value of this object uniquely identifies this fjdaryScu entry."
    ::= { fjdaryScuEntry 1 }

fjdaryScuItemId OBJECT-TYPE
    SYNTAX INTEGER(-2147483648..2147483647)
    ACCESS read-only
    STATUS mandatory
    DESCRIPTION
        "The value of this object indicates the identification number
         of this SCU.
         the following definition:
           0x0f00MM00
                 |
                 +-fjdaryCmModuleId"
    ::= { fjdaryScuEntry 2 }

fjdaryScuStatus OBJECT-TYPE
    SYNTAX FjdaryComponentStatus
    ACCESS read-only
    STATUS mandatory
    DESCRIPTION
        "The value of this object indicates the state of this SCU.
         But, it doesn't become warning or alarm when maintaining it.
         (In the maintenance work, fjdaryMgtMaintenanceMode is on)"
    ::= { fjdaryScuEntry 3 }

fjdaryScuSubStatus OBJECT-TYPE
    SYNTAX FjdaryComponentStatus
    ACCESS read-only
    STATUS mandatory
    DESCRIPTION
        "The value of this object indicates the state of this SCU.
         It becomes warning and alarm while even maintaining it.
         (In the maintenance work, fjdaryMgtMaintenanceMode is on)"
    ::= { fjdaryScuEntry 4 }

fjdaryScuVoltage OBJECT-TYPE
    SYNTAX INTEGER(-2147483648..2147483647)
    ACCESS read-only
    STATUS mandatory
    DESCRIPTION
        "The value of this object indicates the voltage of this SCU.
         The unit is 1/20 volts."
    ::= { fjdaryScuEntry 5 }

fjdaryScuPartNo OBJECT-TYPE
    SYNTAX OCTET STRING (SIZE (0..256))
    ACCESS read-only
    STATUS mandatory
    DESCRIPTION
        "The value of this object indicates the Part No of this SCU."
    ::= { fjdaryScuEntry 6 }

fjdaryScuSerialNo OBJECT-TYPE
    SYNTAX OCTET STRING (SIZE (0..256))
    ACCESS read-only
    STATUS mandatory
    DESCRIPTION
        "The value of this object indicates the Serial No of this SCU."
    ::= { fjdaryScuEntry 7 }

fjdaryScuRevision OBJECT-TYPE
    SYNTAX OCTET STRING (SIZE (0..256))
    ACCESS read-only
    STATUS mandatory
    DESCRIPTION
        "The value of this object indicates the Revision of this SCU."
    ::= { fjdaryScuEntry 8 }

-------------------------------------------------------------------------------
--   fjdaryCe                                                                --
-------------------------------------------------------------------------------
fjdaryCeCount OBJECT-TYPE
    SYNTAX INTEGER(0..2147483647)
    ACCESS read-only
    STATUS mandatory
    DESCRIPTION
        "The number of CE(controller enclosure)'s informations
         (regardless of their current state) present on this system."
    ::= { fjdaryCe 1 }

fjdaryCeTable OBJECT-TYPE
    SYNTAX SEQUENCE OF FjdaryCeEntry
    ACCESS not-accessible
    STATUS mandatory
    DESCRIPTION
        ""
    ::= { fjdaryCe 2 }

fjdaryCeEntry OBJECT-TYPE
    SYNTAX FjdaryCeEntry
    ACCESS not-accessible
    STATUS mandatory
    DESCRIPTION
        ""
    INDEX { fjdaryCeIndex }
    ::= { fjdaryCeTable 1 }

FjdaryCeEntry ::=
    SEQUENCE{
        fjdaryCeIndex     INTEGER,
        fjdaryCeItemId    INTEGER,
        fjdaryCeStatus    FjdaryComponentStatus,
        fjdaryCeSubStatus FjdaryComponentStatus
    }

fjdaryCeIndex OBJECT-TYPE
    SYNTAX INTEGER(0..2147483647)
    ACCESS read-only
    STATUS mandatory
    DESCRIPTION
        "The value of this object uniquely identifies this fjdaryCe entry."
    ::= { fjdaryCeEntry 1 }

fjdaryCeItemId OBJECT-TYPE
    SYNTAX INTEGER(-2147483648..2147483647)
    ACCESS read-only
    STATUS mandatory
    DESCRIPTION
        "The value of this object indicates the identification number
         of this CE.
         the following definition:
           0x70000000"
    ::= { fjdaryCeEntry 2 }

fjdaryCeStatus OBJECT-TYPE
    SYNTAX FjdaryComponentStatus
    ACCESS read-only
    STATUS mandatory
    DESCRIPTION
        "The value of this object indicates the state of this CE.
         But, it doesn't become warning or alarm when maintaining it.
         (In the maintenance work, fjdaryMgtMaintenanceMode is on)"
    ::= { fjdaryCeEntry 3 }

fjdaryCeSubStatus OBJECT-TYPE
    SYNTAX FjdaryComponentStatus
    ACCESS read-only
    STATUS mandatory
    DESCRIPTION
        "The value of this object indicates the state of this CE.
         It becomes warning and alarm while even maintaining it.
         (In the maintenance work, fjdaryMgtMaintenanceMode is on)"
    ::= { fjdaryCeEntry 4 }

-------------------------------------------------------------------------------
--   fjdaryCeinletthml                                                       --
-------------------------------------------------------------------------------
fjdaryCeinletthmlCount OBJECT-TYPE
    SYNTAX INTEGER(0..2147483647)
    ACCESS read-only
    STATUS mandatory
    DESCRIPTION
        "The number of CE inlet thermal sensor's informations
         (regardless of their current state) present on this system."
    ::= { fjdaryCeinletthml 1 }

fjdaryCeinletthmlTable OBJECT-TYPE
    SYNTAX SEQUENCE OF FjdaryCeinletthmlEntry
    ACCESS not-accessible
    STATUS mandatory
    DESCRIPTION
        ""
    ::= { fjdaryCeinletthml 2 }

fjdaryCeinletthmlEntry OBJECT-TYPE
    SYNTAX FjdaryCeinletthmlEntry
    ACCESS not-accessible
    STATUS mandatory
    DESCRIPTION
        ""
    INDEX { fjdaryCeinletthmlIndex }
    ::= { fjdaryCeinletthmlTable 1 }

FjdaryCeinletthmlEntry ::=
    SEQUENCE{
        fjdaryCeinletthmlIndex     INTEGER,
        fjdaryCeinletthmlItemId    INTEGER,
        fjdaryCeinletthmlStatus    FjdaryComponentStatus,
        fjdaryCeinletthmlSubStatus FjdaryComponentStatus
    }

fjdaryCeinletthmlIndex OBJECT-TYPE
    SYNTAX INTEGER(0..2147483647)
    ACCESS read-only
    STATUS mandatory
    DESCRIPTION
        "The value of this object uniquely identifies this fjdaryCeinletthml
         entry."
    ::= { fjdaryCeinletthmlEntry 1 }

fjdaryCeinletthmlItemId OBJECT-TYPE
    SYNTAX INTEGER(-2147483648..2147483647)
    ACCESS read-only
    STATUS mandatory
    DESCRIPTION
        "The value of this object indicates the identification number
         of this CE inlet thermal sensor.
         the following definition:
         It becomes either definition by the type.
           0x7b000000           0xdb000000"
    ::= { fjdaryCeinletthmlEntry 2 }

fjdaryCeinletthmlStatus OBJECT-TYPE
    SYNTAX FjdaryComponentStatus
    ACCESS read-only
    STATUS mandatory
    DESCRIPTION
        "The value of this object indicates the state of this CE inlet thermal
         sensor.
         But, it doesn't become warning or alarm when maintaining it.
         (In the maintenance work, fjdaryMgtMaintenanceMode is on)"
    ::= { fjdaryCeinletthmlEntry 3 }

fjdaryCeinletthmlSubStatus OBJECT-TYPE
    SYNTAX FjdaryComponentStatus
    ACCESS read-only
    STATUS mandatory
    DESCRIPTION
        "The value of this object indicates the state of this CE inlet thermal
         sensor.
         It becomes warning and alarm while even maintaining it.
         (In the maintenance work, fjdaryMgtMaintenanceMode is on)"
    ::= { fjdaryCeinletthmlEntry 4 }

-------------------------------------------------------------------------------
--   fjdaryCethml                                                            --
-------------------------------------------------------------------------------
fjdaryCethmlCount OBJECT-TYPE
    SYNTAX INTEGER(0..2147483647)
    ACCESS read-only
    STATUS mandatory
    DESCRIPTION
        "The number of CE thermal sensor's informations
         (regardless of their current state) present on this system."
    ::= { fjdaryCethml 1 }

fjdaryCethmlTable OBJECT-TYPE
    SYNTAX SEQUENCE OF FjdaryCethmlEntry
    ACCESS not-accessible
    STATUS mandatory
    DESCRIPTION
        ""
    ::= { fjdaryCethml 2 }

fjdaryCethmlEntry OBJECT-TYPE
    SYNTAX FjdaryCethmlEntry
    ACCESS not-accessible
    STATUS mandatory
    DESCRIPTION
        ""
    INDEX { fjdaryCethmlIndex }
    ::= { fjdaryCethmlTable 1 }

FjdaryCethmlEntry ::=
    SEQUENCE{
        fjdaryCethmlIndex     INTEGER,
        fjdaryCethmlItemId    INTEGER,
        fjdaryCethmlStatus    FjdaryComponentStatus,
        fjdaryCethmlSubStatus FjdaryComponentStatus
    }

fjdaryCethmlIndex OBJECT-TYPE
    SYNTAX INTEGER(0..2147483647)
    ACCESS read-only
    STATUS mandatory
    DESCRIPTION
        "The value of this object uniquely identifies this fjdaryCethml entry."
    ::= { fjdaryCethmlEntry 1 }

fjdaryCethmlItemId OBJECT-TYPE
    SYNTAX INTEGER(-2147483648..2147483647)
    ACCESS read-only
    STATUS mandatory
    DESCRIPTION
        "The value of this object indicates the identification number
         of this CE thermal sensor.
         the following definition:
         It becomes either definition by the type.
           0x7a000000           0xda000000"
    ::= { fjdaryCethmlEntry 2 }

fjdaryCethmlStatus OBJECT-TYPE
    SYNTAX FjdaryComponentStatus
    ACCESS read-only
    STATUS mandatory
    DESCRIPTION
        "The value of this object indicates the state of this CE thermal
         sensor.
         But, it doesn't become warning or alarm when maintaining it.
         (In the maintenance work, fjdaryMgtMaintenanceMode is on)"
    ::= { fjdaryCethmlEntry 3 }

fjdaryCethmlSubStatus OBJECT-TYPE
    SYNTAX FjdaryComponentStatus
    ACCESS read-only
    STATUS mandatory
    DESCRIPTION
        "The value of this object indicates the state of this CE thermal
         sensor.
         It becomes warning and alarm while even maintaining it.
         (In the maintenance work, fjdaryMgtMaintenanceMode is on)"
    ::= { fjdaryCethmlEntry 4 }

-------------------------------------------------------------------------------
--   fjdaryCpsu                                                              --
-------------------------------------------------------------------------------
fjdaryCpsuCount OBJECT-TYPE
    SYNTAX INTEGER(0..2147483647)
    ACCESS read-only
    STATUS mandatory
    DESCRIPTION
        "The number of CPSU(power supply unit mounted on CE)'s informations
         (regardless of their current state) present on this system."
    ::= { fjdaryCpsu 1 }

fjdaryCpsuTable OBJECT-TYPE
    SYNTAX SEQUENCE OF FjdaryCpsuEntry
    ACCESS not-accessible
    STATUS mandatory
    DESCRIPTION
        ""
    ::= { fjdaryCpsu 2 }

fjdaryCpsuEntry OBJECT-TYPE
    SYNTAX FjdaryCpsuEntry
    ACCESS not-accessible
    STATUS mandatory
    DESCRIPTION
        ""
    INDEX { fjdaryCpsuIndex }
    ::= { fjdaryCpsuTable 1 }

FjdaryCpsuEntry ::=
    SEQUENCE{
        fjdaryCpsuIndex     INTEGER,
        fjdaryCpsuItemId    INTEGER,
        fjdaryCpsuStatus    FjdaryComponentStatus,
        fjdaryCpsuSubStatus FjdaryComponentStatus,
        fjdaryCpsuPartNo    OCTET STRING,
        fjdaryCpsuSerialNo  OCTET STRING,
        fjdaryCpsuRevision  OCTET STRING
    }

fjdaryCpsuIndex OBJECT-TYPE
    SYNTAX INTEGER(0..2147483647)
    ACCESS read-only
    STATUS mandatory
    DESCRIPTION
        "The value of this object uniquely identifies this fjdaryCpsu entry."
    ::= { fjdaryCpsuEntry 1 }

fjdaryCpsuItemId OBJECT-TYPE
    SYNTAX INTEGER(-2147483648..2147483647)
    ACCESS read-only
    STATUS mandatory
    DESCRIPTION
        "The value of this object indicates the identification number
         of this CPSU.
         the following definition:
         It becomes either definition by the type.
           0x7300SS00           0xd20000SS
                 |                      |
                 +-slot number          +-slot number"
    ::= { fjdaryCpsuEntry 2 }

fjdaryCpsuStatus OBJECT-TYPE
    SYNTAX FjdaryComponentStatus
    ACCESS read-only
    STATUS mandatory
    DESCRIPTION
        "The value of this object indicates the state of this CPSU.
         But, it doesn't become warning or alarm when maintaining it.
         (In the maintenance work, fjdaryMgtMaintenanceMode is on)"
    ::= { fjdaryCpsuEntry 3 }

fjdaryCpsuSubStatus OBJECT-TYPE
    SYNTAX FjdaryComponentStatus
    ACCESS read-only
    STATUS mandatory
    DESCRIPTION
        "The value of this object indicates the state of this CPSU.
         It becomes warning and alarm while even maintaining it.
         (In the maintenance work, fjdaryMgtMaintenanceMode is on)"
    ::= { fjdaryCpsuEntry 4 }

fjdaryCpsuPartNo OBJECT-TYPE
    SYNTAX OCTET STRING (SIZE (0..256))
    ACCESS read-only
    STATUS mandatory
    DESCRIPTION
        "The value of this object indicates the Part No of this CPSU."
    ::= { fjdaryCpsuEntry 5 }

fjdaryCpsuSerialNo OBJECT-TYPE
    SYNTAX OCTET STRING (SIZE (0..256))
    ACCESS read-only
    STATUS mandatory
    DESCRIPTION
        "The value of this object indicates the Serial No of this CPSU."
    ::= { fjdaryCpsuEntry 6 }

fjdaryCpsuRevision OBJECT-TYPE
    SYNTAX OCTET STRING (SIZE (0..256))
    ACCESS read-only
    STATUS mandatory
    DESCRIPTION
        "The value of this object indicates the Revision of this CPSU."
    ::= { fjdaryCpsuEntry 7 }

-------------------------------------------------------------------------------
--   fjdaryDe                                                                --
-------------------------------------------------------------------------------
fjdaryDeCount OBJECT-TYPE
    SYNTAX INTEGER(0..2147483647)
    ACCESS read-only
    STATUS mandatory
    DESCRIPTION
        "The number of DE(drive enclosure)'s informations
         (regardless of their current state) present on this system."
    ::= { fjdaryDe 1 }

fjdaryDeTable OBJECT-TYPE
    SYNTAX SEQUENCE OF FjdaryDeEntry
    ACCESS not-accessible
    STATUS mandatory
    DESCRIPTION
        ""
    ::= { fjdaryDe 2 }

fjdaryDeEntry OBJECT-TYPE
    SYNTAX FjdaryDeEntry
    ACCESS not-accessible
    STATUS mandatory
    DESCRIPTION
        ""
    INDEX { fjdaryDeIndex }
    ::= { fjdaryDeTable 1 }

FjdaryDeEntry ::=
    SEQUENCE{
        fjdaryDeIndex     INTEGER,
        fjdaryDeItemId    INTEGER,
        fjdaryDeStatus    FjdaryComponentStatus,
        fjdaryDeSubStatus FjdaryComponentStatus,
        fjdaryDeId        INTEGER,
        fjdaryDeType      INTEGER
    }

fjdaryDeIndex OBJECT-TYPE
    SYNTAX INTEGER(0..2147483647)
    ACCESS read-only
    STATUS mandatory
    DESCRIPTION
        "The value of this object uniquely identifies this fjdaryDe entry."
    ::= { fjdaryDeEntry 1 }

fjdaryDeItemId OBJECT-TYPE
    SYNTAX INTEGER(-2147483648..2147483647)
    ACCESS read-only
    STATUS mandatory
    DESCRIPTION
        "The value of this object indicates the identification number
         of this DE.
         the following definition:
           0xd000DD00
                 |
                 +-fjdaryDeId"
    ::= { fjdaryDeEntry 2 }

fjdaryDeStatus OBJECT-TYPE
    SYNTAX FjdaryComponentStatus
    ACCESS read-only
    STATUS mandatory
    DESCRIPTION
        "The value of this object indicates the state of this DE.
         But, it doesn't become warning or alarm when maintaining it.
         (In the maintenance work, fjdaryMgtMaintenanceMode is on)"
    ::= { fjdaryDeEntry 3 }

fjdaryDeSubStatus OBJECT-TYPE
    SYNTAX FjdaryComponentStatus
    ACCESS read-only
    STATUS mandatory
    DESCRIPTION
        "The value of this object indicates the state of this DE.
         It becomes warning and alarm while even maintaining it.
         (In the maintenance work, fjdaryMgtMaintenanceMode is on)"
    ::= { fjdaryDeEntry 4 }

fjdaryDeId OBJECT-TYPE
    SYNTAX INTEGER(-2147483648..2147483647)
    ACCESS read-only
    STATUS mandatory
    DESCRIPTION
        "The value of this object indicates the identification of this DE."
    ::= { fjdaryDeEntry 5 }

fjdaryDeType OBJECT-TYPE
    SYNTAX INTEGER(-2147483648..2147483647)
    ACCESS read-only
    STATUS mandatory
    DESCRIPTION
        "The value of this object indicates the type of this DE."
    ::= { fjdaryDeEntry 6 }

-------------------------------------------------------------------------------
--   fjdaryIom                                                               --
-------------------------------------------------------------------------------
fjdaryIomCount OBJECT-TYPE
    SYNTAX INTEGER(0..2147483647)
    ACCESS read-only
    STATUS mandatory
    DESCRIPTION
        "The number of IOM's informations
         (regardless of their current state) present on this system."
    ::= { fjdaryIom 1 }

fjdaryIomTable OBJECT-TYPE
    SYNTAX SEQUENCE OF FjdaryIomEntry
    ACCESS not-accessible
    STATUS mandatory
    DESCRIPTION
        ""
    ::= { fjdaryIom 2 }

fjdaryIomEntry OBJECT-TYPE
    SYNTAX FjdaryIomEntry
    ACCESS not-accessible
    STATUS mandatory
    DESCRIPTION
        ""
    INDEX { fjdaryIomIndex }
    ::= { fjdaryIomTable 1 }

FjdaryIomEntry ::=
    SEQUENCE{
        fjdaryIomIndex     INTEGER,
        fjdaryIomItemId    INTEGER,
        fjdaryIomStatus    FjdaryComponentStatus,
        fjdaryIomSubStatus FjdaryComponentStatus,
        fjdaryIomFirmInfo  OCTET STRING,
        fjdaryIomPartNo    OCTET STRING,
        fjdaryIomSerialNo  OCTET STRING,
        fjdaryIomRevision  OCTET STRING
    }

fjdaryIomIndex OBJECT-TYPE
    SYNTAX INTEGER(0..2147483647)
    ACCESS read-only
    STATUS mandatory
    DESCRIPTION
        "The value of this object uniquely identifies this fjdaryIom entry."
    ::= { fjdaryIomEntry 1 }

fjdaryIomItemId OBJECT-TYPE
    SYNTAX INTEGER(-2147483648..2147483647)
    ACCESS read-only
    STATUS mandatory
    DESCRIPTION
        "The value of this object indicates the identification number
         of this IOM.
         the following definition:
           0x9000DDSS
                 | |
                 | +-slot number
                 +-DE ID"
    ::= { fjdaryIomEntry 2 }

fjdaryIomStatus OBJECT-TYPE
    SYNTAX FjdaryComponentStatus
    ACCESS read-only
    STATUS mandatory
    DESCRIPTION
        "The value of this object indicates the state of this IOM.
         But, it doesn't become warning or alarm when maintaining it.
         (In the maintenance work, fjdaryMgtMaintenanceMode is on)"
    ::= { fjdaryIomEntry 3 }

fjdaryIomSubStatus OBJECT-TYPE
    SYNTAX FjdaryComponentStatus
    ACCESS read-only
    STATUS mandatory
    DESCRIPTION
        "The value of this object indicates the state of this IOM.
         It becomes warning and alarm while even maintaining it.
         (In the maintenance work, fjdaryMgtMaintenanceMode is on)"
    ::= { fjdaryIomEntry 4 }

fjdaryIomFirmInfo OBJECT-TYPE
    SYNTAX OCTET STRING (SIZE (0..256))
    ACCESS read-only
    STATUS mandatory
    DESCRIPTION
        "The value of this object indicates the firmware information of this
         IOM."
    ::= { fjdaryIomEntry 5 }

fjdaryIomPartNo OBJECT-TYPE
    SYNTAX OCTET STRING (SIZE (0..256))
    ACCESS read-only
    STATUS mandatory
    DESCRIPTION
        "The value of this object indicates the Part No of this IOM."
    ::= { fjdaryIomEntry 6 }

fjdaryIomSerialNo OBJECT-TYPE
    SYNTAX OCTET STRING (SIZE (0..256))
    ACCESS read-only
    STATUS mandatory
    DESCRIPTION
        "The value of this object indicates the Serial No of this IOM."
    ::= { fjdaryIomEntry 7 }

fjdaryIomRevision OBJECT-TYPE
    SYNTAX OCTET STRING (SIZE (0..256))
    ACCESS read-only
    STATUS mandatory
    DESCRIPTION
        "The value of this object indicates the Revision of this IOM."
    ::= { fjdaryIomEntry 8 }

-------------------------------------------------------------------------------
--   fjdaryPsu                                                               --
-------------------------------------------------------------------------------
fjdaryPsuCount OBJECT-TYPE
    SYNTAX INTEGER(0..2147483647)
    ACCESS read-only
    STATUS mandatory
    DESCRIPTION
        "The number of PSU(power supply unit)'s informations
         (regardless of their current state) present on this system."
    ::= { fjdaryPsu 1 }

fjdaryPsuTable OBJECT-TYPE
    SYNTAX SEQUENCE OF FjdaryPsuEntry
    ACCESS not-accessible
    STATUS mandatory
    DESCRIPTION
        ""
    ::= { fjdaryPsu 2 }

fjdaryPsuEntry OBJECT-TYPE
    SYNTAX FjdaryPsuEntry
    ACCESS not-accessible
    STATUS mandatory
    DESCRIPTION
        ""
    INDEX { fjdaryPsuIndex }
    ::= { fjdaryPsuTable 1 }

FjdaryPsuEntry ::=
    SEQUENCE{
        fjdaryPsuIndex     INTEGER,
        fjdaryPsuItemId    INTEGER,
        fjdaryPsuStatus    FjdaryComponentStatus,
        fjdaryPsuSubStatus FjdaryComponentStatus,
        fjdaryPsuPartNo    OCTET STRING,
        fjdaryPsuSerialNo  OCTET STRING,
        fjdaryPsuRevision  OCTET STRING
    }

fjdaryPsuIndex OBJECT-TYPE
    SYNTAX INTEGER(0..2147483647)
    ACCESS read-only
    STATUS mandatory
    DESCRIPTION
        "The value of this object uniquely identifies this fjdaryPsu entry."
    ::= { fjdaryPsuEntry 1 }

fjdaryPsuItemId OBJECT-TYPE
    SYNTAX INTEGER(-2147483648..2147483647)
    ACCESS read-only
    STATUS mandatory
    DESCRIPTION
        "The value of this object indicates the identification number
         of this PSU.
         the following definition:
           0xd200DDSS
                 | |
                 | +-slot number
                 +-DE ID"
    ::= { fjdaryPsuEntry 2 }

fjdaryPsuStatus OBJECT-TYPE
    SYNTAX FjdaryComponentStatus
    ACCESS read-only
    STATUS mandatory
    DESCRIPTION
        "The value of this object indicates the state of this PSU.
         But, it doesn't become warning or alarm when maintaining it.
         (In the maintenance work, fjdaryMgtMaintenanceMode is on)"
    ::= { fjdaryPsuEntry 3 }

fjdaryPsuSubStatus OBJECT-TYPE
    SYNTAX FjdaryComponentStatus
    ACCESS read-only
    STATUS mandatory
    DESCRIPTION
        "The value of this object indicates the state of this PSU.
         It becomes warning and alarm while even maintaining it.
         (In the maintenance work, fjdaryMgtMaintenanceMode is on)"
    ::= { fjdaryPsuEntry 4 }

fjdaryPsuPartNo OBJECT-TYPE
    SYNTAX OCTET STRING (SIZE (0..256))
    ACCESS read-only
    STATUS mandatory
    DESCRIPTION
        "The value of this object indicates the Part No of this PSU."
    ::= { fjdaryPsuEntry 5 }

fjdaryPsuSerialNo OBJECT-TYPE
    SYNTAX OCTET STRING (SIZE (0..256))
    ACCESS read-only
    STATUS mandatory
    DESCRIPTION
        "The value of this object indicates the Serial No of this PSU."
    ::= { fjdaryPsuEntry 6 }

fjdaryPsuRevision OBJECT-TYPE
    SYNTAX OCTET STRING (SIZE (0..256))
    ACCESS read-only
    STATUS mandatory
    DESCRIPTION
        "The value of this object indicates the Revision of this PSU."
    ::= { fjdaryPsuEntry 7 }

-------------------------------------------------------------------------------
--   fjdaryDeinletthml                                                       --
-------------------------------------------------------------------------------
fjdaryDeinletthmlCount OBJECT-TYPE
    SYNTAX INTEGER(0..2147483647)
    ACCESS read-only
    STATUS mandatory
    DESCRIPTION
        "The number of DE inlet thermal sensor's informations
         (regardless of their current state) present on this system."
    ::= { fjdaryDeinletthml 1 }

fjdaryDeinletthmlTable OBJECT-TYPE
    SYNTAX SEQUENCE OF FjdaryDeinletthmlEntry
    ACCESS not-accessible
    STATUS mandatory
    DESCRIPTION
        ""
    ::= { fjdaryDeinletthml 2 }

fjdaryDeinletthmlEntry OBJECT-TYPE
    SYNTAX FjdaryDeinletthmlEntry
    ACCESS not-accessible
    STATUS mandatory
    DESCRIPTION
        ""
    INDEX { fjdaryDeinletthmlIndex }
    ::= { fjdaryDeinletthmlTable 1 }

FjdaryDeinletthmlEntry ::=
    SEQUENCE{
        fjdaryDeinletthmlIndex     INTEGER,
        fjdaryDeinletthmlItemId    INTEGER,
        fjdaryDeinletthmlStatus    FjdaryComponentStatus,
        fjdaryDeinletthmlSubStatus FjdaryComponentStatus
    }

fjdaryDeinletthmlIndex OBJECT-TYPE
    SYNTAX INTEGER(0..2147483647)
    ACCESS read-only
    STATUS mandatory
    DESCRIPTION
        "The value of this object uniquely identifies this fjdaryDeinletthml
         entry."
    ::= { fjdaryDeinletthmlEntry 1 }

fjdaryDeinletthmlItemId OBJECT-TYPE
    SYNTAX INTEGER(-2147483648..2147483647)
    ACCESS read-only
    STATUS mandatory
    DESCRIPTION
        "The value of this object indicates the identification number
         of this DE inlet thermal sensor.
         the following definition:
           0xdb00DD00
                 |
                 +-DE ID"
    ::= { fjdaryDeinletthmlEntry 2 }

fjdaryDeinletthmlStatus OBJECT-TYPE
    SYNTAX FjdaryComponentStatus
    ACCESS read-only
    STATUS mandatory
    DESCRIPTION
        "The value of this object indicates the state of this DE inlet thermal
         sensor.
         But, it doesn't become warning or alarm when maintaining it.
         (In the maintenance work, fjdaryMgtMaintenanceMode is on)"
    ::= { fjdaryDeinletthmlEntry 3 }

fjdaryDeinletthmlSubStatus OBJECT-TYPE
    SYNTAX FjdaryComponentStatus
    ACCESS read-only
    STATUS mandatory
    DESCRIPTION
        "The value of this object indicates the state of this DE inlet thermal
         sensor.
         It becomes warning and alarm while even maintaining it.
         (In the maintenance work, fjdaryMgtMaintenanceMode is on)"
    ::= { fjdaryDeinletthmlEntry 4 }

-------------------------------------------------------------------------------
--   fjdaryDethml                                                            --
-------------------------------------------------------------------------------
fjdaryDethmlCount OBJECT-TYPE
    SYNTAX INTEGER(0..2147483647)
    ACCESS read-only
    STATUS mandatory
    DESCRIPTION
        "The number of DE thermal sensor's informations
         (regardless of their current state) present on this system."
    ::= { fjdaryDethml 1 }

fjdaryDethmlTable OBJECT-TYPE
    SYNTAX SEQUENCE OF FjdaryDethmlEntry
    ACCESS not-accessible
    STATUS mandatory
    DESCRIPTION
        ""
    ::= { fjdaryDethml 2 }

fjdaryDethmlEntry OBJECT-TYPE
    SYNTAX FjdaryDethmlEntry
    ACCESS not-accessible
    STATUS mandatory
    DESCRIPTION
        ""
    INDEX { fjdaryDethmlIndex }
    ::= { fjdaryDethmlTable 1 }

FjdaryDethmlEntry ::=
    SEQUENCE{
        fjdaryDethmlIndex     INTEGER,
        fjdaryDethmlItemId    INTEGER,
        fjdaryDethmlStatus    FjdaryComponentStatus,
        fjdaryDethmlSubStatus FjdaryComponentStatus
    }

fjdaryDethmlIndex OBJECT-TYPE
    SYNTAX INTEGER(0..2147483647)
    ACCESS read-only
    STATUS mandatory
    DESCRIPTION
        "The value of this object uniquely identifies this fjdaryDethml entry."
    ::= { fjdaryDethmlEntry 1 }

fjdaryDethmlItemId OBJECT-TYPE
    SYNTAX INTEGER(-2147483648..2147483647)
    ACCESS read-only
    STATUS mandatory
    DESCRIPTION
        "The value of this object indicates the identification number
         of this DE thermal sensor.
         the following definition:
           0xda00DD00
                 |
                 +-DE ID"
    ::= { fjdaryDethmlEntry 2 }

fjdaryDethmlStatus OBJECT-TYPE
    SYNTAX FjdaryComponentStatus
    ACCESS read-only
    STATUS mandatory
    DESCRIPTION
        "The value of this object indicates the state of this DE thermal
         sensor.
         But, it doesn't become warning or alarm when maintaining it.
         (In the maintenance work, fjdaryMgtMaintenanceMode is on)"
    ::= { fjdaryDethmlEntry 3 }

fjdaryDethmlSubStatus OBJECT-TYPE
    SYNTAX FjdaryComponentStatus
    ACCESS read-only
    STATUS mandatory
    DESCRIPTION
        "The value of this object indicates the state of this DE thermal
         sensor.
         It becomes warning and alarm while even maintaining it.
         (In the maintenance work, fjdaryMgtMaintenanceMode is on)"
    ::= { fjdaryDethmlEntry 4 }

-------------------------------------------------------------------------------
--   fjdaryDisk                                                              --
-------------------------------------------------------------------------------
fjdaryDiskCount OBJECT-TYPE
    SYNTAX INTEGER(0..2147483647)
    ACCESS read-only
    STATUS mandatory
    DESCRIPTION
        "The number of DISK's informations
         (regardless of their current state) present on this system."
    ::= { fjdaryDisk 1 }

fjdaryDiskTable OBJECT-TYPE
    SYNTAX SEQUENCE OF FjdaryDiskEntry
    ACCESS not-accessible
    STATUS mandatory
    DESCRIPTION
        ""
    ::= { fjdaryDisk 2 }

fjdaryDiskEntry OBJECT-TYPE
    SYNTAX FjdaryDiskEntry
    ACCESS not-accessible
    STATUS mandatory
    DESCRIPTION
        ""
    INDEX { fjdaryDiskIndex }
    ::= { fjdaryDiskTable 1 }

FjdaryDiskEntry ::=
    SEQUENCE{
        fjdaryDiskIndex         INTEGER,
        fjdaryDiskItemId        INTEGER,
        fjdaryDiskStatus        INTEGER,
        fjdaryDiskSubStatus     INTEGER,
        fjdaryDiskCompStatus    FjdaryComponentStatus,
        fjdaryDiskCompSubStatus FjdaryComponentStatus,
        fjdaryDiskPlun          INTEGER,
        fjdaryDiskPurpose       INTEGER,
        fjdaryDiskType          INTEGER,
        fjdaryDiskWwn           OCTET STRING,
        fjdaryDiskVenderId      OCTET STRING,
        fjdaryDiskProductId     OCTET STRING,
        fjdaryDiskFwRevision    OCTET STRING,
        fjdaryDiskDateCode      OCTET STRING,
        fjdaryDiskCfgRevision   OCTET STRING,
        fjdaryDiskSize          INTEGER
    }

fjdaryDiskIndex OBJECT-TYPE
    SYNTAX INTEGER(0..2147483647)
    ACCESS read-only
    STATUS mandatory
    DESCRIPTION
        "The value of this object uniquely identifies this fjdaryDisk entry."
    ::= { fjdaryDiskEntry 1 }

fjdaryDiskItemId OBJECT-TYPE
    SYNTAX INTEGER(-2147483648..2147483647)
    ACCESS read-only
    STATUS mandatory
    DESCRIPTION
        "The value of this object indicates the identification number
         of this DISK.
         the following definition:
           0x8000DDSS
                 | |
                 | +-slot number
                 +-DE ID"
    ::= { fjdaryDiskEntry 2 }

fjdaryDiskStatus OBJECT-TYPE
    SYNTAX INTEGER{
        available(1),
        broken(2),
        notavailable(3),
        notsupported(4),
        present(5),
        readying(6),
        recovering(7),
        partbroken(64),
        spare(65),
        formatting(66),
        unformatted(67),
        notexist(68),
        copying(69)
    }
    ACCESS read-only
    STATUS mandatory
    DESCRIPTION
        "The value of this object indicates the state of this DISK.
         But, it doesn't become warning or alarm when maintaining it.
         (In the maintenance work, fjdaryMgtMaintenanceMode is on)

         available    : Normal state
         broken       : Abnormal state
                        (The data can not be guaranteed)
         notavailable : Not available state
                        (Because the RAID group is not set)
         notsupported : Unsupported error state
         present      : Undefined volume set state
         readying     : Data readying state
         recovering   : Data recovering state
         partbroken   : Abnormal state
         spare        : Using spare disk state
         formatting   : Data formatting state
         unformatted  : Unformatted state
         notexist     : Not exist
         copying      : Data copying state"
    ::= { fjdaryDiskEntry 3 }

fjdaryDiskSubStatus OBJECT-TYPE
    SYNTAX INTEGER{
        available(1),
        broken(2),
        notavailable(3),
        notsupported(4),
        present(5),
        readying(6),
        recovering(7),
        partbroken(64),
        spare(65),
        formatting(66),
        unformatted(67),
        notexist(68),
        copying(69)
    }
    ACCESS read-only
    STATUS mandatory
    DESCRIPTION
        "The value of this object indicates the state of this DISK.
         It becomes warning and alarm while even maintaining it.
         (In the maintenance work, fjdaryMgtMaintenanceMode is on)

         available    : Normal state
         broken       : Abnormal state
                        (The data can not be guaranteed)
         notavailable : Not available state
                        (Because the RAID group is not set)
         notsupported : Unsupported error state
         present      : Undefined volume set state
         readying     : Data readying state
         recovering   : Data recovering state
         partbroken   : Abnormal state
         spare        : Using spare disk state
         formatting   : Data formatting state
         unformatted  : Unformatted state
         notexist     : Not exist
         copying      : Data copying state"
    ::= { fjdaryDiskEntry 4 }

fjdaryDiskCompStatus OBJECT-TYPE
    SYNTAX FjdaryComponentStatus
    ACCESS read-only
    STATUS mandatory
    DESCRIPTION
        "The value of this object indicates the state of this DISK.
         But, it doesn't become warning or alarm when maintaining it.
         (In the maintenance work, fjdaryMgtMaintenanceMode is on)

         Not included in the RAID group and not spare become undefined.
         Under the rebuild copyback become maintenance."
    ::= { fjdaryDiskEntry 5 }

fjdaryDiskCompSubStatus OBJECT-TYPE
    SYNTAX FjdaryComponentStatus
    ACCESS read-only
    STATUS mandatory
    DESCRIPTION
        "The value of this object indicates the state of this DISK.
         It becomes warning and alarm while even maintaining it.
         (In the maintenance work, fjdaryMgtMaintenanceMode is on)

         Not included in the RAID group and not spare become undefined.
         Under the rebuild copyback become maintenance."
    ::= { fjdaryDiskEntry 6 }

fjdaryDiskPlun OBJECT-TYPE
    SYNTAX INTEGER(-2147483648..2147483647)
    ACCESS read-only
    STATUS mandatory
    DESCRIPTION
        "The value of this object indicates the PLUN of this DISK.
         the following definition:
           0xDDSS
             | |
             | +-slot number
             +-DE ID"
    ::= { fjdaryDiskEntry 7 }

fjdaryDiskPurpose OBJECT-TYPE
    SYNTAX INTEGER(-2147483648..2147483647)
    ACCESS read-only
    STATUS mandatory
    DESCRIPTION
        "The value of this object indicates the purpose of this DISK."
    ::= { fjdaryDiskEntry 8 }

fjdaryDiskType OBJECT-TYPE
    SYNTAX INTEGER(-2147483648..2147483647)
    ACCESS read-only
    STATUS mandatory
    DESCRIPTION
        "The value of this object indicates the type of this DISK."
    ::= { fjdaryDiskEntry 9 }

fjdaryDiskWwn OBJECT-TYPE
    SYNTAX OCTET STRING (SIZE (0..256))
    ACCESS read-only
    STATUS mandatory
    DESCRIPTION
        "The value of this object indicates the world wide name of this DISK."
    ::= { fjdaryDiskEntry 10 }

fjdaryDiskVenderId OBJECT-TYPE
    SYNTAX OCTET STRING (SIZE (0..256))
    ACCESS read-only
    STATUS mandatory
    DESCRIPTION
        "The value of this object indicates the vender of this DISK."
    ::= { fjdaryDiskEntry 11 }

fjdaryDiskProductId OBJECT-TYPE
    SYNTAX OCTET STRING (SIZE (0..256))
    ACCESS read-only
    STATUS mandatory
    DESCRIPTION
        "The value of this object indicates the product of this DISK."
    ::= { fjdaryDiskEntry 12 }

fjdaryDiskFwRevision OBJECT-TYPE
    SYNTAX OCTET STRING (SIZE (0..256))
    ACCESS read-only
    STATUS mandatory
    DESCRIPTION
        "The value of this object indicates the firmware revision of this
         DISK."
    ::= { fjdaryDiskEntry 13 }

fjdaryDiskDateCode OBJECT-TYPE
    SYNTAX OCTET STRING (SIZE (0..256))
    ACCESS read-only
    STATUS mandatory
    DESCRIPTION
        "The value of this object indicates the date code of this DISK."
    ::= { fjdaryDiskEntry 14 }

fjdaryDiskCfgRevision OBJECT-TYPE
    SYNTAX OCTET STRING (SIZE (0..256))
    ACCESS read-only
    STATUS mandatory
    DESCRIPTION
        "The value of this object indicates the configuration revision of this
         DISK."
    ::= { fjdaryDiskEntry 15 }

fjdaryDiskSize OBJECT-TYPE
    SYNTAX INTEGER(-2147483648..2147483647)
    ACCESS read-only
    STATUS mandatory
    DESCRIPTION
        "This shows disk capacity. The unit is GB."
    ::= { fjdaryDiskEntry 16 }

-------------------------------------------------------------------------------
--   fjdaryLanport                                                           --
-------------------------------------------------------------------------------
fjdaryLanportCount OBJECT-TYPE
    SYNTAX INTEGER(0..2147483647)
    ACCESS read-only
    STATUS mandatory
    DESCRIPTION
        "The number of LAN port's informations
         (regardless of theier current state) present on this system."
    ::= { fjdaryLanport 1 }

fjdaryLanportTable OBJECT-TYPE
    SYNTAX SEQUENCE OF FjdaryLanportEntry
    ACCESS not-accessible
    STATUS mandatory
    DESCRIPTION
        ""
    ::= { fjdaryLanport 2 }

fjdaryLanportEntry OBJECT-TYPE
    SYNTAX FjdaryLanportEntry
    ACCESS not-accessible
    STATUS mandatory
    DESCRIPTION
        ""
    INDEX { fjdaryLanportIndex }
    ::= { fjdaryLanportTable 1 }

FjdaryLanportEntry ::=
    SEQUENCE{
        fjdaryLanportIndex   INTEGER,
        fjdaryLanportStatus0 INTEGER,
        fjdaryLanportStatus1 INTEGER,
        fjdaryLanportStatus2 INTEGER
    }

fjdaryLanportIndex OBJECT-TYPE
    SYNTAX INTEGER(0..2147483647)
    ACCESS read-only
    STATUS mandatory
    DESCRIPTION
        "The value of this object uniquely identifies this fjdaryLanport
         entry. The number of the unit that mounts LAN port is shown."
    ::= { fjdaryLanportEntry 1 }

fjdaryLanportStatus0 OBJECT-TYPE
    SYNTAX INTEGER{
        linkup(1),
        undefined(4),
        linkdown(6),
        unknown(7)
    }
    ACCESS read-only
    STATUS mandatory
    DESCRIPTION
        "The value of this object indicates the MNT port state.

         linkup      : Link up state
         undefined   : Undefined state
         linkdown    : Link down state
         unknown     : Unknown state"
    ::= { fjdaryLanportEntry 2 }

fjdaryLanportStatus1 OBJECT-TYPE
    SYNTAX INTEGER{
        linkup(1),
        undefined(4),
        linkdown(6),
        unknown(7)
    }
    ACCESS read-only
    STATUS mandatory
    DESCRIPTION
        "The value of this object indicates the RMT port state.

         linkup      : Link up state
         undefined   : Undefined state
         linkdown    : Link down state
         unknown     : Unknown state"
    ::= { fjdaryLanportEntry 3 }

fjdaryLanportStatus2 OBJECT-TYPE
    SYNTAX INTEGER{
        linkup(1),
        undefined(4),
        linkdown(6),
        unknown(7)
    }
    ACCESS read-only
    STATUS mandatory
    DESCRIPTION
        "The value of this object indicates the FST port state.

         linkup      : Link up state
         undefined   : Undefined state
         linkdown    : Link down state
         unknown     : Unknown state"
    ::= { fjdaryLanportEntry 4 }

fjdaryLanportHwAdTable OBJECT-TYPE
    SYNTAX SEQUENCE OF FjdaryLanportHwAdEntry
    ACCESS not-accessible
    STATUS mandatory
    DESCRIPTION
        ""
    ::= { fjdaryLanport 3 }

fjdaryLanportHwAdEntry OBJECT-TYPE
    SYNTAX FjdaryLanportHwAdEntry
    ACCESS not-accessible
    STATUS mandatory
    DESCRIPTION
        ""
    INDEX { fjdaryLanportHwAdIndex }
    ::= { fjdaryLanportHwAdTable 1 }

FjdaryLanportHwAdEntry ::=
    SEQUENCE{
        fjdaryLanportHwAdIndex  INTEGER,
        fjdaryLanportHwAddress0 PhysAddress,
        fjdaryLanportHwAddress1 PhysAddress,
        fjdaryLanportHwAddress2 PhysAddress
    }

fjdaryLanportHwAdIndex OBJECT-TYPE
    SYNTAX INTEGER(0..2147483647)
    ACCESS read-only
    STATUS mandatory
    DESCRIPTION
        "The value of this object uniquely identifies this fjdaryLanportHwAd
         entry. The number of the unit that mounts LAN port is shown."
    ::= { fjdaryLanportHwAdEntry 1 }

fjdaryLanportHwAddress0 OBJECT-TYPE
    SYNTAX PhysAddress
    ACCESS read-only
    STATUS mandatory
    DESCRIPTION
        "The value of this object indicates the MNT port's MAC address.
         If this value is not applicable, return all zero's."
    ::= { fjdaryLanportHwAdEntry 2 }

fjdaryLanportHwAddress1 OBJECT-TYPE
    SYNTAX PhysAddress
    ACCESS read-only
    STATUS mandatory
    DESCRIPTION
        "The value of this object indicates the RMT port's MAC address.
         If this value is not applicable, return all zero's."
    ::= { fjdaryLanportHwAdEntry 3 }

fjdaryLanportHwAddress2 OBJECT-TYPE
    SYNTAX PhysAddress
    ACCESS read-only
    STATUS mandatory
    DESCRIPTION
        "The value of this object indicates the FST port's MAC address.
         If this value is not applicable, return all zero's."
    ::= { fjdaryLanportHwAdEntry 4 }

-------------------------------------------------------------------------------
--   fjdaryFem                                                               --
-------------------------------------------------------------------------------
fjdaryFemCount OBJECT-TYPE
    SYNTAX INTEGER(0..2147483647)
    ACCESS read-only
    STATUS mandatory
    DESCRIPTION
        "The number of FEM's informations (regardless of their current state)
         present on this system."
    ::= { fjdaryFem 1 }

fjdaryFemTable OBJECT-TYPE
    SYNTAX SEQUENCE OF FjdaryFemEntry
    ACCESS not-accessible
    STATUS mandatory
    DESCRIPTION
        ""
    ::= { fjdaryFem 2 }

fjdaryFemEntry OBJECT-TYPE
    SYNTAX FjdaryFemEntry
    ACCESS not-accessible
    STATUS mandatory
    DESCRIPTION
        ""
    INDEX { fjdaryFemIndex }
    ::= { fjdaryFemTable 1 }

FjdaryFemEntry ::=
    SEQUENCE{
        fjdaryFemIndex          INTEGER,
        fjdaryFemItemId         INTEGER,
        fjdaryFemStatus         FjdaryComponentStatus,
        fjdaryFemSubStatus      FjdaryComponentStatus
    }

fjdaryFemIndex OBJECT-TYPE
    SYNTAX INTEGER(0..2147483647)
    ACCESS read-only
    STATUS mandatory
    DESCRIPTION
        "The value of this object uniquely identifies this fjdaryFem entry."
    ::= { fjdaryFemEntry 1 }

fjdaryFemItemId OBJECT-TYPE
    SYNTAX INTEGER(-2147483648..2147483647)
    ACCESS read-only
    STATUS mandatory
    DESCRIPTION
        "The value of this object indicates the identification number
         of this FEM.
         the following definition:
           0x0a00DD00
                 |
                 +-DE ID"
    ::= { fjdaryFemEntry 2 }

fjdaryFemStatus OBJECT-TYPE
    SYNTAX FjdaryComponentStatus
    ACCESS read-only
    STATUS mandatory
    DESCRIPTION
        "The value of this object indicates the state of this FEM.
         But, it doesn't become warning or alarm when maintaining it.
         (In the maintenance work, fjdaryMgtMaintenanceMode is on)"
    ::= { fjdaryFemEntry 3 }

fjdaryFemSubStatus OBJECT-TYPE
    SYNTAX FjdaryComponentStatus
    ACCESS read-only
    STATUS mandatory
    DESCRIPTION
        "The value of this object indicates the state of this FEM.
         It becomes warning and alarm while even maintaining it.
         (In the maintenance work, fjdaryMgtMaintenanceMode is on)"
    ::= { fjdaryFemEntry 4 }

-------------------------------------------------------------------------------
--   fjdaryPfm                                                               --
-------------------------------------------------------------------------------
fjdaryPfmCount OBJECT-TYPE
    SYNTAX INTEGER(0..2147483647)
    ACCESS read-only
    STATUS mandatory
    DESCRIPTION
        "The number of PFM's informations (regardless of their current state)
         present on this system."
    ::= { fjdaryPfm 1 }

fjdaryPfmTable OBJECT-TYPE
    SYNTAX SEQUENCE OF FjdaryPfmEntry
    ACCESS not-accessible
    STATUS mandatory
    DESCRIPTION
        ""
    ::= { fjdaryPfm 2 }

fjdaryPfmEntry OBJECT-TYPE
    SYNTAX FjdaryPfmEntry
    ACCESS not-accessible
    STATUS mandatory
    DESCRIPTION
        ""
    INDEX { fjdaryPfmIndex }
    ::= { fjdaryPfmTable 1 }

FjdaryPfmEntry ::=
    SEQUENCE{
        fjdaryPfmIndex          INTEGER,
        fjdaryPfmItemId         INTEGER,
        fjdaryPfmStatus         FjdaryComponentStatus,
        fjdaryPfmSubStatus      FjdaryComponentStatus
    }

fjdaryPfmIndex OBJECT-TYPE
    SYNTAX INTEGER(0..2147483647)
    ACCESS read-only
    STATUS mandatory
    DESCRIPTION
        "The value of this object uniquely identifies this fjdaryPfm entry."
    ::= { fjdaryPfmEntry 1 }

fjdaryPfmItemId OBJECT-TYPE
    SYNTAX INTEGER(-2147483648..2147483647)
    ACCESS read-only
    STATUS mandatory
    DESCRIPTION
        "The value of this object indicates the identification number
         of this PFM.
         the following definition:
           0x7800MMSS
                 | |
                 | +-slot number
                 +-CM ModuleID"
    ::= { fjdaryPfmEntry 2 }

fjdaryPfmStatus OBJECT-TYPE
    SYNTAX FjdaryComponentStatus
    ACCESS read-only
    STATUS mandatory
    DESCRIPTION
        "The value of this object indicates the state of this PFM.
         But, it doesn't become warning or alarm when maintaining it.
         (In the maintenance work, fjdaryMgtMaintenanceMode is on)"
    ::= { fjdaryPfmEntry 3 }

fjdaryPfmSubStatus OBJECT-TYPE
    SYNTAX FjdaryComponentStatus
    ACCESS read-only
    STATUS mandatory
    DESCRIPTION
        "The value of this object indicates the state of this PFM.
         It becomes warning and alarm while even maintaining it.
         (In the maintenance work, fjdaryMgtMaintenanceMode is on)"
    ::= { fjdaryPfmEntry 4 }

--***************************************************************************--
--   Logical Configuration                                                   --
--***************************************************************************--
-------------------------------------------------------------------------------
--   fjdaryCaPort                                                            --
-------------------------------------------------------------------------------
fjdaryCaPortCount OBJECT-TYPE
    SYNTAX INTEGER(0..2147483647)
    ACCESS read-only
    STATUS mandatory
    DESCRIPTION
        "The number of CA port's informations
         (regardless of their current state) present on this system."
    ::= { fjdaryCaPort 1 }

fjdaryCaPortTable OBJECT-TYPE
    SYNTAX SEQUENCE OF FjdaryCaPortEntry
    ACCESS not-accessible
    STATUS mandatory
    DESCRIPTION
        ""
    ::= { fjdaryCaPort 2 }

fjdaryCaPortEntry OBJECT-TYPE
    SYNTAX FjdaryCaPortEntry
    ACCESS not-accessible
    STATUS mandatory
    DESCRIPTION
        ""
    INDEX { fjdaryCaPortIndex }
    ::= { fjdaryCaPortTable 1 }

FjdaryCaPortEntry ::=
    SEQUENCE{
        fjdaryCaPortIndex           INTEGER,
        fjdaryCaPortPortInfo        OCTET STRING,
        fjdaryCaPortiscsiInfo       OCTET STRING,
        fjdaryCaPortiscsiName       OCTET STRING,
        fjdaryCaPortiscsiAliasName  OCTET STRING,
        fjdaryCaPortiscsiIpAddress  IpAddress,
        fjdaryCaPortiscsiSubnetMask IpAddress,
        fjdaryCaPortiscsiIsnsServer IpAddress,
        fjdaryCaPortMode            INTEGER
    }

fjdaryCaPortIndex OBJECT-TYPE
    SYNTAX INTEGER(0..2147483647)
    ACCESS read-only
    STATUS mandatory
    DESCRIPTION
        "The value of this object uniquely identifies this fjdaryCaPort entry.
         Ascending order of fjdaryCaModuleId."
    ::= { fjdaryCaPortEntry 1 }

fjdaryCaPortPortInfo OBJECT-TYPE
    SYNTAX OCTET STRING (SIZE (0..256))
    ACCESS read-only
    STATUS mandatory
    DESCRIPTION
        "The value of this object indicates the CA port information.
         This information is a little endian.

                  byte 0       byte 1       byte 2       byte 3
              +------------+------------+------------+------------+
          0x00|Reserved                 |Factor      |Port No     |
              +------------+------------+------------+------------+
          0x04|Mapping     |CM CPU MID  |Reserved                 |
              | Table No   |            |                         |
              +------------+------------+------------+------------+
          0x08|Security    |Transfer    |Reserved    |CA Mode     |
              | Mode       | Rate       |            |            |
              +------------+------------+------------+------------+
          0x0c|Reserved                                           |
              :                                                   :
          0x1c|                                                   |
              +------------+------------+------------+------------+
          0x20|Host        |Method      |Loop ID     |Service     |
              | Connection |            |            | Class      |
              +------------+------------+------------+------------+
          0x24|FC Frame Size            |Reserved                 |
              +------------+------------+------------+------------+"
    ::= { fjdaryCaPortEntry 2 }

fjdaryCaPortiscsiInfo OBJECT-TYPE
    SYNTAX OCTET STRING (SIZE (0..256))
    ACCESS read-only
    STATUS mandatory
    DESCRIPTION
        "The value of this object indicates the CA port iscsi information.
         This information is a little endian.

                  byte 0       byte 1       byte 2       byte 3
              +------------+------------+------------+------------+
          0x00|iSCSI Flag                                         |
              +------------+------------+------------+------------+
          0x04|Reserved                                           |
              :                                                   :
          0x24|                                                   |
              +------------+------------+------------+------------+
          0x28|Valid       |Reserved                              |
              +------------+------------+------------+------------+
          0x2c|Reserved                                           |
              +------------+------------+------------+------------+"
    ::= { fjdaryCaPortEntry 3 }

fjdaryCaPortiscsiName OBJECT-TYPE
    SYNTAX OCTET STRING (SIZE (0..256))
    ACCESS read-only
    STATUS mandatory
    DESCRIPTION
        "The value of this object indicates an iscsi name of this CA port."
    ::= { fjdaryCaPortEntry 4 }

fjdaryCaPortiscsiAliasName OBJECT-TYPE
    SYNTAX OCTET STRING (SIZE (0..256))
    ACCESS read-only
    STATUS mandatory
    DESCRIPTION
        "The value of this object indicates an iscsi alias name of this CA
         port."
    ::= { fjdaryCaPortEntry 5 }

fjdaryCaPortiscsiIpAddress OBJECT-TYPE
    SYNTAX IpAddress
    ACCESS read-only
    STATUS mandatory
    DESCRIPTION
        "The value of this object indicates an iscsi ip address of this CA
         port."
    ::= { fjdaryCaPortEntry 6 }

fjdaryCaPortiscsiSubnetMask OBJECT-TYPE
    SYNTAX IpAddress
    ACCESS read-only
    STATUS mandatory
    DESCRIPTION
        "The value of this object indicates an iscsi subnet mask of this CA
         port."
    ::= { fjdaryCaPortEntry 7 }

fjdaryCaPortiscsiIsnsServer OBJECT-TYPE
    SYNTAX IpAddress
    ACCESS read-only
    STATUS mandatory
    DESCRIPTION
        "The value of this object indicates an isns server ip address of this
         CA port."
    ::= { fjdaryCaPortEntry 8 }

fjdaryCaPortMode OBJECT-TYPE
    SYNTAX INTEGER {
        ca(11),
        ra(12),
        cara(13),
        initiator(20)
    }
    ACCESS read-only
    STATUS mandatory
    DESCRIPTION
        "The value of this object indicates the mode of this CA port."
    ::= { fjdaryCaPortEntry 9 }

-------------------------------------------------------------------------------
--   fjdaryOlu                                                               --
-------------------------------------------------------------------------------
fjdaryOluCount OBJECT-TYPE
    SYNTAX INTEGER(0..2147483647)
    ACCESS read-only
    STATUS mandatory
    DESCRIPTION
        "The number of OLU's informations
         (regardless of their current state) present on this system."
    ::= { fjdaryOlu 1 }

fjdaryOluTable OBJECT-TYPE
    SYNTAX SEQUENCE OF FjdaryOluEntry
    ACCESS not-accessible
    STATUS mandatory
    DESCRIPTION
        ""
    ::= { fjdaryOlu 2 }

fjdaryOluEntry OBJECT-TYPE
    SYNTAX FjdaryOluEntry
    ACCESS not-accessible
    STATUS mandatory
    DESCRIPTION
        ""
    INDEX { fjdaryOluIndex }
    ::= { fjdaryOluTable 1 }

FjdaryOluEntry ::=
    SEQUENCE{
        fjdaryOluIndex     INTEGER,
        fjdaryOluInfoTable OCTET STRING
    }

fjdaryOluIndex OBJECT-TYPE
    SYNTAX INTEGER(0..2147483647)
    ACCESS read-only
    STATUS mandatory
    DESCRIPTION
        "The value of this object uniquely identifies this fjdaryOlu entry."
    ::= { fjdaryOluEntry 1 }

fjdaryOluInfoTable OBJECT-TYPE
    SYNTAX OCTET STRING (SIZE (0..256))
    ACCESS read-only
    STATUS mandatory
    DESCRIPTION
        "The value of this object indicates the OLU information.
         This information is a little endian.

                  byte 0       byte 1       byte 2       byte 3
              +------------+------------+------------+------------+
          0x00|OLU info#index*2 (96 bytes)                        |
              +------------+------------+------------+------------+
          0x60|OLU info#index*2+1 (96 bytes)                      |
              +------------+------------+------------+------------+

         OLU info#
                  byte 0       byte 1       byte 2       byte 3
              +------------+------------+------------+------------+
          0x00|OLUN                     |Status                   |
              +------------+------------+------------+------------+
          0x04|SLU Count   |Reserved    |Pool No                  |
              +------------+------------+------------+------------+
          0x08|Reserved                                           |
              :                                                   :
          0x14|                                                   |
              +------------+------------+------------+------------+
          0x18|SLUN 0x00                |SLUN 0x01                |
              +------------+------------+------------+------------+
              :                                                   :
              +------------+------------+------------+------------+
          0x34|SLUN 0x0E                |SLUN 0x0F                |
              +------------+------------+------------+------------+
          0x38|Reserved                                           |
              :                                                   :
          0x5c|                                                   |
              +------------+------------+------------+------------+"
    ::= { fjdaryOluEntry 2 }

-------------------------------------------------------------------------------
--   fjdarySlu                                                               --
-------------------------------------------------------------------------------
fjdarySluCount OBJECT-TYPE
    SYNTAX INTEGER(0..2147483647)
    ACCESS read-only
    STATUS mandatory
    DESCRIPTION
        "The number of SLU's informations
         (regardless of their current state) present on this system."
    ::= { fjdarySlu 1 }

fjdarySluTable OBJECT-TYPE
    SYNTAX SEQUENCE OF FjdarySluEntry
    ACCESS not-accessible
    STATUS mandatory
    DESCRIPTION
        ""
    ::= { fjdarySlu 2 }

fjdarySluEntry OBJECT-TYPE
    SYNTAX FjdarySluEntry
    ACCESS not-accessible
    STATUS mandatory
    DESCRIPTION
        ""
    INDEX { fjdarySluIndex }
    ::= { fjdarySluTable 1 }

FjdarySluEntry ::=
    SEQUENCE{
        fjdarySluIndex     INTEGER,
        fjdarySluInfoTable OCTET STRING
    }

fjdarySluIndex OBJECT-TYPE
    SYNTAX INTEGER(0..2147483647)
    ACCESS read-only
    STATUS mandatory
    DESCRIPTION
        "The value of this object uniquely identifies this fjdarySlu entry."
    ::= { fjdarySluEntry 1 }

fjdarySluInfoTable OBJECT-TYPE
    SYNTAX OCTET STRING (SIZE (0..256))
    ACCESS read-only
    STATUS mandatory
    DESCRIPTION
        "The value of this object indicates the SLU information.
         Part of raid group or the entire volume is shown.
         This information is a little endian.

                  byte 0       byte 1       byte 2       byte 3
              +------------+------------+------------+------------+
          0x00|SLUN                     |Status                   |
              +------------+------------+------------+------------+
          0x04|LU Type     |Reserved                              |
              +------------+------------+------------+------------+
          0x08|RLUN                     |Temporary RLUN           |
              +------------+------------+------------+------------+
          0x0c|MLUN                     |OLUN                     |
              +------------+------------+------------+------------+
          0x10|Reserved                                           |
              :                                                   :
          0x1c|                                                   |
              +------------+------------+------------+------------+
          0x20|Start RLBA                                         |
              +                                                   +
          0x24|                                                   |
              +------------+------------+------------+------------+
          0x28|Temporary Start RLBA                               |
              +                                                   +
          0x2c|                                                   |
              +------------+------------+------------+------------+
          0x30|Start OLBA                                         |
              +                                                   +
          0x34|                                                   |
              +------------+------------+------------+------------+
          0x38|OLBA Count                                         |
              +                                                   +
          0x3c|                                                   |
              +------------+------------+------------+------------+
          0x40|SLBA Count                                         |
              +                                                   +
          0x44|                                                   |
              +------------+------------+------------+------------+
          0x48|Temporary SLBA Count                               |
              +                                                   +
          0x4c|                                                   |
              +------------+------------+------------+------------+
          0x50|Start SLBA for OLU                                 |
              +                                                   +
          0x54|                                                   |
              +------------+------------+------------+------------+
          0x58|SLBA Count for OLU                                 |
              +                                                   +
          0x5c|                                                   |
              +------------+------------+------------+------------+
          0x60|Virtual OLBA Count                                 |
              +                                                   +
          0x64|                                                   |
              +------------+------------+------------+------------+
          0x68|Reserved                                           |
              :                                                   :
          0xac|                                                   |
              +------------+------------+------------+------------+"
    ::= { fjdarySluEntry 2 }

-------------------------------------------------------------------------------
--   fjdaryRlu                                                               --
-------------------------------------------------------------------------------
fjdaryRluCount OBJECT-TYPE
    SYNTAX INTEGER(0..2147483647)
    ACCESS read-only
    STATUS mandatory
    DESCRIPTION
        "The number of RLU's informations
         (regardless of their current state) present on this system."
    ::= { fjdaryRlu 1 }

fjdaryRluTable OBJECT-TYPE
    SYNTAX SEQUENCE OF FjdaryRluEntry
    ACCESS not-accessible
    STATUS mandatory
    DESCRIPTION
        ""
    ::= { fjdaryRlu 2 }

fjdaryRluEntry OBJECT-TYPE
    SYNTAX FjdaryRluEntry
    ACCESS not-accessible
    STATUS mandatory
    DESCRIPTION
        ""
    INDEX { fjdaryRluIndex }
    ::= { fjdaryRluTable 1 }

FjdaryRluEntry ::=
    SEQUENCE{
        fjdaryRluIndex      INTEGER,
        fjdaryRluInfoTable0 OCTET STRING,
        fjdaryRluInfoTable1 OCTET STRING,
        fjdaryRluInfoTable2 OCTET STRING,
        fjdaryRluInfoTable3 OCTET STRING
    }

fjdaryRluIndex OBJECT-TYPE
    SYNTAX INTEGER(0..2147483647)
    ACCESS read-only
    STATUS mandatory
    DESCRIPTION
        "The value of this object uniquely identifies this fjdaryRlu entry."
    ::= { fjdaryRluEntry 1 }

fjdaryRluInfoTable0 OBJECT-TYPE
    SYNTAX OCTET STRING (SIZE (0..256))
    ACCESS read-only
    STATUS mandatory
    DESCRIPTION
        "The value of this object indicates the RLU information.
         This information is a little endian.

                  byte 0       byte 1       byte 2       byte 3
              +------------+------------+------------+------------+
          0x00|RLUN                     |Status                   |
              +------------+------------+------------+------------+
          0x04|Define      |Current     |Reserved                 |
              | CM CPU MID | CM CPU MID |                         |
              +------------+------------+------------+------------+
          0x08|RAID Level  |RLU Mode    |Blockade    |RLU Enable  |
              |            |            |            | Flag       |
              +------------+------------+------------+------------+
          0x0c|Reserved                 |Pool No                  |
              +------------+------------+------------+------------+
          0x10|RLBA Count                                         |
              +                                                   +
          0x14|                                                   |
              +------------+------------+------------+------------+
          0x18|Stripe Depth                                       |
              +------------+------------+------------+------------+
          0x1c|Stripe Size                                        |
              +------------+------------+------------+------------+
          0x20|Expanded RLUN            |Temporary RLUN           |
              +------------+------------+------------+------------+
          0x24|Reserved                                           |
              :                                                   :
          0x2c|                                                   |
              +------------+------------+------------+------------+
          0x30|SLU Count   |Reserved                              |
              +------------+------------+------------+------------+"
    ::= { fjdaryRluEntry 2 }

fjdaryRluInfoTable1 OBJECT-TYPE
    SYNTAX OCTET STRING (SIZE (0..256))
    ACCESS read-only
    STATUS mandatory
    DESCRIPTION
        "The value of this object indicates the RLU information.
         This information is a little endian.

                  byte 0       byte 1       byte 2       byte 3
              +------------+------------+------------+------------+
          0x00|SLUN 0x00                |SLUN 0x01                |
              +------------+------------+------------+------------+
              :                                                   :
              +------------+------------+------------+------------+
          0xfc|SLUN 0x7E                |SLUN 0x7F                |
              +------------+------------+------------+------------+"
    ::= { fjdaryRluEntry 3 }

fjdaryRluInfoTable2 OBJECT-TYPE
    SYNTAX OCTET STRING (SIZE (0..256))
    ACCESS read-only
    STATUS mandatory
    DESCRIPTION
        "The value of this object indicates the RLU information.
         This information is a little endian.

                  byte 0       byte 1       byte 2       byte 3
              +------------+------------+------------+------------+
          0x00|SLUN 0x80                |SLUN 0x81                |
              +------------+------------+------------+------------+
              :                                                   :
              +------------+------------+------------+------------+
          0xfc|SLUN 0xFE                |Reserved                 |
              +------------+------------+------------+------------+"
    ::= { fjdaryRluEntry 4 }

fjdaryRluInfoTable3 OBJECT-TYPE
    SYNTAX OCTET STRING (SIZE (0..256))
    ACCESS read-only
    STATUS mandatory
    DESCRIPTION
        "The value of this object indicates the RLU information.
         This information is a little endian.

                  byte 0       byte 1       byte 2       byte 3
              +------------+------------+------------+------------+
          0x00|Member Disk |Reserved                              |
              | Count      |                                      |
              +------------+------------+------------+------------+
          0x04|DLUN 0x00                |DLUN 0x01                |
              +------------+------------+------------+------------+
              :                                                   :
              +------------+------------+------------+------------+
          0x20|DLUN 0x0E                |DLUN 0x0F                |
              +------------+------------+------------+------------+"
    ::= { fjdaryRluEntry 5 }

-------------------------------------------------------------------------------
--   fjdaryDlu                                                               --
-------------------------------------------------------------------------------
fjdaryDluCount OBJECT-TYPE
    SYNTAX INTEGER(0..2147483647)
    ACCESS read-only
    STATUS mandatory
    DESCRIPTION
        "The number of DLU's informations
         (regardless of their current state) present on this system."
    ::= { fjdaryDlu 1 }

fjdaryDluTable OBJECT-TYPE
    SYNTAX SEQUENCE OF FjdaryDluEntry
    ACCESS not-accessible
    STATUS mandatory
    DESCRIPTION
        ""
    ::= { fjdaryDlu 2 }

fjdaryDluEntry OBJECT-TYPE
    SYNTAX FjdaryDluEntry
    ACCESS not-accessible
    STATUS mandatory
    DESCRIPTION
        ""
    INDEX { fjdaryDluIndex }
    ::= { fjdaryDluTable 1 }

FjdaryDluEntry ::=
    SEQUENCE{
        fjdaryDluIndex     INTEGER,
        fjdaryDluInfoTable OCTET STRING
    }

fjdaryDluIndex OBJECT-TYPE
    SYNTAX INTEGER(0..2147483647)
    ACCESS read-only
    STATUS mandatory
    DESCRIPTION
        "The value of this object uniquely identifies this fjdaryDlu entry."
    ::= { fjdaryDluEntry 1 }

fjdaryDluInfoTable OBJECT-TYPE
    SYNTAX OCTET STRING (SIZE (0..256))
    ACCESS read-only
    STATUS mandatory
    DESCRIPTION
        "The value of this object indicates the DLU information.
         Information to relate RLU to DISK is shown.
         This information is a little endian.

                  byte 0       byte 1       byte 2       byte 3
              +------------+------------+------------+------------+
          0x00|DLUN                     |Status                   |
              +------------+------------+------------+------------+
          0x04|RLUN                     |Member Disk |Reserved    |
              |                         | Number     |            |
              +------------+------------+------------+------------+
          0x08|Start DLBA                                         |
              +                                                   +
          0x0c|                                                   |
              +------------+------------+------------+------------+
          0x10|Block Count                                        |
              +                                                   +
          0x14|                                                   |
              +------------+------------+------------+------------+
          0x18|Stripe Depth                                       |
              +------------+------------+------------+------------+
          0x1c|Stripe Size                                        |
              +------------+------------+------------+------------+
          0x20|Member Disk |Reserved                              |
              | Count      |                                      |
              +------------+------------+------------+------------+
          0x24|Reserved                                           |
              :                                                   :
          0x2c|                                                   |
              +------------+------------+------------+------------+
          0x30|PLU in Use 0x00          |PLU in Use 0x01          |
              +------------+------------+------------+------------+
              :                                                   :
              +------------+------------+------------+------------+
          0x6c|PLU in Use 0x1E          |PLU in Use 0x1F          |
              +------------+------------+------------+------------+
          0x70|Defined PLU 0x00         |Defined PLU 0x01         |
              +------------+------------+------------+------------+
              :                                                   :
              +------------+------------+------------+------------+
          0xac|Defined PLU 0x1E         |Defined PLU 0x1F         |
              +------------+------------+------------+------------+"
    ::= { fjdaryDluEntry 2 }

-------------------------------------------------------------------------------
--   fjdaryMlu                                                               --
-------------------------------------------------------------------------------
fjdaryMluCount OBJECT-TYPE
    SYNTAX INTEGER(0..2147483647)
    ACCESS read-only
    STATUS mandatory
    DESCRIPTION
        "The number of MLU's informations
         (regardless of their current state) present on this system."
    ::= { fjdaryMlu 1 }

fjdaryMluTable OBJECT-TYPE
    SYNTAX SEQUENCE OF FjdaryMluEntry
    ACCESS not-accessible
    STATUS mandatory
    DESCRIPTION
        ""
    ::= { fjdaryMlu 2 }

fjdaryMluEntry OBJECT-TYPE
    SYNTAX FjdaryMluEntry
    ACCESS not-accessible
    STATUS mandatory
    DESCRIPTION
        ""
    INDEX { fjdaryMluIndex }
    ::= { fjdaryMluTable 1 }

FjdaryMluEntry ::=
    SEQUENCE{
        fjdaryMluIndex     INTEGER,
        fjdaryMluInfoTable OCTET STRING
    }

fjdaryMluIndex OBJECT-TYPE
    SYNTAX INTEGER(0..2147483647)
    ACCESS read-only
    STATUS mandatory
    DESCRIPTION
        "The value of this object uniquely identifies this fjdaryMlu entry."
    ::= { fjdaryMluEntry 1 }

fjdaryMluInfoTable OBJECT-TYPE
    SYNTAX OCTET STRING (SIZE (0..256))
    ACCESS read-only
    STATUS mandatory
    DESCRIPTION
        "The value of this object indicates the MLU information.
         This information is a little endian.

                  byte 0       byte 1       byte 2       byte 3
              +------------+------------+------------+------------+
          0x00|MLU info#index*5 (48 bytes)                        |
              +------------+------------+------------+------------+
          0x30|MLU info#index*5+1 (48 bytes)                      |
              +------------+------------+------------+------------+
          0x60|MLU info#index*5+2 (48 bytes)                      |
              +------------+------------+------------+------------+
          0x90|MLU info#index*5+3 (48 bytes)                      |
              +------------+------------+------------+------------+
          0xc0|MLU info#index*5+4 (48 bytes)                      |
              +------------+------------+------------+------------+

         MLU info#
                  byte 0       byte 1       byte 2       byte 3
              +------------+------------+------------+------------+
          0x00|MLUN                     |Status                   |
              +------------+------------+------------+------------+
          0x04|Type Index  |MLU Mode    |Reserved                 |
              +------------+------------+------------+------------+
          0x08|SLUN                     |Reserved                 |
              +------------+------------+------------+------------+
          0x0c|MLBA Count                                         |
              +------------+------------+------------+------------+
          0x10|Reserved                                           |
              :                                                   :
          0x2c|                                                   |
              +------------+------------+------------+------------+"
    ::= { fjdaryMluEntry 2 }

-------------------------------------------------------------------------------
--   fjdaryOpenmap                                                           --
-------------------------------------------------------------------------------
fjdaryOpenmapCount OBJECT-TYPE
    SYNTAX INTEGER(0..2147483647)
    ACCESS read-only
    STATUS mandatory
    DESCRIPTION
        "The number of open volume mapping table's informations
         (regardless of their current state) present on this system."
    ::= { fjdaryOpenmap 1 }

fjdaryOpenmapTable OBJECT-TYPE
    SYNTAX SEQUENCE OF FjdaryOpenmapEntry
    ACCESS not-accessible
    STATUS mandatory
    DESCRIPTION
        ""
    ::= { fjdaryOpenmap 2 }

fjdaryOpenmapEntry OBJECT-TYPE
    SYNTAX FjdaryOpenmapEntry
    ACCESS not-accessible
    STATUS mandatory
    DESCRIPTION
        ""
    INDEX { fjdaryOpenmapIndex }
    ::= { fjdaryOpenmapTable 1 }

FjdaryOpenmapEntry ::=
    SEQUENCE{
        fjdaryOpenmapIndex      INTEGER,
        fjdaryOpenmapInfo       OCTET STRING,
        fjdaryOpenmapHostTable0 OCTET STRING,
        fjdaryOpenmapHostTable1 OCTET STRING,
        fjdaryOpenmapHostTable2 OCTET STRING,
        fjdaryOpenmapHostTable3 OCTET STRING,
        fjdaryOpenmapHostTable4 OCTET STRING,
        fjdaryOpenmapHostTable5 OCTET STRING,
        fjdaryOpenmapHostTable6 OCTET STRING,
        fjdaryOpenmapHostTable7 OCTET STRING
    }

fjdaryOpenmapIndex OBJECT-TYPE
    SYNTAX INTEGER(0..2147483647)
    ACCESS read-only
    STATUS mandatory
    DESCRIPTION
        "The value of this object uniquely identifies this fjdaryOpenmap
         entry."
    ::= { fjdaryOpenmapEntry 1 }

fjdaryOpenmapInfo OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Map No      |Reserved    |CA MID      |Port No     |
              +------------+------------+------------+------------+
          0x04|LUN Mapping No           |Valid Count              |
              +------------+------------+------------+------------+
          0x08|Reserved                                           |
              :                                                   :
          0x1c|                                                   |
              +------------+------------+------------+------------+"
    ::= { fjdaryOpenmapEntry 2 }

fjdaryOpenmapHostTable0 OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Host 0x00                |Affinity Grp 0x00        |
              +------------+------------+------------+------------+
          0x04|Enable      |Reserved                              |
              | Access     |                                      |
              +------------+------------+------------+------------+
              :                                                   :
              +------------+------------+------------+------------+
          0xf8|Host 0x1F                |Affinity Grp 0x1F        |
              +------------+------------+------------+------------+
          0xfc|Enable      |Reserved                              |
              | Access     |                                      |
              +------------+------------+------------+------------+"
    ::= { fjdaryOpenmapEntry 3 }

fjdaryOpenmapHostTable1 OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Host 0x20                |Affinity Grp 0x20        |
              +------------+------------+------------+------------+
          0x04|Enable      |Reserved                              |
              | Access     |                                      |
              +------------+------------+------------+------------+
              :                                                   :
              +------------+------------+------------+------------+
          0xf8|Host 0x3F                |Affinity Grp 0x3F        |
              +------------+------------+------------+------------+
          0xfc|Enable      |Reserved                              |
              | Access     |                                      |
              +------------+------------+------------+------------+"
    ::= { fjdaryOpenmapEntry 4 }

fjdaryOpenmapHostTable2 OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Host 0x40                |Affinity Grp 0x40        |
              +------------+------------+------------+------------+
          0x04|Enable      |Reserved                              |
              | Access     |                                      |
              +------------+------------+------------+------------+
              :                                                   :
              +------------+------------+------------+------------+
          0xf8|Host 0x5F                |Affinity Grp 0x5F        |
              +------------+------------+------------+------------+
          0xfc|Enable      |Reserved                              |
              | Access     |                                      |
              +------------+------------+------------+------------+"
    ::= { fjdaryOpenmapEntry 5 }

fjdaryOpenmapHostTable3 OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Host 0x60                |Affinity Grp 0x60        |
              +------------+------------+------------+------------+
          0x04|Enable      |Reserved                              |
              | Access     |                                      |
              +------------+------------+------------+------------+
              :                                                   :
              +------------+------------+------------+------------+
          0xf8|Host 0x7F                |Affinity Grp 0x7F        |
              +------------+------------+------------+------------+
          0xfc|Enable      |Reserved                              |
              | Access     |                                      |
              +------------+------------+------------+------------+"
    ::= { fjdaryOpenmapEntry 6 }

fjdaryOpenmapHostTable4 OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Host 0x80                |Affinity Grp 0x80        |
              +------------+------------+------------+------------+
          0x04|Enable      |Reserved                              |
              | Access     |                                      |
              +------------+------------+------------+------------+
              :                                                   :
              +------------+------------+------------+------------+
          0xf8|Host 0x9F                |Affinity Grp 0x9F        |
              +------------+------------+------------+------------+
          0xfc|Enable      |Reserved                              |
              | Access     |                                      |
              +------------+------------+------------+------------+"
    ::= { fjdaryOpenmapEntry 7 }

fjdaryOpenmapHostTable5 OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Host 0xA0                |Affinity Grp 0xA0        |
              +------------+------------+------------+------------+
          0x04|Enable      |Reserved                              |
              | Access     |                                      |
              +------------+------------+------------+------------+
              :                                                   :
              +------------+------------+------------+------------+
          0xf8|Host 0xBF                |Affinity Grp 0xBF        |
              +------------+------------+------------+------------+
          0xfc|Enable      |Reserved                              |
              | Access     |                                      |
              +------------+------------+------------+------------+"
    ::= { fjdaryOpenmapEntry 8 }

fjdaryOpenmapHostTable6 OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Host 0xC0                |Affinity Grp 0xC0        |
              +------------+------------+------------+------------+
          0x04|Enable      |Reserved                              |
              | Access     |                                      |
              +------------+------------+------------+------------+
              :                                                   :
              +------------+------------+------------+------------+
          0xf8|Host 0xDF                |Affinity Grp 0xDF        |
              +------------+------------+------------+------------+
          0xfc|Enable      |Reserved                              |
              | Access     |                                      |
              +------------+------------+------------+------------+"
    ::= { fjdaryOpenmapEntry 9 }

fjdaryOpenmapHostTable7 OBJECT-TYPE
    SYNTAX OCTET STRING (SIZE (0..256))
    ACCESS read-only
    STATUS mandatory
    DESCRIPTION
        "The value of this object indicates the open volume mapping table
         information.
         This information is a little endian.

                  byte 0       byte 1       byte 2       byte 3
              +------------+------------+------------+------------+
          0x00|Host 0xE0                |Affinity Grp 0xE0        |
              +------------+------------+------------+------------+
          0x04|Enable      |Reserved                              |
              | Access     |                                      |
              +------------+------------+------------+------------+
              :                                                   :
              +------------+------------+------------+------------+
          0xf8|Host 0xFF                |Affinity Grp 0xFF        |
              +------------+------------+------------+------------+
          0xfc|Enable      |Reserved                              |
              | Access     |                                      |
              +------------+------------+------------+------------+"
    ::= { fjdaryOpenmapEntry 10 }

-------------------------------------------------------------------------------
--   fjdaryLunmap                                                            --
-------------------------------------------------------------------------------
fjdaryLunmapCount OBJECT-TYPE
    SYNTAX INTEGER(0..2147483647)
    ACCESS read-only
    STATUS mandatory
    DESCRIPTION
        "The number of LUN mapping table's informations
         (regardless of their current state) present on this system."
    ::= { fjdaryLunmap 1 }

fjdaryLunmapTable OBJECT-TYPE
    SYNTAX SEQUENCE OF FjdaryLunmapEntry
    ACCESS not-accessible
    STATUS mandatory
    DESCRIPTION
        ""
    ::= { fjdaryLunmap 2 }

fjdaryLunmapEntry OBJECT-TYPE
    SYNTAX FjdaryLunmapEntry
    ACCESS not-accessible
    STATUS mandatory
    DESCRIPTION
        ""
    INDEX { fjdaryLunmapIndex }
    ::= { fjdaryLunmapTable 1 }

FjdaryLunmapEntry ::=
    SEQUENCE{
        fjdaryLunmapIndex  INTEGER,
        fjdaryLunmapInfo   OCTET STRING,
        fjdaryLunmapTable0 OCTET STRING,
        fjdaryLunmapTable1 OCTET STRING,
        fjdaryLunmapTable2 OCTET STRING,
        fjdaryLunmapTable3 OCTET STRING
    }

fjdaryLunmapIndex OBJECT-TYPE
    SYNTAX INTEGER(0..2147483647)
    ACCESS read-only
    STATUS mandatory
    DESCRIPTION
        "The value of this object uniquely identifies this fjdaryLunmap entry."
    ::= { fjdaryLunmapEntry 1 }

fjdaryLunmapInfo OBJECT-TYPE
    SYNTAX OCTET STRING (SIZE (0..256))
    ACCESS read-only
    STATUS mandatory
    DESCRIPTION
        "The value of this object indicates the LUN mapping table information.
         This information is a little endian.

                  byte 0       byte 1       byte 2       byte 3
              +------------+------------+------------+------------+
          0x00|LUN Map Number           |Definition  |Reserved    |
              +------------+------------+------------+------------+
          0x04|LUN Map Name                                       |
              :                                                   :
          0x10|                                                   |
              +------------+------------+------------+------------+
          0x14|Host Response Table No   |Reserved                 |
              +------------+------------+------------+------------+
          0x18|Reserved                                           |
              +                                                   +
          0x1c|                                                   |
              +------------+------------+------------+------------+"
    ::= { fjdaryLunmapEntry 2 }

fjdaryLunmapTable0 OBJECT-TYPE
    SYNTAX OCTET STRING (SIZE (0..256))
    ACCESS read-only
    STATUS mandatory
    DESCRIPTION
        "The value of this object indicates the LUN mapping table information.
         This information is a little endian.

                  byte 0       byte 1       byte 2       byte 3
              +------------+------------+------------+------------+
          0x00|LUN#000-OLU#             |LUN#001-OLU#             |
              +------------+------------+------------+------------+
              :                                                   :
              +------------+------------+------------+------------+
          0xfc|LUN#126-OLU#             |LUN#127-OLU#             |
              +------------+------------+------------+------------+"
    ::= { fjdaryLunmapEntry 3 }

fjdaryLunmapTable1 OBJECT-TYPE
    SYNTAX OCTET STRING (SIZE (0..256))
    ACCESS read-only
    STATUS mandatory
    DESCRIPTION
        "The value of this object indicates the LUN mapping table information.
         This information is a little endian.

                  byte 0       byte 1       byte 2       byte 3
              +------------+------------+------------+------------+
          0x00|LUN#128-OLU#             |LUN#129-OLU#             |
              +------------+------------+------------+------------+
              :                                                   :
              +------------+------------+------------+------------+
          0xfc|LUN#254-OLU#             |LUN#255-OLU#             |
              +------------+------------+------------+------------+"
    ::= { fjdaryLunmapEntry 4 }

fjdaryLunmapTable2 OBJECT-TYPE
    SYNTAX OCTET STRING (SIZE (0..256))
    ACCESS read-only
    STATUS mandatory
    DESCRIPTION
        "The value of this object indicates the LUN mapping table information.
         This information is a little endian.

                  byte 0       byte 1       byte 2       byte 3
              +------------+------------+------------+------------+
          0x00|LUN#256-OLU#             |LUN#257-OLU#             |
              +------------+------------+------------+------------+
              :                                                   :
              +------------+------------+------------+------------+
          0xfc|LUN#382-OLU#             |LUN#383-OLU#             |
              +------------+------------+------------+------------+"
    ::= { fjdaryLunmapEntry 5 }

fjdaryLunmapTable3 OBJECT-TYPE
    SYNTAX OCTET STRING (SIZE (0..256))
    ACCESS read-only
    STATUS mandatory
    DESCRIPTION
        "The value of this object indicates the LUN mapping table information.
         This information is a little endian.

                  byte 0       byte 1       byte 2       byte 3
              +------------+------------+------------+------------+
          0x00|LUN#384-OLU#             |LUN#385-OLU#             |
              +------------+------------+------------+------------+
              :                                                   :
              +------------+------------+------------+------------+
          0xfc|LUN#510-OLU#             |LUN#511-OLU#             |
              +------------+------------+------------+------------+"
    ::= { fjdaryLunmapEntry 6 }

-------------------------------------------------------------------------------
--   fjdaryAffinityGrp                                                       --
-------------------------------------------------------------------------------
fjdaryAffinityGrpCount OBJECT-TYPE
    SYNTAX INTEGER(0..2147483647)
    ACCESS read-only
    STATUS mandatory
    DESCRIPTION
        "The number of affinity group table's informations
         (regardless of their current state) present on this system."
    ::= { fjdaryAffinityGrp 1 }

fjdaryAffinityGrpTable OBJECT-TYPE
    SYNTAX SEQUENCE OF FjdaryAffinityGrpEntry
    ACCESS not-accessible
    STATUS mandatory
    DESCRIPTION
        ""
    ::= { fjdaryAffinityGrp 2 }

fjdaryAffinityGrpEntry OBJECT-TYPE
    SYNTAX FjdaryAffinityGrpEntry
    ACCESS not-accessible
    STATUS mandatory
    DESCRIPTION
        ""
    INDEX { fjdaryAffinityGrpIndex }
    ::= { fjdaryAffinityGrpTable 1 }

FjdaryAffinityGrpEntry ::=
    SEQUENCE{
        fjdaryAffinityGrpIndex  INTEGER,
        fjdaryAffinityGrpInfo   OCTET STRING,
        fjdaryAffinityGrpTable0 OCTET STRING,
        fjdaryAffinityGrpTable1 OCTET STRING,
        fjdaryAffinityGrpTable2 OCTET STRING,
        fjdaryAffinityGrpTable3 OCTET STRING
    }

fjdaryAffinityGrpIndex OBJECT-TYPE
    SYNTAX INTEGER(0..2147483647)
    ACCESS read-only
    STATUS mandatory
    DESCRIPTION
        "The value of this object uniquely identifies this fjdaryAffinityGrp
         entry."
    ::= { fjdaryAffinityGrpEntry 1 }

fjdaryAffinityGrpInfo OBJECT-TYPE
    SYNTAX OCTET STRING (SIZE (0..256))
    ACCESS read-only
    STATUS mandatory
    DESCRIPTION
        "The value of this object indicates the affinity group table
         information.
         This information is a little endian.

                  byte 0       byte 1       byte 2       byte 3
              +------------+------------+------------+------------+
          0x00|Affinity Group Number    |Definition  |Reserved    |
              +------------+------------+------------+------------+
          0x04|Affinity Group Name                                |
              :                                                   :
          0x10|                                                   |
              +------------+------------+------------+------------+
          0x14|Previous Affinity Group  |Next Affinity Group      |
              | Number                  | Number                  |
              +------------+------------+------------+------------+
          0x18|Reserved                                           |
              +                                                   +
          0x1c|                                                   |
              +------------+------------+------------+------------+"
    ::= { fjdaryAffinityGrpEntry 2 }

fjdaryAffinityGrpTable0 OBJECT-TYPE
    SYNTAX OCTET STRING (SIZE (0..256))
    ACCESS read-only
    STATUS mandatory
    DESCRIPTION
        "The value of this object indicates the affinity group table
         information.
         This information is a little endian.

                  byte 0       byte 1       byte 2       byte 3
              +------------+------------+------------+------------+
          0x00|LUN#000-OLU#             |LUN#001-OLU#             |
              +------------+------------+------------+------------+
              :                                                   :
              +------------+------------+------------+------------+
          0xfc|LUN#126-OLU#             |LUN#127-OLU#             |
              +------------+------------+------------+------------+"
    ::= { fjdaryAffinityGrpEntry 3 }

fjdaryAffinityGrpTable1 OBJECT-TYPE
    SYNTAX OCTET STRING (SIZE (0..256))
    ACCESS read-only
    STATUS mandatory
    DESCRIPTION
        "The value of this object indicates the affinity group table
         information.
         This information is a little endian.

                  byte 0       byte 1       byte 2       byte 3
              +------------+------------+------------+------------+
          0x00|LUN#128-OLU#             |LUN#129-OLU#             |
              +------------+------------+------------+------------+
              :                                                   :
              +------------+------------+------------+------------+
          0xfc|LUN#254-OLU#             |LUN#255-OLU#             |
              +------------+------------+------------+------------+"
    ::= { fjdaryAffinityGrpEntry 4 }

fjdaryAffinityGrpTable2 OBJECT-TYPE
    SYNTAX OCTET STRING (SIZE (0..256))
    ACCESS read-only
    STATUS mandatory
    DESCRIPTION
        "The value of this object indicates the affinity group table
         information.
         This information is a little endian.

                  byte 0       byte 1       byte 2       byte 3
              +------------+------------+------------+------------+
          0x00|LUN#256-OLU#             |LUN#257-OLU#             |
              +------------+------------+------------+------------+
              :                                                   :
              +------------+------------+------------+------------+
          0xfc|LUN#382-OLU#             |LUN#383-OLU#             |
              +------------+------------+------------+------------+"
    ::= { fjdaryAffinityGrpEntry 5 }

fjdaryAffinityGrpTable3 OBJECT-TYPE
    SYNTAX OCTET STRING (SIZE (0..256))
    ACCESS read-only
    STATUS mandatory
    DESCRIPTION
        "The value of this object indicates the affinity group table
         information.
         This information is a little endian.

                  byte 0       byte 1       byte 2       byte 3
              +------------+------------+------------+------------+
          0x00|LUN#384-OLU#             |LUN#385-OLU#             |
              +------------+------------+------------+------------+
              :                                                   :
              +------------+------------+------------+------------+
          0xfc|LUN#510-OLU#             |LUN#511-OLU#             |
              +------------+------------+------------+------------+"
    ::= { fjdaryAffinityGrpEntry 6 }

-------------------------------------------------------------------------------
--   fjdaryHostwwn                                                           --
-------------------------------------------------------------------------------
fjdaryHostwwnCount OBJECT-TYPE
    SYNTAX INTEGER(0..2147483647)
    ACCESS read-only
    STATUS mandatory
    DESCRIPTION
        "The number of host wwn table's informations
         (regardless of their current state) present on this system."
    ::= { fjdaryHostwwn 1 }

fjdaryHostwwnTable OBJECT-TYPE
    SYNTAX SEQUENCE OF FjdaryHostwwnEntry
    ACCESS not-accessible
    STATUS mandatory
    DESCRIPTION
        ""
    ::= { fjdaryHostwwn 2 }

fjdaryHostwwnEntry OBJECT-TYPE
    SYNTAX FjdaryHostwwnEntry
    ACCESS not-accessible
    STATUS mandatory
    DESCRIPTION
        ""
    INDEX { fjdaryHostwwnIndex }
    ::= { fjdaryHostwwnTable 1 }

FjdaryHostwwnEntry ::=
    SEQUENCE{
        fjdaryHostwwnIndex INTEGER,
        fjdaryHostwwnWWN   OCTET STRING
    }

fjdaryHostwwnIndex OBJECT-TYPE
    SYNTAX INTEGER(0..2147483647)
    ACCESS read-only
    STATUS mandatory
    DESCRIPTION
        "The value of this object uniquely identifies this fjdaryHostwwn
         entry."
    ::= { fjdaryHostwwnEntry 1 }

fjdaryHostwwnWWN OBJECT-TYPE
    SYNTAX OCTET STRING (SIZE (0..256))
    ACCESS read-only
    STATUS mandatory
    DESCRIPTION
        "The value of this object indicates the host wwn table information.
         This information is a little endian.

                  byte 0       byte 1       byte 2       byte 3
              +------------+------------+------------+------------+
          0x00|Host WWN                                           |
              +                                                   +
          0x04|                                                   |
              +------------+------------+------------+------------+
          0x08|Host Response Table No   |Valid Flag  |Reserved    |
              +------------+------------+------------+------------+
          0x0c|Reserved                                           |
              :                                                   :
          0x1c|                                                   |
              +------------+------------+------------+------------+"
    ::= { fjdaryHostwwnEntry 2 }

-------------------------------------------------------------------------------
--   fjdaryResetpath                                                         --
-------------------------------------------------------------------------------
fjdaryResetpathCount OBJECT-TYPE
    SYNTAX INTEGER(0..2147483647)
    ACCESS read-only
    STATUS mandatory
    DESCRIPTION
        "The number of reset path group table's informations
         (regardless of their current state) present on this system."
    ::= { fjdaryResetpath 1 }

fjdaryResetpathTable OBJECT-TYPE
    SYNTAX SEQUENCE OF FjdaryResetpathEntry
    ACCESS not-accessible
    STATUS mandatory
    DESCRIPTION
        ""
    ::= { fjdaryResetpath 2 }

fjdaryResetpathEntry OBJECT-TYPE
    SYNTAX FjdaryResetpathEntry
    ACCESS not-accessible
    STATUS mandatory
    DESCRIPTION
        ""
    INDEX { fjdaryResetpathIndex }
    ::= { fjdaryResetpathTable 1 }

FjdaryResetpathEntry ::=
    SEQUENCE{
        fjdaryResetpathIndex INTEGER,
        fjdaryResetpathGroup OCTET STRING
    }

fjdaryResetpathIndex OBJECT-TYPE
    SYNTAX INTEGER(0..2147483647)
    ACCESS read-only
    STATUS mandatory
    DESCRIPTION
        "The value of this object uniquely identifies this fjdaryResetpath
         entry."
    ::= { fjdaryResetpathEntry 1 }

fjdaryResetpathGroup OBJECT-TYPE
    SYNTAX OCTET STRING (SIZE (0..256))
    ACCESS read-only
    STATUS  mandatory
    DESCRIPTION
        "The value of this object indicates the reset path group table
         information.

                  byte 0       byte 1       byte 2       byte 3
              +------------+------------+------------+------------+
          0x00|Reset Path Group (bitmap)                          |
              :                                                   :
          0x0c|                                                   |
              +------------+------------+------------+------------+

         Grouped CA is stored from bit0 in ascending order of
         fjdaryCaModuleId.
          bit   0: CA MID 0x40 Port#0
          bit   1: CA MID 0x40 Port#1
          bit   2: CA MID 0x41 Port#0
                        :
          bit 127: CA MID 0x7F Port#1

         The bit definition is as follows.
              +------------+------------+------------+------------+
          0x00|bit 7-0     |bit 15-8    |bit 23-16   |bit 31-24   |
              +------------+------------+------------+------------+
          0x04|bit 39-32   |bit 47-40   |bit 55-48   |bit 63-56   |
              +------------+------------+------------+------------+
          0x08|bit 71-64   |bit 79-72   |bit 87-80   |bit 95-88   |
              +------------+------------+------------+------------+
          0x0c|bit 103-96  |bit 111-104 |bit 119-112 |bit 127-120 |
              +------------+------------+------------+------------+"
    ::= { fjdaryResetpathEntry 2 }

-------------------------------------------------------------------------------
--   fjdaryHostiscsi                                                         --
-------------------------------------------------------------------------------
fjdaryHostiscsiCount OBJECT-TYPE
    SYNTAX INTEGER(0..2147483647)
    ACCESS read-only
    STATUS mandatory
    DESCRIPTION
        "The number of host iscsi informations
         (regardless of their current state) present on this system."
    ::= { fjdaryHostiscsi 1 }

fjdaryHostiscsiTable OBJECT-TYPE
    SYNTAX SEQUENCE OF FjdaryHostiscsiEntry
    ACCESS not-accessible
    STATUS mandatory
    DESCRIPTION
        ""
    ::= { fjdaryHostiscsi 2 }

fjdaryHostiscsiEntry OBJECT-TYPE
    SYNTAX FjdaryHostiscsiEntry
    ACCESS not-accessible
    STATUS mandatory
    DESCRIPTION
        ""
    INDEX { fjdaryHostiscsiIndex }
    ::= { fjdaryHostiscsiTable 1 }

FjdaryHostiscsiEntry ::=
    SEQUENCE{
        fjdaryHostiscsiIndex     INTEGER,
        fjdaryHostiscsiDefine    OCTET STRING,
        fjdaryHostiscsiName      OCTET STRING,
        fjdaryHostiscsiAliasName OCTET STRING,
        fjdaryHostiscsiIpAddress IpAddress
    }

fjdaryHostiscsiIndex OBJECT-TYPE
    SYNTAX INTEGER(0..2147483647)
    ACCESS read-only
    STATUS mandatory
    DESCRIPTION
        "The value of this object uniquely identifies this fjdaryHostiscsi
         entry."
    ::= { fjdaryHostiscsiEntry 1 }

fjdaryHostiscsiDefine OBJECT-TYPE
    SYNTAX OCTET STRING (SIZE (0..256))
    ACCESS read-only
    STATUS mandatory
    DESCRIPTION
        "The value of this object indicates the host iscsi information.
         This information is a little endian.

                  byte 0       byte 1       byte 2       byte 3
              +------------+------------+------------+------------+
          0x00|Valid Flag  |Reserved                              |
              +------------+------------+------------+------------+
          0x04|Reserved                                           |
              +------------+------------+------------+------------+
          0x08|Host Response Table No   |TCP Port No              |
              +------------+------------+------------+------------+"
    ::= { fjdaryHostiscsiEntry 2 }

fjdaryHostiscsiName OBJECT-TYPE
    SYNTAX OCTET STRING (SIZE (0..256))
    ACCESS read-only
    STATUS mandatory
    DESCRIPTION
        "The value of this object shows iscsi name of a host."
    ::= { fjdaryHostiscsiEntry 3 }

fjdaryHostiscsiAliasName OBJECT-TYPE
    SYNTAX OCTET STRING (SIZE (0..256))
    ACCESS read-only
    STATUS mandatory
    DESCRIPTION
        "The value of this object shows alias name of a host."
    ::= { fjdaryHostiscsiEntry 4 }

fjdaryHostiscsiIpAddress OBJECT-TYPE
    SYNTAX IpAddress
    ACCESS read-only
    STATUS mandatory
    DESCRIPTION
        "The value of this object shows ip address of a host."
    ::= { fjdaryHostiscsiEntry 5 }

-------------------------------------------------------------------------------
--   fjdaryHostResponse                                                      --
-------------------------------------------------------------------------------
fjdaryHostResponseCount OBJECT-TYPE
    SYNTAX INTEGER(0..2147483647)
    ACCESS read-only
    STATUS mandatory
    DESCRIPTION
        "The number of host response informations
         (regardless of their current state) present on this system."
    ::= { fjdaryHostResponse 1 }

fjdaryHostResponseTable OBJECT-TYPE
    SYNTAX SEQUENCE OF FjdaryHostResponseEntry
    ACCESS not-accessible
    STATUS mandatory
    DESCRIPTION
        ""
    ::= { fjdaryHostResponse 2 }

fjdaryHostResponseEntry OBJECT-TYPE
    SYNTAX FjdaryHostResponseEntry
    ACCESS not-accessible
    STATUS mandatory
    DESCRIPTION
        ""
    INDEX { fjdaryHostResponseIndex }
    ::= { fjdaryHostResponseTable 1 }

FjdaryHostResponseEntry ::=
    SEQUENCE{
        fjdaryHostResponseIndex     INTEGER,
        fjdaryHostResponseInfoTable OCTET STRING
    }

fjdaryHostResponseIndex OBJECT-TYPE
    SYNTAX INTEGER(0..2147483647)
    ACCESS read-only
    STATUS mandatory
    DESCRIPTION
        "The value of this object uniquely identifies this fjdaryHostResponse
         entry."
    ::= { fjdaryHostResponseEntry 1 }

fjdaryHostResponseInfoTable OBJECT-TYPE
    SYNTAX OCTET STRING (SIZE (0..256))
    ACCESS read-only
    STATUS mandatory
    DESCRIPTION
        "The value of this object indicates the host response information.
         This information is a little endian.

                  byte 0       byte 1       byte 2       byte 3
              +------------+------------+------------+------------+
          0x00|Table No                 |Valid Flag  |Reserved    |
              +------------+------------+------------+------------+
          0x04|Reserved                                           |
              :                                                   :
          0x14|                                                   |
              +------------+------------+------------+------------+
          0x18|SCC Mode    |Host Command|Sense Control            |
              |            | Timeout    |                         |
              +------------+------------+------------+------------+
          0x1c|Ope Mode    |Ope Mode    | Reserved                |
              | Flag0      | Flag1      |                         |
              +------------+------------+------------+------------+
          0x20|Status      |Reserved                              |
              | Control    |                                      |
              +------------+------------+------------+------------+
          0x24|Reserved                                           |
              :                                                   :
          0x3c|                                                   |
              +------------+------------+------------+------------+
          0x40|Inquiry     |Inquiry     |Inquiry     |Reserved    |
              | Byte0 Mode | VPD ID Type| StdData Ver|            |
              +------------+------------+------------+------------+
          0x44|Reserved                                           |
              +------------+------------+------------+------------+
          0x48|Entry       |Entry       |Entry       |Entry       |
              | Sense Key  | Sense Code | Sub Sense  | Convert Bit|
              |            |            | Code       |            |
              +------------+------------+------------+------------+
          0x4c|Report      |Report      |Report      |Report      |
              | Sense Key  | Sense Code | Sub Sense  | Convert Bit|
              |            |            | Code       |            |
              +------------+------------+------------+------------+
              :                                                   :
              +------------+------------+------------+------------+
          0x80|Entry       |Entry       |Entry       |Entry       |
              | Sense Key  | Sense Code | Sub Sense  | Convert Bit|
              |            |            | Code       |            |
              +------------+------------+------------+------------+
          0x84|Report      |Report      |Report      |Report      |
              | Sense Key  | Sense Code | Sub Sense  | Convert Bit|
              |            |            | Code       |            |
              +------------+------------+------------+------------+
          0x88|Reserved                                           |
              +                                                   +
          0x8c|                                                   |
              +------------+------------+------------+------------+"
    ::= { fjdaryHostResponseEntry 2 }

--***************************************************************************--
--   Sensor Information                                                      --
--***************************************************************************--
-------------------------------------------------------------------------------
--   fjdaryMachinePower                                                      --
-------------------------------------------------------------------------------
fjdaryMachinePowerCount OBJECT-TYPE
    SYNTAX INTEGER(0..2147483647)
    ACCESS read-only
    STATUS mandatory
    DESCRIPTION
        "The number of power consumption information table's entry on this
         machine."
    ::= { fjdaryMachinePower 1 }

fjdaryMachinePowerTable OBJECT-TYPE
    SYNTAX SEQUENCE OF FjdaryMachinePowerEntry
    ACCESS not-accessible
    STATUS mandatory
    DESCRIPTION
        ""
    ::= { fjdaryMachinePower 2 }

fjdaryMachinePowerEntry OBJECT-TYPE
    SYNTAX FjdaryMachinePowerEntry
    ACCESS not-accessible
    STATUS mandatory
    DESCRIPTION
        ""
    INDEX { fjdaryMachinePowerIndex }
    ::= { fjdaryMachinePowerTable 1 }

FjdaryMachinePowerEntry ::=
    SEQUENCE{
        fjdaryMachinePowerIndex  INTEGER,
        fjdaryMachinePowerFlag   INTEGER,
        fjdaryMachinePowerCmNum  INTEGER,
        fjdaryMachinePowerTime   INTEGER,
        fjdaryMachinePowerInfo0  INTEGER,
        fjdaryMachinePowerInfo1  INTEGER,
        fjdaryMachinePowerInfo2  INTEGER,
        fjdaryMachinePowerInfo3  INTEGER,
        fjdaryMachinePowerInfo4  INTEGER,
        fjdaryMachinePowerInfo5  INTEGER,
        fjdaryMachinePowerInfo6  INTEGER,
        fjdaryMachinePowerInfo7  INTEGER,
        fjdaryMachinePowerInfo8  INTEGER,
        fjdaryMachinePowerInfo9  INTEGER,
        fjdaryMachinePowerInfo10 INTEGER,
        fjdaryMachinePowerInfo11 INTEGER,
        fjdaryMachinePowerInfo12 INTEGER,
        fjdaryMachinePowerInfo13 INTEGER,
        fjdaryMachinePowerInfo14 INTEGER,
        fjdaryMachinePowerInfo15 INTEGER,
        fjdaryMachinePowerInfo16 INTEGER,
        fjdaryMachinePowerInfo17 INTEGER,
        fjdaryMachinePowerInfo18 INTEGER,
        fjdaryMachinePowerInfo19 INTEGER,
        fjdaryMachinePowerInfo20 INTEGER,
        fjdaryMachinePowerInfo21 INTEGER,
        fjdaryMachinePowerInfo22 INTEGER,
        fjdaryMachinePowerInfo23 INTEGER,
        fjdaryMachinePowerInfo24 INTEGER
    }

fjdaryMachinePowerIndex OBJECT-TYPE
    SYNTAX INTEGER(0..2147483647)
    ACCESS read-only
    STATUS mandatory
    DESCRIPTION
        "The value of this object uniquely identifies this fjdaryMachinePower
         entry."
    ::= { fjdaryMachinePowerEntry 1 }

fjdaryMachinePowerFlag OBJECT-TYPE
    SYNTAX INTEGER {
        invalid(255),
        updating(1),
        valid(2)
    }
    ACCESS read-only
    STATUS mandatory
    DESCRIPTION
        "The state of information concerned index is shown."
    ::= { fjdaryMachinePowerEntry 2 }

fjdaryMachinePowerCmNum OBJECT-TYPE
    SYNTAX INTEGER(-2147483648..2147483647)
    ACCESS read-only
    STATUS mandatory
    DESCRIPTION
        "CM number in which this information is gathered."
    ::= { fjdaryMachinePowerEntry 3 }

fjdaryMachinePowerTime OBJECT-TYPE
    SYNTAX INTEGER(-2147483648..2147483647)
    ACCESS read-only
    STATUS mandatory
    DESCRIPTION
        "Passage second when this information was gathered."
    ::= { fjdaryMachinePowerEntry 4 }

fjdaryMachinePowerInfo0 OBJECT-TYPE
    SYNTAX INTEGER(-2147483648..2147483647)
    ACCESS read-only
    STATUS mandatory
    DESCRIPTION
        "The average power consumption is shown during one hour in the past.
         The unit is Watt."
    ::= { fjdaryMachinePowerEntry 5 }

fjdaryMachinePowerInfo1 OBJECT-TYPE
    SYNTAX INTEGER(-2147483648..2147483647)
    ACCESS read-only
    STATUS mandatory
    DESCRIPTION
        "The average power consumption 1 hour ago is shown. The unit is Watt."
    ::= { fjdaryMachinePowerEntry 6 }

fjdaryMachinePowerInfo2 OBJECT-TYPE
    SYNTAX INTEGER(-2147483648..2147483647)
    ACCESS read-only
    STATUS mandatory
    DESCRIPTION
        "The average power consumption 2 hour ago is shown. The unit is Watt."
    ::= { fjdaryMachinePowerEntry 7 }

fjdaryMachinePowerInfo3 OBJECT-TYPE
    SYNTAX INTEGER(-2147483648..2147483647)
    ACCESS read-only
    STATUS mandatory
    DESCRIPTION
        "The average power consumption 3 hour ago is shown. The unit is Watt."
    ::= { fjdaryMachinePowerEntry 8 }

fjdaryMachinePowerInfo4 OBJECT-TYPE
    SYNTAX INTEGER(-2147483648..2147483647)
    ACCESS read-only
    STATUS mandatory
    DESCRIPTION
        "The average power consumption 4 hour ago is shown. The unit is Watt."
    ::= { fjdaryMachinePowerEntry 9 }

fjdaryMachinePowerInfo5 OBJECT-TYPE
    SYNTAX INTEGER(-2147483648..2147483647)
    ACCESS read-only
    STATUS mandatory
    DESCRIPTION
        "The average power consumption 5 hour ago is shown. The unit is Watt."
    ::= { fjdaryMachinePowerEntry 10 }

fjdaryMachinePowerInfo6 OBJECT-TYPE
    SYNTAX INTEGER(-2147483648..2147483647)
    ACCESS read-only
    STATUS mandatory
    DESCRIPTION
        "The average power consumption 6 hour ago is shown. The unit is Watt."
    ::= { fjdaryMachinePowerEntry 11 }

fjdaryMachinePowerInfo7 OBJECT-TYPE
    SYNTAX INTEGER(-2147483648..2147483647)
    ACCESS read-only
    STATUS mandatory
    DESCRIPTION
        "The average power consumption 7 hour ago is shown. The unit is Watt."
    ::= { fjdaryMachinePowerEntry 12 }

fjdaryMachinePowerInfo8 OBJECT-TYPE
    SYNTAX INTEGER(-2147483648..2147483647)
    ACCESS read-only
    STATUS mandatory
    DESCRIPTION
        "The average power consumption 8 hour ago is shown. The unit is Watt."
    ::= { fjdaryMachinePowerEntry 13 }

fjdaryMachinePowerInfo9 OBJECT-TYPE
    SYNTAX INTEGER(-2147483648..2147483647)
    ACCESS read-only
    STATUS mandatory
    DESCRIPTION
        "The average power consumption 9 hour ago is shown. The unit is Watt."
    ::= { fjdaryMachinePowerEntry 14 }

fjdaryMachinePowerInfo10 OBJECT-TYPE
    SYNTAX INTEGER(-2147483648..2147483647)
    ACCESS read-only
    STATUS mandatory
    DESCRIPTION
        "The average power consumption 10 hour ago is shown. The unit is Watt."
    ::= { fjdaryMachinePowerEntry 15 }

fjdaryMachinePowerInfo11 OBJECT-TYPE
    SYNTAX INTEGER(-2147483648..2147483647)
    ACCESS read-only
    STATUS mandatory
    DESCRIPTION
        "The average power consumption 11 hour ago is shown. The unit is Watt."
    ::= { fjdaryMachinePowerEntry 16 }

fjdaryMachinePowerInfo12 OBJECT-TYPE
    SYNTAX INTEGER(-2147483648..2147483647)
    ACCESS read-only
    STATUS mandatory
    DESCRIPTION
        "The average power consumption 12 hour ago is shown. The unit is Watt."
    ::= { fjdaryMachinePowerEntry 17 }

fjdaryMachinePowerInfo13 OBJECT-TYPE
    SYNTAX INTEGER(-2147483648..2147483647)
    ACCESS read-only
    STATUS mandatory
    DESCRIPTION
        "The average power consumption 13 hour ago is shown. The unit is Watt."
    ::= { fjdaryMachinePowerEntry 18 }

fjdaryMachinePowerInfo14 OBJECT-TYPE
    SYNTAX INTEGER(-2147483648..2147483647)
    ACCESS read-only
    STATUS mandatory
    DESCRIPTION
        "The average power consumption 14 hour ago is shown. The unit is Watt."
    ::= { fjdaryMachinePowerEntry 19 }

fjdaryMachinePowerInfo15 OBJECT-TYPE
    SYNTAX INTEGER(-2147483648..2147483647)
    ACCESS read-only
    STATUS mandatory
    DESCRIPTION
        "The average power consumption 15 hour ago is shown. The unit is Watt."
    ::= { fjdaryMachinePowerEntry 20 }

fjdaryMachinePowerInfo16 OBJECT-TYPE
    SYNTAX INTEGER(-2147483648..2147483647)
    ACCESS read-only
    STATUS mandatory
    DESCRIPTION
        "The average power consumption 16 hour ago is shown. The unit is Watt."
    ::= { fjdaryMachinePowerEntry 21 }

fjdaryMachinePowerInfo17 OBJECT-TYPE
    SYNTAX INTEGER(-2147483648..2147483647)
    ACCESS read-only
    STATUS mandatory
    DESCRIPTION
        "The average power consumption 17 hour ago is shown. The unit is Watt."
    ::= { fjdaryMachinePowerEntry 22 }

fjdaryMachinePowerInfo18 OBJECT-TYPE
    SYNTAX INTEGER(-2147483648..2147483647)
    ACCESS read-only
    STATUS mandatory
    DESCRIPTION
        "The average power consumption 18 hour ago is shown. The unit is Watt."
    ::= { fjdaryMachinePowerEntry 23 }

fjdaryMachinePowerInfo19 OBJECT-TYPE
    SYNTAX INTEGER(-2147483648..2147483647)
    ACCESS read-only
    STATUS mandatory
    DESCRIPTION
        "The average power consumption 19 hour ago is shown. The unit is Watt."
    ::= { fjdaryMachinePowerEntry 24 }

fjdaryMachinePowerInfo20 OBJECT-TYPE
    SYNTAX INTEGER(-2147483648..2147483647)
    ACCESS read-only
    STATUS mandatory
    DESCRIPTION
        "The average power consumption 20 hour ago is shown. The unit is Watt."
    ::= { fjdaryMachinePowerEntry 25 }

fjdaryMachinePowerInfo21 OBJECT-TYPE
    SYNTAX INTEGER(-2147483648..2147483647)
    ACCESS read-only
    STATUS mandatory
    DESCRIPTION
        "The average power consumption 21 hour ago is shown. The unit is Watt."
    ::= { fjdaryMachinePowerEntry 26 }

fjdaryMachinePowerInfo22 OBJECT-TYPE
    SYNTAX INTEGER(-2147483648..2147483647)
    ACCESS read-only
    STATUS mandatory
    DESCRIPTION
        "The average power consumption 22 hour ago is shown. The unit is Watt."
    ::= { fjdaryMachinePowerEntry 27 }

fjdaryMachinePowerInfo23 OBJECT-TYPE
    SYNTAX INTEGER(-2147483648..2147483647)
    ACCESS read-only
    STATUS mandatory
    DESCRIPTION
        "The average power consumption 23 hour ago is shown. The unit is Watt."
    ::= { fjdaryMachinePowerEntry 28 }

fjdaryMachinePowerInfo24 OBJECT-TYPE
    SYNTAX INTEGER(-2147483648..2147483647)
    ACCESS read-only
    STATUS mandatory
    DESCRIPTION
        "The average power consumption 24 hour ago is shown. The unit is Watt."
    ::= { fjdaryMachinePowerEntry 29 }

-------------------------------------------------------------------------------
--   fjdaryEncPower                                                          --
-------------------------------------------------------------------------------
fjdaryEncPowerCount OBJECT-TYPE
    SYNTAX INTEGER(0..2147483647)
    ACCESS read-only
    STATUS mandatory
    DESCRIPTION
        "The number of power consumption information table's entry of each
         enclosure."
    ::= { fjdaryEncPower 1 }

fjdaryEncPowerTable OBJECT-TYPE
    SYNTAX SEQUENCE OF FjdaryEncPowerEntry
    ACCESS not-accessible
    STATUS mandatory
    DESCRIPTION
        ""
    ::= { fjdaryEncPower 2 }

fjdaryEncPowerEntry OBJECT-TYPE
    SYNTAX FjdaryEncPowerEntry
    ACCESS not-accessible
    STATUS mandatory
    DESCRIPTION
        ""
    INDEX { fjdaryEncPowerIndex }
    ::= { fjdaryEncPowerTable 1 }

FjdaryEncPowerEntry ::=
    SEQUENCE{
        fjdaryEncPowerIndex  INTEGER,
        fjdaryEncPowerFlag   INTEGER,
        fjdaryEncPowerCmNum  INTEGER,
        fjdaryEncPowerDeId   INTEGER,
        fjdaryEncPowerTime   INTEGER,
        fjdaryEncPowerType   INTEGER,
        fjdaryEncPowerInfo0  INTEGER,
        fjdaryEncPowerInfo1  INTEGER,
        fjdaryEncPowerInfo2  INTEGER,
        fjdaryEncPowerInfo3  INTEGER,
        fjdaryEncPowerInfo4  INTEGER,
        fjdaryEncPowerInfo5  INTEGER,
        fjdaryEncPowerInfo6  INTEGER,
        fjdaryEncPowerInfo7  INTEGER,
        fjdaryEncPowerInfo8  INTEGER,
        fjdaryEncPowerInfo9  INTEGER,
        fjdaryEncPowerInfo10 INTEGER,
        fjdaryEncPowerInfo11 INTEGER,
        fjdaryEncPowerInfo12 INTEGER,
        fjdaryEncPowerInfo13 INTEGER,
        fjdaryEncPowerInfo14 INTEGER,
        fjdaryEncPowerInfo15 INTEGER,
        fjdaryEncPowerInfo16 INTEGER,
        fjdaryEncPowerInfo17 INTEGER,
        fjdaryEncPowerInfo18 INTEGER,
        fjdaryEncPowerInfo19 INTEGER,
        fjdaryEncPowerInfo20 INTEGER,
        fjdaryEncPowerInfo21 INTEGER,
        fjdaryEncPowerInfo22 INTEGER,
        fjdaryEncPowerInfo23 INTEGER,
        fjdaryEncPowerInfo24 INTEGER
    }

fjdaryEncPowerIndex OBJECT-TYPE
    SYNTAX INTEGER(0..2147483647)
    ACCESS read-only
    STATUS mandatory
    DESCRIPTION
        "The value of this object uniquely identifies this fjdaryEncPower
         entry."
    ::= { fjdaryEncPowerEntry 1 }

fjdaryEncPowerFlag OBJECT-TYPE
    SYNTAX INTEGER {
        invalid(255),
        updating(1),
        valid(2)
    }
    ACCESS read-only
    STATUS mandatory
    DESCRIPTION
        "The state of information concerned index is shown."
    ::= { fjdaryEncPowerEntry 2 }

fjdaryEncPowerCmNum OBJECT-TYPE
    SYNTAX INTEGER(-2147483648..2147483647)
    ACCESS read-only
    STATUS mandatory
    DESCRIPTION
        "CM number in which this information is gathered."
    ::= { fjdaryEncPowerEntry 3 }

fjdaryEncPowerDeId OBJECT-TYPE
    SYNTAX INTEGER(-2147483648..2147483647)
    ACCESS read-only
    STATUS mandatory
    DESCRIPTION
        "DE ID in which this information is gathered.
         When fjdaryEncPowerType is de, this information is effective."
    ::= { fjdaryEncPowerEntry 4 }

fjdaryEncPowerTime OBJECT-TYPE
    SYNTAX INTEGER(-2147483648..2147483647)
    ACCESS read-only
    STATUS mandatory
    DESCRIPTION
        "Passage second when this information was gathered."
    ::= { fjdaryEncPowerEntry 5 }

fjdaryEncPowerType OBJECT-TYPE
    SYNTAX INTEGER {
        ce(16),
        de(32)
    }
    ACCESS read-only
    STATUS mandatory
    DESCRIPTION
        "enclosure type in which this information is gathered."
    ::= { fjdaryEncPowerEntry 6 }

fjdaryEncPowerInfo0 OBJECT-TYPE
    SYNTAX INTEGER(-2147483648..2147483647)
    ACCESS read-only
    STATUS mandatory
    DESCRIPTION
        "The average power consumption is shown during one hour in the past.
         The unit is Watt."
    ::= { fjdaryEncPowerEntry 7 }

fjdaryEncPowerInfo1 OBJECT-TYPE
    SYNTAX INTEGER(-2147483648..2147483647)
    ACCESS read-only
    STATUS mandatory
    DESCRIPTION
        "The average power consumption 1 hour ago is shown. The unit is Watt."
    ::= { fjdaryEncPowerEntry 8 }

fjdaryEncPowerInfo2 OBJECT-TYPE
    SYNTAX INTEGER(-2147483648..2147483647)
    ACCESS read-only
    STATUS mandatory
    DESCRIPTION
        "The average power consumption 2 hour ago is shown. The unit is Watt."
    ::= { fjdaryEncPowerEntry 9 }

fjdaryEncPowerInfo3 OBJECT-TYPE
    SYNTAX INTEGER(-2147483648..2147483647)
    ACCESS read-only
    STATUS mandatory
    DESCRIPTION
        "The average power consumption 3 hour ago is shown. The unit is Watt."
    ::= { fjdaryEncPowerEntry 10 }

fjdaryEncPowerInfo4 OBJECT-TYPE
    SYNTAX INTEGER(-2147483648..2147483647)
    ACCESS read-only
    STATUS mandatory
    DESCRIPTION
        "The average power consumption 4 hour ago is shown. The unit is Watt."
    ::= { fjdaryEncPowerEntry 11 }

fjdaryEncPowerInfo5 OBJECT-TYPE
    SYNTAX INTEGER(-2147483648..2147483647)
    ACCESS read-only
    STATUS mandatory
    DESCRIPTION
        "The average power consumption 5 hour ago is shown. The unit is Watt."
    ::= { fjdaryEncPowerEntry 12 }

fjdaryEncPowerInfo6 OBJECT-TYPE
    SYNTAX INTEGER(-2147483648..2147483647)
    ACCESS read-only
    STATUS mandatory
    DESCRIPTION
        "The average power consumption 6 hour ago is shown. The unit is Watt."
    ::= { fjdaryEncPowerEntry 13 }

fjdaryEncPowerInfo7 OBJECT-TYPE
    SYNTAX INTEGER(-2147483648..2147483647)
    ACCESS read-only
    STATUS mandatory
    DESCRIPTION
        "The average power consumption 7 hour ago is shown. The unit is Watt."
    ::= { fjdaryEncPowerEntry 14 }

fjdaryEncPowerInfo8 OBJECT-TYPE
    SYNTAX INTEGER(-2147483648..2147483647)
    ACCESS read-only
    STATUS mandatory
    DESCRIPTION
        "The average power consumption 8 hour ago is shown. The unit is Watt."
    ::= { fjdaryEncPowerEntry 15 }

fjdaryEncPowerInfo9 OBJECT-TYPE
    SYNTAX INTEGER(-2147483648..2147483647)
    ACCESS read-only
    STATUS mandatory
    DESCRIPTION
        "The average power consumption 9 hour ago is shown. The unit is Watt."
    ::= { fjdaryEncPowerEntry 16 }

fjdaryEncPowerInfo10 OBJECT-TYPE
    SYNTAX INTEGER(-2147483648..2147483647)
    ACCESS read-only
    STATUS mandatory
    DESCRIPTION
        "The average power consumption 10 hour ago is shown. The unit is Watt."
    ::= { fjdaryEncPowerEntry 17 }

fjdaryEncPowerInfo11 OBJECT-TYPE
    SYNTAX INTEGER(-2147483648..2147483647)
    ACCESS read-only
    STATUS mandatory
    DESCRIPTION
        "The average power consumption 11 hour ago is shown. The unit is Watt."
    ::= { fjdaryEncPowerEntry 18 }

fjdaryEncPowerInfo12 OBJECT-TYPE
    SYNTAX INTEGER(-2147483648..2147483647)
    ACCESS read-only
    STATUS mandatory
    DESCRIPTION
        "The average power consumption 12 hour ago is shown. The unit is Watt."
    ::= { fjdaryEncPowerEntry 19 }

fjdaryEncPowerInfo13 OBJECT-TYPE
    SYNTAX INTEGER(-2147483648..2147483647)
    ACCESS read-only
    STATUS mandatory
    DESCRIPTION
        "The average power consumption 13 hour ago is shown. The unit is Watt."
    ::= { fjdaryEncPowerEntry 20 }

fjdaryEncPowerInfo14 OBJECT-TYPE
    SYNTAX INTEGER(-2147483648..2147483647)
    ACCESS read-only
    STATUS mandatory
    DESCRIPTION
        "The average power consumption 14 hour ago is shown. The unit is Watt."
    ::= { fjdaryEncPowerEntry 21 }

fjdaryEncPowerInfo15 OBJECT-TYPE
    SYNTAX INTEGER(-2147483648..2147483647)
    ACCESS read-only
    STATUS mandatory
    DESCRIPTION
        "The average power consumption 15 hour ago is shown. The unit is Watt."
    ::= { fjdaryEncPowerEntry 22 }

fjdaryEncPowerInfo16 OBJECT-TYPE
    SYNTAX INTEGER(-2147483648..2147483647)
    ACCESS read-only
    STATUS mandatory
    DESCRIPTION
        "The average power consumption 16 hour ago is shown. The unit is Watt."
    ::= { fjdaryEncPowerEntry 23 }

fjdaryEncPowerInfo17 OBJECT-TYPE
    SYNTAX INTEGER(-2147483648..2147483647)
    ACCESS read-only
    STATUS mandatory
    DESCRIPTION
        "The average power consumption 17 hour ago is shown. The unit is Watt."
    ::= { fjdaryEncPowerEntry 24 }

fjdaryEncPowerInfo18 OBJECT-TYPE
    SYNTAX INTEGER(-2147483648..2147483647)
    ACCESS read-only
    STATUS mandatory
    DESCRIPTION
        "The average power consumption 18 hour ago is shown. The unit is Watt."
    ::= { fjdaryEncPowerEntry 25 }

fjdaryEncPowerInfo19 OBJECT-TYPE
    SYNTAX INTEGER(-2147483648..2147483647)
    ACCESS read-only
    STATUS mandatory
    DESCRIPTION
        "The average power consumption 19 hour ago is shown. The unit is Watt."
    ::= { fjdaryEncPowerEntry 26 }

fjdaryEncPowerInfo20 OBJECT-TYPE
    SYNTAX INTEGER(-2147483648..2147483647)
    ACCESS read-only
    STATUS mandatory
    DESCRIPTION
        "The average power consumption 20 hour ago is shown. The unit is Watt."
    ::= { fjdaryEncPowerEntry 27 }

fjdaryEncPowerInfo21 OBJECT-TYPE
    SYNTAX INTEGER(-2147483648..2147483647)
    ACCESS read-only
    STATUS mandatory
    DESCRIPTION
        "The average power consumption 21 hour ago is shown. The unit is Watt."
    ::= { fjdaryEncPowerEntry 28 }

fjdaryEncPowerInfo22 OBJECT-TYPE
    SYNTAX INTEGER(-2147483648..2147483647)
    ACCESS read-only
    STATUS mandatory
    DESCRIPTION
        "The average power consumption 22 hour ago is shown. The unit is Watt."
    ::= { fjdaryEncPowerEntry 29 }

fjdaryEncPowerInfo23 OBJECT-TYPE
    SYNTAX INTEGER(-2147483648..2147483647)
    ACCESS read-only
    STATUS mandatory
    DESCRIPTION
        "The average power consumption 23 hour ago is shown. The unit is Watt."
    ::= { fjdaryEncPowerEntry 30 }

fjdaryEncPowerInfo24 OBJECT-TYPE
    SYNTAX INTEGER(-2147483648..2147483647)
    ACCESS read-only
    STATUS mandatory
    DESCRIPTION
        "The average power consumption 24 hour ago is shown. The unit is Watt."
    ::= { fjdaryEncPowerEntry 31 }

-------------------------------------------------------------------------------
--   fjdaryMachineTemp                                                       --
-------------------------------------------------------------------------------
fjdaryMachineTempCount OBJECT-TYPE
    SYNTAX INTEGER(0..2147483647)
    ACCESS read-only
    STATUS mandatory
    DESCRIPTION
        "The number of temperature information table's entry on this machine."
    ::= { fjdaryMachineTemp 1 }

fjdaryMachineTempTable OBJECT-TYPE
    SYNTAX SEQUENCE OF FjdaryMachineTempEntry
    ACCESS not-accessible
    STATUS mandatory
    DESCRIPTION
        ""
    ::= { fjdaryMachineTemp 2 }

fjdaryMachineTempEntry OBJECT-TYPE
    SYNTAX FjdaryMachineTempEntry
    ACCESS not-accessible
    STATUS mandatory
    DESCRIPTION
        ""
    INDEX { fjdaryMachineTempIndex }
    ::= { fjdaryMachineTempTable 1 }

FjdaryMachineTempEntry ::=
    SEQUENCE{
        fjdaryMachineTempIndex  INTEGER,
        fjdaryMachineTempFlag   INTEGER,
        fjdaryMachineTempCmNum  INTEGER,
        fjdaryMachineTempTime   INTEGER,
        fjdaryMachineTempInfo0  INTEGER,
        fjdaryMachineTempInfo1  INTEGER,
        fjdaryMachineTempInfo2  INTEGER,
        fjdaryMachineTempInfo3  INTEGER,
        fjdaryMachineTempInfo4  INTEGER,
        fjdaryMachineTempInfo5  INTEGER,
        fjdaryMachineTempInfo6  INTEGER,
        fjdaryMachineTempInfo7  INTEGER,
        fjdaryMachineTempInfo8  INTEGER,
        fjdaryMachineTempInfo9  INTEGER,
        fjdaryMachineTempInfo10 INTEGER,
        fjdaryMachineTempInfo11 INTEGER,
        fjdaryMachineTempInfo12 INTEGER,
        fjdaryMachineTempInfo13 INTEGER,
        fjdaryMachineTempInfo14 INTEGER,
        fjdaryMachineTempInfo15 INTEGER,
        fjdaryMachineTempInfo16 INTEGER,
        fjdaryMachineTempInfo17 INTEGER,
        fjdaryMachineTempInfo18 INTEGER,
        fjdaryMachineTempInfo19 INTEGER,
        fjdaryMachineTempInfo20 INTEGER,
        fjdaryMachineTempInfo21 INTEGER,
        fjdaryMachineTempInfo22 INTEGER,
        fjdaryMachineTempInfo23 INTEGER,
        fjdaryMachineTempInfo24 INTEGER
    }

fjdaryMachineTempIndex OBJECT-TYPE
    SYNTAX INTEGER(0..2147483647)
    ACCESS read-only
    STATUS mandatory
    DESCRIPTION
        "The value of this object uniquely identifies this fjdaryMachineTemp
         entry."
    ::= { fjdaryMachineTempEntry 1 }

fjdaryMachineTempFlag OBJECT-TYPE
    SYNTAX INTEGER {
        invalid(255),
        updating(1),
        valid(2)
    }
    ACCESS read-only
    STATUS mandatory
    DESCRIPTION
        "The state of information concerned index is shown."
    ::= { fjdaryMachineTempEntry 2 }

fjdaryMachineTempCmNum OBJECT-TYPE
    SYNTAX INTEGER(-2147483648..2147483647)
    ACCESS read-only
    STATUS mandatory
    DESCRIPTION
        "CM number in which this information is gathered."
    ::= { fjdaryMachineTempEntry 3 }

fjdaryMachineTempTime OBJECT-TYPE
    SYNTAX INTEGER(-2147483648..2147483647)
    ACCESS read-only
    STATUS mandatory
    DESCRIPTION
        "Passage second when this information was gathered."
    ::= { fjdaryMachineTempEntry 4 }

fjdaryMachineTempInfo0 OBJECT-TYPE
    SYNTAX INTEGER(-2147483648..2147483647)
    ACCESS read-only
    STATUS mandatory
    DESCRIPTION
        "The maximum temperature is shown during one hour in the past.
         The unit is Celsius."
    ::= { fjdaryMachineTempEntry 5 }

fjdaryMachineTempInfo1 OBJECT-TYPE
    SYNTAX INTEGER(-2147483648..2147483647)
    ACCESS read-only
    STATUS mandatory
    DESCRIPTION
        "The maximum temperature 1 hour ago is shown. The unit is Celsius."
    ::= { fjdaryMachineTempEntry 6 }

fjdaryMachineTempInfo2 OBJECT-TYPE
    SYNTAX INTEGER(-2147483648..2147483647)
    ACCESS read-only
    STATUS mandatory
    DESCRIPTION
        "The maximum temperature 2 hour ago is shown. The unit is Celsius."
    ::= { fjdaryMachineTempEntry 7 }

fjdaryMachineTempInfo3 OBJECT-TYPE
    SYNTAX INTEGER(-2147483648..2147483647)
    ACCESS read-only
    STATUS mandatory
    DESCRIPTION
        "The maximum temperature 3 hour ago is shown. The unit is Celsius."
    ::= { fjdaryMachineTempEntry 8 }

fjdaryMachineTempInfo4 OBJECT-TYPE
    SYNTAX INTEGER(-2147483648..2147483647)
    ACCESS read-only
    STATUS mandatory
    DESCRIPTION
        "The maximum temperature 4 hour ago is shown. The unit is Celsius."
    ::= { fjdaryMachineTempEntry 9 }

fjdaryMachineTempInfo5 OBJECT-TYPE
    SYNTAX INTEGER(-2147483648..2147483647)
    ACCESS read-only
    STATUS mandatory
    DESCRIPTION
        "The maximum temperature 5 hour ago is shown. The unit is Celsius."
    ::= { fjdaryMachineTempEntry 10 }

fjdaryMachineTempInfo6 OBJECT-TYPE
    SYNTAX INTEGER(-2147483648..2147483647)
    ACCESS read-only
    STATUS mandatory
    DESCRIPTION
        "The maximum temperature 6 hour ago is shown. The unit is Celsius."
    ::= { fjdaryMachineTempEntry 11 }

fjdaryMachineTempInfo7 OBJECT-TYPE
    SYNTAX INTEGER(-2147483648..2147483647)
    ACCESS read-only
    STATUS mandatory
    DESCRIPTION
        "The maximum temperature 7 hour ago is shown. The unit is Celsius."
    ::= { fjdaryMachineTempEntry 12 }

fjdaryMachineTempInfo8 OBJECT-TYPE
    SYNTAX INTEGER(-2147483648..2147483647)
    ACCESS read-only
    STATUS mandatory
    DESCRIPTION
        "The maximum temperature 8 hour ago is shown. The unit is Celsius."
    ::= { fjdaryMachineTempEntry 13 }

fjdaryMachineTempInfo9 OBJECT-TYPE
    SYNTAX INTEGER(-2147483648..2147483647)
    ACCESS read-only
    STATUS mandatory
    DESCRIPTION
        "The maximum temperature 9 hour ago is shown. The unit is Celsius."
    ::= { fjdaryMachineTempEntry 14 }

fjdaryMachineTempInfo10 OBJECT-TYPE
    SYNTAX INTEGER(-2147483648..2147483647)
    ACCESS read-only
    STATUS mandatory
    DESCRIPTION
        "The maximum temperature 10 hour ago is shown. The unit is Celsius."
    ::= { fjdaryMachineTempEntry 15 }

fjdaryMachineTempInfo11 OBJECT-TYPE
    SYNTAX INTEGER(-2147483648..2147483647)
    ACCESS read-only
    STATUS mandatory
    DESCRIPTION
        "The maximum temperature 11 hour ago is shown. The unit is Celsius."
    ::= { fjdaryMachineTempEntry 16 }

fjdaryMachineTempInfo12 OBJECT-TYPE
    SYNTAX INTEGER(-2147483648..2147483647)
    ACCESS read-only
    STATUS mandatory
    DESCRIPTION
        "The maximum temperature 12 hour ago is shown. The unit is Celsius."
    ::= { fjdaryMachineTempEntry 17 }

fjdaryMachineTempInfo13 OBJECT-TYPE
    SYNTAX INTEGER(-2147483648..2147483647)
    ACCESS read-only
    STATUS mandatory
    DESCRIPTION
        "The maximum temperature 13 hour ago is shown. The unit is Celsius."
    ::= { fjdaryMachineTempEntry 18 }

fjdaryMachineTempInfo14 OBJECT-TYPE
    SYNTAX INTEGER(-2147483648..2147483647)
    ACCESS read-only
    STATUS mandatory
    DESCRIPTION
        "The maximum temperature 14 hour ago is shown. The unit is Celsius."
    ::= { fjdaryMachineTempEntry 19 }

fjdaryMachineTempInfo15 OBJECT-TYPE
    SYNTAX INTEGER(-2147483648..2147483647)
    ACCESS read-only
    STATUS mandatory
    DESCRIPTION
        "The maximum temperature 15 hour ago is shown. The unit is Celsius."
    ::= { fjdaryMachineTempEntry 20 }

fjdaryMachineTempInfo16 OBJECT-TYPE
    SYNTAX INTEGER(-2147483648..2147483647)
    ACCESS read-only
    STATUS mandatory
    DESCRIPTION
        "The maximum temperature 16 hour ago is shown. The unit is Celsius."
    ::= { fjdaryMachineTempEntry 21 }

fjdaryMachineTempInfo17 OBJECT-TYPE
    SYNTAX INTEGER(-2147483648..2147483647)
    ACCESS read-only
    STATUS mandatory
    DESCRIPTION
        "The maximum temperature 17 hour ago is shown. The unit is Celsius."
    ::= { fjdaryMachineTempEntry 22 }

fjdaryMachineTempInfo18 OBJECT-TYPE
    SYNTAX INTEGER(-2147483648..2147483647)
    ACCESS read-only
    STATUS mandatory
    DESCRIPTION
        "The maximum temperature 18 hour ago is shown. The unit is Celsius."
    ::= { fjdaryMachineTempEntry 23 }

fjdaryMachineTempInfo19 OBJECT-TYPE
    SYNTAX INTEGER(-2147483648..2147483647)
    ACCESS read-only
    STATUS mandatory
    DESCRIPTION
        "The maximum temperature 19 hour ago is shown. The unit is Celsius."
    ::= { fjdaryMachineTempEntry 24 }

fjdaryMachineTempInfo20 OBJECT-TYPE
    SYNTAX INTEGER(-2147483648..2147483647)
    ACCESS read-only
    STATUS mandatory
    DESCRIPTION
        "The maximum temperature 20 hour ago is shown. The unit is Celsius."
    ::= { fjdaryMachineTempEntry 25 }

fjdaryMachineTempInfo21 OBJECT-TYPE
    SYNTAX INTEGER(-2147483648..2147483647)
    ACCESS read-only
    STATUS mandatory
    DESCRIPTION
        "The maximum temperature 21 hour ago is shown. The unit is Celsius."
    ::= { fjdaryMachineTempEntry 26 }

fjdaryMachineTempInfo22 OBJECT-TYPE
    SYNTAX INTEGER(-2147483648..2147483647)
    ACCESS read-only
    STATUS mandatory
    DESCRIPTION
        "The maximum temperature 22 hour ago is shown. The unit is Celsius."
    ::= { fjdaryMachineTempEntry 27 }

fjdaryMachineTempInfo23 OBJECT-TYPE
    SYNTAX INTEGER(-2147483648..2147483647)
    ACCESS read-only
    STATUS mandatory
    DESCRIPTION
        "The maximum temperature 23 hour ago is shown. The unit is Celsius."
    ::= { fjdaryMachineTempEntry 28 }

fjdaryMachineTempInfo24 OBJECT-TYPE
    SYNTAX INTEGER(-2147483648..2147483647)
    ACCESS read-only
    STATUS mandatory
    DESCRIPTION
        "The maximum temperature 24 hour ago is shown. The unit is Celsius."
    ::= { fjdaryMachineTempEntry 29 }

-------------------------------------------------------------------------------
--   fjdaryEncTemp                                                           --
-------------------------------------------------------------------------------
fjdaryEncTempCount OBJECT-TYPE
    SYNTAX INTEGER(0..2147483647)
    ACCESS read-only
    STATUS mandatory
    DESCRIPTION
        "The number of temperature information table's entry of each
         enclosure."
    ::= { fjdaryEncTemp 1 }

fjdaryEncTempTable OBJECT-TYPE
    SYNTAX SEQUENCE OF FjdaryEncTempEntry
    ACCESS not-accessible
    STATUS mandatory
    DESCRIPTION
        ""
    ::= { fjdaryEncTemp 2 }

fjdaryEncTempEntry OBJECT-TYPE
    SYNTAX FjdaryEncTempEntry
    ACCESS not-accessible
    STATUS mandatory
    DESCRIPTION
        ""
    INDEX { fjdaryEncTempIndex }
    ::= { fjdaryEncTempTable 1 }

FjdaryEncTempEntry ::=
    SEQUENCE{
        fjdaryEncTempIndex  INTEGER,
        fjdaryEncTempFlag   INTEGER,
        fjdaryEncTempCmNum  INTEGER,
        fjdaryEncTempDeId   INTEGER,
        fjdaryEncTempTime   INTEGER,
        fjdaryEncTempType   INTEGER,
        fjdaryEncTempInfo0  INTEGER,
        fjdaryEncTempInfo1  INTEGER,
        fjdaryEncTempInfo2  INTEGER,
        fjdaryEncTempInfo3  INTEGER,
        fjdaryEncTempInfo4  INTEGER,
        fjdaryEncTempInfo5  INTEGER,
        fjdaryEncTempInfo6  INTEGER,
        fjdaryEncTempInfo7  INTEGER,
        fjdaryEncTempInfo8  INTEGER,
        fjdaryEncTempInfo9  INTEGER,
        fjdaryEncTempInfo10 INTEGER,
        fjdaryEncTempInfo11 INTEGER,
        fjdaryEncTempInfo12 INTEGER,
        fjdaryEncTempInfo13 INTEGER,
        fjdaryEncTempInfo14 INTEGER,
        fjdaryEncTempInfo15 INTEGER,
        fjdaryEncTempInfo16 INTEGER,
        fjdaryEncTempInfo17 INTEGER,
        fjdaryEncTempInfo18 INTEGER,
        fjdaryEncTempInfo19 INTEGER,
        fjdaryEncTempInfo20 INTEGER,
        fjdaryEncTempInfo21 INTEGER,
        fjdaryEncTempInfo22 INTEGER,
        fjdaryEncTempInfo23 INTEGER,
        fjdaryEncTempInfo24 INTEGER
    }

fjdaryEncTempIndex OBJECT-TYPE
    SYNTAX INTEGER(0..2147483647)
    ACCESS read-only
    STATUS mandatory
    DESCRIPTION
        "The value of this object uniquely identifies this fjdaryEncTemp
         entry."
    ::= { fjdaryEncTempEntry 1 }

fjdaryEncTempFlag OBJECT-TYPE
    SYNTAX INTEGER {
        invalid(255),
        updating(1),
        valid(2)
    }
    ACCESS read-only
    STATUS mandatory
    DESCRIPTION
        "The state of information concerned index is shown."
    ::= { fjdaryEncTempEntry 2 }

fjdaryEncTempCmNum OBJECT-TYPE
    SYNTAX INTEGER(-2147483648..2147483647)
    ACCESS read-only
    STATUS mandatory
    DESCRIPTION
        "CM number in which this information is gathered."
    ::= { fjdaryEncTempEntry 3 }

fjdaryEncTempDeId OBJECT-TYPE
    SYNTAX INTEGER(-2147483648..2147483647)
    ACCESS read-only
    STATUS mandatory
    DESCRIPTION
        "DE ID in which this information is gathered.
         When fjdaryEncTempType is de, this information is effective"
    ::= { fjdaryEncTempEntry 4 }

fjdaryEncTempTime OBJECT-TYPE
    SYNTAX INTEGER(-2147483648..2147483647)
    ACCESS read-only
    STATUS mandatory
    DESCRIPTION
        "Passage second when this information was gathered."
    ::= { fjdaryEncTempEntry 5 }

fjdaryEncTempType OBJECT-TYPE
    SYNTAX INTEGER {
        ce(16),
        de(32)
    }
    ACCESS read-only
    STATUS mandatory
    DESCRIPTION
        "enclosure type in which this information is gathered."
    ::= { fjdaryEncTempEntry 6 }

fjdaryEncTempInfo0 OBJECT-TYPE
    SYNTAX INTEGER(-2147483648..2147483647)
    ACCESS read-only
    STATUS mandatory
    DESCRIPTION
        "The maximum temperature is shown during one hour in the past.
         The unit is Celsius."
    ::= { fjdaryEncTempEntry 7 }

fjdaryEncTempInfo1 OBJECT-TYPE
    SYNTAX INTEGER(-2147483648..2147483647)
    ACCESS read-only
    STATUS mandatory
    DESCRIPTION
        "The maximum temperature 1 hour ago is shown. The unit is Celsius."
    ::= { fjdaryEncTempEntry 8 }

fjdaryEncTempInfo2 OBJECT-TYPE
    SYNTAX INTEGER(-2147483648..2147483647)
    ACCESS read-only
    STATUS mandatory
    DESCRIPTION
        "The maximum temperature 2 hour ago is shown. The unit is Celsius."
    ::= { fjdaryEncTempEntry 9 }

fjdaryEncTempInfo3 OBJECT-TYPE
    SYNTAX INTEGER(-2147483648..2147483647)
    ACCESS read-only
    STATUS mandatory
    DESCRIPTION
        "The maximum temperature 3 hour ago is shown. The unit is Celsius."
    ::= { fjdaryEncTempEntry 10 }

fjdaryEncTempInfo4 OBJECT-TYPE
    SYNTAX INTEGER(-2147483648..2147483647)
    ACCESS read-only
    STATUS mandatory
    DESCRIPTION
        "The maximum temperature 4 hour ago is shown. The unit is Celsius."
    ::= { fjdaryEncTempEntry 11 }

fjdaryEncTempInfo5 OBJECT-TYPE
    SYNTAX INTEGER(-2147483648..2147483647)
    ACCESS read-only
    STATUS mandatory
    DESCRIPTION
        "The maximum temperature 5 hour ago is shown. The unit is Celsius."
    ::= { fjdaryEncTempEntry 12 }

fjdaryEncTempInfo6 OBJECT-TYPE
    SYNTAX INTEGER(-2147483648..2147483647)
    ACCESS read-only
    STATUS mandatory
    DESCRIPTION
        "The maximum temperature 6 hour ago is shown. The unit is Celsius."
    ::= { fjdaryEncTempEntry 13 }

fjdaryEncTempInfo7 OBJECT-TYPE
    SYNTAX INTEGER(-2147483648..2147483647)
    ACCESS read-only
    STATUS mandatory
    DESCRIPTION
        "The maximum temperature 7 hour ago is shown. The unit is Celsius."
    ::= { fjdaryEncTempEntry 14 }

fjdaryEncTempInfo8 OBJECT-TYPE
    SYNTAX INTEGER(-2147483648..2147483647)
    ACCESS read-only
    STATUS mandatory
    DESCRIPTION
        "The maximum temperature 8 hour ago is shown. The unit is Celsius."
    ::= { fjdaryEncTempEntry 15 }

fjdaryEncTempInfo9 OBJECT-TYPE
    SYNTAX INTEGER(-2147483648..2147483647)
    ACCESS read-only
    STATUS mandatory
    DESCRIPTION
        "The maximum temperature 9 hour ago is shown. The unit is Celsius."
    ::= { fjdaryEncTempEntry 16 }

fjdaryEncTempInfo10 OBJECT-TYPE
    SYNTAX INTEGER(-2147483648..2147483647)
    ACCESS read-only
    STATUS mandatory
    DESCRIPTION
        "The maximum temperature 10 hour ago is shown. The unit is Celsius."
    ::= { fjdaryEncTempEntry 17 }

fjdaryEncTempInfo11 OBJECT-TYPE
    SYNTAX INTEGER(-2147483648..2147483647)
    ACCESS read-only
    STATUS mandatory
    DESCRIPTION
        "The maximum temperature 11 hour ago is shown. The unit is Celsius."
    ::= { fjdaryEncTempEntry 18 }

fjdaryEncTempInfo12 OBJECT-TYPE
    SYNTAX INTEGER(-2147483648..2147483647)
    ACCESS read-only
    STATUS mandatory
    DESCRIPTION
        "The maximum temperature 12 hour ago is shown. The unit is Celsius."
    ::= { fjdaryEncTempEntry 19 }

fjdaryEncTempInfo13 OBJECT-TYPE
    SYNTAX INTEGER(-2147483648..2147483647)
    ACCESS read-only
    STATUS mandatory
    DESCRIPTION
        "The maximum temperature 13 hour ago is shown. The unit is Celsius."
    ::= { fjdaryEncTempEntry 20 }

fjdaryEncTempInfo14 OBJECT-TYPE
    SYNTAX INTEGER(-2147483648..2147483647)
    ACCESS read-only
    STATUS mandatory
    DESCRIPTION
        "The maximum temperature 14 hour ago is shown. The unit is Celsius."
    ::= { fjdaryEncTempEntry 21 }

fjdaryEncTempInfo15 OBJECT-TYPE
    SYNTAX INTEGER(-2147483648..2147483647)
    ACCESS read-only
    STATUS mandatory
    DESCRIPTION
        "The maximum temperature 15 hour ago is shown. The unit is Celsius."
    ::= { fjdaryEncTempEntry 22 }

fjdaryEncTempInfo16 OBJECT-TYPE
    SYNTAX INTEGER(-2147483648..2147483647)
    ACCESS read-only
    STATUS mandatory
    DESCRIPTION
        "The maximum temperature 16 hour ago is shown. The unit is Celsius."
    ::= { fjdaryEncTempEntry 23 }

fjdaryEncTempInfo17 OBJECT-TYPE
    SYNTAX INTEGER(-2147483648..2147483647)
    ACCESS read-only
    STATUS mandatory
    DESCRIPTION
        "The maximum temperature 17 hour ago is shown. The unit is Celsius."
    ::= { fjdaryEncTempEntry 24 }

fjdaryEncTempInfo18 OBJECT-TYPE
    SYNTAX INTEGER(-2147483648..2147483647)
    ACCESS read-only
    STATUS mandatory
    DESCRIPTION
        "The maximum temperature 18 hour ago is shown. The unit is Celsius."
    ::= { fjdaryEncTempEntry 25 }

fjdaryEncTempInfo19 OBJECT-TYPE
    SYNTAX INTEGER(-2147483648..2147483647)
    ACCESS read-only
    STATUS mandatory
    DESCRIPTION
        "The maximum temperature 19 hour ago is shown. The unit is Celsius."
    ::= { fjdaryEncTempEntry 26 }

fjdaryEncTempInfo20 OBJECT-TYPE
    SYNTAX INTEGER(-2147483648..2147483647)
    ACCESS read-only
    STATUS mandatory
    DESCRIPTION
        "The maximum temperature 20 hour ago is shown. The unit is Celsius."
    ::= { fjdaryEncTempEntry 27 }

fjdaryEncTempInfo21 OBJECT-TYPE
    SYNTAX INTEGER(-2147483648..2147483647)
    ACCESS read-only
    STATUS mandatory
    DESCRIPTION
        "The maximum temperature 21 hour ago is shown. The unit is Celsius."
    ::= { fjdaryEncTempEntry 28 }

fjdaryEncTempInfo22 OBJECT-TYPE
    SYNTAX INTEGER(-2147483648..2147483647)
    ACCESS read-only
    STATUS mandatory
    DESCRIPTION
        "The maximum temperature 22 hour ago is shown. The unit is Celsius."
    ::= { fjdaryEncTempEntry 29 }

fjdaryEncTempInfo23 OBJECT-TYPE
    SYNTAX INTEGER(-2147483648..2147483647)
    ACCESS read-only
    STATUS mandatory
    DESCRIPTION
        "The maximum temperature 23 hour ago is shown. The unit is Celsius."
    ::= { fjdaryEncTempEntry 30 }

fjdaryEncTempInfo24 OBJECT-TYPE
    SYNTAX INTEGER(-2147483648..2147483647)
    ACCESS read-only
    STATUS mandatory
    DESCRIPTION
        "The maximum temperature 24 hour ago is shown. The unit is Celsius."
    ::= { fjdaryEncTempEntry 31 }

--***************************************************************************--
--   Firmware                                                                --
--***************************************************************************--
fjdaryFirmTotal OBJECT-TYPE
    SYNTAX OCTET STRING (SIZE (0..256))
    ACCESS read-only
    STATUS mandatory
    DESCRIPTION
        "The value of this object indicates the total firmware information.
         VVLLSSSS
         | | |
         | | +-firmware suffix
         | +-firmware level
         +-firmware version"
    ::= { fjdaryFirm 1 }

--***************************************************************************--
--   Performance Information                                                 --
--***************************************************************************--
-------------------------------------------------------------------------------
--   fjdaryPfInfo                                                            --
-------------------------------------------------------------------------------
fjdaryPfInfoVersion OBJECT-TYPE
    SYNTAX INTEGER(-2147483648..2147483647)
    ACCESS read-only
    STATUS mandatory
    DESCRIPTION
        "This is the version for this performance information data."
    ::= { fjdaryPfInfo 1 }

fjdaryPfInfoLevel OBJECT-TYPE
    SYNTAX INTEGER(-2147483648..2147483647)
    ACCESS read-only
    STATUS mandatory
    DESCRIPTION
        "This is the level for this performance information data."
    ::= { fjdaryPfInfo 2 }

fjdaryPfInfoIntervalTime OBJECT-TYPE
    SYNTAX INTEGER(-2147483648..2147483647)
    ACCESS read-only
    STATUS mandatory
    DESCRIPTION
        "This indicates the acquisition interval of the performance information
         data. The unit is a second.
         If this value is not applicable, return zero."
    ::= { fjdaryPfInfo 3 }

fjdaryPfInfoUpdateTime OBJECT-TYPE
    SYNTAX INTEGER(-2147483648..2147483647)
    ACCESS read-only
    STATUS mandatory
    DESCRIPTION
        "This indicates the update time of the performance information data.
         The unit is a second."
    ::= { fjdaryPfInfo 4 }

fjdaryPfInfoDataValid OBJECT-TYPE
    SYNTAX INTEGER {
        invalid(255),
        valid(1)
    }
    ACCESS read-only
    STATUS mandatory
    DESCRIPTION
        "This shows whether the performance information data to be acquired
         exists."
    ::= { fjdaryPfInfo 5 }

-------------------------------------------------------------------------------
--   fjdaryPfOlu                                                             --
-------------------------------------------------------------------------------
fjdaryPfOluCount OBJECT-TYPE
    SYNTAX INTEGER(0..2147483647)
    ACCESS read-only
    STATUS mandatory
    DESCRIPTION
        "The number of OLU's performance informations
         (regardless of their current state) present on this system."
    ::= { fjdaryPfOlu 1 }

fjdaryPfOluTable OBJECT-TYPE
    SYNTAX SEQUENCE OF FjdaryPfOluEntry
    ACCESS not-accessible
    STATUS mandatory
    DESCRIPTION
        ""
    ::= { fjdaryPfOlu 2 }

fjdaryPfOluEntry OBJECT-TYPE
    SYNTAX FjdaryPfOluEntry
    ACCESS not-accessible
    STATUS mandatory
    DESCRIPTION
        ""
    INDEX { fjdaryPfOluIndex }
    ::= { fjdaryPfOluTable 1 }

FjdaryPfOluEntry ::=
    SEQUENCE{
        fjdaryPfOluIndex           INTEGER,
        fjdaryPfOluRdIOPS          INTEGER,
        fjdaryPfOluWtIOPS          INTEGER,
        fjdaryPfOluAdCpRdIOPS      INTEGER,
        fjdaryPfOluAdCpWtIOPS      INTEGER,
        fjdaryPfOluRdTp            INTEGER,
        fjdaryPfOluWtTp            INTEGER,
        fjdaryPfOluAdCpRdTp        INTEGER,
        fjdaryPfOluAdCpWtTp        INTEGER,
        fjdaryPfOluRdRspTime       INTEGER,
        fjdaryPfOluWtRspTime       INTEGER,
        fjdaryPfOluRdCacheHit      INTEGER,
        fjdaryPfOluWtCacheHit      INTEGER,
        fjdaryPfOluAdRdCacheHit    INTEGER,
        fjdaryPfOluAdWtCacheHit    INTEGER,
        fjdaryPfOluRdPreFetchHit   INTEGER,
        fjdaryPfOluAdRdPreFetchHit INTEGER,
        fjdaryPfOluRdExcCacheHit   INTEGER,
        fjdaryPfOluAdRdExcCacheHit INTEGER
    }

fjdaryPfOluIndex OBJECT-TYPE
    SYNTAX INTEGER(0..2147483647)
    ACCESS read-only
    STATUS mandatory
    DESCRIPTION
        "The value of this object uniquely identifies this fjdaryPfOlu entry.
         This is the same as OLUN."
    ::= { fjdaryPfOluEntry 1 }

fjdaryPfOluRdIOPS OBJECT-TYPE
    SYNTAX INTEGER(-2147483648..2147483647)
    ACCESS read-only
    STATUS mandatory
    DESCRIPTION
        "This shows the READ IOPS related to host I/O processing."
    ::= { fjdaryPfOluEntry 2 }

fjdaryPfOluWtIOPS OBJECT-TYPE
    SYNTAX INTEGER(-2147483648..2147483647)
    ACCESS read-only
    STATUS mandatory
    DESCRIPTION
        "This shows the WRITE IOPS related to host I/O processing."
    ::= { fjdaryPfOluEntry 3 }

fjdaryPfOluAdCpRdIOPS OBJECT-TYPE
    SYNTAX INTEGER(-2147483648..2147483647)
    ACCESS read-only
    STATUS mandatory
    DESCRIPTION
        "This shows the READ IOPS related to advanced copy processing."
    ::= { fjdaryPfOluEntry 4 }

fjdaryPfOluAdCpWtIOPS OBJECT-TYPE
    SYNTAX INTEGER(-2147483648..2147483647)
    ACCESS read-only
    STATUS mandatory
    DESCRIPTION
        "This shows the WRITE IOPS related to advanced copy processing."
    ::= { fjdaryPfOluEntry 5 }

fjdaryPfOluRdTp OBJECT-TYPE
    SYNTAX INTEGER(-2147483648..2147483647)
    ACCESS read-only
    STATUS mandatory
    DESCRIPTION
        "This shows the READ Throughput related to host I/O processing.
         The unit is MB/sec."
    ::= { fjdaryPfOluEntry 6 }

fjdaryPfOluWtTp OBJECT-TYPE
    SYNTAX INTEGER(-2147483648..2147483647)
    ACCESS read-only
    STATUS mandatory
    DESCRIPTION
        "This shows the WRITE Throughput related to host I/O processing.
         The unit is MB/sec."
    ::= { fjdaryPfOluEntry 7 }

fjdaryPfOluAdCpRdTp OBJECT-TYPE
    SYNTAX INTEGER(-2147483648..2147483647)
    ACCESS read-only
    STATUS mandatory
    DESCRIPTION
        "This shows the READ Throughput related to advanced copy processing.
         The unit is MB/sec."
    ::= { fjdaryPfOluEntry 8 }

fjdaryPfOluAdCpWtTp OBJECT-TYPE
    SYNTAX INTEGER(-2147483648..2147483647)
    ACCESS read-only
    STATUS mandatory
    DESCRIPTION
        "This shows the WRITE Throughput related to advanced copy processing.
         The unit is MB/sec."
    ::= { fjdaryPfOluEntry 9 }

fjdaryPfOluRdRspTime OBJECT-TYPE
    SYNTAX INTEGER(-2147483648..2147483647)
    ACCESS read-only
    STATUS mandatory
    DESCRIPTION
        "This indicates the average of READ Response Time related to host I/O
         processing. The unit is msec."
    ::= { fjdaryPfOluEntry 10 }

fjdaryPfOluWtRspTime OBJECT-TYPE
    SYNTAX INTEGER(-2147483648..2147483647)
    ACCESS read-only
    STATUS mandatory
    DESCRIPTION
        "This indicates the average of WRITE Response Time related to host I/O
         processing. The unit is msec."
    ::= { fjdaryPfOluEntry 11 }

fjdaryPfOluRdCacheHit OBJECT-TYPE
    SYNTAX INTEGER(-2147483648..2147483647)
    ACCESS read-only
    STATUS mandatory
    DESCRIPTION
        "This shows the READ Cache Hit Rate related to host I/O processing.
         The unit is percent."
    ::= { fjdaryPfOluEntry 12 }

fjdaryPfOluWtCacheHit OBJECT-TYPE
    SYNTAX INTEGER(-2147483648..2147483647)
    ACCESS read-only
    STATUS mandatory
    DESCRIPTION
        "This shows the WRITE Cache Hit Rate related to host I/O processing.
         The unit is percent."
    ::= { fjdaryPfOluEntry 13 }

fjdaryPfOluAdRdCacheHit OBJECT-TYPE
    SYNTAX INTEGER(-2147483648..2147483647)
    ACCESS read-only
    STATUS mandatory
    DESCRIPTION
        "This shows the READ Cache Hit Rate related to advanced copy
         processing. The unit is percent."
    ::= { fjdaryPfOluEntry 14 }

fjdaryPfOluAdWtCacheHit OBJECT-TYPE
    SYNTAX INTEGER(-2147483648..2147483647)
    ACCESS read-only
    STATUS mandatory
    DESCRIPTION
        "This shows the WRITE Cache Hit Rate related to advanced copy
         processing. The unit is percent."
    ::= { fjdaryPfOluEntry 15 }

fjdaryPfOluRdPreFetchHit OBJECT-TYPE
    SYNTAX INTEGER(-2147483648..2147483647)
    ACCESS read-only
    STATUS mandatory
    DESCRIPTION
        "This shows the READ Prefetch Hit Rate related to host I/O processing.
         The unit is percent."
    ::= { fjdaryPfOluEntry 16 }

fjdaryPfOluAdRdPreFetchHit OBJECT-TYPE
    SYNTAX INTEGER(-2147483648..2147483647)
    ACCESS read-only
    STATUS mandatory
    DESCRIPTION
        "This shows the READ Prefetch Hit Rate related to advanced copy
         processing. The unit is percent."
    ::= { fjdaryPfOluEntry 17 }

fjdaryPfOluRdExcCacheHit OBJECT-TYPE
    SYNTAX INTEGER(-2147483648..2147483647)
    ACCESS read-only
    STATUS mandatory
    DESCRIPTION
        "This shows the READ Extreme Cache Cache Hit Rate related to host I/O
         processing. The unit is percent."
    ::= { fjdaryPfOluEntry 18 }

fjdaryPfOluAdRdExcCacheHit OBJECT-TYPE
    SYNTAX INTEGER(-2147483648..2147483647)
    ACCESS read-only
    STATUS mandatory
    DESCRIPTION
        "This shows the READ Extreme Cache Cache Hit Rate related to
         advanced copy processing. The unit is percent."
    ::= { fjdaryPfOluEntry 19 }

-------------------------------------------------------------------------------
--   fjdaryPfDisk                                                            --
-------------------------------------------------------------------------------
fjdaryPfDiskCount OBJECT-TYPE
    SYNTAX INTEGER(0..2147483647)
    ACCESS read-only
    STATUS mandatory
    DESCRIPTION
        "The number of DISK's performance informations
         (regardless of their current state) present on this system."
    ::= { fjdaryPfDisk 1 }

fjdaryPfDiskTable OBJECT-TYPE
    SYNTAX SEQUENCE OF FjdaryPfDiskEntry
    ACCESS not-accessible
    STATUS mandatory
    DESCRIPTION
        ""
    ::= { fjdaryPfDisk 2 }

fjdaryPfDiskEntry OBJECT-TYPE
    SYNTAX FjdaryPfDiskEntry
    ACCESS not-accessible
    STATUS mandatory
    DESCRIPTION
        ""
    INDEX { fjdaryPfDiskIndex }
    ::= { fjdaryPfDiskTable 1 }

FjdaryPfDiskEntry ::=
    SEQUENCE{
        fjdaryPfDiskIndex INTEGER,
        fjdaryPfDiskPlun  INTEGER,
        fjdaryPfDiskBusy  INTEGER
    }

fjdaryPfDiskIndex OBJECT-TYPE
    SYNTAX INTEGER(0..2147483647)
    ACCESS read-only
    STATUS mandatory
    DESCRIPTION
        "The value of this object uniquely identifies this fjdaryPfDisk entry."
    ::= { fjdaryPfDiskEntry 1 }

fjdaryPfDiskPlun OBJECT-TYPE
    SYNTAX INTEGER(-2147483648..2147483647)
    ACCESS read-only
    STATUS mandatory
    DESCRIPTION
        "This shows PLU number concerned DISK.
         the following definition:
           0xDDSS
             | |
             | +-slot number
             +-DE ID"
    ::= { fjdaryPfDiskEntry 2 }

fjdaryPfDiskBusy OBJECT-TYPE
    SYNTAX INTEGER(-2147483648..2147483647)
    ACCESS read-only
    STATUS mandatory
    DESCRIPTION
        "This shows DISK busy rate. The unit is percent."
    ::= { fjdaryPfDiskEntry 3 }

-------------------------------------------------------------------------------
--   fjdaryPfCm                                                              --
-------------------------------------------------------------------------------
fjdaryPfCmCount OBJECT-TYPE
    SYNTAX INTEGER(0..2147483647)
    ACCESS read-only
    STATUS mandatory
    DESCRIPTION
        "The number of CM's performance informations
         (regardless of their current state) present on this system."
    ::= { fjdaryPfCm 1 }

fjdaryPfCmTable OBJECT-TYPE
    SYNTAX SEQUENCE OF FjdaryPfCmEntry
    ACCESS not-accessible
    STATUS mandatory
    DESCRIPTION
        ""
    ::= { fjdaryPfCm 2 }

fjdaryPfCmEntry OBJECT-TYPE
    SYNTAX FjdaryPfCmEntry
    ACCESS not-accessible
    STATUS mandatory
    DESCRIPTION
        ""
    INDEX { fjdaryPfCmIndex }
    ::= { fjdaryPfCmTable 1 }

FjdaryPfCmEntry ::=
    SEQUENCE{
        fjdaryPfCmIndex    INTEGER,
        fjdaryPfCmBusy     INTEGER,
        fjdaryPfCmCpRemain OCTET STRING
    }

fjdaryPfCmIndex OBJECT-TYPE
    SYNTAX INTEGER(0..2147483647)
    ACCESS read-only
    STATUS mandatory
    DESCRIPTION
        "The value of this object uniquely identifies this fjdaryPfCm entry."
    ::= { fjdaryPfCmEntry 1 }

fjdaryPfCmBusy OBJECT-TYPE
    SYNTAX INTEGER(-2147483648..2147483647)
    ACCESS read-only
    STATUS mandatory
    DESCRIPTION
        "This shows the average of CPU busy rate. The unit is percent."
    ::= { fjdaryPfCmEntry 2 }

fjdaryPfCmCpRemain OBJECT-TYPE
    SYNTAX OCTET STRING (SIZE (0..256))
    ACCESS read-only
    STATUS mandatory
    DESCRIPTION
        "This shows the amount of the copy remainder. The unit is Byte."
    ::= { fjdaryPfCmEntry 3 }

-------------------------------------------------------------------------------
--   fjdaryPfCaPort                                                          --
-------------------------------------------------------------------------------
fjdaryPfCaPortCount OBJECT-TYPE
    SYNTAX INTEGER(0..2147483647)
    ACCESS read-only
    STATUS mandatory
    DESCRIPTION
        "The number of CA port's performance informations
         (regardless of their current state) present on this system."
    ::= { fjdaryPfCaPort 1 }

fjdaryPfCaPortTable OBJECT-TYPE
    SYNTAX SEQUENCE OF FjdaryPfCaPortEntry
    ACCESS not-accessible
    STATUS mandatory
    DESCRIPTION
        ""
    ::= { fjdaryPfCaPort 2 }

fjdaryPfCaPortEntry OBJECT-TYPE
    SYNTAX FjdaryPfCaPortEntry
    ACCESS not-accessible
    STATUS mandatory
    DESCRIPTION
        ""
    INDEX { fjdaryPfCaPortIndex }
    ::= { fjdaryPfCaPortTable 1 }

FjdaryPfCaPortEntry ::=
    SEQUENCE{
        fjdaryPfCaPortIndex  INTEGER,
        fjdaryPfCaPortMode   INTEGER,
        fjdaryPfCaPortRdIOPS INTEGER,
        fjdaryPfCaPortWtIOPS INTEGER,
        fjdaryPfCaPortRdTp   INTEGER,
        fjdaryPfCaPortWtTp   INTEGER
    }

fjdaryPfCaPortIndex OBJECT-TYPE
    SYNTAX INTEGER(0..2147483647)
    ACCESS read-only
    STATUS mandatory
    DESCRIPTION
        "The value of this object uniquely identifies this fjdaryPfCaPort
         entry."
    ::= { fjdaryPfCaPortEntry 1 }

fjdaryPfCaPortMode OBJECT-TYPE
    SYNTAX INTEGER {
        ca(11),
        ra(12),
        cara(13),
        initiator(20)
    }
    ACCESS read-only
    STATUS mandatory
    DESCRIPTION
        "This shows a mode concerned CA."
    ::= { fjdaryPfCaPortEntry 2 }

fjdaryPfCaPortRdIOPS OBJECT-TYPE
    SYNTAX INTEGER(-2147483648..2147483647)
    ACCESS read-only
    STATUS mandatory
    DESCRIPTION
        "This shows the READ IOPS for the CA,CARA mode.
         The Initiator IOPS is shown for RA,Initiator mode."
    ::= { fjdaryPfCaPortEntry 3 }

fjdaryPfCaPortWtIOPS OBJECT-TYPE
    SYNTAX INTEGER(-2147483648..2147483647)
    ACCESS read-only
    STATUS mandatory
    DESCRIPTION
        "This shows the WRITE IOPS for the CA,CARA mode.
         The Target IOPS is shown for the RA mode.
         This information is an invalid value for the Initiator mode."
    ::= { fjdaryPfCaPortEntry 4 }

fjdaryPfCaPortRdTp OBJECT-TYPE
    SYNTAX INTEGER(-2147483648..2147483647)
    ACCESS read-only
    STATUS mandatory
    DESCRIPTION
        "This shows the amount of the READ Throughput for the CA,CARA mode.
         The Initiator Throughput is shown for RA,Initiator mode.
         The unit is MB/sec."
    ::= { fjdaryPfCaPortEntry 5 }

fjdaryPfCaPortWtTp OBJECT-TYPE
    SYNTAX INTEGER(-2147483648..2147483647)
    ACCESS read-only
    STATUS mandatory
    DESCRIPTION
        "This shows the amount of the WRITE Throughput for the CA,CARA mode.
         The Target Throughput is shown for the RA mode.
         The unit is MB/sec.
         This information is an invalid value for the Initiator mode."
    ::= { fjdaryPfCaPortEntry 6 }

-------------------------------------------------------------------------------
--   fjdaryPfDtOlu                                                           --
-------------------------------------------------------------------------------
fjdaryPfDtOluCount OBJECT-TYPE
    SYNTAX INTEGER(0..2147483647)
    ACCESS read-only
    STATUS mandatory
    DESCRIPTION
        "The number of OLU's performance informations
         (regardless of their current state) present on this system."
    ::= { fjdaryPfDtOlu 1 }

fjdaryPfDtOluTable OBJECT-TYPE
    SYNTAX SEQUENCE OF FjdaryPfDtOluEntry
    ACCESS not-accessible
    STATUS mandatory
    DESCRIPTION
        ""
    ::= { fjdaryPfDtOlu 2 }

fjdaryPfDtOluEntry OBJECT-TYPE
    SYNTAX FjdaryPfDtOluEntry
    ACCESS not-accessible
    STATUS mandatory
    DESCRIPTION
        ""
    INDEX { fjdaryPfDtOluIndex }
    ::= { fjdaryPfDtOluTable 1 }

FjdaryPfDtOluEntry ::=
    SEQUENCE{
        fjdaryPfDtOluIndex INTEGER,
        fjdaryPfDtOluInfo  OCTET STRING
    }

fjdaryPfDtOluIndex OBJECT-TYPE
    SYNTAX INTEGER(0..2147483647)
    ACCESS read-only
    STATUS mandatory
    DESCRIPTION
        "The value of this object uniquely identifies this fjdaryPfDtOlu
         entry."
    ::= { fjdaryPfDtOluEntry 1 }

fjdaryPfDtOluInfo OBJECT-TYPE
    SYNTAX OCTET STRING (SIZE (0..256))
    ACCESS read-only
    STATUS mandatory
    DESCRIPTION
        "The value of this object indicates the OLU performance information.
         This information is a little endian.

                  byte 0       byte 1       byte 2       byte 3
              +------------+------------+------------+------------+
          0x00|OLU info#index*2 (80 bytes)                        |
              +------------+------------+------------+------------+
          0x50|OLU info#index*2+1 (80 bytes)                      |
              +------------+------------+------------+------------+

         OLU info#
                  byte 0       byte 1       byte 2       byte 3
              +------------+------------+------------+------------+
          0x00|fjdaryPfOluRdIOPS                                  |
              +------------+------------+------------+------------+
          0x04|fjdaryPfOluWtIOPS                                  |
              +------------+------------+------------+------------+
          0x08|fjdaryPfOluAdCpRdIOPS                              |
              +------------+------------+------------+------------+
          0x0c|fjdaryPfOluAdCpWtIOPS                              |
              +------------+------------+------------+------------+
          0x10|fjdaryPfOluRdTp                                    |
              +------------+------------+------------+------------+
          0x14|fjdaryPfOluWtTp                                    |
              +------------+------------+------------+------------+
          0x18|fjdaryPfOluAdCpRdTp                                |
              +------------+------------+------------+------------+
          0x1c|fjdaryPfOluAdCpWtTp                                |
              +------------+------------+------------+------------+
          0x20|fjdaryPfOluRdRspTime                               |
              +------------+------------+------------+------------+
          0x24|fjdaryPfOluWtRspTime                               |
              +------------+------------+------------+------------+
          0x28|Reserved                                           |
              +                                                   +
          0x2c|                                                   |
              +------------+------------+------------+------------+
          0x30|fjdaryPfOluRdCacheHit                              |
              +------------+------------+------------+------------+
          0x34|fjdaryPfOluWtCacheHit                              |
              +------------+------------+------------+------------+
          0x38|fjdaryPfOluAdRdCacheHit                            |
              +------------+------------+------------+------------+
          0x3c|fjdaryPfOluAdWtCacheHit                            |
              +------------+------------+------------+------------+
          0x40|fjdaryPfOluRdPreFetchHit                           |
              +------------+------------+------------+------------+
          0x44|fjdaryPfOluAdRdPreFetchHit                         |
              +------------+------------+------------+------------+
          0x48|fjdaryPfOluRdExcCacheHit                           |
              +------------+------------+------------+------------+
          0x4c|fjdaryPfOluAdRdExcCacheHit                         |
              +------------+------------+------------+------------+"
    ::= { fjdaryPfDtOluEntry 2 }

-------------------------------------------------------------------------------
--   fjdaryPfDtDisk                                                          --
-------------------------------------------------------------------------------
fjdaryPfDtDiskCount OBJECT-TYPE
    SYNTAX INTEGER(0..2147483647)
    ACCESS read-only
    STATUS mandatory
    DESCRIPTION
        "The number of DISK's performance informations
         (regardless of their current state) present on this system."
    ::= { fjdaryPfDtDisk 1 }

fjdaryPfDtDiskTable OBJECT-TYPE
    SYNTAX SEQUENCE OF FjdaryPfDtDiskEntry
    ACCESS not-accessible
    STATUS mandatory
    DESCRIPTION
        ""
    ::= { fjdaryPfDtDisk 2 }

fjdaryPfDtDiskEntry OBJECT-TYPE
    SYNTAX FjdaryPfDtDiskEntry
    ACCESS not-accessible
    STATUS mandatory
    DESCRIPTION
        ""
    INDEX { fjdaryPfDtDiskIndex }
    ::= { fjdaryPfDtDiskTable 1 }

FjdaryPfDtDiskEntry ::=
    SEQUENCE{
        fjdaryPfDtDiskIndex INTEGER,
        fjdaryPfDtDiskInfo  OCTET STRING
    }

fjdaryPfDtDiskIndex OBJECT-TYPE
    SYNTAX INTEGER(0..2147483647)
    ACCESS read-only
    STATUS mandatory
    DESCRIPTION
        "The value of this object uniquely identifies this fjdaryPfDtDisk
         entry."
    ::= { fjdaryPfDtDiskEntry 1 }

fjdaryPfDtDiskInfo OBJECT-TYPE
    SYNTAX OCTET STRING (SIZE (0..256))
    ACCESS read-only
    STATUS mandatory
    DESCRIPTION
        "The value of this object indicates the DISK performance information.
         This information is a little endian.

                  byte 0       byte 1       byte 2       byte 3
              +------------+------------+------------+------------+
          0x00|DISK info#index*26 (8 bytes)                       |
              +------------+------------+------------+------------+
          0x08|DISK info#index*26+1 (8 bytes)                     |
              +------------+------------+------------+------------+
              :                                                   :
              +------------+------------+------------+------------+
          0xcc|DISK info#index*26+25 (8 bytes)                    |
              +------------+------------+------------+------------+

         DISK info#
                  byte 0       byte 1       byte 2       byte 3
              +------------+------------+------------+------------+
          0x00|fjdaryPfDiskPlun         |Reserved                 |
              +------------+------------+------------+------------+
          0x04|fjdaryPfDiskBusy                                   |
              +------------+------------+------------+------------+"
    ::= { fjdaryPfDtDiskEntry 2 }

-------------------------------------------------------------------------------
--   fjdaryPfDtCm                                                            --
-------------------------------------------------------------------------------
fjdaryPfDtCmCount OBJECT-TYPE
    SYNTAX INTEGER(0..2147483647)
    ACCESS read-only
    STATUS mandatory
    DESCRIPTION
        "The number of CM's performance informations
         (regardless of their current state) present on this system."
    ::= { fjdaryPfDtCm 1 }

fjdaryPfDtCmTable OBJECT-TYPE
    SYNTAX SEQUENCE OF FjdaryPfDtCmEntry
    ACCESS not-accessible
    STATUS mandatory
    DESCRIPTION
        ""
    ::= { fjdaryPfDtCm 2 }

fjdaryPfDtCmEntry OBJECT-TYPE
    SYNTAX FjdaryPfDtCmEntry
    ACCESS not-accessible
    STATUS mandatory
    DESCRIPTION
        ""
    INDEX { fjdaryPfDtCmIndex }
    ::= { fjdaryPfDtCmTable 1 }

FjdaryPfDtCmEntry ::=
    SEQUENCE{
        fjdaryPfDtCmIndex INTEGER,
        fjdaryPfDtCmInfo  OCTET STRING
    }

fjdaryPfDtCmIndex OBJECT-TYPE
    SYNTAX INTEGER(0..2147483647)
    ACCESS read-only
    STATUS mandatory
    DESCRIPTION
        "The value of this object uniquely identifies this fjdaryPfDtCm entry."
    ::= { fjdaryPfDtCmEntry 1 }

fjdaryPfDtCmInfo OBJECT-TYPE
    SYNTAX OCTET STRING (SIZE (0..256))
    ACCESS read-only
    STATUS mandatory
    DESCRIPTION
        "The value of this object indicates the CM performance information.
         This information is a little endian.

                  byte 0       byte 1       byte 2       byte 3
              +------------+------------+------------+------------+
          0x00|CM info#index0 (16 bytes)                          |
              +------------+------------+------------+------------+
          0x10|CM info#index1 (16 bytes)                          |
              +------------+------------+------------+------------+

         CM info#
                  byte 0       byte 1       byte 2       byte 3
              +------------+------------+------------+------------+
          0x00|fjdaryPfCmBusy                                     |
              +------------+------------+------------+------------+
          0x04|Reserved                                           |
              +------------+------------+------------+------------+
          0x08|fjdaryPfCmCpRemain                                 |
              +                                                   +
          0x0c|                                                   |
              +------------+------------+------------+------------+"
    ::= { fjdaryPfDtCmEntry 2 }

-------------------------------------------------------------------------------
--   fjdaryPfDtCaPort                                                        --
-------------------------------------------------------------------------------
fjdaryPfDtCaPortCount OBJECT-TYPE
    SYNTAX INTEGER(0..2147483647)
    ACCESS read-only
    STATUS mandatory
    DESCRIPTION
        "The number of CA port's performance informations
         (regardless of their current state) present on this system."
    ::= { fjdaryPfDtCaPort 1 }

fjdaryPfDtCaPortTable OBJECT-TYPE
    SYNTAX SEQUENCE OF FjdaryPfDtCaPortEntry
    ACCESS not-accessible
    STATUS mandatory
    DESCRIPTION
        ""
    ::= { fjdaryPfDtCaPort 2 }

fjdaryPfDtCaPortEntry OBJECT-TYPE
    SYNTAX FjdaryPfDtCaPortEntry
    ACCESS not-accessible
    STATUS mandatory
    DESCRIPTION
        ""
    INDEX { fjdaryPfDtCaPortIndex }
    ::= { fjdaryPfDtCaPortTable 1 }

FjdaryPfDtCaPortEntry ::=
    SEQUENCE{
        fjdaryPfDtCaPortIndex INTEGER,
        fjdaryPfDtCaPortInfo  OCTET STRING
    }

fjdaryPfDtCaPortIndex OBJECT-TYPE
    SYNTAX INTEGER(0..2147483647)
    ACCESS read-only
    STATUS mandatory
    DESCRIPTION
        "The value of this object uniquely identifies this fjdaryPfDtCaPort
         entry."
    ::= { fjdaryPfDtCaPortEntry 1 }

fjdaryPfDtCaPortInfo OBJECT-TYPE
    SYNTAX OCTET STRING (SIZE (0..256))
    ACCESS read-only
    STATUS mandatory
    DESCRIPTION
        "The value of this object indicates the CA port performance
         information.
         This information is a little endian.
         This information is an invalid value for the RA,Initiator mode.

                  byte 0       byte 1       byte 2       byte 3
              +------------+------------+------------+------------+
          0x00|CA port info#index*16 (16 bytes)                   |
              +------------+------------+------------+------------+
          0x10|CA port info#index*16+1 (16 bytes)                 |
              +------------+------------+------------+------------+
              :                                                   :
              +------------+------------+------------+------------+
          0xf0|CA port info#index*16+15 (16 bytes)                |
              +------------+------------+------------+------------+

         CA port info#
                  byte 0       byte 1       byte 2       byte 3
              +------------+------------+------------+------------+
          0x00|fjdaryPfCaPortRdIOPS                               |
              +------------+------------+------------+------------+
          0x04|fjdaryPfCaPortWtIOPS                               |
              +------------+------------+------------+------------+
          0x08|fjdaryPfCaPortRdTp                                 |
              +------------+------------+------------+------------+
          0x0c|fjdaryPfCaPortWtTp                                 |
              +------------+------------+------------+------------+"
    ::= { fjdaryPfDtCaPortEntry 2 }

-------------------------------------------------------------------------------
--   fjdaryPfRaPort                                                          --
-------------------------------------------------------------------------------
fjdaryPfRaPortCount OBJECT-TYPE
    SYNTAX INTEGER(0..2147483647)
    ACCESS read-only
    STATUS mandatory
    DESCRIPTION
        "The number of CA port's performance informations
         (regardless of their current state) present on this system."
    ::= { fjdaryPfRaPort 1 }

fjdaryPfRaPortTable OBJECT-TYPE
    SYNTAX SEQUENCE OF FjdaryPfRaPortEntry
    ACCESS not-accessible
    STATUS mandatory
    DESCRIPTION
        ""
    ::= { fjdaryPfRaPort 2 }

fjdaryPfRaPortEntry OBJECT-TYPE
    SYNTAX FjdaryPfRaPortEntry
    ACCESS not-accessible
    STATUS mandatory
    DESCRIPTION
        ""
    INDEX { fjdaryPfRaPortIndex }
    ::= { fjdaryPfRaPortTable 1 }

FjdaryPfRaPortEntry ::=
    SEQUENCE{
        fjdaryPfRaPortIndex  INTEGER,
        fjdaryPfRaPortMode   INTEGER,
        fjdaryPfRaPortRdIOPS INTEGER,
        fjdaryPfRaPortWtIOPS INTEGER,
        fjdaryPfRaPortRdTp   INTEGER,
        fjdaryPfRaPortWtTp   INTEGER
    }

fjdaryPfRaPortIndex OBJECT-TYPE
    SYNTAX INTEGER(0..2147483647)
    ACCESS read-only
    STATUS mandatory
    DESCRIPTION
        "The value of this object uniquely identifies this fjdaryPfRaPort
         entry."
    ::= { fjdaryPfRaPortEntry 1 }

fjdaryPfRaPortMode OBJECT-TYPE
    SYNTAX INTEGER {
        ca(11),
        ra(12),
        cara(13),
        initiator(20)
    }
    ACCESS read-only
    STATUS mandatory
    DESCRIPTION
        "This shows a mode concerned CA."
    ::= { fjdaryPfRaPortEntry 2 }

fjdaryPfRaPortRdIOPS OBJECT-TYPE
    SYNTAX INTEGER(-2147483648..2147483647)
    ACCESS read-only
    STATUS mandatory
    DESCRIPTION
        "The Initiator IOPS is shown for RA,Initiator,CARA mode.
         This information is an invalid value for the CA mode."
    ::= { fjdaryPfRaPortEntry 3 }

fjdaryPfRaPortWtIOPS OBJECT-TYPE
    SYNTAX INTEGER(-2147483648..2147483647)
    ACCESS read-only
    STATUS mandatory
    DESCRIPTION
        "The Target IOPS is shown for the RA,CARA mode.
         This information is an invalid value for the Initiator,CA mode."
    ::= { fjdaryPfRaPortEntry 4 }

fjdaryPfRaPortRdTp OBJECT-TYPE
    SYNTAX INTEGER(-2147483648..2147483647)
    ACCESS read-only
    STATUS mandatory
    DESCRIPTION
        "The Initiator Throughput is shown for RA,Initiator,CARA mode.
         The unit is MB/sec.
         This information is an invalid value for the CA mode."
    ::= { fjdaryPfRaPortEntry 5 }

fjdaryPfRaPortWtTp OBJECT-TYPE
    SYNTAX INTEGER(-2147483648..2147483647)
    ACCESS read-only
    STATUS mandatory
    DESCRIPTION
        "The Target Throughput is shown for the RA,CARA mode.
         The unit is MB/sec.
         This information is an invalid value for the Initiator,CA mode."
    ::= { fjdaryPfRaPortEntry 6 }

-------------------------------------------------------------------------------
--   fjdaryPfDtRaPort                                                        --
-------------------------------------------------------------------------------
fjdaryPfDtRaPortCount OBJECT-TYPE
    SYNTAX INTEGER(0..2147483647)
    ACCESS read-only
    STATUS mandatory
    DESCRIPTION
        "The number of CA port's performance informations
         (regardless of their current state) present on this system."
    ::= { fjdaryPfDtRaPort 1 }

fjdaryPfDtRaPortTable OBJECT-TYPE
    SYNTAX SEQUENCE OF FjdaryPfDtRaPortEntry
    ACCESS not-accessible
    STATUS mandatory
    DESCRIPTION
        ""
    ::= { fjdaryPfDtRaPort 2 }

fjdaryPfDtRaPortEntry OBJECT-TYPE
    SYNTAX FjdaryPfDtRaPortEntry
    ACCESS not-accessible
    STATUS mandatory
    DESCRIPTION
        ""
    INDEX { fjdaryPfDtRaPortIndex }
    ::= { fjdaryPfDtRaPortTable 1 }

FjdaryPfDtRaPortEntry ::=
    SEQUENCE{
        fjdaryPfDtRaPortIndex INTEGER,
        fjdaryPfDtRaPortInfo  OCTET STRING
    }

fjdaryPfDtRaPortIndex OBJECT-TYPE
    SYNTAX INTEGER(0..2147483647)
    ACCESS read-only
    STATUS mandatory
    DESCRIPTION
        "The value of this object uniquely identifies this fjdaryPfDtRaPort
         entry."
    ::= { fjdaryPfDtRaPortEntry 1 }

fjdaryPfDtRaPortInfo OBJECT-TYPE
    SYNTAX OCTET STRING (SIZE (0..256))
    ACCESS read-only
    STATUS mandatory
    DESCRIPTION
        "The value of this object indicates the CA port performance
         information.
         This information is a little endian.
         This information is an invalid value for the CA mode.

                  byte 0       byte 1       byte 2       byte 3
              +------------+------------+------------+------------+
          0x00|CA port info#index*16 (16 bytes)                   |
              +------------+------------+------------+------------+
          0x10|CA port info#index*16+1 (16 bytes)                 |
              +------------+------------+------------+------------+
              :                                                   :
              +------------+------------+------------+------------+
          0xf0|CA port info#index*16+15 (16 bytes)                |
              +------------+------------+------------+------------+

         CA port info#
                  byte 0       byte 1       byte 2       byte 3
              +------------+------------+------------+------------+
          0x00|fjdaryPfRaPortRdIOPS                               |
              +------------+------------+------------+------------+
          0x04|fjdaryPfRaPortWtIOPS                               |
              +------------+------------+------------+------------+
          0x08|fjdaryPfRaPortRdTp                                 |
              +------------+------------+------------+------------+
          0x0c|fjdaryPfRaPortWtTp                                 |
              +------------+------------+------------+------------+"
    ::= { fjdaryPfDtRaPortEntry 2 }

-------------------------------------------------------------------------------
--   fjdaryPfPfm                                                             --
-------------------------------------------------------------------------------
fjdaryPfPfmCount OBJECT-TYPE
    SYNTAX INTEGER(0..2147483647)
    ACCESS read-only
    STATUS mandatory
    DESCRIPTION
        "The number of PFM's performance informations
         (regardless of their current state) present on this system."
    ::= { fjdaryPfPfm 1 }

fjdaryPfPfmTable OBJECT-TYPE
    SYNTAX SEQUENCE OF FjdaryPfPfmEntry
    ACCESS not-accessible
    STATUS mandatory
    DESCRIPTION
        ""
    ::= { fjdaryPfPfm 2 }

fjdaryPfPfmEntry OBJECT-TYPE
    SYNTAX FjdaryPfPfmEntry
    ACCESS not-accessible
    STATUS mandatory
    DESCRIPTION
        ""
    INDEX { fjdaryPfPfmIndex }
    ::= { fjdaryPfPfmTable 1 }

FjdaryPfPfmEntry ::=
    SEQUENCE{
        fjdaryPfPfmIndex     INTEGER,
        fjdaryPfPfmBusy      INTEGER
    }

fjdaryPfPfmIndex OBJECT-TYPE
    SYNTAX INTEGER(0..2147483647)
    ACCESS read-only
    STATUS mandatory
    DESCRIPTION
        "The value of this object uniquely identifies this fjdaryPfPfm entry."
    ::= { fjdaryPfPfmEntry 1 }

fjdaryPfPfmBusy OBJECT-TYPE
    SYNTAX INTEGER(-2147483648..2147483647)
    ACCESS read-only
    STATUS mandatory
    DESCRIPTION
        "This shows a busy rate of PFM. The unit is percent."
    ::= { fjdaryPfPfmEntry 2 }

-------------------------------------------------------------------------------
--   fjdaryPfDtPfm                                                           --
-------------------------------------------------------------------------------
fjdaryPfDPfmCount OBJECT-TYPE
    SYNTAX INTEGER(0..2147483647)
    ACCESS read-only
    STATUS mandatory
    DESCRIPTION
        "The number of PFM's performance informations
         (regardless of their current state) present on this system."
    ::= { fjdaryPfDtPfm 1 }

fjdaryPfDtPfmTable OBJECT-TYPE
    SYNTAX SEQUENCE OF FjdaryPfDtPfmEntry
    ACCESS not-accessible
    STATUS mandatory
    DESCRIPTION
        ""
    ::= { fjdaryPfDtPfm 2 }

fjdaryPfDtPfmEntry OBJECT-TYPE
    SYNTAX FjdaryPfDtPfmEntry
    ACCESS not-accessible
    STATUS mandatory
    DESCRIPTION
        ""
    INDEX { fjdaryPfDtPfmIndex }
    ::= { fjdaryPfDtPfmTable 1 }

FjdaryPfDtPfmEntry ::=
    SEQUENCE{
        fjdaryPfDtPfmIndex   INTEGER,
        fjdaryPfDtPfmInfo    OCTET STRING
    }

fjdaryPfDtPfmIndex OBJECT-TYPE
    SYNTAX INTEGER(0..2147483647)
    ACCESS read-only
    STATUS mandatory
    DESCRIPTION
        "The value of this object uniquely identifies this fjdaryPfDtPfm
         entry."
    ::= { fjdaryPfDtPfmEntry 1 }

fjdaryPfDtPfmInfo OBJECT-TYPE
    SYNTAX OCTET STRING (SIZE (0..256))
    ACCESS read-only
    STATUS mandatory
    DESCRIPTION
        "The value of this object indicates the PFM performance
         information.
         This information is a little endian.

                  byte 0       byte 1       byte 2       byte 3
              +------------+------------+------------+------------+
          0x00|PFM info#index0 (8 bytes)                          |
              +------------+------------+------------+------------+
          0x08|PFM info#index1 (8 bytes)                          |
              +------------+------------+------------+------------+
              :                                                   :
              +------------+------------+------------+------------+
          0x3c|PFM info#index7 (8 bytes)                          |
              +------------+------------+------------+------------+

         PFM info#
                  byte 0       byte 1       byte 2       byte 3
              +------------+------------+------------+------------+
          0x00|PFM No                   |Reserved                 |
              +------------+------------+------------+------------+
          0x04|fjdaryPfPfmBusy                                    |
              +------------+------------+------------+------------+"
    ::= { fjdaryPfDtPfmEntry 2 }

-------------------------------------------------------------------------------
--   fjdaryPfCmCore                                                          --
-------------------------------------------------------------------------------
fjdaryPfCmCoreCount OBJECT-TYPE
    SYNTAX INTEGER(0..2147483647)
    ACCESS read-only
    STATUS mandatory
    DESCRIPTION
        "The number of CM core's performance informations
         (regardless of their current state) present on this system."
    ::= { fjdaryPfCmCore 1 }

fjdaryPfCmCoreTable OBJECT-TYPE
    SYNTAX SEQUENCE OF FjdaryPfCmCoreEntry
    ACCESS not-accessible
    STATUS mandatory
    DESCRIPTION
        ""
    ::= { fjdaryPfCmCore 2 }

fjdaryPfCmCoreEntry OBJECT-TYPE
    SYNTAX FjdaryPfCmCoreEntry
    ACCESS not-accessible
    STATUS mandatory
    DESCRIPTION
        ""
    INDEX { fjdaryPfCmCoreIndex }
    ::= { fjdaryPfCmCoreTable 1 }

FjdaryPfCmCoreEntry ::=
    SEQUENCE{
        fjdaryPfCmCoreIndex      INTEGER,
        fjdaryPfCmCoreValidCount INTEGER,
        fjdaryPfCmCoreBusy0      INTEGER,
        fjdaryPfCmCoreBusy1      INTEGER,
        fjdaryPfCmCoreBusy2      INTEGER,
        fjdaryPfCmCoreBusy3      INTEGER,
        fjdaryPfCmCoreBusy4      INTEGER,
        fjdaryPfCmCoreBusy5      INTEGER,
        fjdaryPfCmCoreBusy6      INTEGER,
        fjdaryPfCmCoreBusy7      INTEGER,
        fjdaryPfCmCoreBusy8      INTEGER,
        fjdaryPfCmCoreBusy9      INTEGER,
        fjdaryPfCmCoreBusy10     INTEGER,
        fjdaryPfCmCoreBusy11     INTEGER,
        fjdaryPfCmCoreBusy12     INTEGER,
        fjdaryPfCmCoreBusy13     INTEGER,
        fjdaryPfCmCoreBusy14     INTEGER,
        fjdaryPfCmCoreBusy15     INTEGER,
        fjdaryPfCmCoreBusy16     INTEGER,
        fjdaryPfCmCoreBusy17     INTEGER,
        fjdaryPfCmCoreBusy18     INTEGER,
        fjdaryPfCmCoreBusy19     INTEGER
    }

fjdaryPfCmCoreIndex OBJECT-TYPE
    SYNTAX INTEGER(0..2147483647)
    ACCESS read-only
    STATUS mandatory
    DESCRIPTION
        "The value of this object uniquely identifies this fjdaryPfCmCore
         entry."
    ::= { fjdaryPfCmCoreEntry 1 }

fjdaryPfCmCoreValidCount OBJECT-TYPE
    SYNTAX INTEGER(-2147483648..2147483647)
    ACCESS read-only
    STATUS mandatory
    DESCRIPTION
        "This shows an effective number of this information.
         For instance, when this value is two, fjdaryPfCmCoreBusy0
         and fjdaryPfCmCoreBusy1 become effective information."
    ::= { fjdaryPfCmCoreEntry 2 }

fjdaryPfCmCoreBusy0 OBJECT-TYPE
    SYNTAX INTEGER(-2147483648..2147483647)
    ACCESS read-only
    STATUS mandatory
    DESCRIPTION
        "This shows the busy rate of CPU core#0 for SAN.
         The unit is percent."
    ::= { fjdaryPfCmCoreEntry 3 }

fjdaryPfCmCoreBusy1 OBJECT-TYPE
    SYNTAX INTEGER(-2147483648..2147483647)
    ACCESS read-only
    STATUS mandatory
    DESCRIPTION
        "This shows the busy rate of CPU core#1 for SAN.
         The unit is percent."
    ::= { fjdaryPfCmCoreEntry 4 }

fjdaryPfCmCoreBusy2 OBJECT-TYPE
    SYNTAX INTEGER(-2147483648..2147483647)
    ACCESS read-only
    STATUS mandatory
    DESCRIPTION
        "This shows the busy rate of CPU core#2 for SAN.
         The unit is percent."
    ::= { fjdaryPfCmCoreEntry 5 }

fjdaryPfCmCoreBusy3 OBJECT-TYPE
    SYNTAX INTEGER(-2147483648..2147483647)
    ACCESS read-only
    STATUS mandatory
    DESCRIPTION
        "This shows the busy rate of CPU core#3 for SAN.
         The unit is percent."
    ::= { fjdaryPfCmCoreEntry 6 }

fjdaryPfCmCoreBusy4 OBJECT-TYPE
    SYNTAX INTEGER(-2147483648..2147483647)
    ACCESS read-only
    STATUS mandatory
    DESCRIPTION
        "This shows the busy rate of CPU core#4 for SAN.
         The unit is percent."
    ::= { fjdaryPfCmCoreEntry 7 }

fjdaryPfCmCoreBusy5 OBJECT-TYPE
    SYNTAX INTEGER(-2147483648..2147483647)
    ACCESS read-only
    STATUS mandatory
    DESCRIPTION
        "This shows the busy rate of CPU core#5 for SAN.
         The unit is percent."
    ::= { fjdaryPfCmCoreEntry 8 }

fjdaryPfCmCoreBusy6 OBJECT-TYPE
    SYNTAX INTEGER(-2147483648..2147483647)
    ACCESS read-only
    STATUS mandatory
    DESCRIPTION
        "This shows the busy rate of CPU core#6 for SAN.
         The unit is percent."
    ::= { fjdaryPfCmCoreEntry 9 }

fjdaryPfCmCoreBusy7 OBJECT-TYPE
    SYNTAX INTEGER(-2147483648..2147483647)
    ACCESS read-only
    STATUS mandatory
    DESCRIPTION
        "This shows the busy rate of CPU core#7 for SAN.
         The unit is percent."
    ::= { fjdaryPfCmCoreEntry 10 }

fjdaryPfCmCoreBusy8 OBJECT-TYPE
    SYNTAX INTEGER(-2147483648..2147483647)
    ACCESS read-only
    STATUS mandatory
    DESCRIPTION
        "This shows the busy rate of CPU core#8 for SAN.
         The unit is percent."
    ::= { fjdaryPfCmCoreEntry 11 }

fjdaryPfCmCoreBusy9 OBJECT-TYPE
    SYNTAX INTEGER(-2147483648..2147483647)
    ACCESS read-only
    STATUS mandatory
    DESCRIPTION
        "This shows the busy rate of CPU core#9 for SAN.
         The unit is percent."
    ::= { fjdaryPfCmCoreEntry 12 }

fjdaryPfCmCoreBusy10 OBJECT-TYPE
    SYNTAX INTEGER(-2147483648..2147483647)
    ACCESS read-only
    STATUS mandatory
    DESCRIPTION
        "This shows the busy rate of CPU core#10 for SAN.
         The unit is percent."
    ::= { fjdaryPfCmCoreEntry 13 }

fjdaryPfCmCoreBusy11 OBJECT-TYPE
    SYNTAX INTEGER(-2147483648..2147483647)
    ACCESS read-only
    STATUS mandatory
    DESCRIPTION
        "This shows the busy rate of CPU core#11 for SAN.
         The unit is percent."
    ::= { fjdaryPfCmCoreEntry 14 }

fjdaryPfCmCoreBusy12 OBJECT-TYPE
    SYNTAX INTEGER(-2147483648..2147483647)
    ACCESS read-only
    STATUS mandatory
    DESCRIPTION
        "This shows the busy rate of CPU core#12 for SAN.
         The unit is percent."
    ::= { fjdaryPfCmCoreEntry 15 }

fjdaryPfCmCoreBusy13 OBJECT-TYPE
    SYNTAX INTEGER(-2147483648..2147483647)
    ACCESS read-only
    STATUS mandatory
    DESCRIPTION
        "This shows the busy rate of CPU core#13 for SAN.
         The unit is percent."
    ::= { fjdaryPfCmCoreEntry 16 }

fjdaryPfCmCoreBusy14 OBJECT-TYPE
    SYNTAX INTEGER(-2147483648..2147483647)
    ACCESS read-only
    STATUS mandatory
    DESCRIPTION
        "This shows the busy rate of CPU core#14 for SAN.
         The unit is percent."
    ::= { fjdaryPfCmCoreEntry 17 }

fjdaryPfCmCoreBusy15 OBJECT-TYPE
    SYNTAX INTEGER(-2147483648..2147483647)
    ACCESS read-only
    STATUS mandatory
    DESCRIPTION
        "This shows the busy rate of CPU core#15 for SAN.
         The unit is percent."
    ::= { fjdaryPfCmCoreEntry 18 }

fjdaryPfCmCoreBusy16 OBJECT-TYPE
    SYNTAX INTEGER(-2147483648..2147483647)
    ACCESS read-only
    STATUS mandatory
    DESCRIPTION
        "This shows the busy rate of CPU core#16 for SAN.
         The unit is percent."
    ::= { fjdaryPfCmCoreEntry 19 }

fjdaryPfCmCoreBusy17 OBJECT-TYPE
    SYNTAX INTEGER(-2147483648..2147483647)
    ACCESS read-only
    STATUS mandatory
    DESCRIPTION
        "This shows the busy rate of CPU core#17 for SAN.
         The unit is percent."
    ::= { fjdaryPfCmCoreEntry 20 }

fjdaryPfCmCoreBusy18 OBJECT-TYPE
    SYNTAX INTEGER(-2147483648..2147483647)
    ACCESS read-only
    STATUS mandatory
    DESCRIPTION
        "This shows the busy rate of CPU core#18 for SAN.
         The unit is percent."
    ::= { fjdaryPfCmCoreEntry 21 }

fjdaryPfCmCoreBusy19 OBJECT-TYPE
    SYNTAX INTEGER(-2147483648..2147483647)
    ACCESS read-only
    STATUS mandatory
    DESCRIPTION
        "This shows the busy rate of CPU core#19 for SAN.
         The unit is percent."
    ::= { fjdaryPfCmCoreEntry 22 }

-------------------------------------------------------------------------------
--   fjdaryPfDtCmCore                                                        --
-------------------------------------------------------------------------------
fjdaryPfDtCmCoreCount OBJECT-TYPE
    SYNTAX INTEGER(0..2147483647)
    ACCESS read-only
    STATUS mandatory
    DESCRIPTION
        "The number of CM core's performance informations
         (regardless of their current state) present on this system."
    ::= { fjdaryPfDtCmCore 1 }

fjdaryPfDtCmCoreTable OBJECT-TYPE
    SYNTAX SEQUENCE OF FjdaryPfDtCmCoreEntry
    ACCESS not-accessible
    STATUS mandatory
    DESCRIPTION
        ""
    ::= { fjdaryPfDtCmCore 2 }

fjdaryPfDtCmCoreEntry OBJECT-TYPE
    SYNTAX FjdaryPfDtCmCoreEntry
    ACCESS not-accessible
    STATUS mandatory
    DESCRIPTION
        ""
    INDEX { fjdaryPfDtCmCoreIndex }
    ::= { fjdaryPfDtCmCoreTable 1 }

FjdaryPfDtCmCoreEntry ::=
    SEQUENCE{
        fjdaryPfDtCmCoreIndex INTEGER,
        fjdaryPfDtCmCoreInfo  OCTET STRING
    }

fjdaryPfDtCmCoreIndex OBJECT-TYPE
    SYNTAX INTEGER(0..2147483647)
    ACCESS read-only
    STATUS mandatory
    DESCRIPTION
        "The value of this object uniquely identifies this fjdaryPfDtCmCore
         entry."
    ::= { fjdaryPfDtCmCoreEntry 1 }

fjdaryPfDtCmCoreInfo OBJECT-TYPE
    SYNTAX OCTET STRING (SIZE (0..256))
    ACCESS read-only
    STATUS mandatory
    DESCRIPTION
        "The value of this object indicates the CM core performance
         information. This information is a little endian.

                  byte 0       byte 1       byte 2       byte 3
              +------------+------------+------------+------------+
          0x00|CM core info#index0 (88 bytes)                     |
              +------------+------------+------------+------------+
          0x58|CM core info#index1 (88 bytes)                     |
              +------------+------------+------------+------------+

         CM core info#
                  byte 0       byte 1       byte 2       byte 3
              +------------+------------+------------+------------+
          0x00|fjdaryPfCm  |Reserved                              |
              | Core       |                                      |
              | ValidCount |                                      |
              +------------+------------+------------+------------+
          0x04|Reserved                                           |
              +------------+------------+------------+------------+
          0x08|fjdaryPfCmCoreBusy0                                |
              +------------+------------+------------+------------+
          0x0c|fjdaryPfCmCoreBusy1                                |
              +------------+------------+------------+------------+
              :                                                   :
              +------------+------------+------------+------------+
          0x54|fjdaryPfCmCoreBusy19                               |
              +------------+------------+------------+------------+"
    ::= { fjdaryPfDtCmCoreEntry 2 }

-------------------------------------------------------------------------------
--   fjdaryPfCmNas                                                           --
-------------------------------------------------------------------------------
fjdaryPfCmNasCount OBJECT-TYPE
    SYNTAX INTEGER(0..2147483647)
    ACCESS read-only
    STATUS mandatory
    DESCRIPTION
        "The number of CM NAS performance informations
         (regardless of their current state) present on this system."
    ::= { fjdaryPfCmNas 1 }

fjdaryPfCmNasTable OBJECT-TYPE
    SYNTAX SEQUENCE OF FjdaryPfCmNasEntry
    ACCESS not-accessible
    STATUS mandatory
    DESCRIPTION
        ""
    ::= { fjdaryPfCmNas 2 }

fjdaryPfCmNasEntry OBJECT-TYPE
    SYNTAX FjdaryPfCmNasEntry
    ACCESS not-accessible
    STATUS mandatory
    DESCRIPTION
        ""
    INDEX { fjdaryPfCmNasIndex }
    ::= { fjdaryPfCmNasTable 1 }

FjdaryPfCmNasEntry ::=
    SEQUENCE{
        fjdaryPfCmNasIndex           INTEGER,
        fjdaryPfCmNasIOWaitTime      INTEGER,
        fjdaryPfCmNasRdThroughput    INTEGER,
        fjdaryPfCmNasWtThroughput    INTEGER,
        fjdaryPfCmNasIOCPUBusy       INTEGER,
        fjdaryPfCmNasUsageRate       INTEGER,
        fjdaryPfCmNasUsedAmount      INTEGER,
        fjdaryPfCmNasSambaOpCount    INTEGER,
        fjdaryPfCmNasNFSOpCount      INTEGER,
        fjdaryPfCmNasNtInThroughput  INTEGER,
        fjdaryPfCmNasNtOutThroughput INTEGER,
        fjdaryPfCmNasCPUBusy         INTEGER,
        fjdaryPfCmNasFreeMemory      INTEGER,
        fjdaryPfCmNasCachedMemory    INTEGER,
        fjdaryPfCmNasCPUIOWait       INTEGER
    }

fjdaryPfCmNasIndex OBJECT-TYPE
    SYNTAX INTEGER(0..2147483647)
    ACCESS read-only
    STATUS mandatory
    DESCRIPTION
        "The value of this object uniquely identifies this fjdaryPfCmNas
         entry."
    ::= { fjdaryPfCmNasEntry 1 }

fjdaryPfCmNasIOWaitTime OBJECT-TYPE
    SYNTAX INTEGER(-2147483648..2147483647)
    ACCESS read-only
    STATUS mandatory
    DESCRIPTION
        "This shows the average of the I/O request at waiting time.
         The unit is msec."
    ::= { fjdaryPfCmNasEntry 2 }

fjdaryPfCmNasRdThroughput OBJECT-TYPE
    SYNTAX INTEGER(-2147483648..2147483647)
    ACCESS read-only
    STATUS mandatory
    DESCRIPTION
        "This shows the READ Throughput. The unit is MB/sec."
    ::= { fjdaryPfCmNasEntry 3 }

fjdaryPfCmNasWtThroughput OBJECT-TYPE
    SYNTAX INTEGER(-2147483648..2147483647)
    ACCESS read-only
    STATUS mandatory
    DESCRIPTION
        "This shows the WRITE Throughput. The unit is MB/sec."
    ::= { fjdaryPfCmNasEntry 4 }

fjdaryPfCmNasIOCPUBusy OBJECT-TYPE
    SYNTAX INTEGER(-2147483648..2147483647)
    ACCESS read-only
    STATUS mandatory
    DESCRIPTION
        "This shows the busy rate of CPU at the I/O request period.
         The unit is percent."
    ::= { fjdaryPfCmNasEntry 5 }

fjdaryPfCmNasUsageRate OBJECT-TYPE
    SYNTAX INTEGER(-2147483648..2147483647)
    ACCESS read-only
    STATUS mandatory
    DESCRIPTION
        "This shows the usage rate of the NAS volume. The unit is percent."
    ::= { fjdaryPfCmNasEntry 6 }

fjdaryPfCmNasUsedAmount OBJECT-TYPE
    SYNTAX INTEGER(-2147483648..2147483647)
    ACCESS read-only
    STATUS mandatory
    DESCRIPTION
        "This shows the used amount of the NAS volume. The unit is KB."
    ::= { fjdaryPfCmNasEntry 7 }

fjdaryPfCmNasSambaOpCount OBJECT-TYPE
    SYNTAX INTEGER(-2147483648..2147483647)
    ACCESS read-only
    STATUS mandatory
    DESCRIPTION
        "This shows the number of per second of Samba operations."
    ::= { fjdaryPfCmNasEntry 8 }

fjdaryPfCmNasNFSOpCount OBJECT-TYPE
    SYNTAX INTEGER(-2147483648..2147483647)
    ACCESS read-only
    STATUS mandatory
    DESCRIPTION
        "This shows the number of per second of NFS operations."
    ::= { fjdaryPfCmNasEntry 9 }

fjdaryPfCmNasNtInThroughput OBJECT-TYPE
    SYNTAX INTEGER(-2147483648..2147483647)
    ACCESS read-only
    STATUS mandatory
    DESCRIPTION
        "This shows the receive throughput in the network interface.
         The unit is MB/sec."
    ::= { fjdaryPfCmNasEntry 10 }

fjdaryPfCmNasNtOutThroughput OBJECT-TYPE
    SYNTAX INTEGER(-2147483648..2147483647)
    ACCESS read-only
    STATUS mandatory
    DESCRIPTION
        "This shows the transmit throughput in the network interface.
         The unit is MB/sec."
    ::= { fjdaryPfCmNasEntry 11 }

fjdaryPfCmNasCPUBusy OBJECT-TYPE
    SYNTAX INTEGER(-2147483648..2147483647)
    ACCESS read-only
    STATUS mandatory
    DESCRIPTION
        "This shows the average of CPU busy rate for NAS.
         The unit is percent."
    ::= { fjdaryPfCmNasEntry 12 }

fjdaryPfCmNasFreeMemory OBJECT-TYPE
    SYNTAX INTEGER(-2147483648..2147483647)
    ACCESS read-only
    STATUS mandatory
    DESCRIPTION
        "This shows an unused amount of the memory. The unit is KB."
    ::= { fjdaryPfCmNasEntry 13 }

fjdaryPfCmNasCachedMemory OBJECT-TYPE
    SYNTAX INTEGER(-2147483648..2147483647)
    ACCESS read-only
    STATUS mandatory
    DESCRIPTION
        "This shows the amount of the memory in which the cache data is
         retained when the disk is accessed. The unit is KB."
    ::= { fjdaryPfCmNasEntry 14 }

fjdaryPfCmNasCPUIOWait OBJECT-TYPE
    SYNTAX INTEGER(-2147483648..2147483647)
    ACCESS read-only
    STATUS mandatory
    DESCRIPTION
        "This shows the average of CPU I/O wait rate for NAS.
         The unit is percent."
    ::= { fjdaryPfCmNasEntry 15 }

-------------------------------------------------------------------------------
--   fjdaryPfDtCmNas                                                         --
-------------------------------------------------------------------------------
fjdaryPfDtCmNasCount OBJECT-TYPE
    SYNTAX INTEGER(0..2147483647)
    ACCESS read-only
    STATUS mandatory
    DESCRIPTION
        "The number of CM NAS performance informations
         (regardless of their current state) present on this system."
    ::= { fjdaryPfDtCmNas 1 }

fjdaryPfDtCmNasTable OBJECT-TYPE
    SYNTAX SEQUENCE OF FjdaryPfDtCmNasEntry
    ACCESS not-accessible
    STATUS mandatory
    DESCRIPTION
        ""
    ::= { fjdaryPfDtCmNas 2 }

fjdaryPfDtCmNasEntry OBJECT-TYPE
    SYNTAX FjdaryPfDtCmNasEntry
    ACCESS not-accessible
    STATUS mandatory
    DESCRIPTION
        ""
    INDEX { fjdaryPfDtCmNasIndex }
    ::= { fjdaryPfDtCmNasTable 1 }

FjdaryPfDtCmNasEntry ::=
    SEQUENCE{
        fjdaryPfDtCmNasIndex INTEGER,
        fjdaryPfDtCmNasInfo  OCTET STRING
    }

fjdaryPfDtCmNasIndex OBJECT-TYPE
    SYNTAX INTEGER(0..2147483647)
    ACCESS read-only
    STATUS mandatory
    DESCRIPTION
        "The value of this object uniquely identifies this fjdaryPfDtCmNas
         entry."
    ::= { fjdaryPfDtCmNasEntry 1 }

fjdaryPfDtCmNasInfo OBJECT-TYPE
    SYNTAX OCTET STRING (SIZE (0..256))
    ACCESS read-only
    STATUS mandatory
    DESCRIPTION
        "The value of this object indicates the CM NAS performance
         information. This information is a little endian.

                  byte 0       byte 1       byte 2       byte 3
              +------------+------------+------------+------------+
          0x00|fjdaryPfCmNasIOWaitTime                            |
              +------------+------------+------------+------------+
          0x04|Reserved                                           |
              +------------+------------+------------+------------+
          0x08|fjdaryPfCmNasRdThroughput                          |
              +------------+------------+------------+------------+
          0x0c|Reserved                                           |
              +------------+------------+------------+------------+
          0x10|fjdaryPfCmNasWtThroughput                          |
              +------------+------------+------------+------------+
          0x14|Reserved                                           |
              +------------+------------+------------+------------+
          0x18|fjdaryPfCm  |Reserved                              |
              | NasIOCPU   |                                      |
              | Busy       |                                      |
              +------------+------------+------------+------------+
          0x1c|fjdaryPfCm  |Reserved                              |
              | NasUsage   |                                      |
              | Rate       |                                      |
              +------------+------------+------------+------------+
          0x20|fjdaryPfCmNasUsedAmount                            |
              +                                                   +
          0x24|                                                   |
              +------------+------------+------------+------------+
          0x28|Reserved                                           |
              +                                                   +
          0x2c|                                                   |
              +------------+------------+------------+------------+
          0x30|fjdaryPfCmNasSambaOpCount                          |
              +                                                   +
          0x34|                                                   |
              +------------+------------+------------+------------+
          0x38|fjdaryPfCmNasNFSOpCount                            |
              +                                                   +
          0x3c|                                                   |
              +------------+------------+------------+------------+
          0x40|Reserved                                           |
              :                                                   :
          0x74|                                                   |
              +------------+------------+------------+------------+
          0x78|fjdaryPfCmNasNtInThroughput                        |
              +------------+------------+------------+------------+
          0x7c|Reserved                                           |
              :                                                   :
          0x84|                                                   |
              +------------+------------+------------+------------+
          0x88|fjdaryPfCmNasNtOutThroughput                       |
              +------------+------------+------------+------------+
          0x8c|Reserved                                           |
              +------------+------------+------------+------------+
          0x90|fjdaryPfCm  |fjdaryPfCm  |Reserved                 |
              | NasCPU     | NasCPU     |                         |
              | Busy       | IOWait     |                         |
              +------------+------------+------------+------------+
          0x94|fjdaryPfCmNasFreeMemory                            |
              +------------+------------+------------+------------+
          0x98|fjdaryPfCmNasCachedMemory                          |
              +------------+------------+------------+------------+
          0x9c|Reserved                                           |
              :                                                   :
          0xbc|                                                   |
              +------------+------------+------------+------------+"
    ::= { fjdaryPfDtCmNasEntry 2 }

-------------------------------------------------------------------------------
--   fjdaryPfCmNasCore                                                       --
-------------------------------------------------------------------------------
fjdaryPfCmNasCoreCount OBJECT-TYPE
    SYNTAX INTEGER(0..2147483647)
    ACCESS read-only
    STATUS mandatory
    DESCRIPTION
        "The number of CM NAS core's performance informations
         (regardless of their current state) present on this system."
    ::= { fjdaryPfCmNasCore 1 }

fjdaryPfCmNasCoreTable OBJECT-TYPE
    SYNTAX SEQUENCE OF FjdaryPfCmNasCoreEntry
    ACCESS not-accessible
    STATUS mandatory
    DESCRIPTION
        ""
    ::= { fjdaryPfCmNasCore 2 }

fjdaryPfCmNasCoreEntry OBJECT-TYPE
    SYNTAX FjdaryPfCmNasCoreEntry
    ACCESS not-accessible
    STATUS mandatory
    DESCRIPTION
        ""
    INDEX { fjdaryPfCmNasCoreIndex }
    ::= { fjdaryPfCmNasCoreTable 1 }

FjdaryPfCmNasCoreEntry ::=
    SEQUENCE{
        fjdaryPfCmNasCoreIndex      INTEGER,
        fjdaryPfCmNasCoreValidCount INTEGER,
        fjdaryPfCmNasCoreBusy0      INTEGER,
        fjdaryPfCmNasCoreBusy1      INTEGER,
        fjdaryPfCmNasCoreBusy2      INTEGER,
        fjdaryPfCmNasCoreBusy3      INTEGER,
        fjdaryPfCmNasCoreBusy4      INTEGER,
        fjdaryPfCmNasCoreBusy5      INTEGER,
        fjdaryPfCmNasCoreBusy6      INTEGER,
        fjdaryPfCmNasCoreBusy7      INTEGER,
        fjdaryPfCmNasCoreBusy8      INTEGER,
        fjdaryPfCmNasCoreBusy9      INTEGER,
        fjdaryPfCmNasCoreBusy10     INTEGER,
        fjdaryPfCmNasCoreBusy11     INTEGER,
        fjdaryPfCmNasCoreBusy12     INTEGER,
        fjdaryPfCmNasCoreBusy13     INTEGER,
        fjdaryPfCmNasCoreBusy14     INTEGER,
        fjdaryPfCmNasCoreBusy15     INTEGER,
        fjdaryPfCmNasCoreBusy16     INTEGER,
        fjdaryPfCmNasCoreBusy17     INTEGER,
        fjdaryPfCmNasCoreBusy18     INTEGER,
        fjdaryPfCmNasCoreBusy19     INTEGER
    }

fjdaryPfCmNasCoreIndex OBJECT-TYPE
    SYNTAX INTEGER(0..2147483647)
    ACCESS read-only
    STATUS mandatory
    DESCRIPTION
        "The value of this object uniquely identifies this
         fjdaryPfCmNasCore entry."
    ::= { fjdaryPfCmNasCoreEntry 1 }

fjdaryPfCmNasCoreValidCount OBJECT-TYPE
    SYNTAX INTEGER(-2147483648..2147483647)
    ACCESS read-only
    STATUS mandatory
    DESCRIPTION
        "This shows an effective number of this information.
         For instance, when this value is two, fjdaryPfCmNasCoreBusy0
         and fjdaryPfCmNasCoreBusy1 become effective information."
    ::= { fjdaryPfCmNasCoreEntry 2 }

fjdaryPfCmNasCoreBusy0 OBJECT-TYPE
    SYNTAX INTEGER(-2147483648..2147483647)
    ACCESS read-only
    STATUS mandatory
    DESCRIPTION
        "This shows the busy rate of CPU core#0 for NAS.
         The unit is percent."
    ::= { fjdaryPfCmNasCoreEntry 3 }

fjdaryPfCmNasCoreBusy1 OBJECT-TYPE
    SYNTAX INTEGER(-2147483648..2147483647)
    ACCESS read-only
    STATUS mandatory
    DESCRIPTION
        "This shows the busy rate of CPU core#1 for NAS.
         The unit is percent."
    ::= { fjdaryPfCmNasCoreEntry 4 }

fjdaryPfCmNasCoreBusy2 OBJECT-TYPE
    SYNTAX INTEGER(-2147483648..2147483647)
    ACCESS read-only
    STATUS mandatory
    DESCRIPTION
        "This shows the busy rate of CPU core#2 for NAS.
         The unit is percent."
    ::= { fjdaryPfCmNasCoreEntry 5 }

fjdaryPfCmNasCoreBusy3 OBJECT-TYPE
    SYNTAX INTEGER(-2147483648..2147483647)
    ACCESS read-only
    STATUS mandatory
    DESCRIPTION
        "This shows the busy rate of CPU core#3 for NAS.
         The unit is percent."
    ::= { fjdaryPfCmNasCoreEntry 6 }

fjdaryPfCmNasCoreBusy4 OBJECT-TYPE
    SYNTAX INTEGER(-2147483648..2147483647)
    ACCESS read-only
    STATUS mandatory
    DESCRIPTION
        "This shows the busy rate of CPU core#4 for NAS.
         The unit is percent."
    ::= { fjdaryPfCmNasCoreEntry 7 }

fjdaryPfCmNasCoreBusy5 OBJECT-TYPE
    SYNTAX INTEGER(-2147483648..2147483647)
    ACCESS read-only
    STATUS mandatory
    DESCRIPTION
        "This shows the busy rate of CPU core#5 for NAS.
         The unit is percent."
    ::= { fjdaryPfCmNasCoreEntry 8 }

fjdaryPfCmNasCoreBusy6 OBJECT-TYPE
    SYNTAX INTEGER(-2147483648..2147483647)
    ACCESS read-only
    STATUS mandatory
    DESCRIPTION
        "This shows the busy rate of CPU core#6 for NAS.
         The unit is percent."
    ::= { fjdaryPfCmNasCoreEntry 9 }

fjdaryPfCmNasCoreBusy7 OBJECT-TYPE
    SYNTAX INTEGER(-2147483648..2147483647)
    ACCESS read-only
    STATUS mandatory
    DESCRIPTION
        "This shows the busy rate of CPU core#7 for NAS.
         The unit is percent."
    ::= { fjdaryPfCmNasCoreEntry 10 }

fjdaryPfCmNasCoreBusy8 OBJECT-TYPE
    SYNTAX INTEGER(-2147483648..2147483647)
    ACCESS read-only
    STATUS mandatory
    DESCRIPTION
        "This shows the busy rate of CPU core#8 for NAS.
         The unit is percent."
    ::= { fjdaryPfCmNasCoreEntry 11 }

fjdaryPfCmNasCoreBusy9 OBJECT-TYPE
    SYNTAX INTEGER(-2147483648..2147483647)
    ACCESS read-only
    STATUS mandatory
    DESCRIPTION
        "This shows the busy rate of CPU core#9 for NAS.
         The unit is percent."
    ::= { fjdaryPfCmNasCoreEntry 12 }

fjdaryPfCmNasCoreBusy10 OBJECT-TYPE
    SYNTAX INTEGER(-2147483648..2147483647)
    ACCESS read-only
    STATUS mandatory
    DESCRIPTION
        "This shows the busy rate of CPU core#10 for NAS.
         The unit is percent."
    ::= { fjdaryPfCmNasCoreEntry 13 }

fjdaryPfCmNasCoreBusy11 OBJECT-TYPE
    SYNTAX INTEGER(-2147483648..2147483647)
    ACCESS read-only
    STATUS mandatory
    DESCRIPTION
        "This shows the busy rate of CPU core#11 for NAS.
         The unit is percent."
    ::= { fjdaryPfCmNasCoreEntry 14 }

fjdaryPfCmNasCoreBusy12 OBJECT-TYPE
    SYNTAX INTEGER(-2147483648..2147483647)
    ACCESS read-only
    STATUS mandatory
    DESCRIPTION
        "This shows the busy rate of CPU core#12 for NAS.
         The unit is percent."
    ::= { fjdaryPfCmNasCoreEntry 15 }

fjdaryPfCmNasCoreBusy13 OBJECT-TYPE
    SYNTAX INTEGER(-2147483648..2147483647)
    ACCESS read-only
    STATUS mandatory
    DESCRIPTION
        "This shows the busy rate of CPU core#13 for NAS.
         The unit is percent."
    ::= { fjdaryPfCmNasCoreEntry 16 }

fjdaryPfCmNasCoreBusy14 OBJECT-TYPE
    SYNTAX INTEGER(-2147483648..2147483647)
    ACCESS read-only
    STATUS mandatory
    DESCRIPTION
        "This shows the busy rate of CPU core#14 for NAS.
         The unit is percent."
    ::= { fjdaryPfCmNasCoreEntry 17 }

fjdaryPfCmNasCoreBusy15 OBJECT-TYPE
    SYNTAX INTEGER(-2147483648..2147483647)
    ACCESS read-only
    STATUS mandatory
    DESCRIPTION
        "This shows the busy rate of CPU core#15 for NAS.
         The unit is percent."
    ::= { fjdaryPfCmNasCoreEntry 18 }

fjdaryPfCmNasCoreBusy16 OBJECT-TYPE
    SYNTAX INTEGER(-2147483648..2147483647)
    ACCESS read-only
    STATUS mandatory
    DESCRIPTION
        "This shows the busy rate of CPU core#16 for NAS.
         The unit is percent."
    ::= { fjdaryPfCmNasCoreEntry 19 }

fjdaryPfCmNasCoreBusy17 OBJECT-TYPE
    SYNTAX INTEGER(-2147483648..2147483647)
    ACCESS read-only
    STATUS mandatory
    DESCRIPTION
        "This shows the busy rate of CPU core#17 for NAS.
         The unit is percent."
    ::= { fjdaryPfCmNasCoreEntry 20 }

fjdaryPfCmNasCoreBusy18 OBJECT-TYPE
    SYNTAX INTEGER(-2147483648..2147483647)
    ACCESS read-only
    STATUS mandatory
    DESCRIPTION
        "This shows the busy rate of CPU core#18 for NAS.
         The unit is percent."
    ::= { fjdaryPfCmNasCoreEntry 21 }

fjdaryPfCmNasCoreBusy19 OBJECT-TYPE
    SYNTAX INTEGER(-2147483648..2147483647)
    ACCESS read-only
    STATUS mandatory
    DESCRIPTION
        "This shows the busy rate of CPU core#19 for NAS.
         The unit is percent."
    ::= { fjdaryPfCmNasCoreEntry 22 }

-------------------------------------------------------------------------------
--   fjdaryPfDtCmNasCore                                                     --
-------------------------------------------------------------------------------
fjdaryPfDtCmNasCoreCount OBJECT-TYPE
    SYNTAX INTEGER(0..2147483647)
    ACCESS read-only
    STATUS mandatory
    DESCRIPTION
        "The number of CM NAS core's performance informations
         (regardless of their current state) present on this system."
    ::= { fjdaryPfDtCmNasCore 1 }

fjdaryPfDtCmNasCoreTable OBJECT-TYPE
    SYNTAX SEQUENCE OF FjdaryPfDtCmNasCoreEntry
    ACCESS not-accessible
    STATUS mandatory
    DESCRIPTION
        ""
    ::= { fjdaryPfDtCmNasCore 2 }

fjdaryPfDtCmNasCoreEntry OBJECT-TYPE
    SYNTAX FjdaryPfDtCmNasCoreEntry
    ACCESS not-accessible
    STATUS mandatory
    DESCRIPTION
        ""
    INDEX { fjdaryPfDtCmNasCoreIndex }
    ::= { fjdaryPfDtCmNasCoreTable 1 }

FjdaryPfDtCmNasCoreEntry ::=
    SEQUENCE{
        fjdaryPfDtCmNasCoreIndex INTEGER,
        fjdaryPfDtCmNasCoreInfo  OCTET STRING
    }

fjdaryPfDtCmNasCoreIndex OBJECT-TYPE
    SYNTAX INTEGER(0..2147483647)
    ACCESS read-only
    STATUS mandatory
    DESCRIPTION
        "The value of this object uniquely identifies this fjdaryPfDtCmNasCore
         entry."
    ::= { fjdaryPfDtCmNasCoreEntry 1 }

fjdaryPfDtCmNasCoreInfo OBJECT-TYPE
    SYNTAX OCTET STRING (SIZE (0..256))
    ACCESS read-only
    STATUS mandatory
    DESCRIPTION
        "The value of this object indicates the CM core performance
         information. This information is a little endian.

                  byte 0       byte 1       byte 2       byte 3
              +------------+------------+------------+------------+
          0x00|CM NAS core info#index0 (32 bytes)                 |
              +------------+------------+------------+------------+
          0x20|CM NAS core info#index1 (32 bytes)                 |
              +------------+------------+------------+------------+

         CM NAS core info#
                  byte 0       byte 1       byte 2       byte 3
              +------------+------------+------------+------------+
          0x00|fjdaryPfCm  |Reserved                              |
              | NasCore    |                                      |
              | CpuCount   |                                      |
              +------------+------------+------------+------------+
          0x04|Reserved                                           |
              +------------+------------+------------+------------+
          0x08|fjdaryPfCm  |fjdaryPfCm  |fjdaryPfCm  |fjdaryPfCm  |
              | NasCore    | NasCore    | NasCore    | NasCore    |
              | Busy0      | Busy1      |     Busy2  |     Busy3  |
              +------------+------------+------------+------------+
              :                                                   :
              +------------+------------+------------+------------+
          0x18|fjdaryPfCm  |fjdaryPfCm  |fjdaryPfCm  |fjdaryPfCm  |
              | NasCore    | NasCore    | NasCore    | NasCore    |
              | Busy16     | Busy17     | Busy18     | Busy19     |
              +------------+------------+------------+------------+
          0x1c|Reserved                                           |
              +------------+------------+------------+------------+"
    ::= { fjdaryPfDtCmNasCoreEntry 2 }

-------------------------------------------------------------------------------
--   fjdaryPfCmNasCoreIOWait                                                 --
-------------------------------------------------------------------------------
fjdaryPfCmNasCoreIOWaitCount OBJECT-TYPE
    SYNTAX INTEGER(0..2147483647)
    ACCESS read-only
    STATUS mandatory
    DESCRIPTION
        "The number of CM NAS core's I/O wait performance informations
         (regardless of their current state) present on this system."
    ::= { fjdaryPfCmNasCoreIOWait 1 }

fjdaryPfCmNasCoreIOWaitTable OBJECT-TYPE
    SYNTAX SEQUENCE OF FjdaryPfCmNasCoreIOWaitEntry
    ACCESS not-accessible
    STATUS mandatory
    DESCRIPTION
        ""
    ::= { fjdaryPfCmNasCoreIOWait 2 }

fjdaryPfCmNasCoreIOWaitEntry OBJECT-TYPE
    SYNTAX FjdaryPfCmNasCoreIOWaitEntry
    ACCESS not-accessible
    STATUS mandatory
    DESCRIPTION
        ""
    INDEX { fjdaryPfCmNasCoreIOWaitIndex }
    ::= { fjdaryPfCmNasCoreIOWaitTable 1 }

FjdaryPfCmNasCoreIOWaitEntry ::=
    SEQUENCE{
        fjdaryPfCmNasCoreIOWaitIndex      INTEGER,
        fjdaryPfCmNasCoreIOWaitValidCount INTEGER,
        fjdaryPfCmNasCoreIOWait0          INTEGER,
        fjdaryPfCmNasCoreIOWait1          INTEGER,
        fjdaryPfCmNasCoreIOWait2          INTEGER,
        fjdaryPfCmNasCoreIOWait3          INTEGER,
        fjdaryPfCmNasCoreIOWait4          INTEGER,
        fjdaryPfCmNasCoreIOWait5          INTEGER,
        fjdaryPfCmNasCoreIOWait6          INTEGER,
        fjdaryPfCmNasCoreIOWait7          INTEGER,
        fjdaryPfCmNasCoreIOWait8          INTEGER,
        fjdaryPfCmNasCoreIOWait9          INTEGER,
        fjdaryPfCmNasCoreIOWait10         INTEGER,
        fjdaryPfCmNasCoreIOWait11         INTEGER,
        fjdaryPfCmNasCoreIOWait12         INTEGER,
        fjdaryPfCmNasCoreIOWait13         INTEGER,
        fjdaryPfCmNasCoreIOWait14         INTEGER,
        fjdaryPfCmNasCoreIOWait15         INTEGER,
        fjdaryPfCmNasCoreIOWait16         INTEGER,
        fjdaryPfCmNasCoreIOWait17         INTEGER,
        fjdaryPfCmNasCoreIOWait18         INTEGER,
        fjdaryPfCmNasCoreIOWait19         INTEGER
    }

fjdaryPfCmNasCoreIOWaitIndex OBJECT-TYPE
    SYNTAX INTEGER(0..2147483647)
    ACCESS read-only
    STATUS mandatory
    DESCRIPTION
        "The value of this object uniquely identifies this
         fjdaryPfCmNasCoreIOWait entry."
    ::= { fjdaryPfCmNasCoreIOWaitEntry 1 }

fjdaryPfCmNasCoreIOWaitValidCount OBJECT-TYPE
    SYNTAX INTEGER(-2147483648..2147483647)
    ACCESS read-only
    STATUS mandatory
    DESCRIPTION
        "This shows an effective number of this information.
         For instance, when this value is two, fjdaryPfCmNasCoreIOWait0
         and fjdaryPfCmNasCoreIOWait1 become effective information."
    ::= { fjdaryPfCmNasCoreIOWaitEntry 2 }

fjdaryPfCmNasCoreIOWait0 OBJECT-TYPE
    SYNTAX INTEGER(-2147483648..2147483647)
    ACCESS read-only
    STATUS mandatory
    DESCRIPTION
        "This shows the I/O wait rate of CPU core#0 for NAS.
         The unit is percent."
    ::= { fjdaryPfCmNasCoreIOWaitEntry 3 }

fjdaryPfCmNasCoreIOWait1 OBJECT-TYPE
    SYNTAX INTEGER(-2147483648..2147483647)
    ACCESS read-only
    STATUS mandatory
    DESCRIPTION
        "This shows the I/O wait rate of CPU core#1 for NAS.
         The unit is percent."
    ::= { fjdaryPfCmNasCoreIOWaitEntry 4 }

fjdaryPfCmNasCoreIOWait2 OBJECT-TYPE
    SYNTAX INTEGER(-2147483648..2147483647)
    ACCESS read-only
    STATUS mandatory
    DESCRIPTION
        "This shows the I/O wait rate of CPU core#2 for NAS.
         The unit is percent."
    ::= { fjdaryPfCmNasCoreIOWaitEntry 5 }

fjdaryPfCmNasCoreIOWait3 OBJECT-TYPE
    SYNTAX INTEGER(-2147483648..2147483647)
    ACCESS read-only
    STATUS mandatory
    DESCRIPTION
        "This shows the I/O wait rate of CPU core#3 for NAS.
         The unit is percent."
    ::= { fjdaryPfCmNasCoreIOWaitEntry 6 }

fjdaryPfCmNasCoreIOWait4 OBJECT-TYPE
    SYNTAX INTEGER(-2147483648..2147483647)
    ACCESS read-only
    STATUS mandatory
    DESCRIPTION
        "This shows the I/O wait rate of CPU core#4 for NAS.
         The unit is percent."
    ::= { fjdaryPfCmNasCoreIOWaitEntry 7 }

fjdaryPfCmNasCoreIOWait5 OBJECT-TYPE
    SYNTAX INTEGER(-2147483648..2147483647)
    ACCESS read-only
    STATUS mandatory
    DESCRIPTION
        "This shows the I/O wait rate of CPU core#5 for NAS.
         The unit is percent."
    ::= { fjdaryPfCmNasCoreIOWaitEntry 8 }

fjdaryPfCmNasCoreIOWait6 OBJECT-TYPE
    SYNTAX INTEGER(-2147483648..2147483647)
    ACCESS read-only
    STATUS mandatory
    DESCRIPTION
        "This shows the I/O wait rate of CPU core#6 for NAS.
         The unit is percent."
    ::= { fjdaryPfCmNasCoreIOWaitEntry 9 }

fjdaryPfCmNasCoreIOWait7 OBJECT-TYPE
    SYNTAX INTEGER(-2147483648..2147483647)
    ACCESS read-only
    STATUS mandatory
    DESCRIPTION
        "This shows the I/O wait rate of CPU core#7 for NAS.
         The unit is percent."
    ::= { fjdaryPfCmNasCoreIOWaitEntry 10 }

fjdaryPfCmNasCoreIOWait8 OBJECT-TYPE
    SYNTAX INTEGER(-2147483648..2147483647)
    ACCESS read-only
    STATUS mandatory
    DESCRIPTION
        "This shows the I/O wait rate of CPU core#8 for NAS.
         The unit is percent."
    ::= { fjdaryPfCmNasCoreIOWaitEntry 11 }

fjdaryPfCmNasCoreIOWait9 OBJECT-TYPE
    SYNTAX INTEGER(-2147483648..2147483647)
    ACCESS read-only
    STATUS mandatory
    DESCRIPTION
        "This shows the I/O wait rate of CPU core#9 for NAS.
         The unit is percent."
    ::= { fjdaryPfCmNasCoreIOWaitEntry 12 }

fjdaryPfCmNasCoreIOWait10 OBJECT-TYPE
    SYNTAX INTEGER(-2147483648..2147483647)
    ACCESS read-only
    STATUS mandatory
    DESCRIPTION
        "This shows the I/O wait rate of CPU core#10 for NAS.
         The unit is percent."
    ::= { fjdaryPfCmNasCoreIOWaitEntry 13 }

fjdaryPfCmNasCoreIOWait11 OBJECT-TYPE
    SYNTAX INTEGER(-2147483648..2147483647)
    ACCESS read-only
    STATUS mandatory
    DESCRIPTION
        "This shows the I/O wait rate of CPU core#11 for NAS.
         The unit is percent."
    ::= { fjdaryPfCmNasCoreIOWaitEntry 14 }

fjdaryPfCmNasCoreIOWait12 OBJECT-TYPE
    SYNTAX INTEGER(-2147483648..2147483647)
    ACCESS read-only
    STATUS mandatory
    DESCRIPTION
        "This shows the I/O wait rate of CPU core#12 for NAS.
         The unit is percent."
    ::= { fjdaryPfCmNasCoreIOWaitEntry 15 }

fjdaryPfCmNasCoreIOWait13 OBJECT-TYPE
    SYNTAX INTEGER(-2147483648..2147483647)
    ACCESS read-only
    STATUS mandatory
    DESCRIPTION
        "This shows the I/O wait rate of CPU core#13 for NAS.
         The unit is percent."
    ::= { fjdaryPfCmNasCoreIOWaitEntry 16 }

fjdaryPfCmNasCoreIOWait14 OBJECT-TYPE
    SYNTAX INTEGER(-2147483648..2147483647)
    ACCESS read-only
    STATUS mandatory
    DESCRIPTION
        "This shows the I/O wait rate of CPU core#14 for NAS.
         The unit is percent."
    ::= { fjdaryPfCmNasCoreIOWaitEntry 17 }

fjdaryPfCmNasCoreIOWait15 OBJECT-TYPE
    SYNTAX INTEGER(-2147483648..2147483647)
    ACCESS read-only
    STATUS mandatory
    DESCRIPTION
        "This shows the I/O wait rate of CPU core#15 for NAS.
         The unit is percent."
    ::= { fjdaryPfCmNasCoreIOWaitEntry 18 }

fjdaryPfCmNasCoreIOWait16 OBJECT-TYPE
    SYNTAX INTEGER(-2147483648..2147483647)
    ACCESS read-only
    STATUS mandatory
    DESCRIPTION
        "This shows the I/O wait rate of CPU core#16 for NAS.
         The unit is percent."
    ::= { fjdaryPfCmNasCoreIOWaitEntry 19 }

fjdaryPfCmNasCoreIOWait17 OBJECT-TYPE
    SYNTAX INTEGER(-2147483648..2147483647)
    ACCESS read-only
    STATUS mandatory
    DESCRIPTION
        "This shows the I/O wait rate of CPU core#17 for NAS.
         The unit is percent."
    ::= { fjdaryPfCmNasCoreIOWaitEntry 20 }

fjdaryPfCmNasCoreIOWait18 OBJECT-TYPE
    SYNTAX INTEGER(-2147483648..2147483647)
    ACCESS read-only
    STATUS mandatory
    DESCRIPTION
        "This shows the I/O wait rate of CPU core#18 for NAS.
         The unit is percent."
    ::= { fjdaryPfCmNasCoreIOWaitEntry 21 }

fjdaryPfCmNasCoreIOWait19 OBJECT-TYPE
    SYNTAX INTEGER(-2147483648..2147483647)
    ACCESS read-only
    STATUS mandatory
    DESCRIPTION
        "This shows the I/O wait rate of CPU core#19 for NAS.
         The unit is percent."
    ::= { fjdaryPfCmNasCoreIOWaitEntry 22 }

-------------------------------------------------------------------------------
--   fjdaryPfDtCmNasCoreIOWait                                               --
-------------------------------------------------------------------------------
fjdaryPfDtCmNasCoreIOWaitCount OBJECT-TYPE
    SYNTAX INTEGER(0..2147483647)
    ACCESS read-only
    STATUS mandatory
    DESCRIPTION
        "The number of CM NAS core's I/O wait performance informations
         (regardless of their current state) present on this system."
    ::= { fjdaryPfDtCmNasCoreIOWait 1 }

fjdaryPfDtCmNasCoreIOWaitTable OBJECT-TYPE
    SYNTAX SEQUENCE OF FjdaryPfDtCmNasCoreIOWaitEntry
    ACCESS not-accessible
    STATUS mandatory
    DESCRIPTION
        ""
    ::= { fjdaryPfDtCmNasCoreIOWait 2 }

fjdaryPfDtCmNasCoreIOWaitEntry OBJECT-TYPE
    SYNTAX FjdaryPfDtCmNasCoreIOWaitEntry
    ACCESS not-accessible
    STATUS mandatory
    DESCRIPTION
        ""
    INDEX { fjdaryPfDtCmNasCoreIOWaitIndex }
    ::= { fjdaryPfDtCmNasCoreIOWaitTable 1 }

FjdaryPfDtCmNasCoreIOWaitEntry ::=
    SEQUENCE{
        fjdaryPfDtCmNasCoreIOWaitIndex INTEGER,
        fjdaryPfDtCmNasCoreIOWaitInfo  OCTET STRING
    }

fjdaryPfDtCmNasCoreIOWaitIndex OBJECT-TYPE
    SYNTAX INTEGER(0..2147483647)
    ACCESS read-only
    STATUS mandatory
    DESCRIPTION
        "The value of this object uniquely identifies this
         fjdaryPfDtCmNasCoreIOWait entry."
    ::= { fjdaryPfDtCmNasCoreIOWaitEntry 1 }

fjdaryPfDtCmNasCoreIOWaitInfo OBJECT-TYPE
    SYNTAX OCTET STRING (SIZE (0..256))
    ACCESS read-only
    STATUS mandatory
    DESCRIPTION
        "The value of this object indicates the CM core I/O wait performance
         information. This information is a little endian.

                  byte 0       byte 1       byte 2       byte 3
              +------------+------------+------------+------------+
          0x00|CM NAS core info#index0 (32 bytes)                 |
              +------------+------------+------------+------------+
          0x20|CM NAS core info#index1 (32 bytes)                 |
              +------------+------------+------------+------------+

         CM NAS core info#
                  byte 0       byte 1       byte 2       byte 3
              +------------+------------+------------+------------+
          0x00|fjdaryPfCm  |Reserved                              |
              | NasCore    |                                      |
              | IOWait     |                                      |
              | ValidCount |                                      |
              +------------+------------+------------+------------+
          0x04|Reserved                                           |
              +------------+------------+------------+------------+
          0x08|fjdaryPfCm  |fjdaryPfCm  |fjdaryPfCm  |fjdaryPfCm  |
              | NasCore    | NasCore    | NasCore    | NasCore    |
              | IOWait0    | IOWait1    | IOWait2    | IOWait3    |
              +------------+------------+------------+------------+
              :                                                   :
              +------------+------------+------------+------------+
          0x18|fjdaryPfCm  |fjdaryPfCm  |fjdaryPfCm  |fjdaryPfCm  |
              | NasCore    | NasCore    | NasCore    | NasCore    |
              | IOWait16   | IOWait17   | IOWait18   | IOWait19   |
              +------------+------------+------------+------------+
          0x1c|Reserved                                           |
              +------------+------------+------------+------------+"
    ::= { fjdaryPfDtCmNasCoreIOWaitEntry 2 }

-------------------------------------------------------------------------------
--   fjdaryPfCaPortNas                                                       --
-------------------------------------------------------------------------------
fjdaryPfCaPortNasCount OBJECT-TYPE
    SYNTAX INTEGER(0..2147483647)
    ACCESS read-only
    STATUS mandatory
    DESCRIPTION
        "The number of CA port's performance informations
         (regardless of their current state) present on this system."
    ::= { fjdaryPfCaPortNas 1 }

fjdaryPfCaPortNasTable OBJECT-TYPE
    SYNTAX SEQUENCE OF FjdaryPfCaPortNasEntry
    ACCESS not-accessible
    STATUS mandatory
    DESCRIPTION
        ""
    ::= { fjdaryPfCaPortNas 2 }

fjdaryPfCaPortNasEntry OBJECT-TYPE
    SYNTAX FjdaryPfCaPortNasEntry
    ACCESS not-accessible
    STATUS mandatory
    DESCRIPTION
        ""
    INDEX { fjdaryPfCaPortNasIndex }
    ::= { fjdaryPfCaPortNasTable 1 }

FjdaryPfCaPortNasEntry ::=
    SEQUENCE{
        fjdaryPfCaPortNasIndex           INTEGER,
        fjdaryPfCaPortNasNtInThroughput  INTEGER,
        fjdaryPfCaPortNasNtOutThroughput INTEGER
    }

fjdaryPfCaPortNasIndex OBJECT-TYPE
    SYNTAX INTEGER(0..2147483647)
    ACCESS read-only
    STATUS mandatory
    DESCRIPTION
        "The value of this object uniquely identifies this fjdaryPfCaPortNas
         entry."
    ::= { fjdaryPfCaPortNasEntry 1 }

fjdaryPfCaPortNasNtInThroughput OBJECT-TYPE
    SYNTAX INTEGER(-2147483648..2147483647)
    ACCESS read-only
    STATUS mandatory
    DESCRIPTION
        "This shows the receive throughput in the CA port interface.
         The unit is MB/sec."
    ::= { fjdaryPfCaPortNasEntry 2 }

fjdaryPfCaPortNasNtOutThroughput OBJECT-TYPE
    SYNTAX INTEGER(-2147483648..2147483647)
    ACCESS read-only
    STATUS mandatory
    DESCRIPTION
        "This shows the transmit throughput in the CA port interface.
         The unit is MB/sec."
    ::= { fjdaryPfCaPortNasEntry 3 }

-------------------------------------------------------------------------------
--   fjdaryPfDtCaPortNas                                                     --
-------------------------------------------------------------------------------
fjdaryPfDtCaPortNasCount OBJECT-TYPE
    SYNTAX INTEGER(0..2147483647)
    ACCESS read-only
    STATUS mandatory
    DESCRIPTION
        "The number of CA port's performance informations
         (regardless of their current state) present on this system."
    ::= { fjdaryPfDtCaPortNas 1 }

fjdaryPfDtCaPortNasTable OBJECT-TYPE
    SYNTAX SEQUENCE OF FjdaryPfDtCaPortNasEntry
    ACCESS not-accessible
    STATUS mandatory
    DESCRIPTION
        ""
    ::= { fjdaryPfDtCaPortNas 2 }

fjdaryPfDtCaPortNasEntry OBJECT-TYPE
    SYNTAX FjdaryPfDtCaPortNasEntry
    ACCESS not-accessible
    STATUS mandatory
    DESCRIPTION
        ""
    INDEX { fjdaryPfDtCaPortNasIndex }
    ::= { fjdaryPfDtCaPortNasTable 1 }

FjdaryPfDtCaPortNasEntry ::=
    SEQUENCE{
        fjdaryPfDtCaPortNasIndex INTEGER,
        fjdaryPfDtCaPortNasInfo  OCTET STRING
    }

fjdaryPfDtCaPortNasIndex OBJECT-TYPE
    SYNTAX INTEGER(0..2147483647)
    ACCESS read-only
    STATUS mandatory
    DESCRIPTION
        "The value of this object uniquely identifies this fjdaryPfDtCaPortNas
         entry."
    ::= { fjdaryPfDtCaPortNasEntry 1 }

fjdaryPfDtCaPortNasInfo OBJECT-TYPE
    SYNTAX OCTET STRING (SIZE (0..256))
    ACCESS read-only
    STATUS mandatory
    DESCRIPTION
        "The value of this object indicates the CA port performance
         information.
         This information is a little endian.

                  byte 0       byte 1       byte 2       byte 3
              +------------+------------+------------+------------+
          0x00|CA port info#index*16 (8 bytes)                    |
              +------------+------------+------------+------------+
          0x08|CA port info#index*16+1 (8 bytes)                  |
              +------------+------------+------------+------------+
              :                                                   :
              +------------+------------+------------+------------+
          0x80|CA port info#index*16+15 (8 bytes)                 |
              +------------+------------+------------+------------+

         CA port info#
                  byte 0       byte 1       byte 2       byte 3
              +------------+------------+------------+------------+
          0x00|fjdaryPfCaPortNasNtInThroughput                    |
              +------------+------------+------------+------------+
          0x04|fjdaryPfCaPortNasNtOutThroughput                   |
              +------------+------------+------------+------------+"
    ::= { fjdaryPfDtCaPortNasEntry 2 }

-------------------------------------------------------------------------------
--   fjdaryPfCmNasVol                                                        --
-------------------------------------------------------------------------------
fjdaryPfCmNasVolCount OBJECT-TYPE
    SYNTAX INTEGER(0..2147483647)
    ACCESS read-only
    STATUS mandatory
    DESCRIPTION
        "The number of CM NAS volume performance informations
         (regardless of their current state) present on this system."
    ::= { fjdaryPfCmNasVol 1 }

fjdaryPfCmNasVolTable OBJECT-TYPE
    SYNTAX SEQUENCE OF FjdaryPfCmNasVolEntry
    ACCESS not-accessible
    STATUS mandatory
    DESCRIPTION
        ""
    ::= { fjdaryPfCmNasVol 2 }

fjdaryPfCmNasVolEntry OBJECT-TYPE
    SYNTAX FjdaryPfCmNasVolEntry
    ACCESS not-accessible
    STATUS mandatory
    DESCRIPTION
        ""
    INDEX { fjdaryPfCmNasVolIndex }
    ::= { fjdaryPfCmNasVolTable 1 }

FjdaryPfCmNasVolEntry ::=
    SEQUENCE{
        fjdaryPfCmNasVolIndex      INTEGER,
        fjdaryPfCmNasVolOluNo      INTEGER,
        fjdaryPfCmNasVolIOWaitTime INTEGER,
        fjdaryPfCmNasVolRdTp       INTEGER,
        fjdaryPfCmNasVolWtTp       INTEGER,
        fjdaryPfCmNasVolIOCPUBusy  INTEGER,
        fjdaryPfCmNasVolUsageRate  INTEGER,
        fjdaryPfCmNasVolUsedAmount INTEGER
    }

fjdaryPfCmNasVolIndex OBJECT-TYPE
    SYNTAX INTEGER(0..2147483647)
    ACCESS read-only
    STATUS mandatory
    DESCRIPTION
        "The value of this object uniquely identifies this fjdaryPfCmNasVol
         entry."
    ::= { fjdaryPfCmNasVolEntry 1 }

fjdaryPfCmNasVolOluNo OBJECT-TYPE
    SYNTAX INTEGER(-2147483648..2147483647)
    ACCESS read-only
    STATUS mandatory
    DESCRIPTION
        "This shows the OLU number of NAS volume."
    ::= { fjdaryPfCmNasVolEntry 2 }

fjdaryPfCmNasVolIOWaitTime OBJECT-TYPE
    SYNTAX INTEGER(-2147483648..2147483647)
    ACCESS read-only
    STATUS mandatory
    DESCRIPTION
        "This shows the average of the I/O request at waiting time.
         The unit is msec."
    ::= { fjdaryPfCmNasVolEntry 3 }

fjdaryPfCmNasVolRdTp OBJECT-TYPE
    SYNTAX INTEGER(-2147483648..2147483647)
    ACCESS read-only
    STATUS mandatory
    DESCRIPTION
        "This shows the READ Throughput. The unit is MB/sec."
    ::= { fjdaryPfCmNasVolEntry 4 }

fjdaryPfCmNasVolWtTp OBJECT-TYPE
    SYNTAX INTEGER(-2147483648..2147483647)
    ACCESS read-only
    STATUS mandatory
    DESCRIPTION
        "This shows the WRITE Throughput. The unit is MB/sec."
    ::= { fjdaryPfCmNasVolEntry 5 }

fjdaryPfCmNasVolIOCPUBusy OBJECT-TYPE
    SYNTAX INTEGER(-2147483648..2147483647)
    ACCESS read-only
    STATUS mandatory
    DESCRIPTION
        "This shows the busy rate of CPU at the I/O request period.
         The unit is percent."
    ::= { fjdaryPfCmNasVolEntry 6 }

fjdaryPfCmNasVolUsageRate OBJECT-TYPE
    SYNTAX INTEGER(-2147483648..2147483647)
    ACCESS read-only
    STATUS mandatory
    DESCRIPTION
        "This shows the usage rate of the NAS volume. The unit is percent."
    ::= { fjdaryPfCmNasVolEntry 7 }

fjdaryPfCmNasVolUsedAmount OBJECT-TYPE
    SYNTAX INTEGER(-2147483648..2147483647)
    ACCESS read-only
    STATUS mandatory
    DESCRIPTION
        "This shows the used amount of the NAS volume. The unit is KB."
    ::= { fjdaryPfCmNasVolEntry 8 }

-------------------------------------------------------------------------------
--   fjdaryPfDtCmNasVol                                                      --
-------------------------------------------------------------------------------
fjdaryPfDtCmNasVolCount OBJECT-TYPE
    SYNTAX INTEGER(0..2147483647)
    ACCESS read-only
    STATUS mandatory
    DESCRIPTION
        "The number of CM NAS volume performance informations
         (regardless of their current state) present on this system."
    ::= { fjdaryPfDtCmNasVol 1 }

fjdaryPfDtCmNasVolTable OBJECT-TYPE
    SYNTAX SEQUENCE OF FjdaryPfDtCmNasVolEntry
    ACCESS not-accessible
    STATUS mandatory
    DESCRIPTION
        ""
    ::= { fjdaryPfDtCmNasVol 2 }

fjdaryPfDtCmNasVolEntry OBJECT-TYPE
    SYNTAX FjdaryPfDtCmNasVolEntry
    ACCESS not-accessible
    STATUS mandatory
    DESCRIPTION
        ""
    INDEX { fjdaryPfDtCmNasVolIndex }
    ::= { fjdaryPfDtCmNasVolTable 1 }

FjdaryPfDtCmNasVolEntry ::=
    SEQUENCE{
        fjdaryPfDtCmNasVolIndex INTEGER,
        fjdaryPfDtCmNasVolInfo  OCTET STRING
    }

fjdaryPfDtCmNasVolIndex OBJECT-TYPE
    SYNTAX INTEGER(0..2147483647)
    ACCESS read-only
    STATUS mandatory
    DESCRIPTION
        "The value of this object uniquely identifies this fjdaryPfDtCmNasVol
         entry."
    ::= { fjdaryPfDtCmNasVolEntry 1 }

fjdaryPfDtCmNasVolInfo OBJECT-TYPE
    SYNTAX OCTET STRING (SIZE (0..256))
    ACCESS read-only
    STATUS mandatory
    DESCRIPTION
        "The value of this object indicates the CM NAS volume performance
         information. This information is a little endian.

                  byte 0       byte 1       byte 2       byte 3
              +------------+------------+------------+------------+
          0x00|NAS volume info#index*4 (48 bytes)                 |
              +------------+------------+------------+------------+
          0x30|NAS volume info#index*4+1 (48 bytes)               |
              +------------+------------+------------+------------+
          0x60|NAS volume info#index*4+2 (48 bytes)               |
              +------------+------------+------------+------------+
          0x90|NAS volume info#index*4+3 (48 bytes)               |
              +------------+------------+------------+------------+

         NAS volume info#
                  byte 0       byte 1       byte 2       byte 3
              +------------+------------+------------+------------+
          0x00|fjdaryPfCmNasVolOluNo                              |
              +------------+------------+------------+------------+
          0x04|Reserved                                           |
              +------------+------------+------------+------------+
          0x08|fjdaryPfCmNasVolIOWaitTime                         |
              +------------+------------+------------+------------+
          0x0c|Reserved                                           |
              +------------+------------+------------+------------+
          0x10|fjdaryPfCmNasVolRdTp                               |
              +------------+------------+------------+------------+
          0x14|Reserved                                           |
              +------------+------------+------------+------------+
          0x18|fjdaryPfCmNasVolWtTp                               |
              +------------+------------+------------+------------+
          0x1c|Reserved                                           |
              +------------+------------+------------+------------+
          0x20|fjdaryPfCm  |Reserved                              |
              | NasVol     |                                      |
              | IOCPUBusy  |                                      |
              +------------+------------+------------+------------+
          0x24|fjdaryPfCm  |Reserved                              |
              | NasVol     |                                      |
              | UsageRate  |                                      |
              +------------+------------+------------+------------+
          0x28|fjdaryPfCmNasVolUsedAmount                         |
              +                                                   +
          0x2c|                                                   |
              +------------+------------+------------+------------+"
    ::= { fjdaryPfDtCmNasVolEntry 2 }

--***************************************************************************--
--   Management Object                                                       --
--***************************************************************************--
-------------------------------------------------------------------------------
--   fjdaryMgtMachineInfo                                                    --
-------------------------------------------------------------------------------
fjdaryMgtMachineStatus OBJECT-TYPE
    SYNTAX INTEGER {
        unknown(1),
        unused(2),
        ok(3),
        warning(4),
        failed(5)
    }
    ACCESS read-only
    STATUS mandatory
    DESCRIPTION
        "Overall status of this system. Status becomes warning or failed
         when there are broken parts in the system.
         But, it doesn't become warning or failed when maintaining it.
         (In the maintenance work, fjdaryMgtMaintenanceMode is on)
         This is the same as fjdaryUnitStatus."
    ::= { fjdaryMgtMachineInfo 1 }

fjdaryMgtMachineSubStatus OBJECT-TYPE
    SYNTAX INTEGER {
        unknown(1),
        unused(2),
        ok(3),
        warning(4),
        failed(5)
    }
    ACCESS read-only
    STATUS mandatory
    DESCRIPTION
        "Overall status of this system. Status becomes warning or failed
         when there are broken parts in the system.
         It becomes warning and failed while even maintaining it.
         (In the maintenance work, fjdaryMgtMaintenanceMode is on)"
    ::= { fjdaryMgtMachineInfo 2 }

fjdaryMgtMaintenanceMode OBJECT-TYPE
    SYNTAX INTEGER {
        off(1),
        on(2)
    }
    ACCESS read-only
    STATUS mandatory
    DESCRIPTION
        "This shows the state of the mode while maintaining the system.
         (In the maintenance work, fjdaryMgtMaintenanceMode is on)"
    ::= { fjdaryMgtMachineInfo 3 }

fjdaryMgtConfigInfo OBJECT-TYPE
    SYNTAX OCTET STRING (SIZE (0..256))
    ACCESS read-only
    STATUS mandatory
    DESCRIPTION
        "This shows the management data of the configuration information of
         machine. This data is the one only for a certain specific software."
    ::= { fjdaryMgtMachineInfo 4 }

-------------------------------------------------------------------------------
--   fjdaryMgtOpVolume                                                       --
-------------------------------------------------------------------------------
fjdaryMgtOpVolumeTable OBJECT-TYPE
    SYNTAX SEQUENCE OF FjdaryMgtOpVolumeEntry
    ACCESS not-accessible
    STATUS mandatory
    DESCRIPTION
        ""
    ::= { fjdaryMgtOpVolume 2 }

fjdaryMgtOpVolumeEntry OBJECT-TYPE
    SYNTAX FjdaryMgtOpVolumeEntry
    ACCESS not-accessible
    STATUS mandatory
    DESCRIPTION
        ""
    INDEX { fjdaryMgtOpVolumeNumber }
    ::= { fjdaryMgtOpVolumeTable 1 }

FjdaryMgtOpVolumeEntry ::=
    SEQUENCE{
        fjdaryMgtOpVolumeNumber    INTEGER,
        fjdaryMgtOpVolumeStatus    INTEGER,
        fjdaryMgtOpVolumeType      INTEGER,
        fjdaryMgtOpVolumeCapacity  INTEGER,
        fjdaryMgtOpVolumeType2     INTEGER,
        fjdaryMgtOpVolumeAttribute INTEGER
    }

fjdaryMgtOpVolumeNumber OBJECT-TYPE
    SYNTAX INTEGER(0..2147483647)
    ACCESS read-only
    STATUS mandatory
    DESCRIPTION
        "This shows the open volume number."
    ::= { fjdaryMgtOpVolumeEntry 1 }

fjdaryMgtOpVolumeStatus OBJECT-TYPE
    SYNTAX INTEGER {
        unknown(1),
        ok(2),
        degraded(3),
        error(6),
        dormant(15)
    }
    ACCESS read-only
    STATUS mandatory
    DESCRIPTION
        "This shows the status of open volume."
    ::= { fjdaryMgtOpVolumeEntry 2 }

fjdaryMgtOpVolumeType OBJECT-TYPE
    SYNTAX INTEGER {
        unknown(1),
        open(2),
        sdv(3),
        tpv(4),
        sdpv(5)
    }
    ACCESS read-only
    STATUS mandatory
    DESCRIPTION
        "This shows the type of open volume."
    ::= { fjdaryMgtOpVolumeEntry 3 }

fjdaryMgtOpVolumeCapacity OBJECT-TYPE
    SYNTAX INTEGER(-2147483648..2147483647)
    ACCESS read-only
    STATUS mandatory
    DESCRIPTION
        "This shows the open volume capacity. The unit is MB."
    ::= { fjdaryMgtOpVolumeEntry 4 }

fjdaryMgtOpVolumeType2 OBJECT-TYPE
    SYNTAX INTEGER {
        other(1),
        open(2),
        sdv(3),
        tpv(4),
        sdpv(5),
        ftv(6),
        wsv(7)
    }
    ACCESS read-only
    STATUS mandatory
    DESCRIPTION
        "This shows the type of open volume. This is more detailed than
         fjdaryMgtOpVolumeType."
    ::= { fjdaryMgtOpVolumeEntry 5 }

fjdaryMgtOpVolumeAttribute OBJECT-TYPE
    SYNTAX INTEGER(-2147483648..2147483647)
    ACCESS read-only
    STATUS mandatory
    DESCRIPTION
        "This shows the attribute of open volume.
         The value is a bit mask.

         The bits have the following definition:
             Dynamic LUN Mirroring(DLM)    - 4
             Offloaded Data Transfer(ODX)  - 8"
    ::= { fjdaryMgtOpVolumeEntry 6 }

-------------------------------------------------------------------------------
--   fjdaryMgtRaidGrp                                                        --
-------------------------------------------------------------------------------
fjdaryMgtRaidGrpTable OBJECT-TYPE
    SYNTAX SEQUENCE OF FjdaryMgtRaidGrpEntry
    ACCESS not-accessible
    STATUS mandatory
    DESCRIPTION
        ""
    ::= { fjdaryMgtRaidGrp 2 }

fjdaryMgtRaidGrpEntry OBJECT-TYPE
    SYNTAX FjdaryMgtRaidGrpEntry
    ACCESS not-accessible
    STATUS mandatory
    DESCRIPTION
        ""
    INDEX { fjdaryMgtRaidGrpNumber }
    ::= { fjdaryMgtRaidGrpTable 1 }

FjdaryMgtRaidGrpEntry ::=
    SEQUENCE{
        fjdaryMgtRaidGrpNumber    INTEGER,
        fjdaryMgtRaidGrpStatus    INTEGER,
        fjdaryMgtRaidGrpRaidLevel INTEGER,
        fjdaryMgtRaidGrpCapacity  INTEGER
    }

fjdaryMgtRaidGrpNumber OBJECT-TYPE
    SYNTAX INTEGER(0..2147483647)
    ACCESS read-only
    STATUS mandatory
    DESCRIPTION
        "This shows the raid group number."
    ::= { fjdaryMgtRaidGrpEntry 1 }

fjdaryMgtRaidGrpStatus OBJECT-TYPE
    SYNTAX INTEGER {
        unknown(1),
        ok(2),
        degraded(3),
        error(6),
        dormant(15)
    }
    ACCESS read-only
    STATUS mandatory
    DESCRIPTION
        "This shows the status of raid group"
    ::= { fjdaryMgtRaidGrpEntry 2 }

fjdaryMgtRaidGrpRaidLevel OBJECT-TYPE
    SYNTAX INTEGER {
        raid0(100),
        raid1(1),
        raid10(10),
        raid5(5),
        raid50(50),
        raid6(6),
        raid6-fr(106),
        unknown(255)
    }
    ACCESS read-only
    STATUS mandatory
    DESCRIPTION
        "This shows the RAID level.
         the following definition:
           RAID0       - raid0
           RAID1       - raid1
           RAID1+0     - raid10
           RAID5       - raid5
           RAID5+0     - raid50
           RAID6       - raid6
           RAID6-FR    - raid6-fr"
    ::= { fjdaryMgtRaidGrpEntry 3 }

fjdaryMgtRaidGrpCapacity OBJECT-TYPE
    SYNTAX INTEGER(-2147483648..2147483647)
    ACCESS read-only
    STATUS mandatory
    DESCRIPTION
        "This shows the raid group capacity. The unit is MB."
    ::= { fjdaryMgtRaidGrpEntry 4 }

--***************************************************************************--
--   Trap Definitions                                                        --
--***************************************************************************--
-------------------------------------------------------------------------------
--   TRAP-TYPE                                                               --
-------------------------------------------------------------------------------
fjdarye150ItemFault TRAP-TYPE
    ENTERPRISE aplNetFjdarye150
    VARIABLES{
        fjdaryTrapItemId,
        fjdarySspMachineId,
        fjdaryTrapMessage
    }
    DESCRIPTION
        "A itemFault trap signifies that device was failed."
--#TYPE "Item fault"
--#SUMMARY "Item fault event from %s, id: %x, message: %s"
--#ARGUMENTS {1,0,2}
--#SEVERITY CRITICAL
--#TIMEINDEX 6
    ::= 2

fjdarye150BatteryExpiration TRAP-TYPE
    ENTERPRISE aplNetFjdarye150
    VARIABLES{
        fjdaryTrapItemId,
        fjdarySspMachineId,
        fjdaryTrapMessage
    }
    DESCRIPTION
        "A batteryExpiration trap signifies that the exchange time of the
         battery comes."
--#TYPE "Battery expiration"
--#SUMMARY "Battery expiration event from %s, id: %x, message: %s"
--#ARGUMENTS {1,0,2}
--#SEVERITY CRITICAL
--#TIMEINDEX 6
    ::= 3

fjdarye150ItemWarning TRAP-TYPE
    ENTERPRISE aplNetFjdarye150
    VARIABLES{
        fjdaryTrapItemId,
        fjdarySspMachineId,
        fjdaryTrapMessage,
        fjdaryTrapWarningInfo
    }
    DESCRIPTION
        "A itemWarning trap signifies that device was warning."
--#TYPE "Item warning"
--#SUMMARY "Item warning event from %s, id: %x[%x], message: %s"
--#ARGUMENTS {1,0,3,2}
--#SEVERITY MAJOR
--#TIMEINDEX 6
    ::= 5

fjdarye150SensorStatusChange TRAP-TYPE
    ENTERPRISE aplNetFjdarye150
    VARIABLES{
        fjdaryTrapItemId,
        fjdarySspMachineId,
        fjdaryTrapSensorInfo,
        fjdaryTrapMessage
    }
    DESCRIPTION
        "A sensorStatusChange trap signifies that environment sensor status
         changes."
--#TYPE "Sensor status changed"
--#SUMMARY "Sensor status changed event from %s, id: %x[%x], message: %s"
--#ARGUMENTS {1,0,2,3}
--#SEVERITY CRITICAL
--#TIMEINDEX 6
    ::= 6

fjdarye150MaintenanceRequired TRAP-TYPE
    ENTERPRISE aplNetFjdarye150
    VARIABLES{
        fjdarySspMachineId,
        fjdaryTrapMaintenanceInfo,
        fjdaryTrapMessage
    }
    DESCRIPTION
        "A maintenanceRequired trap signifies that maintenance information."
--#TYPE "Maintenance required"
--#SUMMARY "Maintenance required event from %s, id: %x, message: %s"
--#ARGUMENTS {0,1,2}
--#SEVERITY CRITICAL
--#TIMEINDEX 6
    ::= 7

fjdarye150Information TRAP-TYPE
    ENTERPRISE aplNetFjdarye150
    VARIABLES{
        fjdarySspMachineId,
        fjdaryTrapMessage
    }
    DESCRIPTION
        "A Information trap signifies that information events."
--#TYPE "Information event"
--#SUMMARY "Information event from %s, message: %s"
--#ARGUMENTS {0,1}
--#SEVERITY INFORMATIONAL
--#TIMEINDEX 6
    ::= 9

fjdarye150CaPortLinkStatusChange TRAP-TYPE
    ENTERPRISE aplNetFjdarye150
    VARIABLES{
        fjdaryTrapItemId,
        fjdarySspMachineId,
        fjdaryTrapLinkStatusInfo,
        fjdaryTrapMessage
    }
    DESCRIPTION
        "A caPortLinkStatusChange trap signifies that CA port link status
         changes."
--#TYPE "Information event"
--#SUMMARY "CA port link status changed event from %s, id: %x[%x], message: %s"
--#ARGUMENTS {1,0,2,3}
--#SEVERITY INFORMATIONAL
--#TIMEINDEX 6
    ::= 10

fjdarye150StorageClusterEvent TRAP-TYPE
    ENTERPRISE aplNetFjdarye150
    VARIABLES{
        fjdarySspMachineId,
        fjdaryTrapMaintenanceInfo,
        fjdaryTrapMessage
    }
    DESCRIPTION
        "A storageClusterEvent trap signifies that error event of
         Storage Cluster."
--#TYPE "Storage Cluster error event"
--#SUMMARY "Storage Cluster error event from %s, id: %x, message: %s"
--#ARGUMENTS {0,1,2}
--#SEVERITY CRITICAL
--#TIMEINDEX 6
    ::= 11

fjdarye150StorageClusterInformation TRAP-TYPE
    ENTERPRISE aplNetFjdarye150
    VARIABLES{
        fjdarySspMachineId,
        fjdaryTrapMessage
    }
    DESCRIPTION
        "A storageClusterInformation trap signifies that information event of
         Storage Cluster."
--#TYPE "Storage Cluster information event"
--#SUMMARY "Storage Cluster information event from %s, message: %s"
--#ARGUMENTS {0,1}
--#SEVERITY INFORMATIONAL
--#TIMEINDEX 6
    ::= 12

fjdarye150ItemFaultToNormal TRAP-TYPE
    ENTERPRISE aplNetFjdarye150
    VARIABLES{
        fjdaryTrapItemId,
        fjdarySspMachineId,
        fjdaryTrapMessage
    }
    DESCRIPTION
        "A itemFaultToNormal trap signifies that the device state has changed
         to normal after sending itemFault trap."
--#TYPE "Item fault to normal"
--#SUMMARY "Item fault to normal, from %s, id: %x, message: %s"
--#ARGUMENTS {1,0,2}
--#SEVERITY INFORMATIONAL
--#TIMEINDEX 6
    ::= 22

fjdarye150ItemWarningToNormal TRAP-TYPE
    ENTERPRISE aplNetFjdarye150
    VARIABLES{
        fjdaryTrapItemId,
        fjdarySspMachineId,
        fjdaryTrapMessage,
        fjdaryTrapWarningInfo
    }
    DESCRIPTION
        "A itemWarningToNormal trap signifies that the device state has changed
         to normal after sending itemWarning trap."
--#TYPE "Item warning to normal"
--#SUMMARY "Item warning to normal, from %s, id: %x[%x], message: %s"
--#ARGUMENTS {1,0,3,2}
--#SEVERITY INFORMATIONAL
--#TIMEINDEX 6
    ::= 25

fjdarye150SensorStatusChangeToNormal TRAP-TYPE
    ENTERPRISE aplNetFjdarye150
    VARIABLES{
        fjdaryTrapItemId,
        fjdarySspMachineId,
        fjdaryTrapSensorInfo,
        fjdaryTrapMessage
    }
    DESCRIPTION
        "A sensorStatusChangeToNormal trap signifies that the error or warning
         state detected by the environment sensor has returned to normal after
         sending SensorStatusChange trap."
--#TYPE "Sensor status changed to normal"
--#SUMMARY "Sensor status changed to normal, from %s, id: %x[%x], message: %s"
--#SEVERITY INFORMATIONAL
--#ARGUMENTS {1,0,2,3}
--#TIMEINDEX 6
    ::= 26

fjdarye150Error TRAP-TYPE
    ENTERPRISE aplNetFjdarye150
    VARIABLES{
        fjdarySspMachineId,
        fjdaryTrapMessage
    }
    DESCRIPTION
        "An Error trap signifies that error events."
--#TYPE "Error event"
--#SUMMARY "Error event from %s, message: %s"
--#ARGUMENTS {0,1}
--#SEVERITY CRITICAL
--#TIMEINDEX 6
    ::= 50

fjdarye150Warning TRAP-TYPE
    ENTERPRISE aplNetFjdarye150
    VARIABLES{
        fjdarySspMachineId,
        fjdaryTrapMessage
    }
    DESCRIPTION
        "A Warning trap signifies that warning events."
--#TYPE "Warning event"
--#SUMMARY "Warning event from %s, message: %s"
--#ARGUMENTS {0,1}
--#SEVERITY MAJOR
--#TIMEINDEX 6
    ::= 51

fjdarye150QuotaLimitExceeded TRAP-TYPE
    ENTERPRISE aplNetFjdarye150
    VARIABLES{
        fjdarySspMachineId,
        fjdaryTrapMessage
    }
    DESCRIPTION
        "A quotaLimitExceeded trap signifies that the limit of quota is
         exceeded."
--#TYPE "Quota limit exceeded event"
--#SUMMARY "Quota limit exceeded event from %s, message: %s"
--#ARGUMENTS {0,1}
--#SEVERITY MAJOR
--#TIMEINDEX 6
    ::= 60

fjdarye150QuotaWarningExceeded TRAP-TYPE
    ENTERPRISE aplNetFjdarye150
    VARIABLES{
        fjdarySspMachineId,
        fjdaryTrapMessage
    }
    DESCRIPTION
        "A quotaWarningExceeded trap signifies that the limit of quota is
         reached."
--#TYPE "Quota limit warning event"
--#SUMMARY "Quota limit warning event from %s, message: %s"
--#ARGUMENTS {0,1}
--#SEVERITY MAJOR
--#TIMEINDEX 6
    ::= 61

fjdarye150QuotaNormal TRAP-TYPE
    ENTERPRISE aplNetFjdarye150
    VARIABLES{
        fjdarySspMachineId,
        fjdaryTrapMessage
    }
    DESCRIPTION
        "A quotaNormal trap signifies that the quota became less than limit."
--#TYPE "Quota normal event"
--#SUMMARY "Quota normal event from %s, message: %s"
--#ARGUMENTS {0,1}
--#SEVERITY INFORMATIONAL
--#TIMEINDEX 6
    ::= 62

fjdarye150SnapshotInformation TRAP-TYPE
    ENTERPRISE aplNetFjdarye150
    VARIABLES{
        fjdarySspMachineId,
        fjdaryTrapMessage
    }
    DESCRIPTION
        "A snapshotInformation trap signifies that the execution of snapshot
         succeeded."
--#TYPE "Snapshot information event"
--#SUMMARY "Snapshot information event from %s, message: %s"
--#ARGUMENTS {0,1}
--#SEVERITY INFORMATIONAL
--#TIMEINDEX 6
    ::= 63

END
