CLARIION-MIB DEFINITIONS ::= BEGIN



IMPORTS
    OBJECT-TYPE                                         FROM RFC-1212
    DisplayString                                FROM RFC1213-MIB;
   
   clariion                                  OBJECT IDENTIFIER ::= { enterprises 1981 }
   clarInfo                                  OBJECT IDENTIFIER ::= { clariion 1}
   eventMonitor                              OBJECT IDENTIFIER ::= { clarInfo 4}

   deviceType OBJECT-TYPE
            SYNTAX  DisplayString
            ACCESS  read-only
            STATUS  mandatory
            DESCRIPTION
            "A textual description of this device.
            Description for all current devices is 'CLARiiON Storage System'."
            ::= { clarInfo 1 }


    hostName OBJECT-TYPE
            SYNTAX  DisplayString
            ACCESS  read-only
            STATUS  mandatory
            DESCRIPTION
                        "Clariion Host Name."
            ::= { eventMonitor 3 }

    deviceID OBJECT-TYPE
            SYNTAX  DisplayString
            ACCESS  read-only
            STATUS  mandatory
            DESCRIPTION
                        "Clariion Device ID."
            ::= { eventMonitor 4 }

    eventID OBJECT-TYPE
            SYNTAX  DisplayString
            ACCESS  read-only
            STATUS  mandatory
            DESCRIPTION
                        "Event ID."
            ::= { eventMonitor 5 }

    eventText OBJECT-TYPE
            SYNTAX  DisplayString
            ACCESS  read-only
            STATUS  mandatory
            DESCRIPTION
                        "Event description."
            ::= { eventMonitor 6 }

    storageSystem OBJECT-TYPE
            SYNTAX  DisplayString
            ACCESS  read-only
            STATUS  mandatory
            DESCRIPTION
                        "Storage System Name."
            ::= { eventMonitor 7 }

   eventMonitorTrap TRAP-TYPE
              ENTERPRISE  clariion 
              VARIABLES   { hostName, deviceID, 
                            eventID, eventText,
                            storageSystem }
              DESCRIPTION
                          "An eventMonitorTrap is generated in
                          response to a user-specified event.
                          Details can be found in Variables data."
              --#TYPE  "Clariion Informational Trap"
              --#SUMMARY      "A Clariion Trap is generated with details: hostName=%s; deviceID=%d; eventID=%d; eventText=%s; storageSystem=%s"
              --#ARGUMENTS    {0,1,2,3,4}
              --#SEVERITY     INFORMATIONAL
              --#TIMEINDEX    6
               ::= 2

   eventMonitorTrap_Info TRAP-TYPE
              ENTERPRISE  clariion
              VARIABLES   { hostName, deviceID, 
                            eventID, eventText,
                            storageSystem }
              DESCRIPTION
                          "An Informational eventMonitorTrap is generated in
                          response to a user-specified event.
                          Details can be found in Variables data."
              --#TYPE  "Clariion Informational Trap"
              --#SUMMARY      "A Clariion Informational Trap is generated with details: hostName=%s; deviceID=%d; eventID=%d; eventText=%s; storageSystem=%s"
              --#ARGUMENTS    {0,1,2,3,4}
              --#SEVERITY     INFORMATIONAL
              --#TIMEINDEX    6
              ::= 3

   eventMonitorTrap_Warn TRAP-TYPE
              ENTERPRISE  clariion 
              VARIABLES   { hostName, deviceID, 
                            eventID, eventText,
                            storageSystem }
              DESCRIPTION
                          "A Warning eventMonitorTrap is generated in
                          response to a user-specified event.
                          Details can be found in Variables data."
              --#TYPE    "Clariion Warning Trap"
              --#SUMMARY    "A Clariion Warning Trap is generated with details: hostName=%s; deviceID=%d; eventID=%d; eventText=%s; storageSystem=%s"
              --#ARGUMENTS    {0,1,2,3,4}
              --#SEVERITY     MINOR
              --#TIMEINDEX    6
              ::= 4

   eventMonitorTrap_Error TRAP-TYPE
              ENTERPRISE  clariion
              VARIABLES   { hostName, deviceID, 
                            eventID, eventText,
                            storageSystem }
              DESCRIPTION
                          "An Error eventMonitorTrap is generated in
                          response to a user-specified event.
                          Details can be found in Variables data."
              --#TYPE    "Clariion Error Trap"
              --#SUMMARY      "A Clariion Error Trap is generated with details: hostName=%s; deviceID=%d; eventID=%d; eventText=%s; storageSystem=%s"
              --#ARGUMENTS    {0,1,2,3,4}
              --#SEVERITY     MAJOR
              --#TIMEINDEX    6
              ::= 5

   eventMonitorTrap_Fault TRAP-TYPE
              ENTERPRISE  clariion
              VARIABLES   { hostName, deviceID,
                            eventID, eventText,
                            storageSystem }
              DESCRIPTION
                          "A Fault eventMonitorTrap is generated in
                          response to a user-specified event.
                          Details can be found in Variables data."
              --#TYPE   "Clariion Fault Trap"
              --#SUMMARY    "A Clariion Fault Trap is generated with details: hostName=%s; deviceID=%d; eventID=%d; eventText=%s; storageSystem=%s"
              --#ARGUMENTS    {0,1,2,3,4}
              --#SEVERITY     CRITICAL
              --#TIMEINDEX    6
              ::= 6

END
