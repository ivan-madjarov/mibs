-- ======================================================== --
	-- NetApp Custom MIB                                        --
	--                                                          --
	-- This MIB contains only information specific to           --
	-- NetApp products. Other supported mibs are                --
	-- not included in this file.                               --
	-- =======================================================  --

	-- Version 2.20, July 2022 (See NOTE below)

	-- Copyright (c) 1995-2022 NetApp, Inc.
	-- All rights reserved.

	-- This NetApp SNMP Management Information Base
	-- (Specification) embodies NetApp's confidential
	-- and proprietary intellectual property.  NetApp
	-- retains all title and ownership in the Specification,
	-- including any revisions.

	-- This Specification is supplied "AS IS," and NetApp
	-- makes no warranty, either express or implied, as to the use,
	-- operation, condition, or performance of the Specification.

	-- NOTE:   Please maintain the format of the line above
		-- containing the MIB's version number as:
		--
		-- Version <version #>, <Date> (See NOTE below)
		--
		-- This line is parsed during the release process
		-- to extract the version of the MIB.
	        -- Keep the MODULE-IDENTITY in sync with the Version Date.
	        --

	-- =======================================================  --
	-- List of modifications for upgrade to SMIv2 (RFC2578):
	--
	-- Standardized capitalization for grmMonitor
	-- subtyping not allowed in SEQUENCE
	-- hyphens not allowed in value types.
	-- Changed dmpSubtreeEntry to dmpEntry
	-- Removed lastdump and placed entries in dmpEntry
	-- Removed lastsuccess and placed entries in dmpEntry
	-- Renamed initiatorListMemberEntry to initiatorListEntry
	-- Moved enclTempSensorsCurrentTemp to correct location in enclEntry
	-- Add enclSASConn... to enclEntry
	-- Added Counter64 support
	-- Renamed the following netcache OIDS:
	--  ncStreamingOndemandBytesToClients to ncStreamingOBTClients
	--  ncStreamingOndemandBytesFromClients to ncStreamingOBFClients
	--  ncStreamingOndemandBytesToServers to ncStreamingOBTServers
	--  ncStreamingOndemandBytesFromServers to ncStreamingOBFServers
	--  ncStreamingQuickTimeBytesToClients to ncStreamingQTBTClients
	--  ncStreamingQuickTimeBytesFromClients to ncStreamingQTBFClients
	--  ncStreamingQuickTimeBytesToServers to ncStreamingQTBTServers
	--  ncStreamingQuickTimeBytesFromServers to ncStreamingQTBFServers
	--  ncStreamingRtspWMBytesFromClients to ncStreamingRtspWMBFClients
	--  ncStreamingRtspWMBytesFromServers to ncStreamingRtspWMBFServers

	-- Conform to RFC3584 "Coexistence between V1, V2, and V3 of
	--         the Internet-standard Network Management Framework
	-- 2.1.1. Required changes
	-- 1 - IMPORTS statement must reference SNMPv2-SMI
	-- 2 - The MODULE-IDENTITY macro must be invoked.
	-- 3 - SYNTAX Counter32 replaces Counter
	-- 4 - SYNTAX Gauge32 replaces Gauge
	-- 5 - MAX-ACCESS replaces ACCESS
	-- 6 - STATUS current replaces STATUS mandatory
	--     STATUS current replaces STATUS optional
	-- 2.1.1 - Desirable changes
	-- 2 - Integer32 replaces INTEGER in places that don't have ranges
	-- 2.1.2 - Trap and Notification Definitions
	-- 1 - IMPORTS must reference SMIv2-SMI
	-- 2 - ENTERPRISE is removed
	-- 3 - VARIABLES clause must be renamed to OBJECTS clause
	-- 4 - STATUS clause must be added

	-- Add enclXXXpart
	-- =======================================================  --

	NETAPP-MIB DEFINITIONS ::= BEGIN

        IMPORTS
	        MODULE-IDENTITY, OBJECT-TYPE, NOTIFICATION-TYPE, IpAddress, enterprises,
		TimeTicks, Gauge32, Counter32, Counter64, Integer32, Unsigned32, snmpModules, mib-2
		        FROM SNMPv2-SMI
		TEXTUAL-CONVENTION, DisplayString, TestAndIncr, TimeStamp, PhysAddress, DateAndTime
		        FROM SNMPv2-TC
		MODULE-COMPLIANCE, OBJECT-GROUP, NOTIFICATION-GROUP
		        FROM SNMPv2-CONF
		CounterBasedGauge64, ZeroBasedCounter64
		        FROM HCNUM-TC
		SnmpAdminString
		        FROM SNMP-FRAMEWORK-MIB;

        netappModuleId  MODULE-IDENTITY
	LAST-UPDATED      "202207180000Z"
        ORGANIZATION      "NetApp"
        CONTACT-INFO      "www.netapp.com"
        DESCRIPTION       "The mib module for NetApp SNMPv2 entities"

	::= { snmpModules 789 }

        Boolean ::= TEXTUAL-CONVENTION
	    STATUS   current
	    DESCRIPTION
		"false|true"
	    SYNTAX   INTEGER {
                false(0),
		true(1)
	    }

	Uuid ::= TEXTUAL-CONVENTION
	    STATUS   current
	    DESCRIPTION
		"Universally Unique Identifier"
	    SYNTAX   OCTET STRING (SIZE (16))

	TimeTicks64 ::= TEXTUAL-CONVENTION
	    STATUS   current
	    DESCRIPTION
		"Represents time in hundredths (1/100) of a second since an epoch."
	    SYNTAX   Counter64

	FileOrDirectoryString ::= TEXTUAL-CONVENTION
	    DISPLAY-HINT "1023t"
	    STATUS       current
	    DESCRIPTION
		"An octet string containing a file or directory
		 name.

                 UTF-8 encoding is used to represent Unicode
		 characters. See [RFC2279].

		 Essentially, this is a longer variant of
		 SnmpAdminString.
		"
	    SYNTAX       OCTET STRING (SIZE (0..1023))

	FilesystemPathString ::= TEXTUAL-CONVENTION
	    DISPLAY-HINT "4095t"
	    STATUS       current
	    DESCRIPTION
		"An octet string containing a filesystem path.

                 UTF-8 encoding is used to represent Unicode
		 characters. See [RFC2279].

		 Essentially, this is a longer variant of
		 SnmpAdminString.
		"
	    SYNTAX       OCTET STRING (SIZE (0..4095))

	--  MIB-II (same prefix as MIB-I)

	-- the NetApp MIB

	-- NetApp conventions

	netapp OBJECT IDENTIFIER ::= { enterprises 789 }

	netapp0 OBJECT IDENTIFIER ::= { netapp 0 }

	-- the current netapp mib

	netapp1	OBJECT IDENTIFIER ::= { netapp 1 }

	--
	-- This is the tree under which values for the sysObjectID
	-- are allocated.
	--

	netappProducts OBJECT IDENTIFIER ::= { netapp 2 }

	--
	-- This is the tree under which values for the DataFabric Manager
	-- are allocated. Those values are defined in separate mib file,
	-- distributed with DataFabric Manager product.
	--

	netappDataFabricManager OBJECT IDENTIFIER ::= { netapp 3 }

	--
	-- This is the tree under which values for the NetApp Support Console
	-- are allocated. Those values are defined in separate mib file,
	-- distributed with the Support Console
	--

	netappSupportConsole OBJECT IDENTIFIER ::= { netapp 4 }

	--
	-- This is the tree under which values for the OnCommand
	-- management software from Unified Manager version 6.0 onwards
	-- are allocated.
	-- Those values are defined in separate OCUM MIB file, distributed
	-- with OnCommand product.
	--

	netappOnCommand OBJECT IDENTIFIER ::= { netapp 5 }

	--
	-- This is the tree under which values for the netapp metrocluster
	-- are allocated
	--

        netappMcc OBJECT IDENTIFIER ::= { netapp 6 }

	--
	-- We distinguish between filers and NetCaches.
	--

	netappFiler	OBJECT IDENTIFIER ::= { netappProducts 1 }
	netappNetCache	OBJECT IDENTIFIER ::= { netappProducts 2 }
	netappClusteredFiler	OBJECT IDENTIFIER ::= { netappProducts 3 }
	netappNode	OBJECT IDENTIFIER ::= { netappProducts 4 }
	netappCluster	OBJECT IDENTIFIER ::= { netappProducts 5 }
	netappVserver	OBJECT IDENTIFIER ::= { netappProducts 6 }

	--
	-- This is the tree under which values for the netapp metrocluster
	-- Tiebreaker software are allocated.
	-- Those values are defined in sepearate MCCTB MIB file, distributed
        -- with MCCTB product.
	--

        netappMcctb OBJECT IDENTIFIER ::= { netappMcc 1 }

	-- top-level netapp groups

	product	                        OBJECT IDENTIFIER ::= { netapp1 1 }

	sysStat	                        OBJECT IDENTIFIER ::= { netapp1 2 }

	nfs	                        OBJECT IDENTIFIER ::= { netapp1 3 }

	quota	                        OBJECT IDENTIFIER ::= { netapp1 4 }

	filesys	                        OBJECT IDENTIFIER ::= { netapp1 5 }

	raid	                        OBJECT IDENTIFIER ::= { netapp1 6 }

	cifs	                        OBJECT IDENTIFIER ::= { netapp1 7 }

	netcache      	                OBJECT IDENTIFIER ::= { netapp1 8 }

	snapmirror     	                OBJECT IDENTIFIER ::= { netapp1 9 }

	ndmp     	                OBJECT IDENTIFIER ::= { netapp1 10 }

	fabric     	                OBJECT IDENTIFIER ::= { netapp1 11 }

	dafs		                OBJECT IDENTIFIER ::= { netapp1 12 }

	vi		                OBJECT IDENTIFIER ::= { netapp1 13 }

	backup		                OBJECT IDENTIFIER ::= { netapp1 14 }

        vfiler                          OBJECT IDENTIFIER ::= { netapp1 16 }

	blocks		                OBJECT IDENTIFIER ::= { netapp1 17 }

	nfscache	                OBJECT IDENTIFIER ::= { netapp1 18 }

	snapvault     	                OBJECT IDENTIFIER ::= { netapp1 19 }

	ftpd		                OBJECT IDENTIFIER ::= { netapp1 20 }

	storage   	                OBJECT IDENTIFIER ::= { netapp1 21 }

	network		                OBJECT IDENTIFIER ::= { netapp1 22 }

	sis		                OBJECT IDENTIFIER ::= { netapp1 23 }

	compress			OBJECT IDENTIFIER ::= { netapp1 24 }

	cluster         		OBJECT IDENTIFIER ::= { netapp1 25 }

	extcache 			OBJECT IDENTIFIER ::= { netapp1 26 }

	vserver				OBJECT IDENTIFIER ::= { netapp1 27 }

	qos	                        OBJECT IDENTIFIER ::= { netapp1 28 }

	sm	                        OBJECT IDENTIFIER ::= { netapp1 29 }

	-- clusterIdentity group
	clusterIdentity OBJECT IDENTIFIER ::= { cluster 1 }

	clusterIdentityUuid		OBJECT-TYPE
	SYNTAX      			DisplayString
	MAX-ACCESS  			read-only
	STATUS      			current
	DESCRIPTION
		"Cluster's universally unique identifier (UUID)."
	::= { clusterIdentity 1 }

	clusterIdentityName 		OBJECT-TYPE
	SYNTAX      			DisplayString
	MAX-ACCESS  			read-only
	STATUS      			current
	DESCRIPTION
		"Name of the cluster of which this node is a member."
	::= { clusterIdentity 2 }

	clusterIdentitySerialNumber 	OBJECT-TYPE
	SYNTAX      			DisplayString
	MAX-ACCESS  			read-only
	STATUS      			current
	DESCRIPTION
		"Cluster Serial Number"
	::= { clusterIdentity 3 }

	-- nodeTable
	nodeTable			OBJECT-TYPE
	SYNTAX      			SEQUENCE OF NodeEntry
	MAX-ACCESS  			not-accessible
	STATUS      			current
	DESCRIPTION
		"Table of all nodes in the cluster."
	::= { cluster 2 }

	nodeEntry			OBJECT-TYPE
	SYNTAX      			NodeEntry
	MAX-ACCESS  			not-accessible
	STATUS      			current
	DESCRIPTION
		"Entry for a node in the cluster."
	INDEX { IMPLIED nodeName }
	::= { nodeTable 1 }

	NodeEntry ::=
            SEQUENCE {
                nodeName         	DisplayString,
                nodeOwner        	DisplayString,
                nodeLocation     	DisplayString,
                nodeModel        	DisplayString,
		nodeSerialNumber 	DisplayString,
		nodeAssetTag     	DisplayString,
		nodeUptime       	TimeTicks,
		nodeNvramId      	INTEGER,
		nodeSystemId     	DisplayString,
		nodeVendor       	DisplayString,
		nodeHealth       	Boolean,
		nodeEligibility  	Boolean,
		nodeEpsilon      	Boolean,
		nodeUuid         	DisplayString,
		nodeCpuUptime           TimeTicks,
		nodeCpuBusyTime         TimeTicks,
		nodeNvramBatteryStatus  INTEGER,
		nodeEnvOverTemperature  INTEGER,
		nodeEnvFailedFanCount   INTEGER,
		nodeEnvFailedFanMessage DisplayString,
		nodeEnvFailedPowerSupplyCount   INTEGER,
		nodeEnvFailedPowerSupplyMessage DisplayString,
		nodeProductVersion		DisplayString,
		nodeFirmwareVersion		DisplayString
        }

	nodeName 			OBJECT-TYPE
	SYNTAX      			DisplayString
	MAX-ACCESS  			read-only
	STATUS      			current
	DESCRIPTION
		"Node Name. Same as sysName for a specific node."
	::= { nodeEntry 1 }

	nodeOwner			OBJECT-TYPE
	SYNTAX      			DisplayString
	MAX-ACCESS  			read-only
	STATUS      			current
	DESCRIPTION
		"Node Owner. Same as sysContact for a specific node."
	::= { nodeEntry 2 }

	nodeLocation			OBJECT-TYPE
	SYNTAX      			DisplayString
	MAX-ACCESS  			read-only
	STATUS      			current
	DESCRIPTION
		"Node Location. Same as sysLocation for a specific node."
	::= { nodeEntry 3 }

	nodeModel 			OBJECT-TYPE
	SYNTAX      			DisplayString
	MAX-ACCESS  			read-only
	STATUS      			current
	DESCRIPTION
		"Node Model. Same as productModel for a specific node."
	::= { nodeEntry 4 }

	nodeSerialNumber 		OBJECT-TYPE
	SYNTAX      			DisplayString
	MAX-ACCESS  			read-only
	STATUS      			current
	DESCRIPTION
		"Node Serial Number. Same as productSerialNum for a specific node."
	::= { nodeEntry 5 }

	nodeAssetTag 			OBJECT-TYPE
	SYNTAX      			DisplayString
	MAX-ACCESS  			read-only
	STATUS      			current
	DESCRIPTION
		"Value of customer-assigned asset tag for this node."
	::= { nodeEntry 6 }

	nodeUptime 			OBJECT-TYPE
	SYNTAX      			TimeTicks
	MAX-ACCESS  			read-only
	STATUS      			current
	DESCRIPTION
		"Node Uptime. Same as sysUpTime for a specific node."
	::= { nodeEntry 7 }

	nodeNvramId 			OBJECT-TYPE
	SYNTAX      			INTEGER
	MAX-ACCESS  			read-only
	STATUS      			current
	DESCRIPTION
		"NVRAM ID of this node."
	::= { nodeEntry 8 }

	nodeSystemId 			OBJECT-TYPE
	SYNTAX      			DisplayString
	MAX-ACCESS  			read-only
	STATUS      			current
	DESCRIPTION
		"Node System ID. Same as productId for a specific node."
	::= { nodeEntry 9 }

	nodeVendor 			OBJECT-TYPE
	SYNTAX      			DisplayString
	MAX-ACCESS  			read-only
	STATUS      			current
	DESCRIPTION
		"Node Vendor. Similar to productVendor for a specific node."
	::= { nodeEntry 10 }

	nodeHealth 			OBJECT-TYPE
	SYNTAX      			Boolean
	MAX-ACCESS  			read-only
	STATUS      			current
	DESCRIPTION
		"Whether or not the node can communicate with the cluster."
	::= { nodeEntry 11 }

	nodeEligibility 		OBJECT-TYPE
	SYNTAX      			Boolean
	MAX-ACCESS  			read-only
	STATUS      			current
	DESCRIPTION
		"An eligible node is one that has been designated by the
		 administrator as an active participant in the cluster."
	::= { nodeEntry 12 }

	nodeEpsilon 			OBJECT-TYPE
	SYNTAX      			Boolean
	MAX-ACCESS  			read-only
	STATUS      			current
	DESCRIPTION
	    "Whether or not this node has epsilon to keep the quorum
	     up if only half of the nodes can communicate."
	::= { nodeEntry 13 }

	nodeUuid 			OBJECT-TYPE
	SYNTAX      			DisplayString
	MAX-ACCESS  			read-only
	STATUS      			current
	DESCRIPTION
		"Universally unique identifier (UUID) of the node."
	::= { nodeEntry 14 }

	nodeCpuUptime                   OBJECT-TYPE
	SYNTAX      			TimeTicks
	MAX-ACCESS  			read-only
	STATUS      			current
	DESCRIPTION
		"The time (in hundredths of a second) that the
		CPU has been up since the last boot."
	::= { nodeEntry 15 }

	nodeCpuBusyTime 		OBJECT-TYPE
	SYNTAX      			TimeTicks
	MAX-ACCESS  			read-only
	STATUS      			current
	DESCRIPTION
		"The time (in hundredths of a second) that the
		CPU has been doing useful work since the last
		boot."
	::= { nodeEntry 16 }

	nodeNvramBatteryStatus 		OBJECT-TYPE
	SYNTAX      			INTEGER {
	                                     ok(1),
					     partiallyDischarged(2),
					     fullyDischarged(3),
					     notPresent(4),
					     nearEndOfLife(5),
					     atEndOfLife(6),
					     unknown(7),
					     overCharged(8),
					     fullyCharged(9)
					}
	MAX-ACCESS  			read-only
	STATUS      			current
	DESCRIPTION
		"An indication of the current status of the
		 NVRAM battery or batteries.  Batteries which
		 are fully or partially discharged may not
		 fully protect the system during a crash.

		 The end-of-life status values are based on
		 the manufacturer's recommended life for the
		 batteries."
	    ::= { nodeEntry 17 }

	nodeEnvOverTemperature 	        OBJECT-TYPE
	SYNTAX      			INTEGER {
	                                     no(1),
					     yes(2)
					}
	MAX-ACCESS  			read-only
	STATUS      			current
	DESCRIPTION
		"An indication of whether the hardware is
		currently operating outside of its recommended
		temperature range.  The hardware will shutdown
		if the temperature exceeds critical thresholds."
	::= { nodeEntry 18 }

	nodeEnvFailedFanCount 		OBJECT-TYPE
	SYNTAX      			INTEGER
	MAX-ACCESS  			read-only
	STATUS      			current
	DESCRIPTION
		"Count of the number of chassis fans which
		are not operating within the recommended
		RPM range."
	::= { nodeEntry 19 }

	nodeEnvFailedFanMessage 	OBJECT-TYPE
	SYNTAX      			DisplayString
	MAX-ACCESS  			read-only
	STATUS      			current
	DESCRIPTION
		"Text message describing the current condition of
		chassis fans.  This is useful only if
		envFailedFanCount is not zero."
	::= { nodeEntry 20 }

	nodeEnvFailedPowerSupplyCount	OBJECT-TYPE
	SYNTAX      			INTEGER
	MAX-ACCESS  			read-only
	STATUS      			current
	DESCRIPTION
		"Count of the number of power supplies which
		are in degraded mode."
	::= { nodeEntry 21 }

	nodeEnvFailedPowerSupplyMessage OBJECT-TYPE
	SYNTAX      			DisplayString
	MAX-ACCESS  			read-only
	STATUS      			current
	DESCRIPTION
		"Text message describing the state of any
		power supplies which are currently degraded.
		This is useful only if envFailedPowerSupplyCount
		is not zero."
	::= { nodeEntry 22 }

	nodeProductVersion		OBJECT-TYPE
	SYNTAX				DisplayString
	MAX-ACCESS			read-only
	STATUS				current
	DESCRIPTION
		"Node Product Version. Similar to productVersion for
		a specific node."
	::= { nodeEntry 23 }

	nodeFirmwareVersion		OBJECT-TYPE
	SYNTAX				DisplayString
	MAX-ACCESS			read-only
	STATUS				current
	DESCRIPTION
		"Node Firmware Version. Similar to productFirmwareVersion
		for a specific node."
	::= { nodeEntry 24 }

	-- clusterLicenseTable
        clusterLicenseTable 		OBJECT-TYPE
	SYNTAX      			SEQUENCE OF ClusterLicenseEntry
	MAX-ACCESS  			not-accessible
	STATUS      			obsolete
	DESCRIPTION
		"Cluster Licenses"
	::= { cluster 3 }

	clusterLicenseEntry 		OBJECT-TYPE
	SYNTAX      			ClusterLicenseEntry
	MAX-ACCESS  			not-accessible
	STATUS      			obsolete
	DESCRIPTION
		"Details about each installed cluster license."
	INDEX { clusterLicenseFeature }
	::= { clusterLicenseTable 1 }

	ClusterLicenseEntry ::=
            SEQUENCE {
                clusterLicenseFeature         Integer32,
		clusterLicenseCode            DisplayString,
		clusterLicenseDescription     DisplayString,
		clusterLicenseSerialNumber    DisplayString,
		clusterLicenseLimit	      Integer32,
		clusterLicenseExpirationDate  DisplayString
	    }

	clusterLicenseFeature 		OBJECT-TYPE
	SYNTAX      			Integer32 (1..2147483647)
	MAX-ACCESS  			read-only
	STATUS      			obsolete
	DESCRIPTION
		"Cluster license feature ID, see clusterLicenseDescription
	         for the name/description of this feature"
	::= { clusterLicenseEntry 1 }

	clusterLicenseCode 		OBJECT-TYPE
	SYNTAX      			DisplayString
	MAX-ACCESS  			read-only
	STATUS      			obsolete
	DESCRIPTION
		"Cluster License Code"
	::= { clusterLicenseEntry 2 }

	clusterLicenseDescription 	OBJECT-TYPE
	SYNTAX      			DisplayString
	MAX-ACCESS  			read-only
	STATUS      			obsolete
	DESCRIPTION
		"Cluster License Feature Description"
	::= { clusterLicenseEntry 3 }

	clusterLicenseSerialNumber 	OBJECT-TYPE
	SYNTAX      			DisplayString
	MAX-ACCESS  			read-only
	STATUS      			obsolete
	DESCRIPTION
		"Cluster Serial Number"
	::= { clusterLicenseEntry 4 }

	clusterLicenseLimit 		OBJECT-TYPE
	SYNTAX      			Integer32
	MAX-ACCESS  			read-only
	STATUS      			obsolete
	DESCRIPTION
		"Cluster feature limit value. The units of this value
		are feature specific, for example number of nodes, capacity in TB,
		number of streams, etc. Information about this limit will be in
		the clusterLicenseDescription."
	::= { clusterLicenseEntry 5 }

	clusterLicenseExpirationDate 	OBJECT-TYPE
	SYNTAX      			DisplayString
	MAX-ACCESS  			read-only
	STATUS      			obsolete
	DESCRIPTION
		"Cluster License Expiration Date if it exists"
	::= { clusterLicenseEntry 6 }

	-- licenseTable
        licenseTable	 		OBJECT-TYPE
	SYNTAX      			SEQUENCE OF LicenseEntry
	MAX-ACCESS  			not-accessible
	STATUS      			current
	DESCRIPTION
		"Licenses"
	::= { cluster 4 }

	licenseEntry	 		OBJECT-TYPE
	SYNTAX      			LicenseEntry
	MAX-ACCESS  			not-accessible
	STATUS      			current
	DESCRIPTION
		"Details about each installed license."
	INDEX { licenseSerialNumber, licensePackage }
	::= { licenseTable 1 }

	LicenseEntry ::=
            SEQUENCE {
                licenseSerialNumber           DisplayString,
		licensePackage                Integer32,
		licenseOwner                  DisplayString,
		licenseDescription            DisplayString,
		licenseType                   INTEGER,
		licenseExpiration             DateAndTime,
		licenseLegacy                 INTEGER,
		licenseCustomerID             DisplayString
	    }

	licenseSerialNumber 		OBJECT-TYPE
	SYNTAX      			DisplayString
	MAX-ACCESS  			read-only
	STATUS      			current
	DESCRIPTION
		"License Serial Number"
	::= { licenseEntry 1 }

	licensePackage	 		OBJECT-TYPE
	SYNTAX      			Integer32 (1..2147483647)
	MAX-ACCESS  			read-only
	STATUS      			current
	DESCRIPTION
		"License package ID, see licenseDescription
	         for the name/description of this package"
	::= { licenseEntry 2 }

	licenseOwner		 	OBJECT-TYPE
	SYNTAX      			DisplayString
	MAX-ACCESS  			read-only
	STATUS      			current
	DESCRIPTION
		"Name of the Node or Cluster that the license belongs to"
	::= { licenseEntry 3 }

	licenseDescription	 	OBJECT-TYPE
	SYNTAX      			DisplayString
	MAX-ACCESS  			read-only
	STATUS      			current
	DESCRIPTION
		"License Package Description"
	::= { licenseEntry 4 }

	licenseType   		 	OBJECT-TYPE
	SYNTAX      			INTEGER {
	                                    license(2),
					    site(3),
					    demo(4)
					}
	MAX-ACCESS  			read-only
	STATUS      			current
	DESCRIPTION
		"License Type"
	::= { licenseEntry 5 }

	licenseExpiration	 	OBJECT-TYPE
	SYNTAX      		     	DateAndTime
	MAX-ACCESS  			read-only
	STATUS      			current
	DESCRIPTION
		"License Expiration Date if it exists"
	::= { licenseEntry 6 }

	licenseLegacy   		OBJECT-TYPE
	SYNTAX                          INTEGER {
                                             true(1),
                                             false(2)
                                        }
	MAX-ACCESS  			read-only
	STATUS      			current
	DESCRIPTION
		"Indicates if the license is a Legacy License"
	::= { licenseEntry 7 }

	licenseCustomerID   		OBJECT-TYPE
	SYNTAX      			DisplayString
	MAX-ACCESS  			read-only
	STATUS      			current
	DESCRIPTION
		"Customer Identification Number, if exists"
	::= { licenseEntry 8 }

 	-- -- -- -- -- -- -- --
        -- vserver group --
        -- -- -- -- -- -- -- --

	vserverTable                    OBJECT-TYPE
	SYNTAX      			SEQUENCE OF VserverEntry
	MAX-ACCESS  			not-accessible
	STATUS      			current
	DESCRIPTION
		"Virtual Server Table"
	::= { vserver 1 }

	vserverEntry 			OBJECT-TYPE
	SYNTAX      			VserverEntry
	MAX-ACCESS  			not-accessible
	STATUS      			current
	DESCRIPTION
		"Virtual Server Entry"
	INDEX { vserverIndex }
	::= { vserverTable 1 }

	VserverEntry ::=
            SEQUENCE {
                vserverIndex                      Unsigned32,
                vserverName                       DisplayString,
		vserverUuid                       DisplayString,
		vserverRootVolume                 DisplayString,
		vserverAggregate                  DisplayString,
		vserverNsSwitch                   DisplayString,
		vserverNisDomain                  DisplayString,
		vserverRootVolumeSecurityStyle    INTEGER,
		vserverLdapClient                 DisplayString,
		vserverLanguage                   DisplayString,
		vserverSnapshotPolicy             DisplayString,
		vserverComment                    DisplayString,
		vserverAntiVirusOnAccessPolicy    DisplayString,
		vserverQuotaPolicy                DisplayString,
		vserverType                       INTEGER,
		vserverState                      INTEGER,
            	vserverAggrList                   OCTET STRING,
            	vserverAllowedProtocolList        OCTET STRING,
            	vserverNumVolumes                 Integer32,
            	vserverMaxVolumes                 Unsigned32,
		vserverDisallowedProtocolList	  OCTET STRING,
		vserverIPspace                    DisplayString,
		vserverIsRepository		  Boolean,
		vserverOperationalState           INTEGER
            }

	vserverIndex                    OBJECT-TYPE
        SYNTAX                          Unsigned32 (0..4294967295)
	MAX-ACCESS                      not-accessible
        STATUS                          current
	DESCRIPTION
		"Index of virtual server."
	::= { vserverEntry 1 }

	vserverName 			OBJECT-TYPE
	SYNTAX      			DisplayString
	MAX-ACCESS 			read-only
	STATUS      			current
	DESCRIPTION
		"Name of virtual server."
	::= { vserverEntry 2 }

	vserverUuid 			OBJECT-TYPE
	SYNTAX      			DisplayString
	MAX-ACCESS  			read-only
	STATUS      			current
	DESCRIPTION
		"Universally unique identifier (UUID) of virtual server."
	::= { vserverEntry 3 }

	vserverRootVolume 		OBJECT-TYPE
	SYNTAX      			DisplayString
	MAX-ACCESS  			read-only
	STATUS      			current
	DESCRIPTION
		"Virtual server's root volume"
	::= { vserverEntry 4 }

	vserverAggregate 		OBJECT-TYPE
	SYNTAX      			DisplayString
	MAX-ACCESS  			read-only
	STATUS      			current
	DESCRIPTION
		"Name of aggregate the vserver's root volume is in."
	::= { vserverEntry 5 }

	vserverNsSwitch 		OBJECT-TYPE
	SYNTAX      			DisplayString
	MAX-ACCESS  			read-only
	STATUS      			current
	DESCRIPTION
		"Vserver Name Service Switch setting (eg: nis, ldap, file)."
	::= { vserverEntry 6 }

	vserverNisDomain 		OBJECT-TYPE
	SYNTAX   			DisplayString
	MAX-ACCESS  			read-only
	STATUS      			current
	DESCRIPTION
		"Vserver NIS Domain"
	::= { vserverEntry 7 }

	vserverRootVolumeSecurityStyle  OBJECT-TYPE
	SYNTAX      			INTEGER {
	                                     unix(0), -- NFS
					     ntfs(1), -- CIFS
					     mixed(2) -- Mixed
					}
	MAX-ACCESS			read-only
	STATUS      			current
	DESCRIPTION
		"Vserver Root Volume Security Style"
	::= { vserverEntry 8 }

	vserverLdapClient		OBJECT-TYPE
	SYNTAX      			DisplayString
	MAX-ACCESS  			read-only
	STATUS      			current
	DESCRIPTION
		"Vserver LDAP Client"
	::= { vserverEntry 9 }

	vserverLanguage 		OBJECT-TYPE
	SYNTAX      			DisplayString
	MAX-ACCESS  			read-only
	STATUS      			current
	DESCRIPTION
		"Language of this vserver's volumes. For example, 'English'"
	::= { vserverEntry 10 }

	vserverSnapshotPolicy 		OBJECT-TYPE
	SYNTAX      			DisplayString
	MAX-ACCESS  			read-only
	STATUS      			current
	DESCRIPTION
		"Vserver Default Snapshot Policy"
	::= { vserverEntry 11 }

	vserverComment 			OBJECT-TYPE
	SYNTAX      			DisplayString (SIZE (0..255))
	MAX-ACCESS  			read-only
	STATUS      			current
	DESCRIPTION
		"Customer assigned comment for this vserver"
	::= { vserverEntry 12 }

	vserverAntiVirusOnAccessPolicy  OBJECT-TYPE
	SYNTAX      			DisplayString
	MAX-ACCESS  			read-only
	STATUS     			deprecated
	DESCRIPTION
		"Vserver Default Anti-Virus On-Access Policy"
	::= { vserverEntry 13 }

	vserverQuotaPolicy		OBJECT-TYPE
	SYNTAX      			DisplayString
	MAX-ACCESS  			read-only
	STATUS      			current
	DESCRIPTION
		"Quota Policy assigned for all volumes in this vserver"
	::= { vserverEntry 14 }

	vserverType			OBJECT-TYPE
	SYNTAX      			INTEGER {
					     data(0),
                                             admin(1),
                                             node(2),
					     system(4)
                                        }
	MAX-ACCESS  			read-only
	STATUS      			current
	DESCRIPTION
            "Type of the vserver. There are four distinct supported
            types: data, admin, node and system.

            'data' vservers are the default scale-out vservers.
            One 'admin' vserver exists per cluster and it
            provides universal administrative access to the cluster.
            One 'node' vserver exists per node in the cluster and
            identifies the physical controller. 'system' vserver is
	    for	cluster-scoped communications in an IPspace."

	::= { vserverEntry 15 }

       vserverState               OBJECT-TYPE
       SYNTAX                     INTEGER {
                                     running(0),
                                     stopped(1),
				     starting(2),
				     stopping(3)
                                  }
       MAX-ACCESS                 read-only
       STATUS                     current
       DESCRIPTION
           "State of the vserver"
       ::= { vserverEntry 16 }

       vserverAggrList            OBJECT-TYPE
       SYNTAX                     OCTET STRING (SIZE (0..1024))
       MAX-ACCESS                 read-only
       STATUS                     current
       DESCRIPTION
           "This is a comma-separated list of aggregates on which the
            Vserver can perform volume operations. The aggregates may
            be shared for use with other Vservers."
       ::= { vserverEntry 17 }

       vserverAllowedProtocolList OBJECT-TYPE
       SYNTAX                     OCTET STRING (SIZE (0..1024))
       MAX-ACCESS                 read-only
       STATUS			  current
       DESCRIPTION
           "This is a comma-separated list of protocols/services allowed
            to run on the Vserver. Eg: NFS,CIFS,iSCSI,FCP."
       ::= { vserverEntry 18 }

       vserverNumVolumes          OBJECT-TYPE
       SYNTAX                     Integer32
       MAX-ACCESS                 read-only
       STATUS                     current
       DESCRIPTION
           "Number of volumes that are contained in the Vserver."
       ::= { vserverEntry 19 }

       vserverMaxVolumes          OBJECT-TYPE
       SYNTAX                     Unsigned32 (0..4294967295)
       MAX-ACCESS                 read-only
       STATUS                     current
       DESCRIPTION
           "Maximum number of volumes that can be created on the Vserver.
	    A value of 4294967295 indicates there is no limit on the number
	    of volumes that can be created on the Vserver. 4294967295 value
            translates to 'unlimited' when displayed at the CLI."
       ::= { vserverEntry 20 }

       vserverDisallowedProtocolList OBJECT-TYPE
       SYNTAX                     OCTET STRING (SIZE (0..1024))
       MAX-ACCESS                 read-only
       STATUS			  current
       DESCRIPTION
           "This is a comma-separated list of protocols/services disallowed
            to run on the Vserver. Eg: NFS,CIFS,iSCSI,FCP."
       ::= { vserverEntry 21 }

	vserverIPspace				OBJECT-TYPE
	SYNTAX					DisplayString
	MAX-ACCESS				read-only
	STATUS					current
	DESCRIPTION
		"IPspace where the Vserver is assigned."
	::= { vserverEntry 22 }

       vserverIsRepository          OBJECT-TYPE
       SYNTAX                       Boolean
       MAX-ACCESS                   read-only
       STATUS                       current
       DESCRIPTION
           "This parameter defines if this is a Vserver with Infinite Volume.
	    A Vserver with Infinite Volume contains a single Infinite Volume."
       ::= { vserverEntry 23 }

       vserverOperationalState    OBJECT-TYPE
       SYNTAX                     INTEGER {
                                     running(0),
                                     stopped(1)
                                  }
       MAX-ACCESS                 read-only
       STATUS                     current
       DESCRIPTION
           "Operational State of the vserver"
       ::= { vserverEntry 24 }

	-- -- -- -- -- -- -- --
	-- the product group --
	-- -- -- -- -- -- -- --

	productType                     OBJECT-TYPE
	SYNTAX                          INTEGER {
                                             eisaBased(1),
                                             pciBased(2)
                                        }
        MAX-ACCESS                      read-only
        STATUS                          current
	DESCRIPTION
			"The product type representing the target platform."
	::= { product 1 }

	productVersion                  OBJECT-TYPE
	SYNTAX                          DisplayString
        MAX-ACCESS                      read-only
        STATUS                          current
	DESCRIPTION
			"Version String for the Software Running on
			 this platform."
	::= { product 2 }

	productId                       OBJECT-TYPE
	SYNTAX                          DisplayString
        MAX-ACCESS                      read-only
        STATUS                          current
	DESCRIPTION
			"The System ID of this system."
	::= { product 3 }

	productVendor                   OBJECT-TYPE
	SYNTAX                          INTEGER {
                                             netapp(1),
                                             lenovo(4),
                                             fujitsu(5)
                                        }
        MAX-ACCESS                      read-only
        STATUS                          current
	DESCRIPTION
			"The vendor id of this system, indicating the company
			that has supplied the product."
	::= { product 4 }

	productModel                    OBJECT-TYPE
	SYNTAX                          DisplayString
        MAX-ACCESS                      read-only
        STATUS                          current
	DESCRIPTION
			"The model name of the system.  Examples
			 are FAS980 and FAS3050."
	::= { product 5 }

	productFirmwareVersion          OBJECT-TYPE
	SYNTAX                          DisplayString
        MAX-ACCESS                      read-only
        STATUS                          current
	DESCRIPTION
			"Version string for the Firmware running on
			 this platform."
	::= { product 6 }

	productGuiUrl                   OBJECT-TYPE
	SYNTAX                          DisplayString
        MAX-ACCESS                      read-only
        STATUS                          current
	DESCRIPTION
			"The complete URL used to access the administrative GUI
			 for a browser-based interface."
	::= { product 7 }

	productApiUrl                   OBJECT-TYPE
	SYNTAX                          DisplayString
        MAX-ACCESS                      read-only
        STATUS                          current
	DESCRIPTION
			"The complete URL used to access the administrative API
			 for a programmatic interface."
	::= { product 8 }

	productSerialNum                OBJECT-TYPE
	SYNTAX                          DisplayString
        MAX-ACCESS                      read-only
        STATUS                          current
	DESCRIPTION
			  "The product serial number. Returns unknown if it
			   cannot be determined."
	::= { product 9 }

	productPartnerSerialNum         OBJECT-TYPE
	SYNTAX                          DisplayString
        MAX-ACCESS                      read-only
        STATUS                          current
	DESCRIPTION
				  "The partner's serial number, not applicable
				   if there is no partner, and unknown if it
				   cannot be determined."
	::= { product 10 }

	productCPUArch                  OBJECT-TYPE
	SYNTAX                          INTEGER {
                                             x86(1),
                                             alpha(2),
                                             mips(3),
                                             sparc(4)
                                        }
        MAX-ACCESS                      read-only
        STATUS                          current
	DESCRIPTION
	                "The CPU architecture type of this appliance"



        ::= { product 11 }

	productTrapData                 OBJECT-TYPE
	SYNTAX                          DisplayString
        MAX-ACCESS                      read-only
        STATUS                          current
	DESCRIPTION
			"This returns a static string. This object is used
			as a placeholder for enterprise traps."
	::= { product 12 }

	productMachineType              OBJECT-TYPE
	SYNTAX                          DisplayString
        MAX-ACCESS                      read-only
        STATUS                          current
	DESCRIPTION
			"The machine type of the system.  Examples
			 are FAS980 and FAS3050."
	::= { product 13 }

	productLicenseTable             OBJECT-TYPE
	SYNTAX                          SEQUENCE OF ProductLicenseEntry
        MAX-ACCESS                      not-accessible
        STATUS                          deprecated
	DESCRIPTION
			"Returns information about the current list of
			licensed services, the type of license, and,
			if it is a time limited license, the expiration date.
			It also tells the services that are not licensed for
			the appliance, or if a time limited licensed service
			has expired. It will also return whether or not the
			the service was automatically enabled due to
			business packaging policies based on platform type."
	::= { product 14 }

	productLicenseEntry             OBJECT-TYPE
	SYNTAX                          ProductLicenseEntry
        MAX-ACCESS                      not-accessible
        STATUS                          deprecated
	DESCRIPTION
			"Provide a report of licenses."
	INDEX	{ productLicenseIndex }
	::= { productLicenseTable 1 }

	ProductLicenseEntry ::=
	    SEQUENCE {
		productLicenseIndex
		    Integer32,
		licenseService
		    DisplayString,
		licenseIsLicensed
		    INTEGER,
		licenseIsExpired
		    INTEGER,
		licenseIsSite
		    INTEGER,
		licenseExpirationTimeStamp
		    Integer32,
                licenseIsAutoEnabled
		    INTEGER
	    }

	productLicenseIndex             OBJECT-TYPE
	SYNTAX                          Integer32 (1..2147483647)
        MAX-ACCESS                      read-only
        STATUS                          deprecated
	DESCRIPTION
			"Index into the product license table."

	::= { productLicenseEntry 1 }

	licenseService                  OBJECT-TYPE
	SYNTAX                          DisplayString
        MAX-ACCESS                      read-only
        STATUS                          deprecated
	DESCRIPTION
			"Name of the service."

	::= { productLicenseEntry 2 }

	licenseIsLicensed               OBJECT-TYPE
	SYNTAX                          INTEGER {
                                             false(1),
                                             true(2)
                                        }
        MAX-ACCESS                      read-only
        STATUS                          deprecated
	DESCRIPTION
			"True if the service is licensed and has not
			expired, false otherwise."

	::= { productLicenseEntry 3 }

	licenseIsExpired                OBJECT-TYPE
	SYNTAX                          INTEGER {
                                             false(1),
                                             true(2)
                                        }
        MAX-ACCESS                      read-only
        STATUS                          deprecated
	DESCRIPTION
			"True if the promotional/time-expiring/demo license
			has expired, false otherwise."

	::= { productLicenseEntry 4 }

	licenseIsSite                   OBJECT-TYPE
	SYNTAX                          INTEGER {
                                             false(1),
                                             true(2)
                                        }
        MAX-ACCESS                      read-only
        STATUS                          deprecated
	DESCRIPTION
			"True if the service is a site license, false
			otherwise."

	::= { productLicenseEntry 5 }

	licenseExpirationTimeStamp      OBJECT-TYPE
	SYNTAX                          Integer32 (0..2147483647)
        MAX-ACCESS                      read-only
        STATUS                          deprecated
	DESCRIPTION
			"Expected expiration timestamp in seconds since
			January 1, 1970, if it's a promotional/time-expiring
			license. 0 for all other licenses."

	::= { productLicenseEntry 6 }

	licenseIsAutoEnabled            OBJECT-TYPE
	SYNTAX                          INTEGER {
                                             false(1),
                                             true(2)
                                        }
        MAX-ACCESS                      read-only
        STATUS                          deprecated
	DESCRIPTION
			"True if the service is automatically licensed
			(licenseIsLicensed will also be True) false otherwise."

	::= { productLicenseEntry 7 }

	-- -- -- -- -- -- -- --
	-- the sysStat group --
	-- -- -- -- -- -- -- --

	cpu	OBJECT IDENTIFIER ::=	{ sysStat 1 }

	misc	OBJECT IDENTIFIER ::=	{ sysStat 2 }

	cf	OBJECT IDENTIFIER ::=	{ sysStat 3 }

	environment OBJECT IDENTIFIER ::= { sysStat 4 }

	nvram	OBJECT IDENTIFIER ::= { sysStat 5 }

	cp	OBJECT IDENTIFIER ::= { sysStat 6 }

	autosupport OBJECT IDENTIFIER ::= { sysStat 7 }

	nodeStats OBJECT IDENTIFIER ::= { sysStat 10 }

	nodeStatTable 			OBJECT-TYPE
	SYNTAX      			SEQUENCE OF NodeStatEntry
	MAX-ACCESS  			not-accessible
	STATUS      			current
	DESCRIPTION
	                "Table containing all counters in the cluster,
			 organized on a per-node, per-category,
			 per-object basis."
	::= { nodeStats 1 }

	nodeStatEntry			OBJECT-TYPE
	SYNTAX      			NodeStatEntry
	MAX-ACCESS  			not-accessible
	STATUS      			current
	DESCRIPTION
	                "Entry for a single counter in the cluster, on
			 a per-node, per-category, per-object basis."
	INDEX { nodeStatNode, nodeStatCategoryIndex,
	        nodeStatInstanceIndex, nodeStatCounterIndex }
	::= { nodeStatTable 1 }

	NodeStatEntry ::=
            SEQUENCE {
	        nodeStatNode           	DisplayString,
		nodeStatCategoryIndex 	Integer32,
		nodeStatInstanceIndex   Integer32,
		nodeStatCounterIndex    Integer32,
		nodeStatValue           Counter64,
		nodeStatUnits           DisplayString,
		nodeStatDescription     DisplayString,
		nodeStatProperties      DisplayString,
		nodeStatCategoryName    DisplayString,
		nodeStatInstanceName    DisplayString,
		nodeStatCounterName     DisplayString,
		nodeStatLabels          DisplayString,
		nodeStatValues          DisplayString
	    }

	nodeStatNode			OBJECT-TYPE
	SYNTAX				DisplayString
	MAX-ACCESS  			not-accessible
	STATUS      			current
	DESCRIPTION
		        "Node from which the counter is collected."
	::= { nodeStatEntry 1 }

	nodeStatCategoryIndex		OBJECT-TYPE
	SYNTAX				Integer32 (1..2147483647)
        MAX-ACCESS			not-accessible
	STATUS      			current
	DESCRIPTION
		        "Index of category."
        ::= { nodeStatEntry 2 }

        nodeStatInstanceIndex		OBJECT-TYPE
	SYNTAX				Integer32 (1..2147483647)
	MAX-ACCESS			not-accessible
	STATUS				current
	DESCRIPTION
		        "Index of instance on which the counter exists."
	::= { nodeStatEntry 3 }

	nodeStatCounterIndex 		OBJECT-TYPE
	SYNTAX      			Integer32 (1..2147483647)
	MAX-ACCESS  			not-accessible
	STATUS      			current
	DESCRIPTION
		        "Index of counter within this category."
	::= { nodeStatEntry 4 }

	nodeStatValue 			OBJECT-TYPE
	SYNTAX      			Counter64
	MAX-ACCESS  			read-only
	STATUS      			current
	DESCRIPTION
	                "The value of the counter."
	::= { nodeStatEntry 5 }

	nodeStatUnits 			OBJECT-TYPE
	SYNTAX      			DisplayString
	MAX-ACCESS  			read-only
	STATUS      			current
	DESCRIPTION
		        "Units for this counter. Possible values include:
			 'B' (bytes), 's' (seconds), 'ms' (milliseconds),
		         'us' (microseconds), '%' (percent), or '' (none)."
	::= { nodeStatEntry 6 }

	nodeStatDescription 		OBJECT-TYPE
	SYNTAX      			DisplayString
	MAX-ACCESS  			read-only
	STATUS      			current
	DESCRIPTION
		        "Description of this counter."
	::= { nodeStatEntry 7 }

	nodeStatProperties 		OBJECT-TYPE
	SYNTAX      			DisplayString
	MAX-ACCESS  			read-only
	STATUS      			current
	DESCRIPTION
		        "Counter properties. Possible values include:
			 'average', 'rate', 'delta', 'percent', ''."
	::= { nodeStatEntry 8 }

	nodeStatCategoryName 		OBJECT-TYPE
	SYNTAX      			DisplayString
	MAX-ACCESS  			read-only
	STATUS      			current
	DESCRIPTION
		        "Name of counter's category."
	::= { nodeStatEntry 9 }

	nodeStatInstanceName 		OBJECT-TYPE
	SYNTAX      			DisplayString
	MAX-ACCESS  			read-only
	STATUS      			current
	DESCRIPTION
		        "Name of counter's category instance."
	::= { nodeStatEntry 10 }

	nodeStatCounterName		OBJECT-TYPE
	SYNTAX      			DisplayString
	MAX-ACCESS  			read-only
	STATUS      			current
	DESCRIPTION
		        "Name of counter within this category."
	::= { nodeStatEntry 11 }

	nodeStatLabels			OBJECT-TYPE
	SYNTAX     	 		DisplayString
	MAX-ACCESS  			read-only
	STATUS      			current
	DESCRIPTION
		        "List of counter labels. Used for counter arrays
			 of if 'counter' value is not an integer."
	::= { nodeStatEntry 12 }

        nodeStatValues			OBJECT-TYPE
	SYNTAX      			DisplayString
	MAX-ACCESS  			read-only
	STATUS      			current
	DESCRIPTION
	                "List of values. Only used to for counter arrays."
	      ::= { nodeStatEntry 13 }

	-- the cpu group for sysStat

	cpuUpTime                       OBJECT-TYPE
	SYNTAX                          TimeTicks
        MAX-ACCESS                      read-only
        STATUS                          current
	DESCRIPTION
			"The time (in hundredths of a second) that the
			 CPU has been up since the last boot."
	::= { cpu 1 }

	cpuBusyTime                     OBJECT-TYPE
	SYNTAX                          TimeTicks
        MAX-ACCESS                      read-only
        STATUS                          current
	DESCRIPTION
			"The time (in hundredths of a second) that the
			 CPU has been doing useful work since the last
			 boot."
	::= { cpu 2 }

	cpuBusyTimePerCent              OBJECT-TYPE
	SYNTAX                          Integer32 (0..100)
        MAX-ACCESS                      read-only
        STATUS                          current
	DESCRIPTION
			"The percent of time that the CPU has been doing
			 useful work since the last time a client requested
			 the cpuBusyTimePerCent."
	::= { cpu 3 }

	cpuIdleTime                     OBJECT-TYPE
	SYNTAX                          TimeTicks
        MAX-ACCESS                      read-only
        STATUS                          current
	DESCRIPTION
			"The time (in hundredths of a second) that the
			 CPU has been idle since the last boot."
	::= { cpu 4 }

	cpuIdleTimePerCent              OBJECT-TYPE
	SYNTAX                          Integer32 (0..100)
        MAX-ACCESS                      read-only
        STATUS                          current
	DESCRIPTION
			"The percent of time that the CPU has been idle
			 since the last time a client requested the
			 cpuBusyTimePerCent."
	::= { cpu 5 }

	cpuCount                        OBJECT-TYPE
	SYNTAX                          Integer32 (1..16)
        MAX-ACCESS                      read-only
        STATUS                          current
	DESCRIPTION
			"The number of CPUs in the system."

	::= { cpu 6 }

        cpuSwitchInvocations            OBJECT-TYPE
	SYNTAX                          Counter32
        MAX-ACCESS                      read-only
        STATUS                          current
	DESCRIPTION
			"The number of sk_switch invocations."
	::= { cpu 7 }

	cpuContextSwitches              OBJECT-TYPE
	SYNTAX                          Counter32
        MAX-ACCESS                      read-only
        STATUS                          current
	DESCRIPTION
			"The number of hardware context switches."
	::= { cpu 8 }

	cpuInterrupts                   OBJECT-TYPE
	SYNTAX                          Counter32
        MAX-ACCESS                      read-only
        STATUS                          current
	DESCRIPTION
			"The number of interrupts during a CP."
	::= { cpu 9 }


	cpuNonCPInterrupts              OBJECT-TYPE
	SYNTAX                          Counter32
        MAX-ACCESS                      read-only
        STATUS                          current
	DESCRIPTION
			"The number of interrupts not during a CP."
	::= { cpu 10 }

	cpuCPInterruptPercent           OBJECT-TYPE
	SYNTAX                          Integer32 (0..100)
        MAX-ACCESS                      read-only
        STATUS                          current
	DESCRIPTION
			" The percentage of time handling CP interrupts."
	::= { cpu 11 }

        cpuNonCPInterruptPercent        OBJECT-TYPE
	SYNTAX                          Integer32 (0..100)
        MAX-ACCESS                      read-only
        STATUS                          current
	DESCRIPTION
			" The percentage of time handling non-cp interrupts."
        ::= { cpu 12 }

        cpuTotalDomainSwitches          OBJECT-TYPE
	SYNTAX                          Counter32
        MAX-ACCESS                      read-only
        STATUS                          current
	DESCRIPTION
			" The total number of Domain Switches."
        ::= { cpu 13 }

	-- the cpu group for sysStat on per node basis

	cDOTCpuTable                    OBJECT-TYPE
	SYNTAX                          SEQUENCE OF CDOTCpuEntry
        MAX-ACCESS                      not-accessible
        STATUS                          current
	DESCRIPTION
			"Provide a report of the current CPU statistics
			on per node basis"
	::= { cpu 14 }

	cDOTCpuEntry                    OBJECT-TYPE
	SYNTAX                          CDOTCpuEntry
        MAX-ACCESS                      not-accessible
        STATUS                          current
	DESCRIPTION
			"Provide a report of the node's CPU statistics"

	INDEX	{ IMPLIED cDOTCpuNodeName }
	::= { cDOTCpuTable 1 }

	CDOTCpuEntry ::=
	    SEQUENCE {
                cDOTCpuNodeName
		    DisplayString,
		cDOTCpuUpTime
		    TimeTicks64,
		cDOTCpuBusyTime
		    TimeTicks64,
		cDOTCpuBusyTimePerCent
		    Integer32,
		cDOTCpuIdleTime
		    TimeTicks64,
		cDOTCpuIdleTimePerCent
		    Integer32,
		cDOTCpuCount
		    Integer32,
		cDOTCpuSwitchInvocations
		    Counter64,
		cDOTCpuContextSwitches
		    Counter64,
		cDOTCpuInterrupts
		    Counter64,
		cDOTCpuNonCPInterrupts
		    Counter64,
		cDOTCpuCPInterruptPercent
		    Integer32,
		cDOTCpuNonCPInterruptPercent
		    Integer32,
		cDOTCpuTotalDomainSwitches
		    Counter64
	    }

	cDOTCpuNodeName			OBJECT-TYPE
	SYNTAX				DisplayString
	MAX-ACCESS			read-only
	STATUS				current
	DESCRIPTION
		"Node Name. Same as nodeName for a specific node."
	::= { cDOTCpuEntry 1 }

	cDOTCpuUpTime                   OBJECT-TYPE
	SYNTAX                          TimeTicks64
        MAX-ACCESS                      read-only
        STATUS                          current
	DESCRIPTION
			"The time (in hundredths of a second) that the
			 CPU has been up since the last boot."
	::= { cDOTCpuEntry 2 }

	cDOTCpuBusyTime                 OBJECT-TYPE
	SYNTAX                          TimeTicks64
        MAX-ACCESS                      read-only
        STATUS                          current
	DESCRIPTION
			"The time (in hundredths of a second) that the
			 CPU has been doing useful work since the last
			 boot."
	::= { cDOTCpuEntry 3 }

	cDOTCpuBusyTimePerCent          OBJECT-TYPE
	SYNTAX                          Integer32 (0..100)
        MAX-ACCESS                      read-only
        STATUS                          current
	DESCRIPTION
			"The percent of time that the CPU has been doing
			 useful work since the last time a client requested
			 the cDOTCpuBusyTimePerCent."
	::= { cDOTCpuEntry 4 }

	cDOTCpuIdleTime                 OBJECT-TYPE
	SYNTAX                          TimeTicks64
        MAX-ACCESS                      read-only
        STATUS                          current
	DESCRIPTION
			"The time (in hundredths of a second) that the
			 CPU has been idle since the last boot."
	::= { cDOTCpuEntry 5 }

	cDOTCpuIdleTimePerCent          OBJECT-TYPE
	SYNTAX                          Integer32 (0..100)
        MAX-ACCESS                      read-only
        STATUS                          current
	DESCRIPTION
			"The percent of time that the CPU has been idle
			 since the last time a client requested the
			 cDOTCpuBusyTimePerCent."
	::= { cDOTCpuEntry 6 }

	cDOTCpuCount                    OBJECT-TYPE
	SYNTAX                          Integer32 (1..16)
        MAX-ACCESS                      read-only
        STATUS                          current
	DESCRIPTION
			"The number of CPUs in the system."

	::= { cDOTCpuEntry 7 }

        cDOTCpuSwitchInvocations        OBJECT-TYPE
	SYNTAX                          Counter64
        MAX-ACCESS                      read-only
        STATUS                          current
	DESCRIPTION
			"The number of sk_switch invocations."
	::= { cDOTCpuEntry 8 }

	cDOTCpuContextSwitches          OBJECT-TYPE
	SYNTAX                          Counter64
        MAX-ACCESS                      read-only
        STATUS                          current
	DESCRIPTION
			"The number of hardware context switches."
	::= { cDOTCpuEntry 9 }

	cDOTCpuInterrupts               OBJECT-TYPE
	SYNTAX                          Counter64
        MAX-ACCESS                      read-only
        STATUS                          current
	DESCRIPTION
			"The number of interrupts during a CP."
	::= { cDOTCpuEntry 10 }

	cDOTCpuNonCPInterrupts          OBJECT-TYPE
	SYNTAX                          Counter64
        MAX-ACCESS                      read-only
        STATUS                          current
	DESCRIPTION
			"The number of interrupts not during a CP."
	::= { cDOTCpuEntry 11 }

	cDOTCpuCPInterruptPercent       OBJECT-TYPE
	SYNTAX                          Integer32 (0..100)
        MAX-ACCESS                      read-only
        STATUS                          current
	DESCRIPTION
			" The percentage of time handling CP interrupts."
	::= { cDOTCpuEntry 12 }

        cDOTCpuNonCPInterruptPercent    OBJECT-TYPE
	SYNTAX                          Integer32 (0..100)
        MAX-ACCESS                      read-only
        STATUS                          current
	DESCRIPTION
			" The percentage of time handling non-cp interrupts."
        ::= { cDOTCpuEntry 13 }

        cDOTCpuTotalDomainSwitches      OBJECT-TYPE
	SYNTAX                          Counter64
        MAX-ACCESS                      read-only
        STATUS                          current
	DESCRIPTION
			" The total number of Domain Switches."
        ::= { cDOTCpuEntry 14 }

        -- the misc group for sysStat

	miscNfsOps                      OBJECT-TYPE
	SYNTAX                          Integer32
        MAX-ACCESS                      read-only
        STATUS                          deprecated
	DESCRIPTION
			"The total number of Server side NFS calls since
			 the last boot"
	::= { misc 1 }

	miscNetRcvdKB                   OBJECT-TYPE
	SYNTAX                          Integer32
        MAX-ACCESS                      read-only
        STATUS                          deprecated
	DESCRIPTION
			"The total number of KBytes received on all the
			 network interfaces, since the last boot."
	::= { misc 2 }

	miscNetSentKB                   OBJECT-TYPE
	SYNTAX                          Integer32
        MAX-ACCESS                      read-only
        STATUS                          deprecated
	DESCRIPTION
			"The total number of KBytes transmitted on all the
			 network interfaces, since the last boot."
	::= { misc 3 }

	miscGlobalStatus                OBJECT-TYPE
	SYNTAX                          INTEGER {
                                             other(1),
                                             unknown(2),
					     ok(3),
					     nonCritical(4),
					     critical(5),
                                             nonRecoverable(6)
                                        }
        MAX-ACCESS                      read-only
        STATUS                          current
	DESCRIPTION
			"This indicates the overall status of the appliance.
			The algorithm to determine the value uses both
			hardware status (e.g. the number of failed fans) and
			volume status (e.g. number of volumes that are full).
			The algorithm is subject to change in future releases,
			but the range of values will not change."
	::= { misc 4 }

	miscHighNfsOps                  OBJECT-TYPE
	SYNTAX                          Counter32
        MAX-ACCESS                      read-only
        STATUS                          deprecated
	DESCRIPTION
			"The total number of Server side NFS calls since
			 the last boot.  This object returns the most
			 significant 32 bits of the 64 bit unsigned integer.
			 This object is deprecated - Use misc64NfsOps instead."
	::= { misc 5 }

	miscLowNfsOps                   OBJECT-TYPE
	SYNTAX                          Counter32
        MAX-ACCESS                      read-only
        STATUS                          deprecated
	DESCRIPTION
			"The total number of Server side NFS calls since
			 the last boot.  This object returns the least
			 significant 32 bits of the 64 bit unsigned integer.
			 This object is deprecated - Use misc64NfsOps instead."
	::= { misc 6 }

	miscHighCifsOps                 OBJECT-TYPE
	SYNTAX                          Counter32
        MAX-ACCESS                      read-only
        STATUS                          deprecated
	DESCRIPTION
			"The total number of Server side CIFS calls since
			 the last boot.  This object returns the most
			 significant 32 bits of the 64 bit unsigned integer.
			 This object is deprecated - Use misc64CifsOps instead."
	::= { misc 7 }

	miscLowCifsOps                  OBJECT-TYPE
	SYNTAX                          Counter32
        MAX-ACCESS                      read-only
        STATUS                          deprecated
	DESCRIPTION
			"The total number of Server side CIFS calls since
			 the last boot.  This object returns the least
			 significant 32 bits of the 64 bit unsigned integer.
			 This object is deprecated - Use misc64CifsOps instead."
	::= { misc 8 }

	miscHighHttpOps                 OBJECT-TYPE
	SYNTAX                          Counter32
        MAX-ACCESS                      read-only
        STATUS                          deprecated
	DESCRIPTION
			"The total number of HTTP operations received
			 since the last boot.  This object returns the most
			 significant 32 bits of the 64 bit unsigned integer.
			 This object is deprecated - Use misc64HttpOps instead."
	::= { misc 9 }

	miscLowHttpOps                  OBJECT-TYPE
	SYNTAX                          Counter32
        MAX-ACCESS                      read-only
        STATUS                          deprecated
	DESCRIPTION
			"The total number of HTTP operations received
			 since the last boot.  This object returns the least
			 significant 32 bits of the 64 bit unsigned integer.
			 This object is deprecated - Use misc64HttpOps instead."

	::= { misc 10 }


	miscHighNetRcvdBytes            OBJECT-TYPE
	SYNTAX                          Counter32
        MAX-ACCESS                      read-only
        STATUS                          deprecated
	DESCRIPTION
			"The total number of bytes received on all the
			 network interfaces, since the last boot.  This
			 object returns the most significant 32 bits
			 of the 64 bit unsigned integer. This object is
			 deprecated - Use misc64NetRcvdBytes instead."
	::= { misc 11 }

	miscLowNetRcvdBytes             OBJECT-TYPE
	SYNTAX                          Counter32
        MAX-ACCESS                      read-only
        STATUS                          deprecated
	DESCRIPTION
			"The total number of bytes received on all the
			 network interfaces, since the last boot.  This
			 object returns the least significant 32 bits
			 of the 64 bit unsigned integer. This object is
			 deprecated - Use misc64NetRcvdBytes instead."
	::= { misc 12 }

	miscHighNetSentBytes            OBJECT-TYPE
	SYNTAX                          Counter32
        MAX-ACCESS                      read-only
        STATUS                          deprecated
	DESCRIPTION
			"The total number of bytes transmitted on all the
			 network interfaces, since the last boot.  This
			 object returns the most significant 32 bits
			 of the 64 bit unsigned integer. This object is
			 deprecated - Use misc64NetSentBytes instead."
	::= { misc 13 }

	miscLowNetSentBytes             OBJECT-TYPE
	SYNTAX                          Counter32
        MAX-ACCESS                      read-only
        STATUS                          deprecated
	DESCRIPTION
			"The total number of bytes transmitted on all the
			 network interfaces, since the last boot.  This
			 object returns the least significant 32 bits
			 of the 64 bit unsigned integer. This object is
			 deprecated - Use misc64NetSentBytes instead."
	::= { misc 14 }

	miscHighDiskReadBytes           OBJECT-TYPE
	SYNTAX                          Counter32
        MAX-ACCESS                      read-only
        STATUS                          deprecated
	DESCRIPTION
			"The total number of bytes read from disk
			 since the last boot.  This object returns
			 the most significant 32 bits of the 64 bit unsigned
			 integer. This object is deprecated - Use
			 misc64DiskReadBytes instead."
	::= { misc 15 }

	miscLowDiskReadBytes            OBJECT-TYPE
	SYNTAX                          Counter32
        MAX-ACCESS                      read-only
        STATUS                          deprecated
	DESCRIPTION
			"The total number of bytes read from disk since
			 the last boot.  This object returns the least
			 significant 32 bits of the 64 bit unsigned integer.
			 This object is deprecated - Use misc64DiskReadBytes
			 instead."
	::= { misc 16 }


	miscHighDiskWriteBytes          OBJECT-TYPE
	SYNTAX                          Counter32
        MAX-ACCESS                      read-only
        STATUS                          deprecated
	DESCRIPTION
			"The total number of bytes written to disk
			 since the last boot.  This object returns
			 the most significant 32 bits of the 64 bit unsigned
			 integer. This object is deprecated - Use
			 misc64DiskWriteBytes instead."
	::= { misc 17 }

	miscLowDiskWriteBytes           OBJECT-TYPE
	SYNTAX                          Counter32
        MAX-ACCESS                      read-only
        STATUS                          deprecated
	DESCRIPTION
			"The total number of bytes written to disk since
			 the last boot.  This object returns the least
			 significant 32 bits of the 64 bit unsigned integer.
			 This object is deprecated - Use misc64DiskWriteBytes
			 instead."
	::= { misc 18 }

	miscHighTapeReadBytes           OBJECT-TYPE
	SYNTAX                          Counter32
        MAX-ACCESS                      read-only
        STATUS                          deprecated
	DESCRIPTION
			"The total number of bytes read from tape
			 since the last boot.  This object returns
			 the most significant 32 bits of the 64 bit unsigned
			 integer. This object is deprecated - Use
			 misc64TapeReadBytes instead."
	::= { misc 19 }

	miscLowTapeReadBytes            OBJECT-TYPE
	SYNTAX                          Counter32
        MAX-ACCESS                      read-only
        STATUS                          deprecated
	DESCRIPTION
			"The total number of bytes read from tape since
			 the last boot.  This object returns the least
			 significant 32 bits of the 64 bit unsigned integer.
			 This object is deprecated - Use misc64TapeReadBytes
			 instead."
	::= { misc 20 }

	miscHighTapeWriteBytes          OBJECT-TYPE
	SYNTAX                          Counter32
        MAX-ACCESS                      read-only
        STATUS                          deprecated
	DESCRIPTION
			"The total number of bytes written to tape
			 since the last boot.  This object returns
			 the most significant 32 bits of the 64 bit unsigned
			 integer. This object is deprecated - Use
			 misc64TapeWriteBytes instead."
	::= { misc 21 }

	miscLowTapeWriteBytes           OBJECT-TYPE
	SYNTAX                          Counter32
        MAX-ACCESS                      read-only
        STATUS                          deprecated
	DESCRIPTION
			"The total number of bytes written to tape since
			 the last boot.  This object returns the least
			 significant 32 bits of the 64 bit unsigned integer.
			 This object is deprecated - Use misc64TapeWriteBytes
			 instead."
	::= { misc 22 }

	miscCacheAge                    OBJECT-TYPE
	SYNTAX                          Integer32
        MAX-ACCESS                      read-only
        STATUS                          current
	DESCRIPTION
			"Age in minutes of the oldest read-only blocks
			 in the buffer cache.  This indicates how fast
			 read operations are cycling through system
			 memory; when the appliance is reading very
			 large files (larger than the machine's memory
			 size), buffer cache age will be very low."
	::= { misc 23 }

	miscCorrectedMachineChecks      OBJECT-TYPE
	SYNTAX                          Counter32
        MAX-ACCESS                      read-only
        STATUS                          current
	DESCRIPTION
			"Number of corrected machine checks since
			the last boot."

	::= { misc 24 }

	miscGlobalStatusMessage         OBJECT-TYPE
	SYNTAX                          DisplayString
        MAX-ACCESS                      read-only
        STATUS                          current
	DESCRIPTION
			"A string describing the global status,
			including a description of the condition (if
			any) that caused the status to be anything
			other than ok(3)."
	::= { misc 25 }

	miscWindowsSetupWizardVersion   OBJECT-TYPE
	SYNTAX                          Integer32
        MAX-ACCESS                      read-only
        STATUS                          current
	DESCRIPTION
			"The version number of Windows Setup Wizard
			required to configure the appliance.  Windows
			Setup Wizard with a version number lower than
			this integer is not capable of configuring the
			appliance."
	::= { misc 26 }

	misc64NfsOps                    OBJECT-TYPE
	SYNTAX                          Counter64
        MAX-ACCESS                      read-only
        STATUS                          current
	DESCRIPTION
			"The total number of Server side NFS calls since
			 the last boot.  This object returns all of the
			 64 bit unsigned integer."
	::= { misc 27 }

	misc64CifsOps                   OBJECT-TYPE
	SYNTAX                          Counter64
        MAX-ACCESS                      read-only
        STATUS                          current
	DESCRIPTION
			"The total number of Server side CIFS calls since
			 the last boot.  This object returns all of the
			 64 bit unsigned integer."
	::= { misc 28 }

	misc64HttpOps                   OBJECT-TYPE
	SYNTAX                          Counter64
        MAX-ACCESS                      read-only
        STATUS                          current
	DESCRIPTION
			"The total number of HTTP operations received
			 since the last boot.  This object returns all of
			 the 64 bit unsigned integer."
	::= { misc 29 }

	misc64NetRcvdBytes              OBJECT-TYPE
	SYNTAX                          Counter64
        MAX-ACCESS                      read-only
        STATUS                          current
	DESCRIPTION
			"The total number of bytes received on all the
			 network interfaces, since the last boot.  This
			 object returns all of the 64 bit unsigned integer."
	::= { misc 30 }

	misc64NetSentBytes              OBJECT-TYPE
	SYNTAX                          Counter64
        MAX-ACCESS                      read-only
        STATUS                          current
	DESCRIPTION
			"The total number of bytes transmitted on all the
			 network interfaces, since the last boot.  This
			 object returns all of the 64 bit unsigned integer."
	::= { misc 31 }

	misc64DiskReadBytes             OBJECT-TYPE
	SYNTAX                          Counter64
        MAX-ACCESS                      read-only
        STATUS                          current
	DESCRIPTION
			"The total number of bytes read from disk
			 since the last boot.  This object returns
			 all of the 64 bit unsigned integer."
	::= { misc 32 }

	misc64DiskWriteBytes            OBJECT-TYPE
	SYNTAX                          Counter64
        MAX-ACCESS                      read-only
        STATUS                          current
	DESCRIPTION
			"The total number of bytes written to disk
			 since the last boot.  This object returns
			 all of the 64 bit unsigned integer."
	::= { misc 33 }

	misc64TapeReadBytes             OBJECT-TYPE
	SYNTAX                          Counter64
        MAX-ACCESS                      read-only
        STATUS                          current
	DESCRIPTION
			"The total number of bytes read from tape
			 since the last boot.  This object returns
			 all of the 64 bit unsigned integer."
	::= { misc 34 }

	misc64TapeWriteBytes            OBJECT-TYPE
	SYNTAX                          Counter64
        MAX-ACCESS                      read-only
        STATUS                          current
	DESCRIPTION
			"The total number of bytes written to tape
			 since the last boot.  This object returns
			 all of the 64 bit unsigned integer."
	::= { misc 35 }

       cDOTMiscTable                   OBJECT-TYPE
       SYNTAX                          SEQUENCE OF CDOTMiscEntry
       MAX-ACCESS                      not-accessible
       STATUS                          current
       DESCRIPTION
                       "Provide a report of miscellaneous variables
                       on a per node basis."
       ::= { misc 36 }

       cDOTMiscEntry                   OBJECT-TYPE
       SYNTAX                          CDOTMiscEntry
       MAX-ACCESS                      not-accessible
       STATUS                          current
       DESCRIPTION
                       "Provide a report of the node's miscellaneous
                       variables."

       INDEX   { IMPLIED cDOTMiscNodeName }
       ::= { cDOTMiscTable 1 }

       CDOTMiscEntry ::=
           SEQUENCE {
               cDOTMiscNodeName
                   DisplayString,
               cDOTMiscGlobalStatus
                   Integer32,
               cDOTMiscGlobalStatusMessage
                   DisplayString
           }

       cDOTMiscNodeName                OBJECT-TYPE
       SYNTAX                          DisplayString
       MAX-ACCESS                      read-only
       STATUS                          current
       DESCRIPTION
               "Node Name. Same as nodeName for a specific node."
       ::= { cDOTMiscEntry 1 }

       cDOTMiscGlobalStatus            OBJECT-TYPE
       SYNTAX                          INTEGER {
                                             other(1),
                                             unknown(2),
					     ok(3),
					     nonCritical(4),
					     critical(5),
                                             nonRecoverable(6)
                                       }
       MAX-ACCESS                      read-only
       STATUS                          current
       DESCRIPTION
                       "This indicates the overall status of this node.
                       The algorithm to determine the value uses both
                       hardware status (e.g. the number of failed fans) and
                       volume status (e.g. number of volumes that are full).
                       The algorithm is subject to change in future releases,
                       but the range of values will not change."
      ::= { cDOTMiscEntry 2 }

       cDOTMiscGlobalStatusMessage     OBJECT-TYPE
       SYNTAX                          DisplayString
       MAX-ACCESS                      read-only
       STATUS                          current
       DESCRIPTION
                       "A string describing the global status of this node,
                       including a description of the condition (if
                       any) that caused the status to be anything
                       other than ok(3)."
       ::= { cDOTMiscEntry 3 }

	-- the Clustered Failover group

	cfSettings                      OBJECT-TYPE
	SYNTAX                          INTEGER {
                                             notConfigured(1),
                                             enabled(2),
					     disabled(3),
					     takeoverByPartnerDisabled(4),
                                             thisNodeDead(5)
                                        }
        MAX-ACCESS                      read-only
        STATUS                          current
	DESCRIPTION
				"Clustered Failover configuration settings.
				 The value notConfigured(1) indicates that the
				 cluster is not licensed. The thisNodeDead(5)
				 setting indicates that this node has been
				 taken over."
	::= { cf 1 }

	cfState                         OBJECT-TYPE
	SYNTAX                          INTEGER {
                                             dead(1),
                                             canTakeover(2),
					     cannotTakeover(3),
                                             takeover(4)
                                        }
        MAX-ACCESS                      read-only
        STATUS                          current
	DESCRIPTION
				"Clustered Failover state."
	::= { cf 2 }

	cfCannotTakeoverCause           OBJECT-TYPE
	SYNTAX                          INTEGER {
                                             ok(1),
                                             unknownReason(2),
					     disabledByOperator(3),
					     interconnectOffline(4),
					     disabledByPartner(5),
                                             takeoverFailed(6),
					     mailboxDegraded(7),
					     partnerMailboxUninitialised(8),
					     mailboxVersionMismatch(9),
					     nvramSizeMismatch(10),
					     kernelVersionMismatch(11),
					     partnerBootingUp(12),
					     partnerPerformingRevert(13),
					     performingRevert(14),
					     partnerRequestedTakeover(15),
					     alreadyInTakenoverMode(16),
					     nvramLogUnsynchronized(17),
					     backupMailboxProblems(18)
                                        }
        MAX-ACCESS                      read-only
        STATUS                          current
	DESCRIPTION
				"The reason this node cannot takeover its
				 partner"
	::= { cf 3 }

	cfPartnerStatus                 OBJECT-TYPE
	SYNTAX                          INTEGER {
                                             maybeDown(1),
                                             ok(2),
                                             dead(3)
                                        }
        MAX-ACCESS                      read-only
        STATUS                          current
	DESCRIPTION
				"This is the status last returned by the
				 Clustered Failover partner."
	::= { cf 4 }

	cfPartnerLastStatusUpdate       OBJECT-TYPE
	SYNTAX                          TimeTicks
        MAX-ACCESS                      read-only
        STATUS                          current
	DESCRIPTION
				"If non-zero, the absolute time of the last
				 update from the Clustered Failover partner."
	::= { cf 5 }

	cfPartnerName                   OBJECT-TYPE
	SYNTAX                          DisplayString
        MAX-ACCESS                      read-only
        STATUS                          current
	DESCRIPTION
				"Hostname for Clustered Failover partner."
	::= { cf 6 }

	cfPartnerSysid                  OBJECT-TYPE
	SYNTAX                          Integer32
        MAX-ACCESS                      read-only
        STATUS                          current
	DESCRIPTION
				"System ID for Clustered Failover partner."
	::= { cf 7 }

	cfInterconnectStatus            OBJECT-TYPE
	SYNTAX                          INTEGER {
                                             notPresent(1),
                                             down(2),
					     partialFailure(3),
                                             up(4)
                                        }
        MAX-ACCESS                      read-only
        STATUS                          current
	DESCRIPTION
				"The current status of the interconnect.
				 The partialFailure(3) status indicates that
				 one of the links in the interconnect hardware
				 is down."
	::= { cf 8 }

	-- the environment group for sysStat

	envOverTemperature              OBJECT-TYPE
	SYNTAX                          INTEGER {
                                             no(1),
                                             yes(2)
                                        }
        MAX-ACCESS                      read-only
        STATUS                          current
	DESCRIPTION
			"An indication of whether the hardware is
			 currently operating outside of its recommended
			 temperature range.  The hardware will shutdown
			 if the temperature exceeds critical thresholds."

	::= { environment 1 }

	envFailedFanCount               OBJECT-TYPE
	SYNTAX                          Integer32
        MAX-ACCESS                      read-only
        STATUS                          current
	DESCRIPTION
			"Count of the number of chassis fans which
			 are not operating within the recommended
			 RPM range."

	::= { environment 2 }

	envFailedFanMessage             OBJECT-TYPE
	SYNTAX                          DisplayString
        MAX-ACCESS                      read-only
        STATUS                          current
	DESCRIPTION
			"Text message describing the current condition of
			 chassis fans.  This is useful only if
			 envFailedFanCount is not zero."

	::= { environment 3 }


	envFailedPowerSupplyCount       OBJECT-TYPE
	SYNTAX                          Integer32
        MAX-ACCESS                      read-only
        STATUS                          current
	DESCRIPTION
			"Count of the number of power supplies which
			 are in degraded mode."

	::= { environment 4 }

	envFailedPowerSupplyMessage     OBJECT-TYPE
	SYNTAX                          DisplayString
        MAX-ACCESS                      read-only
        STATUS                          current
	DESCRIPTION
			"Text message describing the state of any
			 power supplies which are currently degraded.
			 This is useful only if envFailedPowerSupplyCount
			 is not zero."

	::= { environment 5 }

	-- -- -- -- -- -- --
	-- the nvram group for sysStat

	nvramBatteryStatus              OBJECT-TYPE
	SYNTAX                          INTEGER {
                                             ok(1),
                                             partiallyDischarged(2),
					     fullyDischarged(3),
					     notPresent(4),
					     nearEndOfLife(5),
					     atEndOfLife(6),
					     unknown(7),
					     overCharged(8),
                                             fullyCharged(9)
                                        }
        MAX-ACCESS                      read-only
        STATUS                          current
	DESCRIPTION
			"An indication of the current status of the
			 NVRAM battery or batteries.  Batteries which
			 are fully or partially discharged may not
			 fully protect the system during a crash.

			 The end-of-life status values are based on
			 the manufacturer's recommended life for the
			 batteries."

	::= { nvram 1 }

	-- -- -- -- -- -- --
	-- the cp group for sysStat

	cpTime                          OBJECT-TYPE
	SYNTAX                          TimeTicks
        MAX-ACCESS                      read-only
        STATUS                          current
	DESCRIPTION
			"The time (in hundredths of a second) since boot
			 during which the system has had a consistency point
			 (cp) operation in progress."
	::= { cp 1 }

	cpFromTimerOps                  OBJECT-TYPE
	SYNTAX                          Counter32
        MAX-ACCESS                      read-only
        STATUS                          current
	DESCRIPTION
			"The number of consistency point operations since boot
			 that were caused by timer."
	::= { cp 2 }

	cpFromSnapshotOps               OBJECT-TYPE
	SYNTAX                          Counter32
        MAX-ACCESS                      read-only
        STATUS                          current
	DESCRIPTION
			"The number of consistency point operations since boot
			 that were caused by snapshot operation."
	::= { cp 3 }

	cpFromLowWaterOps               OBJECT-TYPE
	SYNTAX                          Counter32
        MAX-ACCESS                      read-only
        STATUS                          current
	DESCRIPTION
			"The number of consistency point operations since boot
			 that were caused by low water mark."
	::= { cp 4 }

	cpFromHighWaterOps              OBJECT-TYPE
	SYNTAX                          Counter32
        MAX-ACCESS                      read-only
        STATUS                          current
	DESCRIPTION
			"The number of consistency point operations since boot
			 that were caused by high water mark."
	::= { cp 5 }

	cpFromLogFullOps                OBJECT-TYPE
	SYNTAX                          Counter32
        MAX-ACCESS                      read-only
        STATUS                          current
	DESCRIPTION
			"The number of consistency point operations since boot
			 that were caused by nv-log full."
	::= { cp 6 }

	cpFromCpOps                     OBJECT-TYPE
	SYNTAX                          Counter32
        MAX-ACCESS                      read-only
        STATUS                          current
	DESCRIPTION
			"The number of back to back consistency point
			operations since boot."
	::= { cp 7 }

	cpTotalOps                      OBJECT-TYPE
	SYNTAX                          Counter32
        MAX-ACCESS                      read-only
        STATUS                          current
	DESCRIPTION
			"The total number of consistency point operations
			 since boot."
	::= { cp 8 }

	cpFromFlushOps                  OBJECT-TYPE
	SYNTAX                          Counter32
        MAX-ACCESS                      read-only
        STATUS                          current
	DESCRIPTION
			"The number of consistency point operations since boot
			that were caused by flushing unlogged write data."
	::= { cp 9 }

	cpFromSyncOps                   OBJECT-TYPE
	SYNTAX                          Counter32
        MAX-ACCESS                      read-only
        STATUS                          current
	DESCRIPTION
			"The number of consistency point operations since boot
			that were caused by file system sync requests."
	::= { cp 10 }

	cpFromLowVbufOps                OBJECT-TYPE
	SYNTAX                          Counter32
        MAX-ACCESS                      read-only
        STATUS                          current
	DESCRIPTION
			"The number of consistency point operations since boot
			that were caused by low virtual buffers."
	::= { cp 11 }

	cpFromCpDeferredOps             OBJECT-TYPE
	SYNTAX                          Counter32
        MAX-ACCESS                      read-only
        STATUS                          current
	DESCRIPTION
			"The number of back to back consistency point
			operations since boot that were deferred."
	::= { cp 12 }

	cpFromLowDatavecsOps            OBJECT-TYPE
	SYNTAX                          Counter32
        MAX-ACCESS                      read-only
        STATUS                          current
	DESCRIPTION
			"The number of consistency point operations since boot
			that were caused by low datavecs."
	::= { cp 13 }

        cpFromLowMbufOps                OBJECT-TYPE
        SYNTAX                          Counter32
        MAX-ACCESS                      read-only
        STATUS                          current
        DESCRIPTION
                        "The number of consistency point operations since boot
                        that were caused by low mbufs."
        ::= { cp 14 }

        cpFromNvlogReplayTakeoverTime   OBJECT-TYPE
        SYNTAX                          Counter32
        MAX-ACCESS                      read-only
        STATUS                          current
        DESCRIPTION
                        "The number of consistency point operations since boot
                        that were caused by nvlog replay takeover time."
        ::= { cp 15 }

        -- the cp group for sysStat on per node basis

        cDOTCpTable                     OBJECT-TYPE
        SYNTAX                          SEQUENCE OF CDOTCpEntry
        MAX-ACCESS                      not-accessible
        STATUS                          current
        DESCRIPTION
                        "Provide a report of the current CP statistics
                        on per node basis"
        ::= { cp 16 }

        cDOTCpEntry                     OBJECT-TYPE
        SYNTAX                          CDOTCpEntry
        MAX-ACCESS                      not-accessible
        STATUS                          current
        DESCRIPTION
                        "Provide a report of the node's CP statistics"

        INDEX   { IMPLIED cDOTCpNodeName }
        ::= { cDOTCpTable 1 }

        CDOTCpEntry ::=
            SEQUENCE {
                cDOTCpNodeName
                    DisplayString,
                cDOTCpTime
                    TimeTicks64,
                cDOTCpFromTimerOps
                    Counter64,
                cDOTCpFromSnapshotOps
                    Counter64,
                cDOTCpFromLowWaterOps
                    Counter64,
                cDOTCpFromHighWaterOps
                    Counter64,
                cDOTCpFromLogFullOps
                    Counter64,
                cDOTCpFromCpOps
                    Counter64,
                cDOTCpTotalOps
                    Counter64,
                cDOTCpFromFlushOps
                    Counter64,
                cDOTCpFromSyncOps
                    Counter64,
                cDOTCpFromCpDeferredOps
                    Counter64,
                cDOTCpFromLowDatavecsOps
                    Counter64,
                cDOTCpFromLowMbufOps
                    Counter64,
                cDOTCpFromNvlogReplayTakeoverTime
                    Counter64
            }
        cDOTCpNodeName                      OBJECT-TYPE
        SYNTAX                              DisplayString
        MAX-ACCESS                          not-accessible
        STATUS                              current
        DESCRIPTION
                        "Node Name. Same as node name."
        ::= { cDOTCpEntry 1 }

        cDOTCpTime                          OBJECT-TYPE
        SYNTAX                              TimeTicks64
        MAX-ACCESS                          read-only
        STATUS                              current
        DESCRIPTION
                        "The time (in hundredths of a second) since boot
                        during which the system has had a consistency point
                        (cp) operation in progress."
        ::= { cDOTCpEntry 2 }

        cDOTCpFromTimerOps                  OBJECT-TYPE
        SYNTAX                              Counter64
        MAX-ACCESS                          read-only
        STATUS                              current
        DESCRIPTION
                        "The number of consistency point operations since boot
                        that were caused by timer."
        ::= { cDOTCpEntry 3 }

        cDOTCpFromSnapshotOps               OBJECT-TYPE
        SYNTAX                              Counter64
        MAX-ACCESS                          read-only
        STATUS                              current
        DESCRIPTION
                        "The number of consistency point operations since boot
                        that were caused by snapshot operation."
        ::= { cDOTCpEntry 4}

        cDOTCpFromLowWaterOps               OBJECT-TYPE
        SYNTAX                              Counter64
        MAX-ACCESS                          read-only
        STATUS                              current
        DESCRIPTION
                        "The number of consistency point operations since boot
                        that were caused by low water mark."
        ::= { cDOTCpEntry 5 }

        cDOTCpFromHighWaterOps              OBJECT-TYPE
        SYNTAX                              Counter64
        MAX-ACCESS                          read-only
        STATUS                              current
        DESCRIPTION
                        "The number of consistency point operations since boot
                        that were caused by high water mark."
        ::= { cDOTCpEntry 6 }

        cDOTCpFromLogFullOps                OBJECT-TYPE
        SYNTAX                              Counter64
        MAX-ACCESS                          read-only
        STATUS                              current
        DESCRIPTION
                        "The number of consistency point operations since boot
                        that were caused by nv-log full."
        ::= { cDOTCpEntry 7 }

        cDOTCpFromCpOps                     OBJECT-TYPE
        SYNTAX                              Counter64
        MAX-ACCESS                          read-only
        STATUS                              current
        DESCRIPTION
                        "The number of back to back consistency point
                        operations since boot."
        ::= { cDOTCpEntry 8 }

        cDOTCpTotalOps                      OBJECT-TYPE
        SYNTAX                              Counter64
        MAX-ACCESS                          read-only
        STATUS                              current
        DESCRIPTION
                        "The total number of consistency point operations
                        since boot."
        ::= { cDOTCpEntry 9 }

        cDOTCpFromFlushOps                  OBJECT-TYPE
        SYNTAX                              Counter64
        MAX-ACCESS                          read-only
        STATUS                              current
        DESCRIPTION
                        "The number of consistency point operations since boot
                        that were caused by flushing unlogged write data."
        ::= { cDOTCpEntry 10 }

        cDOTCpFromSyncOps                   OBJECT-TYPE
        SYNTAX                              Counter64
        MAX-ACCESS                          read-only
        STATUS                              current
        DESCRIPTION
                        "The number of consistency point operations since boot
                        that were caused by file system sync requests."
        ::= { cDOTCpEntry 11 }

        cDOTCpFromCpDeferredOps             OBJECT-TYPE
        SYNTAX                              Counter64
        MAX-ACCESS                          read-only
        STATUS                              current
        DESCRIPTION
                        "The number of back to back consistency point
                        operations since boot that were deferred."
        ::= { cDOTCpEntry 12 }

        cDOTCpFromLowDatavecsOps            OBJECT-TYPE
        SYNTAX                              Counter64
        MAX-ACCESS                          read-only
        STATUS                              current
        DESCRIPTION
                        "The number of consistency point operations since boot
                        that were caused by low datavecs."
        ::= { cDOTCpEntry 13 }

        cDOTCpFromLowMbufOps                OBJECT-TYPE
        SYNTAX                              Counter64
        MAX-ACCESS                          read-only
        STATUS                              current
        DESCRIPTION
                        "The number of consistency point operations since boot
                        that were caused by low mbufs in mbuf pools."
        ::= { cDOTCpEntry 14 }

        cDOTCpFromNvlogReplayTakeoverTime   OBJECT-TYPE
        SYNTAX                              Counter64
        MAX-ACCESS                          read-only
        STATUS                              current
        DESCRIPTION
                        "The number of consistency point operations since boot
                        that were caused by nvlog replay takeover time."
        ::= { cDOTCpEntry 15 }

	-- -- -- -- -- -- --
	-- the auto support group for sysStat

	autosupportStatus               OBJECT-TYPE
	SYNTAX                          INTEGER {
                                             ok(1),
                                             smtpFailure(2),
					     postFailure(3),
					     smtpPostFailure(4),
                                             unknown(5)
                                        }
        MAX-ACCESS                      read-only
        STATUS                          current
	DESCRIPTION
			"An indication of the current status of
			 auto support on the appliance. Describes
			 the success or failure of most recent
			 attempts to send auto supports."

	::= { autosupport 1 }

	autosupportStatusMessage        OBJECT-TYPE
	SYNTAX                          DisplayString
        MAX-ACCESS                      read-only
        STATUS                          current
	DESCRIPTION
			"A string describing the auto support status,
			including a description of the condition (if
			any) that caused the status to be anything
			other than ok(1)."

	::= { autosupport 2 }

	autosupportSuccessfulSends      OBJECT-TYPE
	SYNTAX                          Counter32
        MAX-ACCESS                      read-only
        STATUS                          current
	DESCRIPTION
			"Count of the number of auto support messages
			 successfully sent since the last reset."

	::= { autosupport 3 }

	autosupportFailedSends          OBJECT-TYPE
	SYNTAX                          Counter32
        MAX-ACCESS                      read-only
        STATUS                          current
	DESCRIPTION
	                 "Count of the number of auto support messages
			 not sent successfully since the last reset."

	::= { autosupport 4 }


	-- -- -- -- -- -- --
	-- the NFS group  --
	-- -- -- -- -- -- --

	curNfs		OBJECT IDENTIFIER ::= { nfs 1 }

	totNfs		OBJECT IDENTIFIER ::= { nfs 2 }

	nfsOptions	OBJECT IDENTIFIER ::= { nfs 3 }


	-- the curNfs group

		-- this group contains NFS statistics since the last
		-- time the statistics were cleared

	rpcServ		OBJECT IDENTIFIER ::= { curNfs 1 }

	nfsServ		OBJECT IDENTIFIER ::= { curNfs 2 }

	nfsPerClient	OBJECT IDENTIFIER ::= { curNfs 3 }



	-- the rpcServ group

 	rpcCalls                        OBJECT-TYPE
	SYNTAX                          Counter32
        MAX-ACCESS                      read-only
        STATUS                          current
	DESCRIPTION
			"The total number of RPC calls received, since
			 the last time the statistics were cleared."
	::= { rpcServ 1 }

	rpcBadCalls                     OBJECT-TYPE
	SYNTAX                          Counter32
        MAX-ACCESS                      read-only
        STATUS                          current
	DESCRIPTION
			"The total number of calls rejected by the RPC
			 layer, since the last time the statistics were
			 cleared."
	::= { rpcServ 2 }

	rpcNullRecvs                    OBJECT-TYPE
	SYNTAX                          Counter32
        MAX-ACCESS                      read-only
        STATUS                          current
	DESCRIPTION
			"The number of times an RPC call was not available
			 when it was thought to be received, since the
			 last time the statistics were cleared."
	::= { rpcServ 3 }

	rpcBadLens                      OBJECT-TYPE
	SYNTAX                          Counter32
        MAX-ACCESS                      read-only
        STATUS                          current
	DESCRIPTION
			"The number of RPC calls received with a length
			 shorter than a minimum-sized RPC call, since the
			 last time the statistics were cleared."
	::= { rpcServ 4 }

	rpcServXDRCalls                 OBJECT-TYPE
	SYNTAX                          Counter32
        MAX-ACCESS                      read-only
        STATUS                          current
	DESCRIPTION
			"The number of RPC calls received whose header
			 could not be XDR decoded, since the last time
			 the statistics were cleared."
	::= { rpcServ 5 }

 	rcpTcpCalls                     OBJECT-TYPE
	SYNTAX                          Counter32
        MAX-ACCESS                      read-only
        STATUS                          current
	DESCRIPTION
			"The total number of RPC calls received for the
			 TCP protocol, since the last time the statistics
			 were cleared."
	::= { rpcServ 6 }

	rcpTcpBadCalls                  OBJECT-TYPE
	SYNTAX                          Counter32
        MAX-ACCESS                      read-only
        STATUS                          current
	DESCRIPTION
			"The total number of calls rejected by the RPC
			 layer for the TCP protocol, since the last
			 time the statistics were cleared."
	::= { rpcServ 7 }

	rcpTcpNullRecvs                 OBJECT-TYPE
	SYNTAX                          Counter32
        MAX-ACCESS                      read-only
        STATUS                          current
	DESCRIPTION
			"The number of times an RPC call for the TCP
			 protocol was not available when it was thought
			 to be received, since the last time the
			 statistics were cleared."
	::= { rpcServ 8 }

	rcpTcpBadLens                   OBJECT-TYPE
	SYNTAX                          Counter32
        MAX-ACCESS                      read-only
        STATUS                          current
	DESCRIPTION
			"The number of RPC calls for the TCP protocol
			 received with a length shorter than a minimum-sized
			 RPC call, since the last time the statistics
			 were cleared."
	::= { rpcServ 9 }

	rcpTcpServXDRCalls              OBJECT-TYPE
	SYNTAX                          Counter32
        MAX-ACCESS                      read-only
        STATUS                          current
	DESCRIPTION
			"The number of RPC calls for the TCP protocol
			 received whose header could not be XDR decoded,
			 since the last time the statistics were cleared."
	::= { rpcServ 10 }

 	rpcUdpCalls                     OBJECT-TYPE
	SYNTAX                          Counter32
        MAX-ACCESS                      read-only
        STATUS                          current
	DESCRIPTION
			"The total number of RPC calls received for the
			 UDP protocol, since the last time the statistics
			 were cleared."
	::= { rpcServ 11 }

	rpcUdpBadCalls                  OBJECT-TYPE
	SYNTAX                          Counter32
        MAX-ACCESS                      read-only
        STATUS                          current
	DESCRIPTION
			"The total number of calls rejected by the RPC
			 layer for the UDP protocol, since the last
			 time the statistics were cleared."
	::= { rpcServ 12 }

	rpcUdpNullRecvs                 OBJECT-TYPE
	SYNTAX                          Counter32
        MAX-ACCESS                      read-only
        STATUS                          current
	DESCRIPTION
			"The number of times an RPC call for the UDP
			 protocol was not available when it was thought
			 to be received, since the last time the
			 statistics were cleared."
	::= { rpcServ 13 }

	rpcUdpBadLens                   OBJECT-TYPE
	SYNTAX                          Counter32
        MAX-ACCESS                      read-only
        STATUS                          current
	DESCRIPTION
			"The number of RPC calls for the UDP protocol
			 received with a length shorter than a minimum-sized
			 RPC call, since the last time the statistics
			 were cleared."
	::= { rpcServ 14 }

	rpcUdpServXDRCalls              OBJECT-TYPE
	SYNTAX                          Counter32
        MAX-ACCESS                      read-only
        STATUS                          current
	DESCRIPTION
			"The number of RPC calls for the UDP protocol
			 received whose header could not be XDR decoded,
			 since the last time the statistics were cleared."
	::= { rpcServ 15 }


	-- the nfsServ group

	nfsCalls                        OBJECT-TYPE
	SYNTAX                          Counter32
        MAX-ACCESS                      read-only
        STATUS                          current
	DESCRIPTION
			"The total number of NFS calls received, since
			 the last time the statistics were cleared."
	::= { nfsServ 1 }

	nfsServBadCalls                 OBJECT-TYPE
	SYNTAX                          Counter32
        MAX-ACCESS                      read-only
        STATUS                          current
	DESCRIPTION
			"The total number of received NFS calls rejected,
			 since the last time the statistics were cleared."
	::= { nfsServ 2 }

	nfsV2		OBJECT IDENTIFIER ::= { nfsServ 3 }

	nfsV3		OBJECT IDENTIFIER ::= { nfsServ 4 }

	replyCache	OBJECT IDENTIFIER ::= { nfsServ 5 }

	nfsrwStats	OBJECT IDENTIFIER ::= { nfsServ 6 }


	-- the nfsV2 group

		-- this group contains statistics for NFS
		-- Version 2 calls processed since the last
		-- time the statistics were cleared

	v2Calls		OBJECT IDENTIFIER ::= { nfsV2 1 }

	v2Percent	OBJECT IDENTIFIER ::= { nfsV2 2 }

	v2CachedCalls	OBJECT IDENTIFIER ::= { nfsV2 3 }

	v2CachedPerCent	OBJECT IDENTIFIER ::= { nfsV2 4 }



	-- the v2Calls group

		-- this group contains statistics for the number of
		-- calls received for each NFS Version 2 procedure
		-- since the last time the statistics were cleared

	v2cNulls                        OBJECT-TYPE
	SYNTAX                          Counter32
        MAX-ACCESS                      read-only
        STATUS                          current
	DESCRIPTION
			"The number of NFS Version 2 calls received
			 for the NFSPROC_NULL (Do Nothing) procedure,
			 since the last time the statistics were cleared."
	::= { v2Calls 1 }

	v2cGetattrs                     OBJECT-TYPE
	SYNTAX                          Counter32
        MAX-ACCESS                      read-only
        STATUS                          current
	DESCRIPTION
			"The number of NFS Version 2 calls received
			 for the NFSPROC_GETATTR (Get File Attributes)
			 procedure, since the last time the statistics
			 were cleared."
	::= { v2Calls 2 }

	v2cSetattrs                     OBJECT-TYPE
	SYNTAX                          Counter32
        MAX-ACCESS                      read-only
        STATUS                          current
	DESCRIPTION
			"The number of NFS Version 2 calls received
			 for the NFSPROC_SETATTR (Set File Attributes)
			 procedure, since the last time the statistics
			 were cleared."
	::= { v2Calls 3 }

	v2cRoots                        OBJECT-TYPE
	SYNTAX                          Counter32
        MAX-ACCESS                      read-only
        STATUS                          current
	DESCRIPTION
			"The number of NFS Version 2 calls received
			 for the NFSPROC_ROOT (Get Filesystem Root)
			 procedure, since the last time the statistics
			 were cleared."
	::= { v2Calls 4 }

	v2cLookups                      OBJECT-TYPE
	SYNTAX                          Counter32
        MAX-ACCESS                      read-only
        STATUS                          current
	DESCRIPTION
			"The number of NFS Version 2 calls received
			 for the NFSPROC_LOOKUP (Look Up File Name)
			 procedure, since the last time the statistics
			 were cleared."
	::= { v2Calls 5 }

	v2cReadlinks                    OBJECT-TYPE
	SYNTAX                          Counter32
        MAX-ACCESS                      read-only
        STATUS                          current
	DESCRIPTION
			"The number of NFS Version 2 calls received
			 for the NFSPROC_READLINK (Read From Symbolic
			 Link) procedure, since the last time the
			 statistics were cleared."
	::= { v2Calls 6 }

	v2cReads                        OBJECT-TYPE
	SYNTAX                          Counter32
        MAX-ACCESS                      read-only
        STATUS                          current
	DESCRIPTION
			"The number of NFS Version 2 calls received
			 for the NFSPROC_READ (Read From File)
			 procedure, since the last time the statistics
			 were cleared."
	::= { v2Calls 7 }

	v2cWrcaches                     OBJECT-TYPE
	SYNTAX                          Counter32
        MAX-ACCESS                      read-only
        STATUS                          current
	DESCRIPTION
			"The number of NFS Version 2 calls received
			 for the NFSPROC_WRITECACHE (Write to Cache)
			 procedure, since the last time the statistics
			 were cleared."
	::= { v2Calls 8 }

	v2cWrites                       OBJECT-TYPE
	SYNTAX                          Counter32
        MAX-ACCESS                      read-only
        STATUS                          current
	DESCRIPTION
			"The number of NFS Version 2 calls received
			 for the NFSPROC_WRITE (Write to File)
			 procedure, since the last time the statistics
			 were cleared."
	::= { v2Calls 9 }

	v2cCreates                      OBJECT-TYPE
	SYNTAX                          Counter32
        MAX-ACCESS                      read-only
        STATUS                          current
	DESCRIPTION
			"The number of NFS Version 2 calls received
			 for the NFSPROC_CREATE (Create File)
			 procedure, since the last time the statistics
			 were cleared."
	::= { v2Calls 10 }

	v2cRemoves                      OBJECT-TYPE
	SYNTAX                          Counter32
        MAX-ACCESS                      read-only
        STATUS                          current
	DESCRIPTION
			"The number of NFS Version 2 calls received
			 for the NFSPROC_REMOVE (Remove File)
			 procedure, since the last time the statistics
			 were cleared."
	::= { v2Calls 11 }

	v2cRenames                      OBJECT-TYPE
	SYNTAX                          Counter32
        MAX-ACCESS                      read-only
        STATUS                          current
	DESCRIPTION
			"The number of NFS Version 2 calls received
			 for the NFSPROC_RENAME (Rename File)
			 procedure, since the last time the statistics
			 were cleared."
	::= { v2Calls 12 }

	v2cLinks                        OBJECT-TYPE
	SYNTAX                          Counter32
        MAX-ACCESS                      read-only
        STATUS                          current
	DESCRIPTION
			"The number of NFS Version 2 calls received
			 for the NFSPROC_LINK (Create Link to File)
			 procedure, since the last time the statistics
			 were cleared."
	::= { v2Calls 13 }

	v2cSymlinks                     OBJECT-TYPE
	SYNTAX                          Counter32
        MAX-ACCESS                      read-only
        STATUS                          current
	DESCRIPTION
			"The number of NFS Version 2 calls received
			 for the NFSPROC_SYMLINK (Create Symbolic Link)
			 procedure, since the last time the statistics
			 were cleared."
	::= { v2Calls 14 }

	v2cMkdirs                       OBJECT-TYPE
	SYNTAX                          Counter32
        MAX-ACCESS                      read-only
        STATUS                          current
	DESCRIPTION
			"The number of NFS Version 2 calls received
			 for the NFSPROC_MKDIR (Create Directory)
			 procedure, since the last time the statistics
			 were cleared."
	::= { v2Calls 15 }

	v2cRmdirs                       OBJECT-TYPE
	SYNTAX                          Counter32
        MAX-ACCESS                      read-only
        STATUS                          current
	DESCRIPTION
			"The number of NFS Version 2 calls received
			 for the NFSPROC_RMDIR (Remove Directory)
			 procedure, since the last time the statistics
			 were cleared."
	::= { v2Calls 16 }

	v2cReaddirs                     OBJECT-TYPE
	SYNTAX                          Counter32
        MAX-ACCESS                      read-only
        STATUS                          current
	DESCRIPTION
			"The number of NFS Version 2 calls received
			 for the NFSPROC_READDIR (Read From Directory)
			 procedure, since the last time the statistics
			 were cleared."
	::= { v2Calls 17 }

	v2cStatfss                      OBJECT-TYPE
	SYNTAX                          Counter32
        MAX-ACCESS                      read-only
        STATUS                          current
	DESCRIPTION
			"The number of NFS Version 2 calls received
			 for the NFSPROC_STATFS (Get Filesystem
			 Attributes) procedure, since the last time
			 the statistics were cleared."
	::= { v2Calls 18 }



	-- the v2Percent group

		-- this group contains statistics for the number of
		-- calls received for each NFS Version 2 procedure,
		-- as a percentage of total NFS calls received,
		-- since the last time the statistics were cleared

	v2pNulls                        OBJECT-TYPE
	SYNTAX                          Integer32 (0..100)
        MAX-ACCESS                      read-only
        STATUS                          current
	DESCRIPTION
			"The number of NFS Version 2 calls received
			 for the NFSPROC_NULL (Do Nothing) procedure
			 as a percentage of total NFS calls received,
			 since the last time the statistics were cleared."
	::= { v2Percent 1 }

	v2pGetattrs                     OBJECT-TYPE
	SYNTAX                          Integer32 (0..100)
        MAX-ACCESS                      read-only
        STATUS                          current
	DESCRIPTION
			"The number of NFS Version 2 calls received
			 for the NFSPROC_GETATTR (Get File Attributes)
			 procedure as a percentage of total NFS calls
			 received, since the last time the statistics
			 were cleared."
	::= { v2Percent 2 }

	v2pSetattrs                     OBJECT-TYPE
	SYNTAX                          Integer32 (0..100)
        MAX-ACCESS                      read-only
        STATUS                          current
	DESCRIPTION
			"The number of NFS Version 2 calls received
			 for the NFSPROC_SETATTR (Set File Attributes)
			 procedure as a percentage of total NFS calls
			 received, since the last time the statistics
			 were cleared."
	::= { v2Percent 3 }

	v2pRoots                        OBJECT-TYPE
	SYNTAX                          Integer32 (0..100)
        MAX-ACCESS                      read-only
        STATUS                          current
	DESCRIPTION
			"The number of NFS Version 2 calls received
			 for the NFSPROC_ROOT (Get Filesystem Root)
			 procedure as a percentage of total NFS calls
			 received, since the last time the statistics
			 were cleared."
	::= { v2Percent 4 }

	v2pLookups                      OBJECT-TYPE
	SYNTAX                          Integer32 (0..100)
        MAX-ACCESS                      read-only
        STATUS                          current
	DESCRIPTION
			"The number of NFS Version 2 calls received
			 for the NFSPROC_LOOKUP (Look Up File Name)
			 procedure as a percentage of total NFS calls
			 received, since the last time the statistics
			 were cleared."
	::= { v2Percent 5 }

	v2pReadlinks                    OBJECT-TYPE
	SYNTAX                          Integer32 (0..100)
        MAX-ACCESS                      read-only
        STATUS                          current
	DESCRIPTION
			"The number of NFS Version 2 calls received
			 for the NFSPROC_READLINK (Read From Symbolic
			 Link) procedure as a percentage of total NFS
			 calls received, since the last time the
			 statistics were cleared."
	::= { v2Percent 6 }

	v2pReads                        OBJECT-TYPE
	SYNTAX                          Integer32 (0..100)
        MAX-ACCESS                      read-only
        STATUS                          current
	DESCRIPTION
			"The number of NFS Version 2 calls received
			 for the NFSPROC_READ (Read From File)
			 procedure as a percentage of total NFS calls
			 received, since the last time the statistics
			 were cleared."
	::= { v2Percent 7 }

	v2pWrcaches                     OBJECT-TYPE
	SYNTAX                          Integer32 (0..100)
        MAX-ACCESS                      read-only
        STATUS                          current
	DESCRIPTION
			"The number of NFS Version 2 calls received
			 for the NFSPROC_WRITECACHE (Write to Cache)
			 procedure as a percentage of total NFS calls
			 received, since the last time the statistics
			 were cleared."
	::= { v2Percent 8 }

	v2pWrites                       OBJECT-TYPE
	SYNTAX                          Integer32 (0..100)
        MAX-ACCESS                      read-only
        STATUS                          current
	DESCRIPTION
			"The number of NFS Version 2 calls received
			 for the NFSPROC_WRITE (Write to File)
			 procedure as a percentage of total NFS calls
			 received, since the last time the statistics
			 were cleared."
	::= { v2Percent 9 }

	v2pCreates                      OBJECT-TYPE
	SYNTAX                          Integer32 (0..100)
        MAX-ACCESS                      read-only
        STATUS                          current
	DESCRIPTION
			"The number of NFS Version 2 calls received
			 for the NFSPROC_CREATE (Create File)
			 procedure as a percentage of total NFS calls
			 received, since the last time the statistics
			 were cleared."
	::= { v2Percent 10 }

	v2pRemoves                      OBJECT-TYPE
	SYNTAX                          Integer32 (0..100)
        MAX-ACCESS                      read-only
        STATUS                          current
	DESCRIPTION
			"The number of NFS Version 2 calls received
			 for the NFSPROC_REMOVE (Remove File)
			 procedure as a percentage of total NFS calls
			 received, since the last time the statistics
			 were cleared."
	::= { v2Percent 11 }

	v2pRenames                      OBJECT-TYPE
	SYNTAX                          Integer32 (0..100)
        MAX-ACCESS                      read-only
        STATUS                          current
	DESCRIPTION
			"The number of NFS Version 2 calls received
			 for the NFSPROC_RENAME (Rename File)
			 procedure as a percentage of total NFS calls
			 received, since the last time the statistics
			 were cleared."
	::= { v2Percent 12 }

	v2pLinks                        OBJECT-TYPE
	SYNTAX                          Integer32 (0..100)
        MAX-ACCESS                      read-only
        STATUS                          current
	DESCRIPTION
			"The number of NFS Version 2 calls received
			 for the NFSPROC_LINK (Create Link to File)
			 procedure as a percentage of total NFS calls
			 received, since the last time the statistics
			 were cleared."
	::= { v2Percent 13 }

	v2pSymlinks                     OBJECT-TYPE
	SYNTAX                          Integer32 (0..100)
        MAX-ACCESS                      read-only
        STATUS                          current
	DESCRIPTION
			"The number of NFS Version 2 calls received
			 for the NFSPROC_SYMLINK (Create Symbolic Link)
			 procedure as a percentage of total NFS calls
			 received, since the last time the statistics
			 were cleared."
	::= { v2Percent 14 }

	v2pMkdirs                       OBJECT-TYPE
	SYNTAX                          Integer32 (0..100)
        MAX-ACCESS                      read-only
        STATUS                          current
	DESCRIPTION
			"The number of NFS Version 2 calls received
			 for the NFSPROC_MKDIR (Create Directory)
			 procedure as a percentage of total NFS calls
			 received, since the last time the statistics
			 were cleared."
	::= { v2Percent 15 }

	v2pRmdirs                       OBJECT-TYPE
	SYNTAX                          Integer32 (0..100)
        MAX-ACCESS                      read-only
        STATUS                          current
	DESCRIPTION
			"The number of NFS Version 2 calls received
			 for the NFSPROC_RMDIR (Remove Directory)
			 procedure as a percentage of total NFS calls
			 received, since the last time the statistics
			 were cleared."
	::= { v2Percent 16 }

	v2pReaddirs                     OBJECT-TYPE
	SYNTAX                          Integer32 (0..100)
        MAX-ACCESS                      read-only
        STATUS                          current
	DESCRIPTION
			"The number of NFS Version 2 calls received
			 for the NFSPROC_READDIR (Read From Directory)
			 procedure as a percentage of total NFS calls
			 received, since the last time the statistics
			 were cleared."
	::= { v2Percent 17 }

	v2pStatfss                      OBJECT-TYPE
	SYNTAX                          Integer32 (0..100)
        MAX-ACCESS                      read-only
        STATUS                          current
	DESCRIPTION
			"The number of NFS Version 2 calls received
			 for the NFSPROC_STATFS (Get Filesystem
			 Attributes) procedure as a percentage of
			 total NFS calls received, since the last
			 time the statistics were cleared."
	::= { v2Percent 18 }



	-- the v2CachedCalls group

		-- this group contains statistics for the number of
		-- calls received for each NFS Version 2 procedure,
		-- that did not result in the filesystem blocking to
		-- read from disk, since the last time the statistics
		-- were cleared

	v2ccNulls                       OBJECT-TYPE
	SYNTAX                          Counter32
        MAX-ACCESS                      read-only
        STATUS                          current
	DESCRIPTION
			"The number of NFS Version 2 calls received
			 for the NFSPROC_NULL (Do Nothing) procedure,
			 that did not result in the filesystem
			 blocking to read from disk, since the last
			 time the statistics were cleared."
	::= { v2CachedCalls 1 }

	v2ccGetattrs                    OBJECT-TYPE
	SYNTAX                          Counter32
        MAX-ACCESS                      read-only
        STATUS                          current
	DESCRIPTION
			"The number of NFS Version 2 calls received
			 for the NFSPROC_GETATTR (Get File Attributes)
			 procedure, that did not result in the
			 filesystem blocking to read from disk, since
			 the last time the statistics were cleared."
	::= { v2CachedCalls 2 }

	v2ccSetattrs                    OBJECT-TYPE
	SYNTAX                          Counter32
        MAX-ACCESS                      read-only
        STATUS                          current
	DESCRIPTION
			"The number of NFS Version 2 calls received
			 for the NFSPROC_SETATTR (Set File Attributes)
			 procedure, that did not result in the
			 filesystem blocking to read from disk, since
			 the last time the statistics were cleared."
	::= { v2CachedCalls 3 }

	v2ccRoots                       OBJECT-TYPE
	SYNTAX                          Counter32
        MAX-ACCESS                      read-only
        STATUS                          current
	DESCRIPTION
			"The number of NFS Version 2 calls received
			 for the NFSPROC_ROOT (Get Filesystem Root)
			 procedure, that did not result in the
			 filesystem blocking to read from disk, since
			 the last time the statistics were cleared."
	::= { v2CachedCalls 4 }

	v2ccLookups                     OBJECT-TYPE
	SYNTAX                          Counter32
        MAX-ACCESS                      read-only
        STATUS                          current
	DESCRIPTION
			"The number of NFS Version 2 calls received
			 for the NFSPROC_LOOKUP (Look Up File Name)
			 procedure, that did not result in the
			 filesystem blocking to read from disk, since
			 the last time the statistics were cleared."
	::= { v2CachedCalls 5 }

	v2ccReadlinks                   OBJECT-TYPE
	SYNTAX                          Counter32
        MAX-ACCESS                      read-only
        STATUS                          current
	DESCRIPTION
			"The number of NFS Version 2 calls received
			 for the NFSPROC_READLINK (Read From Symbolic
			 Link) procedure, that did not result in the
			 filesystem blocking to read from disk, since
			 the last time the statistics were cleared."
	::= { v2CachedCalls 6 }

	v2ccReads                       OBJECT-TYPE
	SYNTAX                          Counter32
        MAX-ACCESS                      read-only
        STATUS                          current
	DESCRIPTION
			"The number of NFS Version 2 calls received
			 for the NFSPROC_READ (Read From File)
			 procedure, that did not result in the
			 filesystem blocking to read from disk, since
			 the last time the statistics were cleared."
	::= { v2CachedCalls 7 }

	v2ccWrcaches                    OBJECT-TYPE
	SYNTAX                          Counter32
        MAX-ACCESS                      read-only
        STATUS                          current
	DESCRIPTION
			"The number of NFS Version 2 calls received
			 for the NFSPROC_WRITECACHE (Write to Cache)
			 procedure, that did not result in the
			 filesystem blocking to read from disk, since
			 the last time the statistics were cleared."
	::= { v2CachedCalls 8 }

	v2ccWrites                      OBJECT-TYPE
	SYNTAX                          Counter32
        MAX-ACCESS                      read-only
        STATUS                          current
	DESCRIPTION
			"The number of NFS Version 2 calls received
			 for the NFSPROC_WRITE (Write to File)
			 procedure, that did not result in the
			 filesystem blocking to read from disk, since
			 the last time the statistics were cleared."
	::= { v2CachedCalls 9 }

	v2ccCreates                     OBJECT-TYPE
	SYNTAX                          Counter32
        MAX-ACCESS                      read-only
        STATUS                          current
	DESCRIPTION
			"The number of NFS Version 2 calls received
			 for the NFSPROC_CREATE (Create File)
			 procedure, that did not result in the
			 filesystem blocking to read from disk, since
			 the last time the statistics were cleared."
	::= { v2CachedCalls 10 }

	v2ccRemoves                     OBJECT-TYPE
	SYNTAX                          Counter32
        MAX-ACCESS                      read-only
        STATUS                          current
	DESCRIPTION
			"The number of NFS Version 2 calls received
			 for the NFSPROC_REMOVE (Remove File)
			 procedure, that did not result in the
			 filesystem blocking to read from disk, since
			 the last time the statistics were cleared."
	::= { v2CachedCalls 11 }

	v2ccRenames                     OBJECT-TYPE
	SYNTAX                          Counter32
        MAX-ACCESS                      read-only
        STATUS                          current
	DESCRIPTION
			"The number of NFS Version 2 calls received
			 for the NFSPROC_RENAME (Rename File)
			 procedure, that did not result in the
			 filesystem blocking to read from disk, since
			 the last time the statistics were cleared."
	::= { v2CachedCalls 12 }

	v2ccLinks                       OBJECT-TYPE
	SYNTAX                          Counter32
        MAX-ACCESS                      read-only
        STATUS                          current
	DESCRIPTION
			"The number of NFS Version 2 calls received
			 for the NFSPROC_LINK (Create Link to File)
			 procedure, that did not result in the
			 filesystem blocking to read from disk, since
			 the last time the statistics were cleared."
	::= { v2CachedCalls 13 }

	v2ccSymlinks                    OBJECT-TYPE
	SYNTAX                          Counter32
        MAX-ACCESS                      read-only
        STATUS                          current
	DESCRIPTION
			"The number of NFS Version 2 calls received
			 for the NFSPROC_SYMLINK (Create Symbolic Link)
			 procedure, that did not result in the
			 filesystem blocking to read from disk, since
			 the last time the statistics were cleared."
	::= { v2CachedCalls 14 }

	v2ccMkdirs                      OBJECT-TYPE
	SYNTAX                          Counter32
        MAX-ACCESS                      read-only
        STATUS                          current
	DESCRIPTION
			"The number of NFS Version 2 calls received
			 for the NFSPROC_MKDIR (Create Directory)
			 procedure, that did not result in the
			 filesystem blocking to read from disk, since
			 the last time the statistics were cleared."
	::= { v2CachedCalls 15 }

	v2ccRmdirs                      OBJECT-TYPE
	SYNTAX                          Counter32
        MAX-ACCESS                      read-only
        STATUS                          current
	DESCRIPTION
			"The number of NFS Version 2 calls received
			 for the NFSPROC_RMDIR (Remove Directory)
			 procedure, that did not result in the
			 filesystem blocking to read from disk, since
			 the last time the statistics were cleared."
	::= { v2CachedCalls 16 }

	v2ccReaddirs                    OBJECT-TYPE
	SYNTAX                          Counter32
        MAX-ACCESS                      read-only
        STATUS                          current
	DESCRIPTION
			"The number of NFS Version 2 calls received
			 for the NFSPROC_READDIR (Read From Directory)
			 procedure, that did not result in the
			 filesystem blocking to read from disk, since
			 the last time the statistics were cleared."
	::= { v2CachedCalls 17 }

	v2ccStatfss                     OBJECT-TYPE
	SYNTAX                          Counter32
        MAX-ACCESS                      read-only
        STATUS                          current
	DESCRIPTION
			"The number of NFS Version 2 calls received
			 for the NFSPROC_STATFS (Get Filesystem
			 Attributes) procedure, that did not result
			 in the filesystem blocking to read from disk,
			 since the last time the statistics were cleared."
	::= { v2CachedCalls 18 }



	-- the v2CachedPerCent group

		-- this group contains statistics for the number of
		-- calls received for each NFS Version 2 procedure,
		-- that did not result in the filesystem blocking to
		-- read from disk, as a percentage of the total
		-- number of calls received for that procedure,
		-- since the last time the statistics were cleared

	v2cpNulls                       OBJECT-TYPE
	SYNTAX                          Integer32 (0..100)
        MAX-ACCESS                      read-only
        STATUS                          current
	DESCRIPTION
			"The number of NFS Version 2 calls received
			 for the NFSPROC_NULL (Do Nothing) procedure,
			 that did not result in the filesystem
			 blocking to read from disk, as a percentage
			 of the total number of calls received for
			 this procedure, since the last time the
			 statistics were cleared."
	::= { v2CachedPerCent 1 }

	v2cpGetattrs                    OBJECT-TYPE
	SYNTAX                          Integer32 (0..100)
        MAX-ACCESS                      read-only
        STATUS                          current
	DESCRIPTION
			"The number of NFS Version 2 calls received
			 for the NFSPROC_GETATTR (Get File Attributes)
			 procedure, that did not result in the
			 filesystem blocking to read from disk, as a
			 percentage of the total number of calls
			 received for this procedure, since the last
			 time the statistics were cleared."
	::= { v2CachedPerCent 2 }

	v2cpSetattrs                    OBJECT-TYPE
	SYNTAX                          Integer32 (0..100)
        MAX-ACCESS                      read-only
        STATUS                          current
	DESCRIPTION
			"The number of NFS Version 2 calls received
			 for the NFSPROC_SETATTR (Set File Attributes)
			 procedure, that did not result in the
			 filesystem blocking to read from disk, as a
			 percentage of the total number of calls
			 received for this procedure, since the last
			 time the statistics were cleared."
	::= { v2CachedPerCent 3 }

	v2cpRoots                       OBJECT-TYPE
	SYNTAX                          Integer32 (0..100)
        MAX-ACCESS                      read-only
        STATUS                          current
	DESCRIPTION
			"The number of NFS Version 2 calls received
			 for the NFSPROC_ROOT (Get Filesystem Root)
			 procedure, that did not result in the
			 filesystem blocking to read from disk, as a
			 percentage of the total number of calls
			 received for this procedure, since the last
			 time the statistics were cleared."
	::= { v2CachedPerCent 4 }

	v2cpLookups                     OBJECT-TYPE
	SYNTAX                          Integer32 (0..100)
        MAX-ACCESS                      read-only
        STATUS                          current
	DESCRIPTION
			"The number of NFS Version 2 calls received
			 for the NFSPROC_LOOKUP (Look Up File Name)
			 procedure, that did not result in the
			 filesystem blocking to read from disk, as a
			 percentage of the total number of calls
			 received for this procedure, since the last
			 time the statistics were cleared."
	::= { v2CachedPerCent 5 }

	v2cpReadlinks                   OBJECT-TYPE
	SYNTAX                          Integer32 (0..100)
        MAX-ACCESS                      read-only
        STATUS                          current
	DESCRIPTION
			"The number of NFS Version 2 calls received
			 for the NFSPROC_READLINK (Read From Symbolic
			 Link) procedure, that did not result in the
			 filesystem blocking to read from disk, as a
			 percentage of the total number of calls
			 received for this procedure, since the last
			 time the statistics were cleared."
	::= { v2CachedPerCent 6 }

	v2cpReads                       OBJECT-TYPE
	SYNTAX                          Integer32 (0..100)
        MAX-ACCESS                      read-only
        STATUS                          current
	DESCRIPTION
			"The number of NFS Version 2 calls received
			 for the NFSPROC_READ (Read From File)
			 procedure, that did not result in the
			 filesystem blocking to read from disk, as a
			 percentage of the total number of calls
			 received for this procedure, since the last
			 time the statistics were cleared."
	::= { v2CachedPerCent 7 }

	v2cpWrcaches                    OBJECT-TYPE
	SYNTAX                          Integer32 (0..100)
        MAX-ACCESS                      read-only
        STATUS                          current
	DESCRIPTION
			"The number of NFS Version 2 calls received
			 for the NFSPROC_WRITECACHE (Write to Cache)
			 procedure, that did not result in the
			 filesystem blocking to read from disk, as a
			 percentage of the total number of calls
			 received for this procedure, since the last
			 time the statistics were cleared."
	::= { v2CachedPerCent 8 }

	v2cpWrites                      OBJECT-TYPE
	SYNTAX                          Integer32 (0..100)
        MAX-ACCESS                      read-only
        STATUS                          current
	DESCRIPTION
			"The number of NFS Version 2 calls received
			 for the NFSPROC_WRITE (Write to File)
			 procedure, that did not result in the
			 filesystem blocking to read from disk, as a
			 percentage of the total number of calls
			 received for this procedure, since the last
			 time the statistics were cleared."
	::= { v2CachedPerCent 9 }

	v2cpCreates                     OBJECT-TYPE
	SYNTAX                          Integer32 (0..100)
        MAX-ACCESS                      read-only
        STATUS                          current
	DESCRIPTION
			"The number of NFS Version 2 calls received
			 for the NFSPROC_CREATE (Create File)
			 procedure, that did not result in the
			 filesystem blocking to read from disk, as a
			 percentage of the total number of calls
			 received for this procedure, since the last
			 time the statistics were cleared."
	::= { v2CachedPerCent 10 }

	v2cpRemoves                     OBJECT-TYPE
	SYNTAX                          Integer32 (0..100)
        MAX-ACCESS                      read-only
        STATUS                          current
	DESCRIPTION
			"The number of NFS Version 2 calls received
			 for the NFSPROC_REMOVE (Remove File)
			 procedure, that did not result in the
			 filesystem blocking to read from disk, as a
			 percentage of the total number of calls
			 received for this procedure, since the last
			 time the statistics were cleared."
	::= { v2CachedPerCent 11 }

	v2cpRenames                     OBJECT-TYPE
	SYNTAX                          Integer32 (0..100)
        MAX-ACCESS                      read-only
        STATUS                          current
	DESCRIPTION
			"The number of NFS Version 2 calls received
			 for the NFSPROC_RENAME (Rename File)
			 procedure, that did not result in the
			 filesystem blocking to read from disk, as a
			 percentage of the total number of calls
			 received for this procedure, since the last
			 time the statistics were cleared."
	::= { v2CachedPerCent 12 }

	v2cpLinks                       OBJECT-TYPE
	SYNTAX                          Integer32 (0..100)
        MAX-ACCESS                      read-only
        STATUS                          current
	DESCRIPTION
			"The number of NFS Version 2 calls received
			 for the NFSPROC_LINK (Create Link to File)
			 procedure, that did not result in the
			 filesystem blocking to read from disk, as a
			 percentage of the total number of calls
			 received for this procedure, since the last
			 time the statistics were cleared."
	::= { v2CachedPerCent 13 }

	v2cpSymlinks                    OBJECT-TYPE
	SYNTAX                          Integer32 (0..100)
        MAX-ACCESS                      read-only
        STATUS                          current
	DESCRIPTION
			"The number of NFS Version 2 calls received
			 for the NFSPROC_SYMLINK (Create Symbolic
			 Link) procedure, that did not result in the
			 filesystem blocking to read from disk, as a
			 percentage of the total number of calls
			 received for this procedure, since the last
			 time the statistics were cleared."
	::= { v2CachedPerCent 14 }

	v2cpMkdirs                      OBJECT-TYPE
	SYNTAX                          Integer32 (0..100)
        MAX-ACCESS                      read-only
        STATUS                          current
	DESCRIPTION
			"The number of NFS Version 2 calls received
			 for the NFSPROC_MKDIR (Create Directory)
			 procedure, that did not result in the
			 filesystem blocking to read from disk, as a
			 percentage of the total number of calls
			 received for this procedure, since the last
			 time the statistics were cleared."
	::= { v2CachedPerCent 15 }

	v2cpRmdirs                      OBJECT-TYPE
	SYNTAX                          Integer32 (0..100)
        MAX-ACCESS                      read-only
        STATUS                          current
	DESCRIPTION
			"The number of NFS Version 2 calls received
			 for the NFSPROC_RMDIR (Remove Directory)
			 procedure, that did not result in the
			 filesystem blocking to read from disk, as a
			 percentage of the total number of calls
			 received for this procedure, since the last
			 time the statistics were cleared."
	::= { v2CachedPerCent 16 }

	v2cpReaddirs                    OBJECT-TYPE
	SYNTAX                          Integer32 (0..100)
        MAX-ACCESS                      read-only
        STATUS                          current
	DESCRIPTION
			"The number of NFS Version 2 calls received
			 for the NFSPROC_READDIR (Read From Directory)
			 procedure, that did not result in the
			 filesystem blocking to read from disk, as a
			 percentage of the total number of calls
			 received for this procedure, since the last
			 time the statistics were cleared."
	::= { v2CachedPerCent 17 }

	v2cpStatfss                     OBJECT-TYPE
	SYNTAX                          Integer32 (0..100)
        MAX-ACCESS                      read-only
        STATUS                          current
	DESCRIPTION
			"The number of NFS Version 2 calls received
			 for the NFSPROC_STATFS (Get Filesystem
			 Attributes) procedure, that did not result
			 in the filesystem blocking to read from
			 disk, as a percentage of the total number
			 of calls received for this procedure, since
			 the last time the statistics were cleared."
	::= { v2CachedPerCent 18 }



	-- the nfsV3 group

		-- this group contains statistics for NFS
		-- Version 3 calls processed since the last
		-- time the statistics were cleared

	v3Calls		OBJECT IDENTIFIER ::= { nfsV3 1 }

	v3Percent	OBJECT IDENTIFIER ::= { nfsV3 2 }

	v3CachedCalls	OBJECT IDENTIFIER ::= { nfsV3 3 }

	v3CachedPerCent	OBJECT IDENTIFIER ::= { nfsV3 4 }



	-- the v3Calls group

		-- this group contains statistics for the number of
		-- calls received for each NFS Version 3 procedure
		-- since the last time the statistics were cleared

	v3cNulls                        OBJECT-TYPE
	SYNTAX                          Counter32
        MAX-ACCESS                      read-only
        STATUS                          current
	DESCRIPTION
			"The number of NFS Version 3 calls received
			 for the NFSPROC3_NULL (Do Nothing) procedure,
			 since the last time the statistics were cleared."
	::= { v3Calls 1 }

	v3cGetattrs                     OBJECT-TYPE
	SYNTAX                          Counter32
        MAX-ACCESS                      read-only
        STATUS                          current
	DESCRIPTION
			"The number of NFS Version 3 calls received
			 for the NFSPROC3_GETATTR (Get File Attributes)
			 procedure, since the last time the statistics
			 were cleared."
	::= { v3Calls 2 }

	v3cSetattrs                     OBJECT-TYPE
	SYNTAX                          Counter32
        MAX-ACCESS                      read-only
        STATUS                          current
	DESCRIPTION
			"The number of NFS Version 3 calls received
			 for the NFSPROC3_SETATTR (Set File Attributes)
			 procedure, since the last time the statistics
			 were cleared."
	::= { v3Calls 3 }

	v3cLookups                      OBJECT-TYPE
	SYNTAX                          Counter32
        MAX-ACCESS                      read-only
        STATUS                          current
	DESCRIPTION
			"The number of NFS Version 3 calls received
			 for the NFSPROC3_LOOKUP (Lookup Filename)
			 procedure, since the last time the statistics
			 were cleared."
	::= { v3Calls 4 }

	v3cAccesss                      OBJECT-TYPE
	SYNTAX                          Counter32
        MAX-ACCESS                      read-only
        STATUS                          current
	DESCRIPTION
			"The number of NFS Version 3 calls received
			 for the NFSPROC3_ACCESS (Check Access Permission)
			 procedure, since the last time the statistics
			 were cleared."
	::= { v3Calls 5 }

	v3cReadlinks                    OBJECT-TYPE
	SYNTAX                          Counter32
        MAX-ACCESS                      read-only
        STATUS                          current
	DESCRIPTION
			"The number of NFS Version 3 calls received
			 for the NFSPROC3_READLINK (Read from Symbolic
			 Link) procedure, since the last time the
			 statistics were cleared."
	::= { v3Calls 6 }

	v3cReads                        OBJECT-TYPE
	SYNTAX                          Counter32
        MAX-ACCESS                      read-only
        STATUS                          current
	DESCRIPTION
			"The number of NFS Version 3 calls received
			 for the NFSPROC3_READ (Read From File)
			 procedure, since the last time the statistics
			 were cleared."
	::= { v3Calls 7 }

	v3cWrites                       OBJECT-TYPE
	SYNTAX                          Counter32
        MAX-ACCESS                      read-only
        STATUS                          current
	DESCRIPTION
			"The number of NFS Version 3 calls received
			 for the NFSPROC3_WRITE (Write to File)
			 procedure, since the last time the statistics
			 were cleared."
	::= { v3Calls 8 }

	v3cCreates                      OBJECT-TYPE
	SYNTAX                          Counter32
        MAX-ACCESS                      read-only
        STATUS                          current
	DESCRIPTION
			"The number of NFS Version 3 calls received
			 for the NFSPROC3_CREATE (Create a File)
			 procedure, since the last time the statistics
			 were cleared."
	::= { v3Calls 9 }

	v3cMkdirs                       OBJECT-TYPE
	SYNTAX                          Counter32
        MAX-ACCESS                      read-only
        STATUS                          current
	DESCRIPTION
			"The number of NFS Version 3 calls received
			 for the NFSPROC3_MKDIR (Create a Directory)
			 procedure, since the last time the statistics
			 were cleared."
	::= { v3Calls 10 }

	v3cSymlinks                     OBJECT-TYPE
	SYNTAX                          Counter32
        MAX-ACCESS                      read-only
        STATUS                          current
	DESCRIPTION
			"The number of NFS Version 3 calls received
			 for the NFSPROC3_SYMLINK (Create a Symbolic
			 Link) procedure, since the last time the
			 statistics were cleared."
	::= { v3Calls 11 }

	v3cMknods                       OBJECT-TYPE
	SYNTAX                          Counter32
        MAX-ACCESS                      read-only
        STATUS                          current
	DESCRIPTION
			"The number of NFS Version 3 calls received
			 for the NFSPROC3_MKNOD (Create a Special
			 Device) procedure, since the last time the
			 statistics were cleared."
	::= { v3Calls 12 }

	v3cRemoves                      OBJECT-TYPE
	SYNTAX                          Counter32
        MAX-ACCESS                      read-only
        STATUS                          current
	DESCRIPTION
			"The number of NFS Version 3 calls received
			 for the NFSPROC3_REMOVE (Remove a File)
			 procedure, since the last time the statistics
			 were cleared."
	::= { v3Calls 13 }

	v3cRmdirs                       OBJECT-TYPE
	SYNTAX                          Counter32
        MAX-ACCESS                      read-only
        STATUS                          current
	DESCRIPTION
			"The number of NFS Version 3 calls received
			 for the NFSPROC3_RMDIR (Remove a Directory)
			 procedure, since the last time the statistics
			 were cleared."
	::= { v3Calls 14 }

	v3cRenames                      OBJECT-TYPE
	SYNTAX                          Counter32
        MAX-ACCESS                      read-only
        STATUS                          current
	DESCRIPTION
			"The number of NFS Version 3 calls received
			 for the NFSPROC3_RENAME (Rename a File or
			 Directory) procedure, since the last time
			 the statistics were cleared."
	::= { v3Calls 15 }

	v3cLinks                        OBJECT-TYPE
	SYNTAX                          Counter32
        MAX-ACCESS                      read-only
        STATUS                          current
	DESCRIPTION
			"The number of NFS Version 3 calls received
			 for the NFSPROC3_LINK (Create Link to an
			 Object) procedure, since the last time the
			 statistics were cleared."
	::= { v3Calls 16 }

	v3cReaddirs                     OBJECT-TYPE
	SYNTAX                          Counter32
        MAX-ACCESS                      read-only
        STATUS                          current
	DESCRIPTION
			"The number of NFS Version 3 calls received
			 for the NFSPROC3_READDIR (Read From Directory)
			 procedure, since the last time the statistics
			 were cleared."
	::= { v3Calls 17 }

	v3cReaddirPluss                 OBJECT-TYPE
	SYNTAX                          Counter32
        MAX-ACCESS                      read-only
        STATUS                          current
	DESCRIPTION
			"The number of NFS Version 3 calls received
			 for the NFSPROC3_READDIRPLUS (Extended Read
			 from Directory) procedure, since the last
			 time the statistics were cleared."
	::= { v3Calls 18 }

	v3cFsstats                      OBJECT-TYPE
	SYNTAX                          Counter32
        MAX-ACCESS                      read-only
        STATUS                          current
	DESCRIPTION
			"The number of NFS Version 3 calls received
			 for the NFSPROC3_FSSTAT (Get Dynamic File
			 System Information) procedure, since the
			 last time the statistics were cleared."
	::= { v3Calls 19 }

	v3cFsinfos                      OBJECT-TYPE
	SYNTAX                          Counter32
        MAX-ACCESS                      read-only
        STATUS                          current
	DESCRIPTION
			"The number of NFS Version 3 calls received
			 for the NFSPROC3_FSINFO (Get Static File System
			 Information) procedure, since the last time
			 the statistics were cleared."
	::= { v3Calls 20 }

	v3cPathconfs                    OBJECT-TYPE
	SYNTAX                          Counter32
        MAX-ACCESS                      read-only
        STATUS                          current
	DESCRIPTION
			"The number of NFS Version 3 calls received
			 for the NFSPROC3_PATHCONF (Retrieve POSIX
			 Information) procedure, since the last time
			 the statistics were cleared."
	::= { v3Calls 21 }

	v3cCommits                      OBJECT-TYPE
	SYNTAX                          Counter32
        MAX-ACCESS                      read-only
        STATUS                          current
	DESCRIPTION
			"The number of NFS Version 3 calls received
			 for the NFSPROC3_COMMIT (Commit Cached Data on
			 a Server to Stable Storage) procedure, since
			 the last time the statistics were cleared."
	::= { v3Calls 22 }



	-- the v3Percent group

		-- this group contains statistics for the number of
		-- calls received for each NFS Version 3 procedure,
		-- as a percentage of total NFS calls received,
		-- since the last time the statistics were cleared

	v3pNulls                        OBJECT-TYPE
	SYNTAX                          Integer32 (0..100)
        MAX-ACCESS                      read-only
        STATUS                          current
	DESCRIPTION
			"The number of NFS Version 3 calls received
			 for the NFSPROC3_NULL (Do Nothing) procedure,
			 as a percentage of the total NFS calls
			 received, since the last time the statistics
			 were cleared."
	::= { v3Percent 1 }

	v3pGetattrs                     OBJECT-TYPE
	SYNTAX                          Integer32 (0..100)
        MAX-ACCESS                      read-only
        STATUS                          current
	DESCRIPTION
			"The number of NFS Version 3 calls received
			 for the NFSPROC3_GETATTR (Get File Attributes)
			 procedure, as a percentage of the total NFS
			 calls received, since the last time the
			 statistics were cleared."
	::= { v3Percent 2 }

	v3pSetattrs                     OBJECT-TYPE
	SYNTAX                          Integer32 (0..100)
        MAX-ACCESS                      read-only
        STATUS                          current
	DESCRIPTION
			"The number of NFS Version 3 calls received
			 for the NFSPROC3_SETATTR (Set File Attributes)
			 procedure, as a percentage of the total NFS
			 calls received, since the last time the
			 statistics were cleared."
	::= { v3Percent 3 }

	v3pLookups                      OBJECT-TYPE
	SYNTAX                          Integer32 (0..100)
        MAX-ACCESS                      read-only
        STATUS                          current
	DESCRIPTION
			"The number of NFS Version 3 calls received
			 for the NFSPROC3_LOOKUP (Lookup Filename)
			 procedure, as a percentage of the total NFS
			 calls received, since the last time the
			 statistics were cleared."
	::= { v3Percent 4 }

	v3pAccesss                      OBJECT-TYPE
	SYNTAX                          Integer32 (0..100)
        MAX-ACCESS                      read-only
        STATUS                          current
	DESCRIPTION
			"The number of NFS Version 3 calls received
			 for the NFSPROC3_ACCESS (Check Access
			 Permission) procedure, as a percentage of
			 the total NFS calls received, since the
			 last time the statistics were cleared."
	::= { v3Percent 5 }

	v3pReadlinks                    OBJECT-TYPE
	SYNTAX                          Integer32 (0..100)
        MAX-ACCESS                      read-only
        STATUS                          current
	DESCRIPTION
			"The number of NFS Version 3 calls received
			 for the NFSPROC3_READLINK (Read from Symbolic
			 Link) procedure, as a percentage of the total
			 NFS calls received, since the last time the
			 statistics were cleared."
	::= { v3Percent 6 }

	v3pReads                        OBJECT-TYPE
	SYNTAX                          Integer32 (0..100)
        MAX-ACCESS                      read-only
        STATUS                          current
	DESCRIPTION
			"The number of NFS Version 3 calls received
			 for the NFSPROC3_READ (Read From File)
			 procedure, as a percentage of the total NFS
			 calls received, since the last time the
			 statistics were cleared."
	::= { v3Percent 7 }

	v3pWrites                       OBJECT-TYPE
	SYNTAX                          Integer32 (0..100)
        MAX-ACCESS                      read-only
        STATUS                          current
	DESCRIPTION
			"The number of NFS Version 3 calls received
			 for the NFSPROC3_WRITE (Write to File)
			 procedure, as a percentage of the total NFS
			 calls received, since the last time the
			 statistics were cleared."
	::= { v3Percent 8 }

	v3pCreates                      OBJECT-TYPE
	SYNTAX                          Integer32 (0..100)
        MAX-ACCESS                      read-only
        STATUS                          current
	DESCRIPTION
			"The number of NFS Version 3 calls received
			 for the NFSPROC3_CREATE (Create a File)
			 procedure, as a percentage of the total NFS
			 calls received, since the last time the
			 statistics were cleared."
	::= { v3Percent 9 }

	v3pMkdirs                       OBJECT-TYPE
	SYNTAX                          Integer32 (0..100)
        MAX-ACCESS                      read-only
        STATUS                          current
	DESCRIPTION
			"The number of NFS Version 3 calls received
			 for the NFSPROC3_MKDIR (Create a Directory)
			 procedure, as a percentage of the total NFS
			 calls received, since the last time the
			 statistics were cleared."
	::= { v3Percent 10 }

	v3pSymlinks                     OBJECT-TYPE
	SYNTAX                          Integer32 (0..100)
        MAX-ACCESS                      read-only
        STATUS                          current
	DESCRIPTION
			"The number of NFS Version 3 calls received
			 for the NFSPROC3_SYMLINK (Create a Symbolic
			 Link) procedure, as a percentage of the total
			 NFS calls received, since the last time the
			 statistics were cleared."
	::= { v3Percent 11 }

	v3pMknods                       OBJECT-TYPE
	SYNTAX                          Integer32 (0..100)
        MAX-ACCESS                      read-only
        STATUS                          current
	DESCRIPTION
			"The number of NFS Version 3 calls received
			 for the NFSPROC3_MKNOD (Create a Special
			 Device) procedure, as a percentage of the
			 total NFS calls received, since the last
			 time the statistics were cleared."
	::= { v3Percent 12 }

	v3pRemoves                      OBJECT-TYPE
	SYNTAX                          Integer32 (0..100)
        MAX-ACCESS                      read-only
        STATUS                          current
	DESCRIPTION
			"The number of NFS Version 3 calls received
			 for the NFSPROC3_REMOVE (Remove a File)
			 procedure, as a percentage of the total NFS
			 calls received, since the last time the
			 statistics were cleared."
	::= { v3Percent 13 }

	v3pRmdirs                       OBJECT-TYPE
	SYNTAX                          Integer32 (0..100)
        MAX-ACCESS                      read-only
        STATUS                          current
	DESCRIPTION
			"The number of NFS Version 3 calls received
			 for the NFSPROC3_RMDIR (Remove a Directory)
			 procedure, as a percentage of the total NFS
			 calls received, since the last time the
			 statistics were cleared."
	::= { v3Percent 14 }

	v3pRenames                      OBJECT-TYPE
	SYNTAX                          Integer32 (0..100)
        MAX-ACCESS                      read-only
        STATUS                          current
	DESCRIPTION
			"The number of NFS Version 3 calls received
			 for the NFSPROC3_RENAME (Rename a File or
			 Directory) procedure, as a percentage of
			 the total NFS calls received, since the
			 last time the statistics were cleared."
	::= { v3Percent 15 }

	v3pLinks                        OBJECT-TYPE
	SYNTAX                          Integer32 (0..100)
        MAX-ACCESS                      read-only
        STATUS                          current
	DESCRIPTION
			"The number of NFS Version 3 calls received
			 for the NFSPROC3_LINK (Create Link to an
			 Object) procedure, as a percentage of
			 the total NFS calls received, since the
			 last time the statistics were cleared."
	::= { v3Percent 16 }

	v3pReaddirs                     OBJECT-TYPE
	SYNTAX                          Integer32 (0..100)
        MAX-ACCESS                      read-only
        STATUS                          current
	DESCRIPTION
			"The number of NFS Version 3 calls received
			 for the NFSPROC3_READDIR (Read From Directory)
			 procedure, as a percentage of the total NFS
			 calls received, since the last time the
			 statistics were cleared."
	::= { v3Percent 17 }

	v3pReaddirPluss                 OBJECT-TYPE
	SYNTAX                          Integer32 (0..100)
        MAX-ACCESS                      read-only
        STATUS                          current
	DESCRIPTION
			"The number of NFS Version 3 calls received
			 for the NFSPROC3_READDIRPLUS (Extended Read
			 from Directory) procedure, as a percentage
			 of the total NFS calls received, since the
			 last time the statistics were cleared."
	::= { v3Percent 18 }

	v3pFsstats                      OBJECT-TYPE
	SYNTAX                          Integer32 (0..100)
        MAX-ACCESS                      read-only
        STATUS                          current
	DESCRIPTION
			"The number of NFS Version 3 calls received
			 for the NFSPROC3_FSSTAT (Get Dynamic File
			 System Information) procedure, as a percentage
			 of the total NFS calls received, since the
			 last time the statistics were cleared."
	::= { v3Percent 19 }

	v3pFsinfos                      OBJECT-TYPE
	SYNTAX                          Integer32 (0..100)
        MAX-ACCESS                      read-only
        STATUS                          current
	DESCRIPTION
			"The number of NFS Version 3 calls received
			 for the NFSPROC3_FSINFO (Get Static File System
			 Information) procedure, as a percentage of the
			 total NFS calls received, since the last time
			 the statistics were cleared."
	::= { v3Percent 20 }

	v3pPathconfs                    OBJECT-TYPE
	SYNTAX                          Integer32 (0..100)
        MAX-ACCESS                      read-only
        STATUS                          current
	DESCRIPTION
			"The number of NFS Version 3 calls received
			 for the NFSPROC3_PATHCONF (Retrieve POSIX
			 Information) procedure, as a percentage of the
			 total NFS calls received, since the last time
			 the statistics were cleared."
	::= { v3Percent 21 }

	v3pCommits                      OBJECT-TYPE
	SYNTAX                          Integer32 (0..100)
        MAX-ACCESS                      read-only
        STATUS                          current
	DESCRIPTION
			"The number of NFS Version 3 calls received
			 for the NFSPROC3_COMMIT (Commit Cached Data on
			 a Server to Stable Storage) procedure, as a
			 percentage of the total NFS calls received,
			 since the last time the statistics were cleared."
	::= { v3Percent 22 }



	-- the v3CachedCalls group

		-- this group contains statistics for the number of
		-- calls received for each NFS Version 3 procedure,
		-- that did not result in the filesystem blocking to
		-- read from disk, since the last time the statistics
		-- were cleared

	v3ccNulls                       OBJECT-TYPE
	SYNTAX                          Counter32
        MAX-ACCESS                      read-only
        STATUS                          current
	DESCRIPTION
			"The number of NFS Version 3 calls received
			 for the NFSPROC3_NULL (Do Nothing) procedure,
			 that did not result in the filesystem
			 blocking to read from disk, since the last
			 time the statistics were cleared."
	::= { v3CachedCalls 1 }

	v3ccGetattrs                    OBJECT-TYPE
	SYNTAX                          Counter32
        MAX-ACCESS                      read-only
        STATUS                          current
	DESCRIPTION
			"The number of NFS Version 3 calls received
			 for the NFSPROC3_GETATTR (Get File Attributes)
			 procedure, that did not result in the filesystem
			 blocking to read from disk, since the last
			 time the statistics were cleared."
	::= { v3CachedCalls 2 }

	v3ccSetattrs                    OBJECT-TYPE
	SYNTAX                          Counter32
        MAX-ACCESS                      read-only
        STATUS                          current
	DESCRIPTION
			"The number of NFS Version 3 calls received
			 for the NFSPROC3_SETATTR (Set File Attributes)
			 procedure, that did not result in the filesystem
			 blocking to read from disk, since the last
			 time the statistics were cleared."
	::= { v3CachedCalls 3 }

	v3ccLookups                     OBJECT-TYPE
	SYNTAX                          Counter32
        MAX-ACCESS                      read-only
        STATUS                          current
	DESCRIPTION
			"The number of NFS Version 3 calls received
			 for the NFSPROC3_LOOKUP (Lookup Filename)
			 procedure, that did not result in the filesystem
			 blocking to read from disk, since the last
			 time the statistics were cleared."
	::= { v3CachedCalls 4 }

	v3ccAccesss                     OBJECT-TYPE
	SYNTAX                          Counter32
        MAX-ACCESS                      read-only
        STATUS                          current
	DESCRIPTION
			"The number of NFS Version 3 calls received
			 for the NFSPROC3_ACCESS (Check Access Permission)
			 procedure, that did not result in the filesystem
			 blocking to read from disk, since the last
			 time the statistics were cleared."
	::= { v3CachedCalls 5 }

	v3ccReadlinks                   OBJECT-TYPE
	SYNTAX                          Counter32
        MAX-ACCESS                      read-only
        STATUS                          current
	DESCRIPTION
			"The number of NFS Version 3 calls received
			 for the NFSPROC3_READLINK (Read from Symbolic
			 Link) procedure, that did not result in the
			 filesystem blocking to read from disk, since
			 the last time the statistics were cleared."
	::= { v3CachedCalls 6 }

	v3ccReads                       OBJECT-TYPE
	SYNTAX                          Counter32
        MAX-ACCESS                      read-only
        STATUS                          current
	DESCRIPTION
			"The number of NFS Version 3 calls received
			 for the NFSPROC3_READ (Read From File)
			 procedure, that did not result in the filesystem
			 blocking to read from disk, since the last
			 time the statistics were cleared."
	::= { v3CachedCalls 7 }

	v3ccWrites                      OBJECT-TYPE
	SYNTAX                          Counter32
        MAX-ACCESS                      read-only
        STATUS                          current
	DESCRIPTION
			"The number of NFS Version 3 calls received
			 for the NFSPROC3_WRITE (Write to File)
			 procedure, that did not result in the filesystem
			 blocking to read from disk, since the last
			 time the statistics were cleared."
	::= { v3CachedCalls 8 }

	v3ccCreates                     OBJECT-TYPE
	SYNTAX                          Counter32
        MAX-ACCESS                      read-only
        STATUS                          current
	DESCRIPTION
			"The number of NFS Version 3 calls received
			 for the NFSPROC3_CREATE (Create a File)
			 procedure, that did not result in the filesystem
			 blocking to read from disk, since the last
			 time the statistics were cleared."
	::= { v3CachedCalls 9 }

	v3ccMkdirs                      OBJECT-TYPE
	SYNTAX                          Counter32
        MAX-ACCESS                      read-only
        STATUS                          current
	DESCRIPTION
			"The number of NFS Version 3 calls received
			 for the NFSPROC3_MKDIR (Create a Directory)
			 procedure, that did not result in the filesystem
			 blocking to read from disk, since the last
			 time the statistics were cleared."
	::= { v3CachedCalls 10 }

	v3ccSymlinks                    OBJECT-TYPE
	SYNTAX                          Counter32
        MAX-ACCESS                      read-only
        STATUS                          current
	DESCRIPTION
			"The number of NFS Version 3 calls received
			 for the NFSPROC3_SYMLINK (Create a Symbolic
			 Link) procedure, that did not result in the
			 filesystem blocking to read from disk, since
			 the last time the statistics were cleared."
	::= { v3CachedCalls 11 }

	v3ccMknods                      OBJECT-TYPE
	SYNTAX                          Counter32
        MAX-ACCESS                      read-only
        STATUS                          current
	DESCRIPTION
			"The number of NFS Version 3 calls received
			 for the NFSPROC3_MKNOD (Create a Special
			 Device) procedure, that did not result in the
			 filesystem blocking to read from disk, since
			 the last time the statistics were cleared."
	::= { v3CachedCalls 12 }

	v3ccRemoves                     OBJECT-TYPE
	SYNTAX                          Counter32
        MAX-ACCESS                      read-only
        STATUS                          current
	DESCRIPTION
			"The number of NFS Version 3 calls received
			 for the NFSPROC3_REMOVE (Remove a File)
			 procedure, that did not result in the
			 filesystem blocking to read from disk, since
			 the last time the statistics were cleared."
	::= { v3CachedCalls 13 }

	v3ccRmdirs                      OBJECT-TYPE
	SYNTAX                          Counter32
        MAX-ACCESS                      read-only
        STATUS                          current
	DESCRIPTION
			"The number of NFS Version 3 calls received
			 for the NFSPROC3_RMDIR (Remove a Directory)
			 procedure, that did not result in the
			 filesystem blocking to read from disk, since
			 the last time the statistics were cleared."
	::= { v3CachedCalls 14 }

	v3ccRenames                     OBJECT-TYPE
	SYNTAX                          Counter32
        MAX-ACCESS                      read-only
        STATUS                          current
	DESCRIPTION
			"The number of NFS Version 3 calls received
			 for the NFSPROC3_RENAME (Rename a File or
			 Directory) procedure, that did not result in
			 the filesystem blocking to read from disk, since
			 the last time the statistics were cleared."
	::= { v3CachedCalls 15 }

	v3ccLinks                       OBJECT-TYPE
	SYNTAX                          Counter32
        MAX-ACCESS                      read-only
        STATUS                          current
	DESCRIPTION
			"The number of NFS Version 3 calls received
			 for the NFSPROC3_LINK (Create Link to an
			 Object) procedure, that did not result in
			 the filesystem blocking to read from disk, since
			 the last time the statistics were cleared."
	::= { v3CachedCalls 16 }

	v3ccReaddirs                    OBJECT-TYPE
	SYNTAX                          Counter32
        MAX-ACCESS                      read-only
        STATUS                          current
	DESCRIPTION
			"The number of NFS Version 3 calls received
			 for the NFSPROC3_READDIR (Read From
			 Directory) procedure, that did not result in
			 the filesystem blocking to read from disk, since
			 the last time the statistics were cleared."
	::= { v3CachedCalls 17 }

	v3ccReaddirPluss                OBJECT-TYPE
	SYNTAX                          Counter32
        MAX-ACCESS                      read-only
        STATUS                          current
	DESCRIPTION
			"The number of NFS Version 3 calls received
			 for the NFSPROC3_READDIRPLUS (Extended Read
			 from Directory) procedure, that did not result in
			 the filesystem blocking to read from disk, since
			 the last time the statistics were cleared."
	::= { v3CachedCalls 18 }

	v3ccFsstats                     OBJECT-TYPE
	SYNTAX                          Counter32
        MAX-ACCESS                      read-only
        STATUS                          current
	DESCRIPTION
			"The number of NFS Version 3 calls received
			 for the NFSPROC3_FSSTAT (Get Dynamic File
			 System Information) procedure, that did not
			 result in the filesystem blocking to read
			 from disk, since the last time the statistics
			 were cleared."
	::= { v3CachedCalls 19 }

	v3ccFsinfos                     OBJECT-TYPE
	SYNTAX                          Counter32
        MAX-ACCESS                      read-only
        STATUS                          current
	DESCRIPTION
			"The number of NFS Version 3 calls received
			 for the NFSPROC3_FSINFO (Get Static File
			 System Information) procedure, that did not
			 result in the filesystem blocking to read
			 from disk, since the last time the statistics
			 were cleared."
	::= { v3CachedCalls 20 }

	v3ccPathconfs                   OBJECT-TYPE
	SYNTAX                          Counter32
        MAX-ACCESS                      read-only
        STATUS                          current
	DESCRIPTION
			"The number of NFS Version 3 calls received
			 for the NFSPROC3_PATHCONF (Retrieve POSIX
			 Information) procedure, that did not result
			 in the filesystem blocking to read from disk,
			 since the last time the statistics were cleared."
	::= { v3CachedCalls 21 }

	v3ccCommits                     OBJECT-TYPE
	SYNTAX                          Counter32
        MAX-ACCESS                      read-only
        STATUS                          current
	DESCRIPTION
			"The number of NFS Version 3 calls received
			 for the NFSPROC3_COMMIT (Commit Cached Data on
			 a Server to Stable Storage) procedure, that did
			 not result in the filesystem blocking to read
			 from disk, since the last time the statistics
			 were cleared."
	::= { v3CachedCalls 22 }



	-- the v3CachedPerCent group

		-- this group contains statistics for the number of
		-- calls received for each NFS Version 3 procedure,
		-- that did not result in the filesystem blocking to
		-- read from disk, as a percentage of the total
		-- number of calls received for that procedure,
		-- since the last time the statistics were cleared

	v3cpNulls                       OBJECT-TYPE
	SYNTAX                          Integer32 (0..100)
        MAX-ACCESS                      read-only
        STATUS                          current
	DESCRIPTION
			"The number of NFS Version 3 calls received
			 for the NFSPROC3_NULL (Do Nothing) procedure,
			 that did not result in the filesystem
			 blocking to read from disk, as a percentage
			 of the total number of calls received for
			 this procedure, since the last time the
			 statistics were cleared."
	::= { v3CachedPerCent 1 }

	v3cpGetattrs                    OBJECT-TYPE
	SYNTAX                          Integer32 (0..100)
        MAX-ACCESS                      read-only
        STATUS                          current
	DESCRIPTION
			"The number of NFS Version 3 calls received
			 for the NFSPROC3_GETATTR (Get File Attributes)
			 procedure, that did not result in the filesystem
			 blocking to read from disk, as a percentage
			 of the total number of calls received for
			 this procedure, since the last time the
			 statistics were cleared."
	::= { v3CachedPerCent 2 }

	v3cpSetattrs                    OBJECT-TYPE
	SYNTAX                          Integer32 (0..100)
        MAX-ACCESS                      read-only
        STATUS                          current
	DESCRIPTION
			"The number of NFS Version 3 calls received
			 for the NFSPROC3_SETATTR (Set File Attributes)
			 procedure, that did not result in the filesystem
			 blocking to read from disk, as a percentage
			 of the total number of calls received for
			 this procedure, since the last time the
			 statistics were cleared."
	::= { v3CachedPerCent 3 }

	v3cpLookups                     OBJECT-TYPE
	SYNTAX                          Integer32 (0..100)
        MAX-ACCESS                      read-only
        STATUS                          current
	DESCRIPTION
			"The number of NFS Version 3 calls received
			 for the NFSPROC3_LOOKUP (Lookup Filename)
			 procedure, that did not result in the filesystem
			 blocking to read from disk, as a percentage
			 of the total number of calls received for
			 this procedure, since the last time the
			 statistics were cleared."
	::= { v3CachedPerCent 4 }

	v3cpAccesss                     OBJECT-TYPE
	SYNTAX                          Integer32 (0..100)
        MAX-ACCESS                      read-only
        STATUS                          current
	DESCRIPTION
			"The number of NFS Version 3 calls received
			 for the NFSPROC3_ACCESS (Check Access Permission)
			 procedure, that did not result in the filesystem
			 blocking to read from disk, as a percentage
			 of the total number of calls received for
			 this procedure, since the last time the
			 statistics were cleared."
	::= { v3CachedPerCent 5 }

	v3cpReadlinks                   OBJECT-TYPE
	SYNTAX                          Integer32 (0..100)
        MAX-ACCESS                      read-only
        STATUS                          current
	DESCRIPTION
			"The number of NFS Version 3 calls received
			 for the NFSPROC3_READLINK (Read from Symbolic
			 Link) procedure, that did not result in the
			 filesystem blocking to read from disk, as a
			 percentage of the total number of calls
			 received for this procedure, since the last
			 time the statistics were cleared."
	::= { v3CachedPerCent 6 }

	v3cpReads                       OBJECT-TYPE
	SYNTAX                          Integer32 (0..100)
        MAX-ACCESS                      read-only
        STATUS                          current
	DESCRIPTION
			"The number of NFS Version 3 calls received
			 for the NFSPROC3_READ (Read From File)
			 procedure, that did not result in the
			 filesystem blocking to read from disk, as a
			 percentage of the total number of calls
			 received for this procedure, since the last
			 time the statistics were cleared."
	::= { v3CachedPerCent 7 }

	v3cpWrites                      OBJECT-TYPE
	SYNTAX                          Integer32 (0..100)
        MAX-ACCESS                      read-only
        STATUS                          current
	DESCRIPTION
			"The number of NFS Version 3 calls received
			 for the NFSPROC3_WRITE (Write to File)
			 procedure, that did not result in the
			 filesystem blocking to read from disk, as a
			 percentage of the total number of calls
			 received for this procedure, since the last
			 time the statistics were cleared."
	::= { v3CachedPerCent 8 }

	v3cpCreates                     OBJECT-TYPE
	SYNTAX                          Integer32 (0..100)
        MAX-ACCESS                      read-only
        STATUS                          current
	DESCRIPTION
			"The number of NFS Version 3 calls received
			 for the NFSPROC3_CREATE (Create a File)
			 procedure, that did not result in the
			 filesystem blocking to read from disk, as a
			 percentage of the total number of calls
			 received for this procedure, since the last
			 time the statistics were cleared."
	::= { v3CachedPerCent 9 }

	v3cpMkdirs                      OBJECT-TYPE
	SYNTAX                          Integer32 (0..100)
        MAX-ACCESS                      read-only
        STATUS                          current
	DESCRIPTION
			"The number of NFS Version 3 calls received
			 for the NFSPROC3_MKDIR (Create a Directory)
			 procedure, that did not result in the
			 filesystem blocking to read from disk, as a
			 percentage of the total number of calls
			 received for this procedure, since the last
			 time the statistics were cleared."
	::= { v3CachedPerCent 10 }

	v3cpSymlinks                    OBJECT-TYPE
	SYNTAX                          Integer32 (0..100)
        MAX-ACCESS                      read-only
        STATUS                          current
	DESCRIPTION
			"The number of NFS Version 3 calls received
			 for the NFSPROC3_SYMLINK (Create a Symbolic
			 Link) procedure, that did not result in the
			 filesystem blocking to read from disk, as a
			 percentage of the total number of calls
			 received for this procedure, since the last
			 time the statistics were cleared."
	::= { v3CachedPerCent 11 }

	v3cpMknods                      OBJECT-TYPE
	SYNTAX                          Integer32 (0..100)
        MAX-ACCESS                      read-only
        STATUS                          current
	DESCRIPTION
			"The number of NFS Version 3 calls received
			 for the NFSPROC3_MKNOD (Create a Special
			 Device) procedure, that did not result in the
			 filesystem blocking to read from disk, as a
			 percentage of the total number of calls
			 received for this procedure, since the last
			 time the statistics were cleared."
	::= { v3CachedPerCent 12 }

	v3cpRemoves                     OBJECT-TYPE
	SYNTAX                          Integer32 (0..100)
        MAX-ACCESS                      read-only
        STATUS                          current
	DESCRIPTION
			"The number of NFS Version 3 calls received
			 for the NFSPROC3_REMOVE (Remove a File)
			 procedure, that did not result in the
			 filesystem blocking to read from disk, as a
			 percentage of the total number of calls
			 received for this procedure, since the last
			 time the statistics were cleared."
	::= { v3CachedPerCent 13 }

	v3cpRmdirs                      OBJECT-TYPE
	SYNTAX                          Integer32 (0..100)
        MAX-ACCESS                      read-only
        STATUS                          current
	DESCRIPTION
			"The number of NFS Version 3 calls received
			 for the NFSPROC3_RMDIR (Remove a Directory)
			 procedure, that did not result in the
			 filesystem blocking to read from disk, as a
			 percentage of the total number of calls
			 received for this procedure, since the last
			 time the statistics were cleared."
	::= { v3CachedPerCent 14 }

	v3cpRenames                     OBJECT-TYPE
	SYNTAX                          Integer32 (0..100)
        MAX-ACCESS                      read-only
        STATUS                          current
	DESCRIPTION
			"The number of NFS Version 3 calls received
			 for the NFSPROC3_RENAME (Rename a File or
			 Directory) procedure, that did not result in
			 the filesystem blocking to read from disk,
			 as a percentage of the total number of calls
			 received for this procedure, since the last
			 time the statistics were cleared."
	::= { v3CachedPerCent 15 }

	v3cpLinks                       OBJECT-TYPE
	SYNTAX                          Integer32 (0..100)
        MAX-ACCESS                      read-only
        STATUS                          current
	DESCRIPTION
			"The number of NFS Version 3 calls received
			 for the NFSPROC3_LINK (Create Link to an
			 Object) procedure, that did not result in
			 the filesystem blocking to read from disk,
			 as a percentage of the total number of calls
			 received for this procedure, since the last
			 time the statistics were cleared."
	::= { v3CachedPerCent 16 }

	v3cpReaddirs                    OBJECT-TYPE
	SYNTAX                          Integer32 (0..100)
        MAX-ACCESS                      read-only
        STATUS                          current
	DESCRIPTION
			"The number of NFS Version 3 calls received
			 for the NFSPROC3_READDIR (Read From Directory)
			 procedure, that did not result in the
			 filesystem blocking to read from disk, as a
			 percentage of the total number of calls
			 received for this procedure, since the last
			 time the statistics were cleared."
	::= { v3CachedPerCent 17 }

	v3cpReaddirPluss                OBJECT-TYPE
	SYNTAX                          Integer32 (0..100)
        MAX-ACCESS                      read-only
        STATUS                          current
	DESCRIPTION
			"The number of NFS Version 3 calls received
			 for the NFSPROC3_READDIRPLUS (Extended Read
			 from Directory) procedure, that did not result
			 in the filesystem blocking to read from disk,
			 as a percentage of the total number of calls
			 received for this procedure, since the last
			 time the statistics were cleared."
	::= { v3CachedPerCent 18 }

	v3cpFsstats                     OBJECT-TYPE
	SYNTAX                          Integer32 (0..100)
        MAX-ACCESS                      read-only
        STATUS                          current
	DESCRIPTION
			"The number of NFS Version 3 calls received
			 for the NFSPROC3_FSSTAT (Get Dynamic File
			 System Information) procedure, that did not
			 result in the filesystem blocking to read from
			 disk, as a percentage of the total number of
			 calls received for this procedure, since the
			 last time the statistics were cleared."
	::= { v3CachedPerCent 19 }

	v3cpFsinfos                     OBJECT-TYPE
	SYNTAX                          Integer32 (0..100)
        MAX-ACCESS                      read-only
        STATUS                          current
	DESCRIPTION
			"The number of NFS Version 3 calls received
			 for the NFSPROC3_FSINFO (Get Static File System
			 Information) procedure, that did not result
			 in the filesystem blocking to read from disk,
			 as a percentage of the total number of calls
			 received for this procedure, since the last
			 time the statistics were cleared."
	::= { v3CachedPerCent 20 }

	v3cpPathconfs                   OBJECT-TYPE
	SYNTAX                          Integer32 (0..100)
        MAX-ACCESS                      read-only
        STATUS                          current
	DESCRIPTION
			"The number of NFS Version 3 calls received
			 for the NFSPROC3_PATHCONF (Retrieve POSIX
			 Information) procedure, that did not result
			 in the filesystem blocking to read from disk,
			 as a percentage of the total number of calls
			 received for this procedure, since the last
			 time the statistics were cleared."
	::= { v3CachedPerCent 21 }

	v3cpCommits                     OBJECT-TYPE
	SYNTAX                          Integer32 (0..100)
        MAX-ACCESS                      read-only
        STATUS                          current
	DESCRIPTION
			"The number of NFS Version 3 calls received
			 for the NFSPROC3_COMMIT (Commit Cached Data on
			 a Server to Stable Storage) procedure, that
			 did not result in the filesystem blocking to
			 read from disk, as a percentage of the total
			 number of calls received for this procedure,
			 since the last time the statistics were cleared."
	::= { v3CachedPerCent 22 }



	-- the replyCache group

		-- this group contains statistics related to the
		-- Reply Cache processing, since the last time the
		-- statistics were cleared

	rcInProgressHits                OBJECT-TYPE
	SYNTAX                          Counter32
        MAX-ACCESS                      read-only
        STATUS                          current
	DESCRIPTION
			"The number of NFS requests that were dropped,
			 for calls already in progress, since the last
			 time the statistics were cleared."
	::= { replyCache 1 }

	rcDelayHits                     OBJECT-TYPE
	SYNTAX                          Counter32
        MAX-ACCESS                      read-only
        STATUS                          deprecated
	DESCRIPTION
			"The number of NFS requests that were dropped,
			 for replies already generated within a short
			 interval, since the last time the statistics
			 were cleared. These stats are deprecated.
			 A value of zero will always be returned
			 for these stats."
	::= { replyCache 2 }

	rcMisses                        OBJECT-TYPE
	SYNTAX                          Counter32
        MAX-ACCESS                      read-only
        STATUS                          current
	DESCRIPTION
			"The number of NFS requests received for which
			 there were no corresponding entries already in
			 the Reply Cache, since the last time the
			 statistics were cleared."
	::= { replyCache 3 }

	rcNonIdemDoneHits               OBJECT-TYPE
	SYNTAX                          Counter32
        MAX-ACCESS                      read-only
        STATUS                          current
	DESCRIPTION
			"The number of NFS requests received that
			 resulted in replies being replayed from
			 the Reply Cache, since the last time the
			 statistics were cleared."
	::= { replyCache 4 }

	rcNonIdemNotDoneHits            OBJECT-TYPE
	SYNTAX                          Counter32
        MAX-ACCESS                      read-only
        STATUS                          current
	DESCRIPTION
			"The number of NFS requests received for calls
			 that resulted in this request being processed
			 as a new request even when a corresponding
			 entry existed in the Reply Cache, since the
			 last time the statistics were cleared."
	::= { replyCache 5 }

	rcTcpInProgressHits             OBJECT-TYPE
	SYNTAX                          Counter32
        MAX-ACCESS                      read-only
        STATUS                          current
	DESCRIPTION
			"The number of NFS requests that were dropped
			 for the TCP protocol, for calls already in
			 progress, since the last time the statistics
			 were cleared."
	::= { replyCache 6 }

	rcTcpDelayHits                  OBJECT-TYPE
	SYNTAX                          Counter32
        MAX-ACCESS                      read-only
        STATUS                          deprecated
	DESCRIPTION
			"The number of NFS requests that were dropped
			 for the TCP protocol, for replies already
			 generated within a short interval, since the
			 last time the statistics were cleared. These
			 stats are deprecated. A value of zero will
			 always be returned for these stats."
	::= { replyCache 7 }

	rcTcpMisses                     OBJECT-TYPE
	SYNTAX                          Counter32
        MAX-ACCESS                      read-only
        STATUS                          current
	DESCRIPTION
			"The number of NFS requests received for the
			 TCP protocol for which there were no
			 corresponding entries already in the Reply
			 Cache, since the last time the statistics
			 were cleared."
	::= { replyCache 8 }

	rcTcpNonIdemDoneHits            OBJECT-TYPE
	SYNTAX                          Counter32
        MAX-ACCESS                      read-only
        STATUS                          current
	DESCRIPTION
			"The number of NFS requests received for the
			 TCP protocol that resulted in replies being
			 replayed from the Reply Cache, since the last
			 time the statistics were cleared."
	::= { replyCache 9 }

	rcTcpNonIdemNotDoneHits         OBJECT-TYPE
	SYNTAX                          Counter32
        MAX-ACCESS                      read-only
        STATUS                          current
	DESCRIPTION
			"The number of NFS requests received for the
			 TCP protocol for calls that resulted in this
			 request being processed as a new request even
			 when a corresponding entry existed in the Reply
			 Cache, since the last time the statistics were
			 cleared."
	::= { replyCache 10 }

	rcUdpInProgressHits             OBJECT-TYPE
	SYNTAX                          Counter32
        MAX-ACCESS                      read-only
        STATUS                          current
	DESCRIPTION
			"The number of NFS requests that were dropped
			 for the UDP protocol, for calls already in
			 progress, since the last time the statistics
			 were cleared."
	::= { replyCache 11 }

	rcUdpDelayHits                  OBJECT-TYPE
	SYNTAX                          Counter32
        MAX-ACCESS                      read-only
        STATUS                          deprecated
	DESCRIPTION
			"The number of NFS requests that were dropped
			 for the UDP protocol, for replies already
			 generated within a short interval, since the
			 last time the statistics were cleared. These
			 stats are deprecated. A value of zero will
			 always be returned for these stats."
	::= { replyCache 12 }

	rcUdpMisses                     OBJECT-TYPE
	SYNTAX                          Counter32
        MAX-ACCESS                      read-only
        STATUS                          current
	DESCRIPTION
			"The number of NFS requests received for the
			 UDP protocol for which there were no
			 corresponding entries already in the Reply
			 Cache, since the last time the statistics
			 were cleared."
	::= { replyCache 13 }

	rcUdpNonIdemDoneHits            OBJECT-TYPE
	SYNTAX                          Counter32
        MAX-ACCESS                      read-only
        STATUS                          current
	DESCRIPTION
			"The number of NFS requests received for the
			 UDP protocol that resulted in replies being
			 replayed from the Reply Cache, since the last
			 time the statistics were cleared."
	::= { replyCache 14 }

	rcUdpNonIdemNotDoneHits         OBJECT-TYPE
	SYNTAX                          Counter32
        MAX-ACCESS                      read-only
        STATUS                          current
	DESCRIPTION
			"The number of NFS requests received for the
			 UDP protocol for calls that resulted in this
			 request being processed as a new request even
			 when a corresponding entry existed in the Reply
			 Cache, since the last time the statistics were
			 cleared."
	::= { replyCache 15 }

	-- the nfsrwStats group

		-- this group contains statistics for the sizes of
                -- NFS version 2 and 3 read and write calls made
		-- since the last time the stats were zeroed.

	v2ReadStats            OBJECT IDENTIFIER ::= { nfsrwStats 1 }

	v2WriteStats           OBJECT IDENTIFIER ::= { nfsrwStats 2 }

        v3ReadStats            OBJECT IDENTIFIER ::= { nfsrwStats 3 }

        v3WriteStats           OBJECT IDENTIFIER ::= { nfsrwStats 4 }


	-- v2ReadStats group

		-- this group contains statistics for the sizes of
		-- NFS version 2 read calls since they were last
		-- zeroed.

	v2Read512Calls                  OBJECT-TYPE
	SYNTAX                          Counter32
        MAX-ACCESS                      read-only
        STATUS                          current
        DESCRIPTION
                        "The number of NFS Version 2 read calls
			received by the server since last zeroing
                        with request sizes between 0-511 bytes."
        ::= { v2ReadStats 1 }

        v2Read1KCalls                   OBJECT-TYPE
	SYNTAX                          Counter32
        MAX-ACCESS                      read-only
        STATUS                          current
        DESCRIPTION
                        "The number of NFS Version 2 read calls
			received by the server since last zeroing
                        with request sizes between 512-1023 bytes."
        ::= { v2ReadStats 2 }

        v2Read2KCalls                   OBJECT-TYPE
	SYNTAX                          Counter32
        MAX-ACCESS                      read-only
        STATUS                          current
        DESCRIPTION
                        "The number of NFS Version 2 read calls
			received by the server since last zeroing
                        with request sizes between 1K-2047 bytes."
	::= { v2ReadStats 3 }

        v2Read4KCalls                   OBJECT-TYPE
	SYNTAX                          Counter32
        MAX-ACCESS                      read-only
        STATUS                          current
        DESCRIPTION
                        "The number of NFS Version 2 read calls
			received by the server since last zeroing
                        with request sizes between 2K-4095 bytes."
        ::= { v2ReadStats 4 }

        v2Read8KCalls                   OBJECT-TYPE
	SYNTAX                          Counter32
        MAX-ACCESS                      read-only
        STATUS                          current
        DESCRIPTION
                        "The number of NFS Version 2 read calls
			received by the server since last zeroing
                        with request sizes between 4K-8191 bytes."
        ::= { v2ReadStats 5 }

        v2Read16KCalls                  OBJECT-TYPE
	SYNTAX                          Counter32
        MAX-ACCESS                      read-only
        STATUS                          current
        DESCRIPTION
                        "The number of NFS Version 2 read calls
			received by the server since last zeroing
                        with request sizes between 8K-16383 bytes."
        ::= { v2ReadStats 6 }

        v2Read32KCalls                  OBJECT-TYPE
	SYNTAX                          Counter32
        MAX-ACCESS                      read-only
        STATUS                          current
        DESCRIPTION
                        "The number of NFS Version 2 read calls
			received by the server since last zeroing
                        with request sizes between 16K-32767 bytes."
        ::= { v2ReadStats 7 }

	v2Read64KCalls                  OBJECT-TYPE
	SYNTAX                          Counter32
        MAX-ACCESS                      read-only
        STATUS                          current
        DESCRIPTION
                        "The number of NFS Version 2 read calls
			received by the server since last zeroing
                        with request sizes between 32K-65535 bytes."
        ::= { v2ReadStats 8 }

        v2Read128KCalls                 OBJECT-TYPE
	SYNTAX                          Counter32
        MAX-ACCESS                      read-only
        STATUS                          current
        DESCRIPTION
                        "The number of NFS Version 2 read calls
			received by the server since last zeroing
                        with request sizes between 64K-131071 bytes."
        ::= { v2ReadStats 9 }


        -- the v2WriteStats group

                -- this group contains statistics for the sizes of
                -- NFS version 2 write calls since they were last
		-- zeroed.

        v2Write512Calls                 OBJECT-TYPE
	SYNTAX                          Counter32
        MAX-ACCESS                      read-only
        STATUS                          current
        DESCRIPTION
                        "The number of NFS Version 2 write calls
			received by the server since last zeroing
                        with request sizes between 0-511 bytes."
        ::= { v2WriteStats 1 }

	v2Write1KCalls                  OBJECT-TYPE
	SYNTAX                          Counter32
        MAX-ACCESS                      read-only
        STATUS                          current
        DESCRIPTION
                        "The number of NFS Version 2 write calls
			received by the server since last zeroing
                        with request sizes between 512-1023 bytes."
        ::= { v2WriteStats 2 }

        v2Write2KCalls                  OBJECT-TYPE
	SYNTAX                          Counter32
        MAX-ACCESS                      read-only
        STATUS                          current
        DESCRIPTION
                        "The number of NFS Version 2 write calls
			received by the server since last zeroing
                        with request sizes between 1K-2047 bytes."
        ::= { v2WriteStats 3 }

        v2Write4KCalls                  OBJECT-TYPE
	SYNTAX                          Counter32
        MAX-ACCESS                      read-only
        STATUS                          current
        DESCRIPTION
                        "The number of NFS Version 2 write calls
			received by the server since last zeroing
                        with request sizes between 2K-4095 bytes."
        ::= { v2WriteStats 4 }

        v2Write8KCalls                  OBJECT-TYPE
	SYNTAX                          Counter32
        MAX-ACCESS                      read-only
        STATUS                          current
        DESCRIPTION
                        "The number of NFS Version 2 write calls
			received by the server since last zeroing
                        with request sizes between 4K-8191 bytes."
        ::= { v2WriteStats 5 }

	v2Write16KCalls                 OBJECT-TYPE
	SYNTAX                          Counter32
        MAX-ACCESS                      read-only
        STATUS                          current
        DESCRIPTION
                        "The number of NFS Version 2 write calls
			received by the server since last zeroing
                        with request sizes between 8K-16383 bytes."
        ::= { v2WriteStats 6 }

        v2Write32KCalls                 OBJECT-TYPE
	SYNTAX                          Counter32
        MAX-ACCESS                      read-only
        STATUS                          current
        DESCRIPTION
                        "The number of NFS Version 2 write calls
			received by the server since last zeroing
                        with request sizes between 16K-32767 bytes."
        ::= { v2WriteStats 7 }

        v2Write64KCalls                 OBJECT-TYPE
	SYNTAX                          Counter32
        MAX-ACCESS                      read-only
        STATUS                          current
        DESCRIPTION
                        "The number of NFS Version 2 write calls
			received by the server since last zeroing
                        with request sizes between 32K-65535 bytes."
        ::= { v2WriteStats 8 }

        v2Write128KCalls                OBJECT-TYPE
	SYNTAX                          Counter32
        MAX-ACCESS                      read-only
        STATUS                          current
        DESCRIPTION
                        "The number of NFS Version 2 write calls
			received by the server since last zeroing
                        with request sizes between 64K-131071 bytes."
        ::= { v2WriteStats 9 }


	-- the v3ReadStats group

                -- this group contains statistics for the sizes of
                -- NFS version 3 read calls since they were last
		-- zeroed.

        v3Read512Calls                  OBJECT-TYPE
	SYNTAX                          Counter32
        MAX-ACCESS                      read-only
        STATUS                          current
        DESCRIPTION
                        "The number of NFS Version 3 read calls
			received by the server since last boot
                        with request sizes between 0-511 bytes."
        ::= { v3ReadStats 1 }

        v3Read1KCalls                   OBJECT-TYPE
	SYNTAX                          Counter32
        MAX-ACCESS                      read-only
        STATUS                          current
        DESCRIPTION
                        "The number of NFS Version 3 read calls
			received by the server since last zeroing
                        with request sizes between 512-1023 bytes."
        ::= { v3ReadStats 2 }

        v3Read2KCalls                   OBJECT-TYPE
	SYNTAX                          Counter32
        MAX-ACCESS                      read-only
        STATUS                          current
        DESCRIPTION
                        "The number of NFS Version 3 read calls
			received by the server since last zeroing
                        with request sizes between 1K-2047 bytes."
        ::= { v3ReadStats 3 }

	v3Read4KCalls                   OBJECT-TYPE
	SYNTAX                          Counter32
        MAX-ACCESS                      read-only
        STATUS                          current
        DESCRIPTION
                        "The number of NFS Version 3 read calls
			received by the server since last zeroing
                        with request sizes between 2K-4095 bytes."
        ::= { v3ReadStats 4 }

        v3Read8KCalls                   OBJECT-TYPE
	SYNTAX                          Counter32
        MAX-ACCESS                      read-only
        STATUS                          current
        DESCRIPTION
                        "The number of NFS Version 3 read calls
			received by the server since last zeroing
                        with request sizes between 4K-8191 bytes."
        ::= { v3ReadStats 5 }

        v3Read16KCalls                  OBJECT-TYPE
	SYNTAX                          Counter32
        MAX-ACCESS                      read-only
        STATUS                          current
        DESCRIPTION
                        "The number of NFS Version 3 read calls
			received by the server since last zeroing
                        with request sizes between 8K-16383 bytes."
        ::= { v3ReadStats 6 }

        v3Read32KCalls                  OBJECT-TYPE
	SYNTAX                          Counter32
        MAX-ACCESS                      read-only
        STATUS                          current
        DESCRIPTION
                        "The number of NFS Version 3 read calls
			received by the server since last zeroing
                        with request sizes between 16K-32767 bytes."
        ::= { v3ReadStats 7 }

	v3Read64KCalls                  OBJECT-TYPE
	SYNTAX                          Counter32
        MAX-ACCESS                      read-only
        STATUS                          current
        DESCRIPTION
                        "The number of NFS Version 3 read calls
			received by the server since last zeroing
                        with request sizes between 32K-65535 bytes."
        ::= { v3ReadStats 8 }

        v3Read128KCalls                 OBJECT-TYPE
	SYNTAX                          Counter32
        MAX-ACCESS                      read-only
        STATUS                          current
        DESCRIPTION
                        "The number of NFS Version 3 read calls
			received by the server since last zeroing
                        with request sizes between 64K-131071 bytes."
        ::= { v3ReadStats 9 }


        -- the v3WriteStats group

                -- this group contains statistics for the sizes of
                -- NFS version 3 write calls since they were last
		-- zeroed.

        v3Write512Calls                 OBJECT-TYPE
	SYNTAX                          Counter32
        MAX-ACCESS                      read-only
        STATUS                          current
        DESCRIPTION
                        "The number of NFS Version 3 write calls
			received by the server since last zeroing
                        with request sizes between 0-511 bytes."
        ::= { v3WriteStats 1 }

	v3Write1KCalls                  OBJECT-TYPE
	SYNTAX                          Counter32
        MAX-ACCESS                      read-only
        STATUS                          current
        DESCRIPTION
                        "The number of NFS Version 3 write calls
			received by the server since last zeroing
                        with request sizes between 512-1023 bytes."
        ::= { v3WriteStats 2 }

        v3Write2KCalls                  OBJECT-TYPE
	SYNTAX                          Counter32
        MAX-ACCESS                      read-only
        STATUS                          current
        DESCRIPTION
                        "The number of NFS Version 3 write calls
			received by the server since last zeroing
                        with request sizes between 1K-2047 bytes."
        ::= { v3WriteStats 3 }

        v3Write4KCalls                  OBJECT-TYPE
	SYNTAX                          Counter32
        MAX-ACCESS                      read-only
        STATUS                          current
        DESCRIPTION
                        "The number of NFS Version 3 write calls
			received by the server since last zeroing
                        with request sizes between 2K-4095 bytes."
        ::= { v3WriteStats 4 }

        v3Write8KCalls                  OBJECT-TYPE
	SYNTAX                          Counter32
        MAX-ACCESS                      read-only
        STATUS                          current
        DESCRIPTION
                        "The number of NFS Version 3 write calls
			received by the server since last zeroing
                        with request sizes between 4K-8191 bytes."
        ::= { v3WriteStats 5 }

	v3Write16KCalls                 OBJECT-TYPE
	SYNTAX                          Counter32
        MAX-ACCESS                      read-only
        STATUS                          current
        DESCRIPTION
                        "The number of NFS Version 3 write calls
			received by the server since last zeroing
                        with request sizes between 8K-16383 bytes."
        ::= { v3WriteStats 6 }

        v3Write32KCalls                 OBJECT-TYPE
	SYNTAX                          Counter32
        MAX-ACCESS                      read-only
        STATUS                          current
        DESCRIPTION
                        "The number of NFS Version 3 write calls
			received by the server since last zeroing
                        with request sizes between 16K-32767 bytes."
        ::= { v3WriteStats 7 }

        v3Write64KCalls                 OBJECT-TYPE
	SYNTAX                          Counter32
        MAX-ACCESS                      read-only
        STATUS                          current
        DESCRIPTION
                        "The number of NFS Version 3 write calls
			received by the server since last zeroing
                        with request sizes between 32K-65535 bytes."
        ::= { v3WriteStats 8 }

        v3Write128KCalls                OBJECT-TYPE
	SYNTAX                          Counter32
        MAX-ACCESS                      read-only
        STATUS                          current
        DESCRIPTION
                        "The number of NFS Version 3 write calls
			received by the server since last zeroing
                        with request sizes between 64K-131071 bytes."
        ::= { v3WriteStats 9 }


	-- the per-client nfs statistics table

	pclTable                        OBJECT-TYPE
	SYNTAX                          SEQUENCE OF PclEntry
        MAX-ACCESS                      not-accessible
        STATUS                          current
	DESCRIPTION
			"Provide a report of per-client NFS statistics
			 since the last time the statistics were cleared."
	::= { nfsPerClient 1 }

	pclEntry                        OBJECT-TYPE
	SYNTAX                          PclEntry
        MAX-ACCESS                      not-accessible
        STATUS                          current
	DESCRIPTION
			"Provide a report of NFS statistics for the
			 referenced NFS client since the last time the
			 statistics were cleared."
	INDEX	{ pclIpAddr }
	::= { pclTable 1 }

	PclEntry ::=
	    SEQUENCE {
		pclIpAddr
		    IpAddress,
		pclRpcCalls
		    Counter32,
		pclRpcBadCalls
		    Counter32,
		pclRpcNullRecvs
		    Counter32,
		pclRpcBadLens
		    Counter32,
		pclRpcServXDRCalls
		    Counter32,
		pclNfsCalls
		    Counter32,
		pclNfsServBadCalls
		    Counter32,
		pclNfsV2Nulls
		    Counter32,
		pclNfsV2Getattrs
		    Counter32,
		pclNfsV2Setattrs
		    Counter32,
		pclNfsV2Roots
		    Counter32,
		pclNfsV2Lookups
		    Counter32,
		pclNfsV2Readlinks
		    Counter32,
		pclNfsV2Reads
		    Counter32,
		pclNfsV2Wrcaches
		    Counter32,
		pclNfsV2Writes
		    Counter32,
		pclNfsV2Creates
		    Counter32,
		pclNfsV2Removes
		    Counter32,
		pclNfsV2Renames
		    Counter32,
		pclNfsV2Links
		    Counter32,
		pclNfsV2Symlinks
		    Counter32,
		pclNfsV2Mkdirs
		    Counter32,
		pclNfsV2Rmdirs
		    Counter32,
		pclNfsV2Readdirs
		    Counter32,
		pclNfsV2Statfss
		    Counter32,
		pclNfsV3Nulls
		    Counter32,
		pclNfsV3Getattrs
		    Counter32,
		pclNfsV3Setattrs
		    Counter32,
		pclNfsV3Lookups
		    Counter32,
		pclNfsV3Accesss
		    Counter32,
		pclNfsV3Readlinks
		    Counter32,
		pclNfsV3Reads
		    Counter32,
		pclNfsV3Writes
		    Counter32,
		pclNfsV3Creates
		    Counter32,
		pclNfsV3Mkdirs
		    Counter32,
		pclNfsV3Symlinks
		    Counter32,
		pclNfsV3Mknods
		    Counter32,
		pclNfsV3Removes
		    Counter32,
		pclNfsV3Rmdirs
		    Counter32,
		pclNfsV3Renames
		    Counter32,
		pclNfsV3Links
		    Counter32,
		pclNfsV3Readdirs
		    Counter32,
		pclNfsV3ReaddirPluss
		    Counter32,
		pclNfsV3Fsstats
		    Counter32,
		pclNfsV3Fsinfos
		    Counter32,
		pclNfsV3Pathconfs
		    Counter32,
		pclNfsV3Commits
		    Counter32,
		pclPerCent
		    Integer32,
		pclNfsV2NullPerCent
		    Integer32,
		pclNfsV2GetattrPerCent
		    Integer32,
		pclNfsV2SetattrPerCent
		    Integer32,
		pclNfsV2RootPerCent
		    Integer32,
		pclNfsV2LookupPerCent
		    Integer32,
		pclNfsV2ReadlinkPerCent
		    Integer32,
		pclNfsV2ReadPerCent
		    Integer32,
		pclNfsV2WrcachePerCent
		    Integer32,
		pclNfsV2WritePerCent
		    Integer32,
		pclNfsV2CreatePerCent
		    Integer32,
		pclNfsV2RemovePerCent
		    Integer32,
		pclNfsV2RenamePerCent
		    Integer32,
		pclNfsV2LinkPerCent
		    Integer32,
		pclNfsV2SymlinkPerCent
		    Integer32,
		pclNfsV2MkdirPerCent
		    Integer32,
		pclNfsV2RmdirPerCent
		    Integer32,
		pclNfsV2ReaddirPerCent
		    Integer32,
		pclNfsV2StatfsPerCent
		    Integer32,
		pclNfsV3NullPerCent
		    Integer32,
		pclNfsV3GetattrPerCent
		    Integer32,
		pclNfsV3SetattrPerCent
		    Integer32,
		pclNfsV3LookupPerCent
		    Integer32,
		pclNfsV3AccessPerCent
		    Integer32,
		pclNfsV3ReadlinkPerCent
		    Integer32,
		pclNfsV3ReadPerCent
		    Integer32,
		pclNfsV3WritePerCent
		    Integer32,
		pclNfsV3CreatePerCent
		    Integer32,
		pclNfsV3MkdirPerCent
		    Integer32,
		pclNfsV3SymlinkPerCent
		    Integer32,
		pclNfsV3MknodPerCent
		    Integer32,
		pclNfsV3RemovePerCent
		    Integer32,
		pclNfsV3RmdirPerCent
		    Integer32,
		pclNfsV3RenamePerCent
		    Integer32,
		pclNfsV3LinkPerCent
		    Integer32,
		pclNfsV3ReaddirPerCent
		    Integer32,
		pclNfsV3ReaddirPlusPerCent
		    Integer32,
		pclNfsV3FsstatPerCent
		    Integer32,
		pclNfsV3FsinfoPerCent
		    Integer32,
		pclNfsV3PathconfPerCent
		    Integer32,
		pclNfsV3CommitPerCent
		    Integer32,
		pclNfsV2Read512Calls
		    Counter32,
		pclNfsV2Read1KCalls
		    Counter32,
		pclNfsV2Read2KCalls
		    Counter32,
		pclNfsV2Read4KCalls
		    Counter32,
		pclNfsV2Read8KCalls
		    Counter32,
		pclNfsV2Read16KCalls
		    Counter32,
		pclNfsV2Read32KCalls
		    Counter32,
		pclNfsV2Read64KCalls
		    Counter32,
		pclNfsV2Read128KCalls
		    Counter32,
		pclNfsV2Write512Calls
		    Counter32,
		pclNfsV2Write1KCalls
		    Counter32,
		pclNfsV2Write2KCalls
		    Counter32,
		pclNfsV2Write4KCalls
		    Counter32,
		pclNfsV2Write8KCalls
		    Counter32,
		pclNfsV2Write16KCalls
		    Counter32,
		pclNfsV2Write32KCalls
		    Counter32,
		pclNfsV2Write64KCalls
		    Counter32,
		pclNfsV2Write128KCalls
		    Counter32,
		pclNfsV3Read512Calls
		    Counter32,
		pclNfsV3Read1KCalls
		    Counter32,
		pclNfsV3Read2KCalls
		    Counter32,
		pclNfsV3Read4KCalls
		    Counter32,
		pclNfsV3Read8KCalls
		    Counter32,
		pclNfsV3Read16KCalls
		    Counter32,
		pclNfsV3Read32KCalls
		    Counter32,
		pclNfsV3Read64KCalls
		    Counter32,
		pclNfsV3Read128KCalls
		    Counter32,
		pclNfsV3Write512Calls
		    Counter32,
		pclNfsV3Write1KCalls
		    Counter32,
		pclNfsV3Write2KCalls
		    Counter32,
		pclNfsV3Write4KCalls
		    Counter32,
		pclNfsV3Write8KCalls
		    Counter32,
		pclNfsV3Write16KCalls
		    Counter32,
		pclNfsV3Write32KCalls
		    Counter32,
		pclNfsV3Write64KCalls
		    Counter32,
		pclNfsV3Write128KCalls
		    Counter32
	    }

	pclIpAddr                       OBJECT-TYPE
	SYNTAX                          IpAddress
        MAX-ACCESS                      read-only
        STATUS                          current
	DESCRIPTION
			"The IP address of the referenced client."
	::= { pclEntry 1 }

	pclRpcCalls                     OBJECT-TYPE
	SYNTAX                          Counter32
        MAX-ACCESS                      read-only
        STATUS                          current
	DESCRIPTION
			"The total number of RPC calls received from
			 the referenced client, since the last time the
			 statistics were cleared."
	::= { pclEntry 2 }

	pclRpcBadCalls                  OBJECT-TYPE
	SYNTAX                          Counter32
        MAX-ACCESS                      read-only
        STATUS                          current
	DESCRIPTION
			"The total number of calls received from the
			 referenced client that were rejected by the
			 RPC layer, since the last time the
			 statistics were cleared."
	::= { pclEntry 3 }

	pclRpcNullRecvs                 OBJECT-TYPE
	SYNTAX                          Counter32
        MAX-ACCESS                      read-only
        STATUS                          current
	DESCRIPTION
			"The number of times an RPC call was not available
			 when it was thought to be received from
			 referenced client, since the last time the
			 statistics were cleared."
	::= { pclEntry 4 }

	pclRpcBadLens                   OBJECT-TYPE
	SYNTAX                          Counter32
        MAX-ACCESS                      read-only
        STATUS                          current
	DESCRIPTION
			"The number of RPC calls received from the
			 referenced client with a length shorter
			 than a minimum-sized RPC call, since the
			 last time the statistics were cleared."
	::= { pclEntry 5 }

	pclRpcServXDRCalls              OBJECT-TYPE
	SYNTAX                          Counter32
        MAX-ACCESS                      read-only
        STATUS                          current
	DESCRIPTION
			   "The number of RPC calls received from the
			    referenced client whose header could not
			    be XDR decoded, since the last time the
			    statistics were cleared."
	::= { pclEntry 6 }

	pclNfsCalls                     OBJECT-TYPE
	SYNTAX                          Counter32
        MAX-ACCESS                      read-only
        STATUS                          current
	DESCRIPTION
			   "The total number of NFS calls received from
			    the referenced client, since the last time
			    the statistics were cleared."
	::= { pclEntry 7 }

	pclNfsServBadCalls              OBJECT-TYPE
	SYNTAX                          Counter32
        MAX-ACCESS                      read-only
        STATUS                          current
	DESCRIPTION
			   "The total number of NFS calls received from
			    the referenced client that were rejected, since
			    the last time the statistics were cleared."
	::= { pclEntry 8 }

	pclNfsV2Nulls                   OBJECT-TYPE
	SYNTAX                          Counter32
        MAX-ACCESS                      read-only
        STATUS                          current
	DESCRIPTION
			"The number of NFS Version 2 calls received
			 from the referenced client for the NFSPROC_NULL
			 (Do Nothing) procedure, since the last time the
			 statistics were cleared."
	::= { pclEntry 9 }

	pclNfsV2Getattrs                OBJECT-TYPE
	SYNTAX                          Counter32
        MAX-ACCESS                      read-only
        STATUS                          current
	DESCRIPTION
			"The number of NFS Version 2 calls received
			 from the referenced client for the NFSPROC_GETATTR
			 (Get File Attributes) procedure, since the last
			 time the statistics were cleared."
	::= { pclEntry 10 }

	pclNfsV2Setattrs                OBJECT-TYPE
	SYNTAX                          Counter32
        MAX-ACCESS                      read-only
        STATUS                          current
	DESCRIPTION
			"The number of NFS Version 2 calls received
			 from the referenced client for the NFSPROC_SETATTR
			 (Set File Attributes) procedure, since the last
			 time the statistics were cleared."
	::= { pclEntry 11 }

	pclNfsV2Roots                   OBJECT-TYPE
	SYNTAX                          Counter32
        MAX-ACCESS                      read-only
        STATUS                          current
	DESCRIPTION
			"The number of NFS Version 2 calls received
			 from the referenced client for the NFSPROC_ROOT
			 (Get Filesystem Root) procedure, since the last
			 time the statistics were cleared."
	::= { pclEntry 12 }

	pclNfsV2Lookups                 OBJECT-TYPE
	SYNTAX                          Counter32
        MAX-ACCESS                      read-only
        STATUS                          current
	DESCRIPTION
			"The number of NFS Version 2 calls received
			 from the referenced client for the NFSPROC_LOOKUP
			 (Look Up File Name) procedure, since the last
			 time the statistics were cleared."
	::= { pclEntry 13 }

	pclNfsV2Readlinks               OBJECT-TYPE
	SYNTAX                          Counter32
        MAX-ACCESS                      read-only
        STATUS                          current
	DESCRIPTION
			 "The number of NFS Version 2 calls received
			  from the referenced client for the NFSPROC_READLINK
			  (Read From Symbolic Link) procedure, since the last
			  time the statistics were cleared."
	::= { pclEntry 14 }

	pclNfsV2Reads                   OBJECT-TYPE
	SYNTAX                          Counter32
        MAX-ACCESS                      read-only
        STATUS                          current
	DESCRIPTION
			"The number of NFS Version 2 calls received
			 from the referenced client for the NFSPROC_READ
			 (Read From File) procedure, since the last
			 time the statistics were cleared."
	::= { pclEntry 15 }

	pclNfsV2Wrcaches                OBJECT-TYPE
	SYNTAX                          Counter32
        MAX-ACCESS                      read-only
        STATUS                          current
	DESCRIPTION
			"The number of NFS Version 2 calls received
			 from the referenced client for the NFSPROC_WRITECACHE
			 (Write to Cache) procedure, since the last
			 time the statistics were cleared."
	::= { pclEntry 16 }

	pclNfsV2Writes                  OBJECT-TYPE
	SYNTAX                          Counter32
        MAX-ACCESS                      read-only
        STATUS                          current
	DESCRIPTION
			"The number of NFS Version 2 calls received
			 from the referenced client for the NFSPROC_WRITE
			 (Write to File) procedure, since the last
			 time the statistics were cleared."
	::= { pclEntry 17 }

	pclNfsV2Creates                 OBJECT-TYPE
	SYNTAX                          Counter32
        MAX-ACCESS                      read-only
        STATUS                          current
	DESCRIPTION
			"The number of NFS Version 2 calls received
			 from the referenced client for the NFSPROC_CREATE
			 (Create File) procedure, since the last
			 time the statistics were cleared."
	::= { pclEntry 18 }

	pclNfsV2Removes                 OBJECT-TYPE
	SYNTAX                          Counter32
        MAX-ACCESS                      read-only
        STATUS                          current
	DESCRIPTION
			"The number of NFS Version 2 calls received
			 from the referenced client for the NFSPROC_REMOVE
			 (Remove File) procedure, since the last
			 time the statistics were cleared."
	::= { pclEntry 19 }

	pclNfsV2Renames                 OBJECT-TYPE
	SYNTAX                          Counter32
        MAX-ACCESS                      read-only
        STATUS                          current
	DESCRIPTION
			"The number of NFS Version 2 calls received
			 from the referenced client for the NFSPROC_RENAME
			 (Rename File) procedure, since the last
			 time the statistics were cleared."
	::= { pclEntry 20 }

	pclNfsV2Links                   OBJECT-TYPE
	SYNTAX                          Counter32
        MAX-ACCESS                      read-only
        STATUS                          current
	DESCRIPTION
			"The number of NFS Version 2 calls received
			 from the referenced client for the NFSPROC_LINK
			 (Create Link to File) procedure, since the last
			 time the statistics were cleared."
	::= { pclEntry 21 }

	pclNfsV2Symlinks                OBJECT-TYPE
	SYNTAX                          Counter32
        MAX-ACCESS                      read-only
        STATUS                          current
	DESCRIPTION
			"The number of NFS Version 2 calls received
			 from the referenced client for the NFSPROC_SYMLINK
			 (Create Symbolic Link) procedure, since the last
			 time the statistics were cleared."
	::= { pclEntry 22 }

	pclNfsV2Mkdirs                  OBJECT-TYPE
	SYNTAX                          Counter32
        MAX-ACCESS                      read-only
        STATUS                          current
	DESCRIPTION
			"The number of NFS Version 2 calls received
			 from the referenced client for the NFSPROC_MKDIR
			 (Create Directory) procedure, since the last
			 time the statistics were cleared."
	::= { pclEntry 23 }

	pclNfsV2Rmdirs                  OBJECT-TYPE
	SYNTAX                          Counter32
        MAX-ACCESS                      read-only
        STATUS                          current
	DESCRIPTION
			"The number of NFS Version 2 calls received
			 from the referenced client for the NFSPROC_RMDIR
			 (Remove Directory) procedure, since the last
			 time the statistics were cleared."
	::= { pclEntry 24 }

	pclNfsV2Readdirs                OBJECT-TYPE
	SYNTAX                          Counter32
        MAX-ACCESS                      read-only
        STATUS                          current
	DESCRIPTION
			"The number of NFS Version 2 calls received
			 from the referenced client for the NFSPROC_READDIR
			 (Read From Directory) procedure, since the last
			 time the statistics were cleared."
	::= { pclEntry 25 }

	pclNfsV2Statfss                 OBJECT-TYPE
	SYNTAX                          Counter32
        MAX-ACCESS                      read-only
        STATUS                          current
	DESCRIPTION
			"The number of NFS Version 2 calls received
			 from the referenced client for the NFSPROC_STATFS
			 (Get Filesystem Attributes) procedure, since the
			 last time the statistics were cleared."
	::= { pclEntry 26 }

	pclNfsV3Nulls                   OBJECT-TYPE
	SYNTAX                          Counter32
        MAX-ACCESS                      read-only
        STATUS                          current
	DESCRIPTION
			"The number of NFS Version 3 calls received
			 from the referenced client for the NFSPROC3_NULL
			 (Do Nothing) procedure, since the last time the
			 statistics were cleared."
	::= { pclEntry 27 }

	pclNfsV3Getattrs                OBJECT-TYPE
	SYNTAX                          Counter32
        MAX-ACCESS                      read-only
        STATUS                          current
	DESCRIPTION
			"The number of NFS Version 3 calls received
			 from the referenced client for the NFSPROC3_GETATTR
			 (Get File Attributes) procedure, since the last
			 time the statistics were cleared."
	::= { pclEntry 28 }

	pclNfsV3Setattrs                OBJECT-TYPE
	SYNTAX                          Counter32
        MAX-ACCESS                      read-only
        STATUS                          current
	DESCRIPTION
			"The number of NFS Version 3 calls received
			 from the referenced client for the NFSPROC3_SETATTR
			 (Set File Attributes) procedure, since the last
			 time the statistics were cleared."
	::= { pclEntry 29 }

	pclNfsV3Lookups                 OBJECT-TYPE
	SYNTAX                          Counter32
        MAX-ACCESS                      read-only
        STATUS                          current
	DESCRIPTION
			"The number of NFS Version 3 calls received
			 from the referenced client for the NFSPROC3_LOOKUP
			 (Lookup Filename) procedure, since the last time
			 the statistics were cleared."
	::= { pclEntry 30 }

	pclNfsV3Accesss                 OBJECT-TYPE
	SYNTAX                          Counter32
        MAX-ACCESS                      read-only
        STATUS                          current
	DESCRIPTION
			"The number of NFS Version 3 calls received
			 from the referenced client for the NFSPROC3_ACCESS
			 (Check Access Permission) procedure, since the
			 last time the statistics were cleared."
	::= { pclEntry 31 }

	pclNfsV3Readlinks               OBJECT-TYPE
	SYNTAX                          Counter32
        MAX-ACCESS                      read-only
        STATUS                          current
	DESCRIPTION
			"The number of NFS Version 3 calls received
			 from the referenced client for the NFSPROC3_READLINK
			 (Read from Symbolic Link) procedure, since the
			 last time the statistics were cleared."
	::= { pclEntry 32 }

	pclNfsV3Reads                   OBJECT-TYPE
	SYNTAX                          Counter32
        MAX-ACCESS                      read-only
        STATUS                          current
	DESCRIPTION
			"The number of NFS Version 3 calls received
			 from the referenced client for the NFSPROC3_READ
			 (Read From File) procedure, since the last time
			 the statistics were cleared."
	::= { pclEntry 33 }

	pclNfsV3Writes                  OBJECT-TYPE
	SYNTAX                          Counter32
        MAX-ACCESS                      read-only
        STATUS                          current
	DESCRIPTION
			"The number of NFS Version 3 calls received
			 from the referenced client for the NFSPROC3_WRITE
			 (Write to File) procedure, since the last time
			 the statistics were cleared."
	::= { pclEntry 34 }

	pclNfsV3Creates                 OBJECT-TYPE
	SYNTAX                          Counter32
        MAX-ACCESS                      read-only
        STATUS                          current
	DESCRIPTION
			"The number of NFS Version 3 calls received
			 from the referenced client for the NFSPROC3_CREATE
			 (Create a File) procedure, since the last time
			 the statistics were cleared."
	::= { pclEntry 35 }

	pclNfsV3Mkdirs                  OBJECT-TYPE
	SYNTAX                          Counter32
        MAX-ACCESS                      read-only
        STATUS                          current
	DESCRIPTION
			"The number of NFS Version 3 calls received
			 from the referenced client for the NFSPROC3_MKDIR
			 (Create a Directory) procedure, since the last
			 time the statistics were cleared."
	::= { pclEntry 36 }

	pclNfsV3Symlinks                OBJECT-TYPE
	SYNTAX                          Counter32
        MAX-ACCESS                      read-only
        STATUS                          current
	DESCRIPTION
			"The number of NFS Version 3 calls received
			 from the referenced client for the NFSPROC3_SYMLINK
			 (Create a Symbolic Link) procedure, since the last
			 time the statistics were cleared."
	::= { pclEntry 37 }

	pclNfsV3Mknods                  OBJECT-TYPE
	SYNTAX                          Counter32
        MAX-ACCESS                      read-only
        STATUS                          current
	DESCRIPTION
			"The number of NFS Version 3 calls received
			 from the referenced client for the NFSPROC3_MKNOD
			 (Create a Special Device) procedure, since the
			 last time the statistics were cleared."
	::= { pclEntry 38 }

	pclNfsV3Removes                 OBJECT-TYPE
	SYNTAX                          Counter32
        MAX-ACCESS                      read-only
        STATUS                          current
	DESCRIPTION
			"The number of NFS Version 3 calls received
			 from the referenced client for the NFSPROC3_REMOVE
			 (Remove a File) procedure, since the last time
			 the statistics were cleared."
	::= { pclEntry 39 }

	pclNfsV3Rmdirs                  OBJECT-TYPE
	SYNTAX                          Counter32
        MAX-ACCESS                      read-only
        STATUS                          current
	DESCRIPTION
			"The number of NFS Version 3 calls received
			 from the referenced client for the NFSPROC3_RMDIR
			 (Remove a Directory) procedure, since the last
			 time the statistics were cleared."
	::= { pclEntry 40 }

	pclNfsV3Renames                 OBJECT-TYPE
	SYNTAX                          Counter32
        MAX-ACCESS                      read-only
        STATUS                          current
	DESCRIPTION
			"The number of NFS Version 3 calls received
			 from the referenced client for the NFSPROC3_RENAME
			 (Rename a File or Directory) procedure, since the
			 last time the statistics were cleared."
	::= { pclEntry 41 }

	pclNfsV3Links                   OBJECT-TYPE
	SYNTAX                          Counter32
        MAX-ACCESS                      read-only
        STATUS                          current
	DESCRIPTION
			"The number of NFS Version 3 calls received
			 from the referenced client for the NFSPROC3_LINK
			 (Create Link to an Object) procedure, since the
			 last time the statistics were cleared."
	::= { pclEntry 42 }

	pclNfsV3Readdirs                OBJECT-TYPE
	SYNTAX                          Counter32
        MAX-ACCESS                      read-only
        STATUS                          current
	DESCRIPTION
			"The number of NFS Version 3 calls received
			 from the referenced client for the NFSPROC3_READDIR
			 (Read From Directory) procedure, since the last
			 time the statistics were cleared."
	::= { pclEntry 43 }

	pclNfsV3ReaddirPluss            OBJECT-TYPE
	SYNTAX                          Counter32
        MAX-ACCESS                      read-only
        STATUS                          current
	DESCRIPTION
			     "The number of NFS Version 3 calls received
			      from the referenced client for the
			      NFSPROC3_READDIRPLUS (Extended Read from
			      Directory) procedure, since the last time
			      the statistics were cleared."
	::= { pclEntry 44 }

	pclNfsV3Fsstats                 OBJECT-TYPE
	SYNTAX                          Counter32
        MAX-ACCESS                      read-only
        STATUS                          current
	DESCRIPTION
			"The number of NFS Version 3 calls received
			 from the referenced client for the NFSPROC3_FSSTAT
			 (Get Dynamic File System Information) procedure,
			 since the last time the statistics were cleared."
	::= { pclEntry 45 }

	pclNfsV3Fsinfos                 OBJECT-TYPE
	SYNTAX                          Counter32
        MAX-ACCESS                      read-only
        STATUS                          current
	DESCRIPTION
			"The number of NFS Version 3 calls received
			 from the referenced client for the NFSPROC3_FSINFO
			 (Get Static File System Information) procedure,
			 since the last time the statistics were cleared."
	::= { pclEntry 46 }

	pclNfsV3Pathconfs               OBJECT-TYPE
	SYNTAX                          Counter32
        MAX-ACCESS                      read-only
        STATUS                          current
	DESCRIPTION
			  "The number of NFS Version 3 calls received
			   from the referenced client for the NFSPROC3_PATHCONF
			   (Retrieve POSIX Information) procedure, since the
			   last time the statistics were cleared."
	::= { pclEntry 47 }

	pclNfsV3Commits                 OBJECT-TYPE
	SYNTAX                          Counter32
        MAX-ACCESS                      read-only
        STATUS                          current
	DESCRIPTION
			"The number of NFS Version 3 calls received
			 from the referenced client for the NFSPROC3_COMMIT
			 (Commit Cached Data on a Server to Stable Storage)
			 procedure, since the last time the statistics were
			 cleared."
	::= { pclEntry 48 }

	pclPerCent                      OBJECT-TYPE
	SYNTAX                          Integer32 (0..100)
        MAX-ACCESS                      read-only
        STATUS                          current
	DESCRIPTION
				"The number of the total NFS calls for the
				 referenced client as a percentage of the
				 total NFS calls received from all
				 clients, since the last time the
				 statistics were cleared."
	::= { pclEntry 49 }

	pclNfsV2NullPerCent             OBJECT-TYPE
	SYNTAX                          Integer32 (0..100)
        MAX-ACCESS                      read-only
        STATUS                          current
	DESCRIPTION
				"The number of NFS Version 2 calls
				 received from the referenced client for
				 the NFSPROC_NULL (Do Nothing) procedure,
				 as a percentage of the total calls
				 received from this client, since the
				 last time the statistics were cleared."
	::= { pclEntry 50 }

	pclNfsV2GetattrPerCent          OBJECT-TYPE
	SYNTAX                          Integer32 (0..100)
        MAX-ACCESS                      read-only
        STATUS                          current
	DESCRIPTION
				"The number of NFS Version 2 calls
				 received from the referenced client for
				 the NFSPROC_GETATTR (Get File Attributes)
				 procedure, as a percentage of the total
				 calls received from this client, since
				 the last time the statistics were cleared."
	::= { pclEntry 51 }

	pclNfsV2SetattrPerCent          OBJECT-TYPE
	SYNTAX                          Integer32 (0..100)
        MAX-ACCESS                      read-only
        STATUS                          current
	DESCRIPTION
				"The number of NFS Version 2 calls
				 received from the referenced client for
				 the NFSPROC_SETATTR (Set File Attributes)
				 procedure, as a percentage of the total
				 calls received from this client, since
				 the last time the statistics were cleared."
	::= { pclEntry 52 }

	pclNfsV2RootPerCent             OBJECT-TYPE
	SYNTAX                          Integer32 (0..100)
        MAX-ACCESS                      read-only
        STATUS                          current
	DESCRIPTION
				"The number of NFS Version 2 calls
				 received from the referenced client for
				 the NFSPROC_ROOT (Get Filesystem Root)
				 procedure, as a percentage of the total
				 calls received from this client, since
				 the last time the statistics were cleared."
	::= { pclEntry 53 }

	pclNfsV2LookupPerCent           OBJECT-TYPE
	SYNTAX                          Integer32 (0..100)
        MAX-ACCESS                      read-only
        STATUS                          current
	DESCRIPTION
				"The number of NFS Version 2 calls
				 received from the referenced client for
				 the NFSPROC_LOOKUP (Look Up File Name)
				 procedure, as a percentage of the total
				 calls received from this client, since
				 the last time the statistics were cleared."
	::= { pclEntry 54 }

	pclNfsV2ReadlinkPerCent         OBJECT-TYPE
	SYNTAX                          Integer32 (0..100)
        MAX-ACCESS                      read-only
        STATUS                          current
	DESCRIPTION
				"The number of NFS Version 2 calls
				 received from the referenced client for
				 the NFSPROC_READLINK (Read From Symbolic
				 Link) procedure, as a percentage of the
				 total calls received from this client,
				 since the last time the statistics were
				 cleared."
	::= { pclEntry 55 }

	pclNfsV2ReadPerCent             OBJECT-TYPE
	SYNTAX                          Integer32 (0..100)
        MAX-ACCESS                      read-only
        STATUS                          current
	DESCRIPTION
				"The number of NFS Version 2 calls
				 received from the referenced client for
				 the NFSPROC_READ (Read From File)
				 procedure, as a percentage of the total
				 calls received from this client, since
				 the last time the statistics were cleared."
	::= { pclEntry 56 }

	pclNfsV2WrcachePerCent          OBJECT-TYPE
	SYNTAX                          Integer32 (0..100)
        MAX-ACCESS                      read-only
        STATUS                          current
	DESCRIPTION
				"The number of NFS Version 2 calls
				 received from the referenced client for
				 the NFSPROC_WRITECACHE (Write to Cache)
				 procedure, as a percentage of the total
				 calls received from this client, since
				 the last time the statistics were cleared."
	::= { pclEntry 57 }

	pclNfsV2WritePerCent            OBJECT-TYPE
	SYNTAX                          Integer32 (0..100)
        MAX-ACCESS                      read-only
        STATUS                          current
	DESCRIPTION
				"The number of NFS Version 2 calls
				 received from the referenced client for
				 the NFSPROC_WRITE (Write to File)
				 procedure, as a percentage of the total
				 calls received from this client, since
				 the last time the statistics were cleared."
	::= { pclEntry 58 }

	pclNfsV2CreatePerCent           OBJECT-TYPE
	SYNTAX                          Integer32 (0..100)
        MAX-ACCESS                      read-only
        STATUS                          current
	DESCRIPTION
				"The number of NFS Version 2 calls
				 received from the referenced client for
				 the NFSPROC_CREATE (Create File)
				 procedure, as a percentage of the total
				 calls received from this client, since
				 the last time the statistics were cleared."
	::= { pclEntry 59 }

	pclNfsV2RemovePerCent           OBJECT-TYPE
	SYNTAX                          Integer32 (0..100)
        MAX-ACCESS                      read-only
        STATUS                          current
	DESCRIPTION
				"The number of NFS Version 2 calls
				 received from the referenced client for
				 the NFSPROC_REMOVE (Remove File)
				 procedure, as a percentage of the total
				 calls received from this client, since
				 the last time the statistics were cleared."
	::= { pclEntry 60 }

	pclNfsV2RenamePerCent           OBJECT-TYPE
	SYNTAX                          Integer32 (0..100)
        MAX-ACCESS                      read-only
        STATUS                          current
	DESCRIPTION
				"The number of NFS Version 2 calls
				 received from the referenced client for
				 the NFSPROC_RENAME (Rename File)
				 procedure, as a percentage of the total
				 calls received from this client, since
				 the last time the statistics were cleared."
	::= { pclEntry 61 }

	pclNfsV2LinkPerCent             OBJECT-TYPE
	SYNTAX                          Integer32 (0..100)
        MAX-ACCESS                      read-only
        STATUS                          current
	DESCRIPTION
				"The number of NFS Version 2 calls
				 received from the referenced client for
				 the NFSPROC_LINK (Create Link to File)
				 procedure, as a percentage of the total
				 calls received from this client, since
				 the last time the statistics were cleared."
	::= { pclEntry 62 }

	pclNfsV2SymlinkPerCent          OBJECT-TYPE
	SYNTAX                          Integer32 (0..100)
        MAX-ACCESS                      read-only
        STATUS                          current
	DESCRIPTION
				"The number of NFS Version 2 calls
				 received from the referenced client for
				 the NFSPROC_SYMLINK (Create Symbolic Link)
				 procedure, as a percentage of the total
				 calls received from this client, since
				 the last time the statistics were cleared."
	::= { pclEntry 63 }

	pclNfsV2MkdirPerCent            OBJECT-TYPE
	SYNTAX                          Integer32 (0..100)
        MAX-ACCESS                      read-only
        STATUS                          current
	DESCRIPTION
				"The number of NFS Version 2 calls
				 received from the referenced client for
				 the NFSPROC_MKDIR (Create Directory)
				 procedure, as a percentage of the total
				 calls received from this client, since
				 the last time the statistics were cleared."
	::= { pclEntry 64 }

	pclNfsV2RmdirPerCent            OBJECT-TYPE
	SYNTAX                          Integer32 (0..100)
        MAX-ACCESS                      read-only
        STATUS                          current
	DESCRIPTION
				"The number of NFS Version 2 calls
				 received from the referenced client for
				 the NFSPROC_RMDIR (Remove Directory)
				 procedure, as a percentage of the total
				 calls received from this client, since
				 the last time the statistics were cleared."
	::= { pclEntry 65 }

	pclNfsV2ReaddirPerCent          OBJECT-TYPE
	SYNTAX                          Integer32 (0..100)
        MAX-ACCESS                      read-only
        STATUS                          current
	DESCRIPTION
				"The number of NFS Version 2 calls
				 received from the referenced client for
				 the NFSPROC_READDIR (Read From Directory)
				 procedure, as a percentage of the total
				 calls received from this client, since
				 the last time the statistics were cleared."
	::= { pclEntry 66 }

	pclNfsV2StatfsPerCent           OBJECT-TYPE
	SYNTAX                          Integer32 (0..100)
        MAX-ACCESS                      read-only
        STATUS                          current
	DESCRIPTION
				"The number of NFS Version 2 calls
				 received from the referenced client for
				 the NFSPROC_STATFS (Get Filesystem
				 Attributes) procedure, as a percentage
				 of the total calls received from this
				 client, since the last time the
				 statistics were cleared."
	::= { pclEntry 67 }

	pclNfsV3NullPerCent             OBJECT-TYPE
	SYNTAX                          Integer32 (0..100)
        MAX-ACCESS                      read-only
        STATUS                          current
	DESCRIPTION
				"The number of NFS Version 3 calls
				 received from the referenced client for
				 the NFSPROC3_NULL (Do Nothing)
				 procedure, as a percentage of the total
				 calls received from this client, since
				 the last time the statistics were cleared."
	::= { pclEntry 68 }

	pclNfsV3GetattrPerCent          OBJECT-TYPE
	SYNTAX                          Integer32 (0..100)
        MAX-ACCESS                      read-only
        STATUS                          current
	DESCRIPTION
				"The number of NFS Version 3 calls
				 received from the referenced client for
				 the NFSPROC3_GETATTR (Get File Attributes)
				 procedure, as a percentage of the total
				 calls received from this client, since
				 the last time the statistics were cleared."
	::= { pclEntry 69 }

	pclNfsV3SetattrPerCent          OBJECT-TYPE
	SYNTAX                          Integer32 (0..100)
        MAX-ACCESS                      read-only
        STATUS                          current
	DESCRIPTION
				"The number of NFS Version 3 calls
				 received from the referenced client for
				 the NFSPROC3_SETATTR (Set File Attributes)
				 procedure, as a percentage of the total
				 calls received from this client, since
				 the last time the statistics were cleared."
	::= { pclEntry 70 }

	pclNfsV3LookupPerCent           OBJECT-TYPE
	SYNTAX                          Integer32 (0..100)
        MAX-ACCESS                      read-only
        STATUS                          current
	DESCRIPTION
				"The number of NFS Version 3 calls
				 received from the referenced client for
				 the NFSPROC3_LOOKUP (Lookup Filename)
				 procedure, as a percentage of the total
				 calls received from this client, since
				 the last time the statistics were cleared."
	::= { pclEntry 71 }

	pclNfsV3AccessPerCent           OBJECT-TYPE
	SYNTAX                          Integer32 (0..100)
        MAX-ACCESS                      read-only
        STATUS                          current
	DESCRIPTION
				"The number of NFS Version 3 calls
				 received from the referenced client for
				 the NFSPROC3_ACCESS (Check Access Permission)
				 procedure, as a percentage of the total
				 calls received from this client, since
				 the last time the statistics were cleared."
	::= { pclEntry 72 }

	pclNfsV3ReadlinkPerCent         OBJECT-TYPE
	SYNTAX                          Integer32 (0..100)
        MAX-ACCESS                      read-only
        STATUS                          current
	DESCRIPTION
				"The number of NFS Version 3 calls
				 received from the referenced client for
				 the NFSPROC3_READLINK (Read from Symbolic
				 Link) procedure, as a percentage of the total
				 calls received from this client, since
				 the last time the statistics were cleared."
	::= { pclEntry 73 }

	pclNfsV3ReadPerCent             OBJECT-TYPE
	SYNTAX                          Integer32 (0..100)
        MAX-ACCESS                      read-only
        STATUS                          current
	DESCRIPTION
				"The number of NFS Version 3 calls
				 received from the referenced client for
				 the NFSPROC3_READ (Read From File)
				 procedure, as a percentage of the total
				 calls received from this client, since
				 the last time the statistics were cleared."
	::= { pclEntry 74 }

	pclNfsV3WritePerCent            OBJECT-TYPE
	SYNTAX                          Integer32 (0..100)
        MAX-ACCESS                      read-only
        STATUS                          current
	DESCRIPTION
				"The number of NFS Version 3 calls
				 received from the referenced client for
				 the NFSPROC3_WRITE (Write to File)
				 procedure, as a percentage of the total
				 calls received from this client, since
				 the last time the statistics were cleared."
	::= { pclEntry 75 }

	pclNfsV3CreatePerCent           OBJECT-TYPE
	SYNTAX                          Integer32 (0..100)
        MAX-ACCESS                      read-only
        STATUS                          current
	DESCRIPTION
				"The number of NFS Version 3 calls
				 received from the referenced client for
				 the NFSPROC3_CREATE (Create a File)
				 procedure, as a percentage of the total
				 calls received from this client, since
				 the last time the statistics were cleared."
	::= { pclEntry 76 }

	pclNfsV3MkdirPerCent            OBJECT-TYPE
	SYNTAX                          Integer32 (0..100)
        MAX-ACCESS                      read-only
        STATUS                          current
	DESCRIPTION
				"The number of NFS Version 3 calls
				 received from the referenced client for
				 the NFSPROC3_MKDIR (Create a Directory)
				 procedure, as a percentage of the total
				 calls received from this client, since
				 the last time the statistics were cleared."
	::= { pclEntry 77 }

	pclNfsV3SymlinkPerCent          OBJECT-TYPE
	SYNTAX                          Integer32 (0..100)
        MAX-ACCESS                      read-only
        STATUS                          current
	DESCRIPTION
				"The number of NFS Version 3 calls
				 received from the referenced client for
				 the NFSPROC3_SYMLINK (Create a Symbolic
				 Link) procedure, as a percentage of the
				 total calls received from this client, since
				 the last time the statistics were cleared."
	::= { pclEntry 78 }

	pclNfsV3MknodPerCent            OBJECT-TYPE
	SYNTAX                          Integer32 (0..100)
        MAX-ACCESS                      read-only
        STATUS                          current
	DESCRIPTION
				"The number of NFS Version 3 calls
				 received from the referenced client for
				 the NFSPROC3_MKNOD (Create a Special
				 Device) procedure, as a percentage of the
				 total calls received from this client, since
				 the last time the statistics were cleared."
	::= { pclEntry 79 }

	pclNfsV3RemovePerCent           OBJECT-TYPE
	SYNTAX                          Integer32 (0..100)
        MAX-ACCESS                      read-only
        STATUS                          current
	DESCRIPTION
				"The number of NFS Version 3 calls
				 received from the referenced client for
				 the NFSPROC3_REMOVE (Remove a File)
				 procedure, as a percentage of the total
				 calls received from this client, since
				 the last time the statistics were cleared."
	::= { pclEntry 80 }

	pclNfsV3RmdirPerCent            OBJECT-TYPE
	SYNTAX                          Integer32 (0..100)
        MAX-ACCESS                      read-only
        STATUS                          current
	DESCRIPTION
				"The number of NFS Version 3 calls
				 received from the referenced client for
				 the NFSPROC3_RMDIR (Remove a Directory)
				 procedure, as a percentage of the total
				 calls received from this client, since
				 the last time the statistics were cleared."
	::= { pclEntry 81 }

	pclNfsV3RenamePerCent           OBJECT-TYPE
	SYNTAX                          Integer32 (0..100)
        MAX-ACCESS                      read-only
        STATUS                          current
	DESCRIPTION
				"The number of NFS Version 3 calls
				 received from the referenced client for
				 the NFSPROC3_RENAME (Rename a File or
				 Directory) procedure, as a percentage of
				 the total calls received from this client,
				 since the last time the statistics were
				 cleared."
	::= { pclEntry 82 }

	pclNfsV3LinkPerCent             OBJECT-TYPE
	SYNTAX                          Integer32 (0..100)
        MAX-ACCESS                      read-only
        STATUS                          current
	DESCRIPTION
				"The number of NFS Version 3 calls
				 received from the referenced client for
				 the NFSPROC3_LINK (Create Link to an Object)
				 procedure, as a percentage of the total
				 calls received from this client, since
				 the last time the statistics were cleared."
	::= { pclEntry 83 }

	pclNfsV3ReaddirPerCent          OBJECT-TYPE
	SYNTAX                          Integer32 (0..100)
        MAX-ACCESS                      read-only
        STATUS                          current
	DESCRIPTION
				"The number of NFS Version 3 calls
				 received from the referenced client for
				 the NFSPROC3_READDIR (Read From Directory)
				 procedure, as a percentage of the total
				 calls received from this client, since
				 the last time the statistics were cleared."
	::= { pclEntry 84 }

	pclNfsV3ReaddirPlusPerCent      OBJECT-TYPE
	SYNTAX                          Integer32 (0..100)
        MAX-ACCESS                      read-only
        STATUS                          current
	DESCRIPTION
				"The number of NFS Version 3 calls
				 received from the referenced client for
				 the NFSPROC3_READDIRPLUS (Extended Read from
				 Directory) procedure, as a percentage of the
				 total calls received from this client, since
				 the last time the statistics were cleared."
	::= { pclEntry 85 }

	pclNfsV3FsstatPerCent           OBJECT-TYPE
	SYNTAX                          Integer32 (0..100)
        MAX-ACCESS                      read-only
        STATUS                          current
	DESCRIPTION
				"The number of NFS Version 3 calls
				 received from the referenced client for
				 the NFSPROC3_FSSTAT (Get Dynamic File
				 System Information) procedure, as a
				 percentage of the total calls received
				 from this client, since the last time
				 the statistics were cleared."
	::= { pclEntry 86 }

	pclNfsV3FsinfoPerCent           OBJECT-TYPE
	SYNTAX                          Integer32 (0..100)
        MAX-ACCESS                      read-only
        STATUS                          current
	DESCRIPTION
				"The number of NFS Version 3 calls
				 received from the referenced client for
				 the NFSPROC3_FSINFO (Get Static File System
				 Information) procedure, as a percentage of the
				 total calls received from this client, since
				 the last time the statistics were cleared."
	::= { pclEntry 87 }

	pclNfsV3PathconfPerCent         OBJECT-TYPE
	SYNTAX                          Integer32 (0..100)
        MAX-ACCESS                      read-only
        STATUS                          current
	DESCRIPTION
				"The number of NFS Version 3 calls
				 received from the referenced client for
				 the NFSPROC3_PATHCONF (Retrieve POSIX
				 Information) procedure, as a percentage of the
				 total calls received from this client, since
				 the last time the statistics were cleared."
	::= { pclEntry 88 }

	pclNfsV3CommitPerCent           OBJECT-TYPE
	SYNTAX                          Integer32 (0..100)
        MAX-ACCESS                      read-only
        STATUS                          current
	DESCRIPTION
				"The number of NFS Version 3 calls
				 received from the referenced client for
				 the NFSPROC3_COMMIT (Commit Cached Data on
				 a Server to Stable Storage) procedure, as
				 a percentage of the total calls received
				 from this client, since the last time the
				 statistics were cleared."
	::= { pclEntry 89 }

	pclNfsV2Read512Calls            OBJECT-TYPE
	SYNTAX                          Counter32
        MAX-ACCESS                      read-only
        STATUS                          current
	DESCRIPTION
				"The number of NFS Version 2 read calls
				with request sizes between 0-511 bytes
				received from this client."
	::= { pclEntry 90 }

	pclNfsV2Read1KCalls             OBJECT-TYPE
	SYNTAX                          Counter32
        MAX-ACCESS                      read-only
        STATUS                          current
	DESCRIPTION
				"The number of NFS Version 2 read calls
				with request sizes between 512-1023 bytes
				received from this client."
	::= { pclEntry 91 }

	pclNfsV2Read2KCalls             OBJECT-TYPE
	SYNTAX                          Counter32
        MAX-ACCESS                      read-only
        STATUS                          current
	DESCRIPTION
				"The number of NFS Version 2 read calls
				with request sizes between 1K-2047 bytes
				received from this client."
	::= { pclEntry 92 }

	pclNfsV2Read4KCalls             OBJECT-TYPE
	SYNTAX                          Counter32
        MAX-ACCESS                      read-only
        STATUS                          current
	DESCRIPTION
				"The number of NFS Version 2 read calls
				with request sizes between 2K-4095 bytes
				received from this client."
	::= { pclEntry 93 }

	pclNfsV2Read8KCalls             OBJECT-TYPE
	SYNTAX                          Counter32
        MAX-ACCESS                      read-only
        STATUS                          current
	DESCRIPTION
				"The number of NFS Version 2 read calls
				with request sizes between 4K-8191 bytes
				received from this client."
	::= { pclEntry 94 }

	pclNfsV2Read16KCalls            OBJECT-TYPE
	SYNTAX                          Counter32
        MAX-ACCESS                      read-only
        STATUS                          current
	DESCRIPTION
				"The number of NFS Version 2 read calls
				with request sizes between 8K-16383 bytes
				received from this client."
	::= { pclEntry 95 }

	pclNfsV2Read32KCalls            OBJECT-TYPE
	SYNTAX                          Counter32
        MAX-ACCESS                      read-only
        STATUS                          current
	DESCRIPTION
				"The number of NFS Version 2 read calls
				with request sizes between 16K-32767 bytes
				received from this client."
	::= { pclEntry 96 }

	pclNfsV2Read64KCalls            OBJECT-TYPE
	SYNTAX                          Counter32
        MAX-ACCESS                      read-only
        STATUS                          current
	DESCRIPTION
				"The number of NFS Version 2 read calls
				with request sizes between 32K-65535 bytes
				received from this client."
	::= { pclEntry 97 }

	pclNfsV2Read128KCalls           OBJECT-TYPE
	SYNTAX                          Counter32
        MAX-ACCESS                      read-only
        STATUS                          current
	DESCRIPTION
				"The number of NFS Version 2 read calls
				with request sizes between 64K-131071 bytes
				received from this client."
	::= { pclEntry 98 }

	pclNfsV2Write512Calls           OBJECT-TYPE
	SYNTAX                          Counter32
        MAX-ACCESS                      read-only
        STATUS                          current
	DESCRIPTION
				"The number of NFS Version 2 write calls
				with request sizes between 0-511 bytes
				received from this client."
	::= { pclEntry 99 }

	pclNfsV2Write1KCalls            OBJECT-TYPE
	SYNTAX                          Counter32
        MAX-ACCESS                      read-only
        STATUS                          current
	DESCRIPTION
				"The number of NFS Version 2 write calls
				with request sizes between 512-1023 bytes
				received from this client."
	::= { pclEntry 100 }

	pclNfsV2Write2KCalls            OBJECT-TYPE
	SYNTAX                          Counter32
        MAX-ACCESS                      read-only
        STATUS                          current
	DESCRIPTION
				"The number of NFS Version 2 write calls
				with request sizes between 1K-2047 bytes
				received from this client."
	::= { pclEntry 101 }

	pclNfsV2Write4KCalls            OBJECT-TYPE
	SYNTAX                          Counter32
        MAX-ACCESS                      read-only
        STATUS                          current
	DESCRIPTION
				"The number of NFS Version 2 write calls
				with request sizes between 2K-4095 bytes
				received from this client."
	::= { pclEntry 102 }

	pclNfsV2Write8KCalls            OBJECT-TYPE
	SYNTAX                          Counter32
        MAX-ACCESS                      read-only
        STATUS                          current
	DESCRIPTION
				"The number of NFS Version 2 write calls
				with request sizes between 4K-8191 bytes
				received from this client."
	::= { pclEntry 103 }

	pclNfsV2Write16KCalls           OBJECT-TYPE
	SYNTAX                          Counter32
        MAX-ACCESS                      read-only
        STATUS                          current
	DESCRIPTION
				"The number of NFS Version 2 write calls
				with request sizes between 8K-16383 bytes
				received from this client."
	::= { pclEntry 104 }

	pclNfsV2Write32KCalls           OBJECT-TYPE
	SYNTAX                          Counter32
        MAX-ACCESS                      read-only
        STATUS                          current
	DESCRIPTION
				"The number of NFS Version 2 write calls
				with request sizes between 16K-32767 bytes
				received from this client."
	::= { pclEntry 105 }

	pclNfsV2Write64KCalls           OBJECT-TYPE
	SYNTAX                          Counter32
        MAX-ACCESS                      read-only
        STATUS                          current
	DESCRIPTION
				"The number of NFS Version 2 write calls
				with request sizes between 32K-65535 bytes
				received from this client."
	::= { pclEntry 106 }

	pclNfsV2Write128KCalls          OBJECT-TYPE
	SYNTAX                          Counter32
        MAX-ACCESS                      read-only
        STATUS                          current
	DESCRIPTION
				"The number of NFS Version 2 write calls
				with request sizes between 64K-131071 bytes
				received from this client."
	::= { pclEntry 107 }

	pclNfsV3Read512Calls            OBJECT-TYPE
	SYNTAX                          Counter32
        MAX-ACCESS                      read-only
        STATUS                          current
	DESCRIPTION
				"The number of NFS Version 3 read calls
				with request sizes between 0-511 bytes
				received from this client."
	::= { pclEntry 108 }

	pclNfsV3Read1KCalls             OBJECT-TYPE
	SYNTAX                          Counter32
        MAX-ACCESS                      read-only
        STATUS                          current
	DESCRIPTION
				"The number of NFS Version 3 read calls
				with request sizes between 512-1023 bytes
				received from this client."
	::= { pclEntry 109 }

	pclNfsV3Read2KCalls             OBJECT-TYPE
	SYNTAX                          Counter32
        MAX-ACCESS                      read-only
        STATUS                          current
	DESCRIPTION
				"The number of NFS Version 3 read calls
				with request sizes between 1K-2047 bytes
				received from this client."
	::= { pclEntry 110 }

	pclNfsV3Read4KCalls             OBJECT-TYPE
	SYNTAX                          Counter32
        MAX-ACCESS                      read-only
        STATUS                          current
	DESCRIPTION
				"The number of NFS Version 3 read calls
				with request sizes between 2K-4095 bytes
				received from this client."
	::= { pclEntry 111 }

	pclNfsV3Read8KCalls             OBJECT-TYPE
	SYNTAX                          Counter32
        MAX-ACCESS                      read-only
        STATUS                          current
	DESCRIPTION
				"The number of NFS Version 3 read calls
				with request sizes between 4K-8191 bytes
				received from this client."
	::= { pclEntry 112 }

	pclNfsV3Read16KCalls            OBJECT-TYPE
	SYNTAX                          Counter32
        MAX-ACCESS                      read-only
        STATUS                          current
	DESCRIPTION
				"The number of NFS Version 3 read calls
				with request sizes between 8K-16383 bytes
				received from this client."
	::= { pclEntry 113 }

	pclNfsV3Read32KCalls            OBJECT-TYPE
	SYNTAX                          Counter32
        MAX-ACCESS                      read-only
        STATUS                          current
	DESCRIPTION
				"The number of NFS Version 3 read calls
				with request sizes between 16K-32767 bytes
				received from this client."
	::= { pclEntry 114 }

	pclNfsV3Read64KCalls            OBJECT-TYPE
	SYNTAX                          Counter32
        MAX-ACCESS                      read-only
        STATUS                          current
	DESCRIPTION
				"The number of NFS Version 3 read calls
				with request sizes between 32K-65535 bytes
				received from this client."
	::= { pclEntry 115 }

	pclNfsV3Read128KCalls           OBJECT-TYPE
	SYNTAX                          Counter32
        MAX-ACCESS                      read-only
        STATUS                          current
	DESCRIPTION
				"The number of NFS Version 3 read calls
				with request sizes between 64K-131071 bytes
				received from this client."
	::= { pclEntry 116 }

	pclNfsV3Write512Calls           OBJECT-TYPE
	SYNTAX                          Counter32
        MAX-ACCESS                      read-only
        STATUS                          current
	DESCRIPTION
				"The number of NFS Version 3 write calls
				with request sizes between 0-511 bytes
				received from this client."
	::= { pclEntry 117 }

	pclNfsV3Write1KCalls            OBJECT-TYPE
	SYNTAX                          Counter32
        MAX-ACCESS                      read-only
        STATUS                          current
	DESCRIPTION
				"The number of NFS Version 3 write calls
				with request sizes between 512-1023 bytes
				received from this client."
	::= { pclEntry 118 }

	pclNfsV3Write2KCalls            OBJECT-TYPE
	SYNTAX                          Counter32
        MAX-ACCESS                      read-only
        STATUS                          current
	DESCRIPTION
				"The number of NFS Version 3 write calls
				with request sizes between 1K-2047 bytes
				received from this client."
	::= { pclEntry 119 }

	pclNfsV3Write4KCalls            OBJECT-TYPE
	SYNTAX                          Counter32
        MAX-ACCESS                      read-only
        STATUS                          current
	DESCRIPTION
				"The number of NFS Version 3 write calls
				with request sizes between 2K-4095 bytes
				received from this client."
	::= { pclEntry 120 }

	pclNfsV3Write8KCalls            OBJECT-TYPE
	SYNTAX                          Counter32
        MAX-ACCESS                      read-only
        STATUS                          current
	DESCRIPTION
				"The number of NFS Version 3 write calls
				with request sizes between 4K-8191 bytes
				received from this client."
	::= { pclEntry 121 }

	pclNfsV3Write16KCalls           OBJECT-TYPE
	SYNTAX                          Counter32
        MAX-ACCESS                      read-only
        STATUS                          current
	DESCRIPTION
				"The number of NFS Version 3 write calls
				with request sizes between 8K-16383 bytes
				received from this client."
	::= { pclEntry 122 }

	pclNfsV3Write32KCalls           OBJECT-TYPE
	SYNTAX                          Counter32
        MAX-ACCESS                      read-only
        STATUS                          current
	DESCRIPTION
				"The number of NFS Version 3 write calls
				with request sizes between 16K-32767 bytes
				received from this client."
	::= { pclEntry 123 }

	pclNfsV3Write64KCalls           OBJECT-TYPE
	SYNTAX                          Counter32
        MAX-ACCESS                      read-only
        STATUS                          current
	DESCRIPTION
				"The number of NFS Version 3 write calls
				with request sizes between 32K-65535 bytes
				received from this client."
	::= { pclEntry 124 }

	pclNfsV3Write128KCalls          OBJECT-TYPE
	SYNTAX                          Counter32
        MAX-ACCESS                      read-only
        STATUS                          current
	DESCRIPTION
				"The number of NFS Version 3 write calls
				with request sizes between 64K-131071 bytes
				received from this client."
	::= { pclEntry 125 }


	pclNumber                       OBJECT-TYPE
	SYNTAX                          Integer32
        MAX-ACCESS                      read-only
        STATUS                          current
	DESCRIPTION
			"Number of entries in the pclTable table."

	::= { nfsPerClient 2 }



	-- the totNfs group

		-- this group contains the NFS statistics since the
		-- last boot

	trpcServ	OBJECT IDENTIFIER ::= { totNfs 1 }

	tnfsServ	OBJECT IDENTIFIER ::= { totNfs 2 }



	-- the trpcServ group

 	trpcCalls                       OBJECT-TYPE
	SYNTAX                          Counter32
        MAX-ACCESS                      read-only
        STATUS                          current
	DESCRIPTION
			"The total number of RPC calls received,
			 since the last boot."
	::= { trpcServ 1 }

	trpcBadCalls                    OBJECT-TYPE
	SYNTAX                          Counter32
        MAX-ACCESS                      read-only
        STATUS                          current
	DESCRIPTION
			"The total number of calls rejected by the RPC
			 layer, since the last boot."
	::= { trpcServ 2 }

	trpcNullRecvs                   OBJECT-TYPE
	SYNTAX                          Counter32
        MAX-ACCESS                      read-only
        STATUS                          current
	DESCRIPTION
			"The number of times an RPC call was not
			 available when it was thought to be received,
			 since the last boot."
	::= { trpcServ 3 }

	trpcBadLens                     OBJECT-TYPE
	SYNTAX                          Counter32
        MAX-ACCESS                      read-only
        STATUS                          current
	DESCRIPTION
			"The number of RPC calls received with a length
			 shorter than a minimum-sized RPC call, since
			 the last boot."
	::= { trpcServ 4 }

	trpcServXDRCalls                OBJECT-TYPE
	SYNTAX                          Counter32
        MAX-ACCESS                      read-only
        STATUS                          current
	DESCRIPTION
			"The number of RPC calls received whose header
			 could not be XDR decoded, since the last boot."
	::= { trpcServ 5 }



	-- the tnfsServ group

	tnfsCalls                       OBJECT-TYPE
	SYNTAX                          Counter32
        MAX-ACCESS                      read-only
        STATUS                          current
	DESCRIPTION
			 "The total number of NFS calls received, since
			  last boot."
	::= { tnfsServ 1 }

	tnfsServBadCalls                OBJECT-TYPE
	SYNTAX                          Counter32
        MAX-ACCESS                      read-only
        STATUS                          current
	DESCRIPTION
			 "The total number of received NFS calls rejected,
			  since last boot."
	::= { tnfsServ 2 }

	tnfsV2		OBJECT IDENTIFIER ::= { tnfsServ 3 }

	tnfsV3		OBJECT IDENTIFIER ::= { tnfsServ 4 }

	treplyCache	OBJECT IDENTIFIER ::= { tnfsServ 5 }

	tnfsrwStats 	OBJECT IDENTIFIER ::= { tnfsServ 6 }



	-- the tnfsV2 group

		-- this group contains statistics for NFS
		-- Version 2 calls processed since the last boot

	tv2Calls		OBJECT IDENTIFIER ::= { tnfsV2 1 }

	tv2Percent		OBJECT IDENTIFIER ::= { tnfsV2 2 }

	tv2CachedCalls		OBJECT IDENTIFIER ::= { tnfsV2 3 }

	tv2CachedPerCent	OBJECT IDENTIFIER ::= { tnfsV2 4 }


	-- the tv2Calls group

		-- this group contains statistics for the number of
		-- calls received for each NFS Version 2 procedure
		-- since the last boot

	tv2cNulls                       OBJECT-TYPE
	SYNTAX                          Counter32
        MAX-ACCESS                      read-only
        STATUS                          current
	DESCRIPTION
			"The number of NFS Version 2 calls received
			 for the NFSPROC_NULL (Do Nothing) procedure,
			 since the last boot."
	::= { tv2Calls 1 }

	tv2cGetattrs                    OBJECT-TYPE
	SYNTAX                          Counter32
        MAX-ACCESS                      read-only
        STATUS                          current
	DESCRIPTION
			"The number of NFS Version 2 calls received
			 for the NFSPROC_GETATTR (Get File Attributes)
			 procedure, since the last boot."
	::= { tv2Calls 2 }

	tv2cSetattrs                    OBJECT-TYPE
	SYNTAX                          Counter32
        MAX-ACCESS                      read-only
        STATUS                          current
	DESCRIPTION
			"The number of NFS Version 2 calls received
			 for the NFSPROC_SETATTR (Set File Attributes)
			 procedure, since the last boot."
	::= { tv2Calls 3 }

	tv2cRoots                       OBJECT-TYPE
	SYNTAX                          Counter32
        MAX-ACCESS                      read-only
        STATUS                          current
	DESCRIPTION
			"The number of NFS Version 2 calls received
			 for the NFSPROC_ROOT (Get Filesystem Root)
			 procedure, since the last boot."
	::= { tv2Calls 4 }

	tv2cLookups                     OBJECT-TYPE
	SYNTAX                          Counter32
        MAX-ACCESS                      read-only
        STATUS                          current
	DESCRIPTION
			"The number of NFS Version 2 calls received
			 for the NFSPROC_LOOKUP (Look Up File Name)
			 procedure, since the last boot."
	::= { tv2Calls 5 }

	tv2cReadlinks                   OBJECT-TYPE
	SYNTAX                          Counter32
        MAX-ACCESS                      read-only
        STATUS                          current
	DESCRIPTION
			"The number of NFS Version 2 calls received
			 for the NFSPROC_READLINK (Read From Symbolic
			 Link) procedure, since the last boot."
	::= { tv2Calls 6 }

	tv2cReads                       OBJECT-TYPE
	SYNTAX                          Counter32
        MAX-ACCESS                      read-only
        STATUS                          current
	DESCRIPTION
			"The number of NFS Version 2 calls received
			 for the NFSPROC_READ (Read From File)
			 procedure, since the last boot."
	::= { tv2Calls 7 }

	tv2cWrcaches                    OBJECT-TYPE
	SYNTAX                          Counter32
        MAX-ACCESS                      read-only
        STATUS                          current
	DESCRIPTION
			"The number of NFS Version 2 calls received
			 for the NFSPROC_WRITECACHE (Write to Cache)
			 procedure, since the last boot."
	::= { tv2Calls 8 }

	tv2cWrites                      OBJECT-TYPE
	SYNTAX                          Counter32
        MAX-ACCESS                      read-only
        STATUS                          current
	DESCRIPTION
			"The number of NFS Version 2 calls received
			 for the NFSPROC_WRITE (Write to File)
			 procedure, since the last boot."
	::= { tv2Calls 9 }

	tv2cCreates                     OBJECT-TYPE
	SYNTAX                          Counter32
        MAX-ACCESS                      read-only
        STATUS                          current
	DESCRIPTION
			"The number of NFS Version 2 calls received
			 for the NFSPROC_CREATE (Create File)
			 procedure, since the last boot."
	::= { tv2Calls 10 }

	tv2cRemoves                     OBJECT-TYPE
	SYNTAX                          Counter32
        MAX-ACCESS                      read-only
        STATUS                          current
	DESCRIPTION
			"The number of NFS Version 2 calls received
			 for the NFSPROC_REMOVE (Remove File)
			 procedure, since the last boot."
	::= { tv2Calls 11 }

	tv2cRenames                     OBJECT-TYPE
	SYNTAX                          Counter32
        MAX-ACCESS                      read-only
        STATUS                          current
	DESCRIPTION
			"The number of NFS Version 2 calls received
			 for the NFSPROC_RENAME (Rename File)
			 procedure, since the last boot."
	::= { tv2Calls 12 }

	tv2cLinks                       OBJECT-TYPE
	SYNTAX                          Counter32
        MAX-ACCESS                      read-only
        STATUS                          current
	DESCRIPTION
			"The number of NFS Version 2 calls received
			 for the NFSPROC_LINK (Create Link to File)
			 procedure, since the last boot."
	::= { tv2Calls 13 }

	tv2cSymlinks                    OBJECT-TYPE
	SYNTAX                          Counter32
        MAX-ACCESS                      read-only
        STATUS                          current
	DESCRIPTION
			"The number of NFS Version 2 calls received
			 for the NFSPROC_SYMLINK (Create Symbolic Link)
			 procedure, since the last boot."
	::= { tv2Calls 14 }

	tv2cMkdirs                      OBJECT-TYPE
	SYNTAX                          Counter32
        MAX-ACCESS                      read-only
        STATUS                          current
	DESCRIPTION
			"The number of NFS Version 2 calls received
			 for the NFSPROC_MKDIR (Create Directory)
			 procedure, since the last boot."
	::= { tv2Calls 15 }

	tv2cRmdirs                      OBJECT-TYPE
	SYNTAX                          Counter32
        MAX-ACCESS                      read-only
        STATUS                          current
	DESCRIPTION
			"The number of NFS Version 2 calls received
			 for the NFSPROC_RMDIR (Remove Directory)
			 procedure, since the last boot."
	::= { tv2Calls 16 }

	tv2cReaddirs                    OBJECT-TYPE
	SYNTAX                          Counter32
        MAX-ACCESS                      read-only
        STATUS                          current
	DESCRIPTION
			"The number of NFS Version 2 calls received
			 for the NFSPROC_READDIR (Read From Directory)
			 procedure, since the last boot."
	::= { tv2Calls 17 }

	tv2cStatfss                     OBJECT-TYPE
	SYNTAX                          Counter32
        MAX-ACCESS                      read-only
        STATUS                          current
	DESCRIPTION
			"The number of NFS Version 2 calls received
			 for the NFSPROC_STATFS (Get Filesystem
			 Attributes) procedure, since the last boot."
	::= { tv2Calls 18 }



	-- the tv2Percent group

		-- this group contains statistics for the number of
		-- calls received for each NFS Version 2 procedure,
		-- as a percentage of total NFS calls received,
		-- since the last boot

	tv2pNulls                       OBJECT-TYPE
	SYNTAX                          Integer32 (0..100)
        MAX-ACCESS                      read-only
        STATUS                          current
	DESCRIPTION
			"The number of NFS Version 2 calls received
			 for the NFSPROC_NULL (Do Nothing) procedure
			 as a percentage of total NFS calls received,
			 since the last boot."
	::= { tv2Percent 1 }

	tv2pGetattrs                    OBJECT-TYPE
	SYNTAX                          Integer32 (0..100)
        MAX-ACCESS                      read-only
        STATUS                          current
	DESCRIPTION
			"The number of NFS Version 2 calls received
			 for the NFSPROC_GETATTR (Get File Attributes)
			 procedure as a percentage of total NFS calls
			 received, since the last boot."
	::= { tv2Percent 2 }

	tv2pSetattrs                    OBJECT-TYPE
	SYNTAX                          Integer32 (0..100)
        MAX-ACCESS                      read-only
        STATUS                          current
	DESCRIPTION
			"The number of NFS Version 2 calls received
			 for the NFSPROC_SETATTR (Set File Attributes)
			 procedure as a percentage of total NFS calls
			 received, since the last boot."
	::= { tv2Percent 3 }

	tv2pRoots                       OBJECT-TYPE
	SYNTAX                          Integer32 (0..100)
        MAX-ACCESS                      read-only
        STATUS                          current
	DESCRIPTION
			"The number of NFS Version 2 calls received
			 for the NFSPROC_ROOT (Get Filesystem Root)
			 procedure as a percentage of total NFS calls
			 received, since the last boot."
	::= { tv2Percent 4 }

	tv2pLookups                     OBJECT-TYPE
	SYNTAX                          Integer32 (0..100)
        MAX-ACCESS                      read-only
        STATUS                          current
	DESCRIPTION
			"The number of NFS Version 2 calls received
			 for the NFSPROC_LOOKUP (Look Up File Name)
			 procedure as a percentage of total NFS calls
			 received, since the last boot."
	::= { tv2Percent 5 }

	tv2pReadlinks                   OBJECT-TYPE
	SYNTAX                          Integer32 (0..100)
        MAX-ACCESS                      read-only
        STATUS                          current
	DESCRIPTION
			"The number of NFS Version 2 calls received
			 for the NFSPROC_READLINK (Read From Symbolic
			 Link) procedure as a percentage of total NFS
			 calls received, since the last boot."
	::= { tv2Percent 6 }

	tv2pReads                       OBJECT-TYPE
	SYNTAX                          Integer32 (0..100)
        MAX-ACCESS                      read-only
        STATUS                          current
	DESCRIPTION
			"The number of NFS Version 2 calls received
			 for the NFSPROC_READ (Read From File)
			 procedure as a percentage of total NFS calls
			 received, since the last boot."
	::= { tv2Percent 7 }

	tv2pWrcaches                    OBJECT-TYPE
	SYNTAX                          Integer32 (0..100)
        MAX-ACCESS                      read-only
        STATUS                          current
	DESCRIPTION
			"The number of NFS Version 2 calls received
			 for the NFSPROC_WRITECACHE (Write to Cache)
			 procedure as a percentage of total NFS calls
			 received, since the last boot."
	::= { tv2Percent 8 }

	tv2pWrites                      OBJECT-TYPE
	SYNTAX                          Integer32 (0..100)
        MAX-ACCESS                      read-only
        STATUS                          current
	DESCRIPTION
			"The number of NFS Version 2 calls received
			 for the NFSPROC_WRITE (Write to File)
			 procedure as a percentage of total NFS calls
			 received, since the last boot."
	::= { tv2Percent 9 }

	tv2pCreates                     OBJECT-TYPE
	SYNTAX                          Integer32 (0..100)
        MAX-ACCESS                      read-only
        STATUS                          current
	DESCRIPTION
			"The number of NFS Version 2 calls received
			 for the NFSPROC_CREATE (Create File)
			 procedure as a percentage of total NFS calls
			 received, since the last boot."
	::= { tv2Percent 10 }

	tv2pRemoves                     OBJECT-TYPE
	SYNTAX                          Integer32 (0..100)
        MAX-ACCESS                      read-only
        STATUS                          current
	DESCRIPTION
			"The number of NFS Version 2 calls received
			 for the NFSPROC_REMOVE (Remove File)
			 procedure as a percentage of total NFS calls
			 received, since the last boot."
	::= { tv2Percent 11 }

	tv2pRenames                     OBJECT-TYPE
	SYNTAX                          Integer32 (0..100)
        MAX-ACCESS                      read-only
        STATUS                          current
	DESCRIPTION
			"The number of NFS Version 2 calls received
			 for the NFSPROC_RENAME (Rename File)
			 procedure as a percentage of total NFS calls
			 received, since the last boot."
	::= { tv2Percent 12 }

	tv2pLinks                       OBJECT-TYPE
	SYNTAX                          Integer32 (0..100)
        MAX-ACCESS                      read-only
        STATUS                          current
	DESCRIPTION
			"The number of NFS Version 2 calls received
			 for the NFSPROC_LINK (Create Link to File)
			 procedure as a percentage of total NFS calls
			 received, since the last boot."
	::= { tv2Percent 13 }

	tv2pSymlinks                    OBJECT-TYPE
	SYNTAX                          Integer32 (0..100)
        MAX-ACCESS                      read-only
        STATUS                          current
	DESCRIPTION
			"The number of NFS Version 2 calls received
			 for the NFSPROC_SYMLINK (Create Symbolic Link)
			 procedure as a percentage of total NFS calls
			 received, since the last boot."
	::= { tv2Percent 14 }

	tv2pMkdirs                      OBJECT-TYPE
	SYNTAX                          Integer32 (0..100)
        MAX-ACCESS                      read-only
        STATUS                          current
	DESCRIPTION
			"The number of NFS Version 2 calls received
			 for the NFSPROC_MKDIR (Create Directory)
			 procedure as a percentage of total NFS calls
			 received, since the last boot."
	::= { tv2Percent 15 }

	tv2pRmdirs                      OBJECT-TYPE
	SYNTAX                          Integer32 (0..100)
        MAX-ACCESS                      read-only
        STATUS                          current
	DESCRIPTION
			"The number of NFS Version 2 calls received
			 for the NFSPROC_RMDIR (Remove Directory)
			 procedure as a percentage of total NFS calls
			 received, since the last boot."
	::= { tv2Percent 16 }

	tv2pReaddirs                    OBJECT-TYPE
	SYNTAX                          Integer32 (0..100)
        MAX-ACCESS                      read-only
        STATUS                          current
	DESCRIPTION
			"The number of NFS Version 2 calls received
			 for the NFSPROC_READDIR (Read From Directory)
			 procedure as a percentage of total NFS calls
			 received, since the last boot."
	::= { tv2Percent 17 }

	tv2pStatfss                     OBJECT-TYPE
	SYNTAX                          Integer32 (0..100)
        MAX-ACCESS                      read-only
        STATUS                          current
	DESCRIPTION
			"The number of NFS Version 2 calls received
			 for the NFSPROC_STATFS (Get Filesystem
			 Attributes) procedure as a percentage of
			 total NFS calls received, since the last boot."
	::= { tv2Percent 18 }



	-- the tv2CachedCalls group

		-- this group contains statistics for the number of
		-- calls received for each NFS Version 2 procedure,
		-- that did not result in the filesystem blocking to
		-- read from disk, since the last boot

	tv2ccNulls                      OBJECT-TYPE
	SYNTAX                          Counter32
        MAX-ACCESS                      read-only
        STATUS                          current
	DESCRIPTION
			"The number of NFS Version 2 calls received
			 for the NFSPROC_NULL (Do Nothing) procedure,
			 that did not result in the filesystem blocking
			 to read from disk, since the last boot."
	::= { tv2CachedCalls 1 }

	tv2ccGetattrs                   OBJECT-TYPE
	SYNTAX                          Counter32
        MAX-ACCESS                      read-only
        STATUS                          current
	DESCRIPTION
			"The number of NFS Version 2 calls received
			 for the NFSPROC_GETATTR (Get File Attributes)
			 procedure, that did not result in the
			 filesystem blocking to read from disk,
			 since the last boot."
	::= { tv2CachedCalls 2 }

	tv2ccSetattrs                   OBJECT-TYPE
	SYNTAX                          Counter32
        MAX-ACCESS                      read-only
        STATUS                          current
	DESCRIPTION
			"The number of NFS Version 2 calls received
			 for the NFSPROC_SETATTR (Set File Attributes)
			 procedure, that did not result in the
			 filesystem blocking to read from disk,
			 since the last boot."
	::= { tv2CachedCalls 3 }

	tv2ccRoots                      OBJECT-TYPE
	SYNTAX                          Counter32
        MAX-ACCESS                      read-only
        STATUS                          current
	DESCRIPTION
			"The number of NFS Version 2 calls received
			 for the NFSPROC_ROOT (Get Filesystem Root)
			 procedure, that did not result in the
			 filesystem blocking to read from disk,
			 since the last boot."
	::= { tv2CachedCalls 4 }

	tv2ccLookups                    OBJECT-TYPE
	SYNTAX                          Counter32
        MAX-ACCESS                      read-only
        STATUS                          current
	DESCRIPTION
			"The number of NFS Version 2 calls received
			 for the NFSPROC_LOOKUP (Look Up File Name)
			 procedure, that did not result in the
			 filesystem blocking to read from disk,
			 since the last boot."
	::= { tv2CachedCalls 5 }

	tv2ccReadlinks                  OBJECT-TYPE
	SYNTAX                          Counter32
        MAX-ACCESS                      read-only
        STATUS                          current
	DESCRIPTION
			"The number of NFS Version 2 calls received
			 for the NFSPROC_READLINK (Read From Symbolic
			 Link) procedure, that did not result in the
			 filesystem blocking to read from disk,
			 since the last boot."
	::= { tv2CachedCalls 6 }

	tv2ccReads                      OBJECT-TYPE
	SYNTAX                          Counter32
        MAX-ACCESS                      read-only
        STATUS                          current
	DESCRIPTION
			"The number of NFS Version 2 calls received
			 for the NFSPROC_READ (Read From File)
			 procedure, that did not result in the
			 filesystem blocking to read from disk,
			 since the last boot."
	::= { tv2CachedCalls 7 }

	tv2ccWrcaches                   OBJECT-TYPE
	SYNTAX                          Counter32
        MAX-ACCESS                      read-only
        STATUS                          current
	DESCRIPTION
			"The number of NFS Version 2 calls received
			 for the NFSPROC_WRITECACHE (Write to Cache)
			 procedure, that did not result in the
			 filesystem blocking to read from disk,
			 since the last boot."
	::= { tv2CachedCalls 8 }

	tv2ccWrites                     OBJECT-TYPE
	SYNTAX                          Counter32
        MAX-ACCESS                      read-only
        STATUS                          current
	DESCRIPTION
			"The number of NFS Version 2 calls received
			 for the NFSPROC_WRITE (Write to File)
			 procedure, that did not result in the
			 filesystem blocking to read from disk,
			 since the last boot."
	::= { tv2CachedCalls 9 }

	tv2ccCreates                    OBJECT-TYPE
	SYNTAX                          Counter32
        MAX-ACCESS                      read-only
        STATUS                          current
	DESCRIPTION
			"The number of NFS Version 2 calls received
			 for the NFSPROC_CREATE (Create File)
			 procedure, that did not result in the
			 filesystem blocking to read from disk,
			 since the last boot."
	::= { tv2CachedCalls 10 }

	tv2ccRemoves                    OBJECT-TYPE
	SYNTAX                          Counter32
        MAX-ACCESS                      read-only
        STATUS                          current
	DESCRIPTION
			"The number of NFS Version 2 calls received
			 for the NFSPROC_REMOVE (Remove File)
			 procedure, that did not result in the
			 filesystem blocking to read from disk,
			 since the last boot."
	::= { tv2CachedCalls 11 }

	tv2ccRenames                    OBJECT-TYPE
	SYNTAX                          Counter32
        MAX-ACCESS                      read-only
        STATUS                          current
	DESCRIPTION
			"The number of NFS Version 2 calls received
			 for the NFSPROC_RENAME (Rename File)
			 procedure, that did not result in the
			 filesystem blocking to read from disk,
			 since the last boot."
	::= { tv2CachedCalls 12 }

	tv2ccLinks                      OBJECT-TYPE
	SYNTAX                          Counter32
        MAX-ACCESS                      read-only
        STATUS                          current
	DESCRIPTION
			"The number of NFS Version 2 calls received
			 for the NFSPROC_LINK (Create Link to File)
			 procedure, that did not result in the
			 filesystem blocking to read from disk,
			 since the last boot."
	::= { tv2CachedCalls 13 }

	tv2ccSymlinks                   OBJECT-TYPE
	SYNTAX                          Counter32
        MAX-ACCESS                      read-only
        STATUS                          current
	DESCRIPTION
			"The number of NFS Version 2 calls received
			 for the NFSPROC_SYMLINK (Create Symbolic Link)
			 procedure, that did not result in the
			 filesystem blocking to read from disk,
			 since the last boot."
	::= { tv2CachedCalls 14 }

	tv2ccMkdirs                     OBJECT-TYPE
	SYNTAX                          Counter32
        MAX-ACCESS                      read-only
        STATUS                          current
	DESCRIPTION
			"The number of NFS Version 2 calls received
			 for the NFSPROC_MKDIR (Create Directory)
			 procedure, that did not result in the
			 filesystem blocking to read from disk,
			 since the last boot."
	::= { tv2CachedCalls 15 }

	tv2ccRmdirs                     OBJECT-TYPE
	SYNTAX                          Counter32
        MAX-ACCESS                      read-only
        STATUS                          current
	DESCRIPTION
			"The number of NFS Version 2 calls received
			 for the NFSPROC_RMDIR (Remove Directory)
			 procedure, that did not result in the
			 filesystem blocking to read from disk,
			 since the last boot."
	::= { tv2CachedCalls 16 }

	tv2ccReaddirs                   OBJECT-TYPE
	SYNTAX                          Counter32
        MAX-ACCESS                      read-only
        STATUS                          current
	DESCRIPTION
			"The number of NFS Version 2 calls received
			 for the NFSPROC_READDIR (Read From Directory)
			 procedure, that did not result in the
			 filesystem blocking to read from disk,
			 since the last boot."
	::= { tv2CachedCalls 17 }

	tv2ccStatfss                    OBJECT-TYPE
	SYNTAX                          Counter32
        MAX-ACCESS                      read-only
        STATUS                          current
	DESCRIPTION
			"The number of NFS Version 2 calls received
			 for the NFSPROC_STATFS (Get Filesystem
			 Attributes) procedure, that did not result
			 in the filesystem blocking to read from disk,
			 since the last boot."
	::= { tv2CachedCalls 18 }



	-- the tv2CachedPerCent group

		-- this group contains statistics for the number of
		-- calls received for each NFS Version 2 procedure,
		-- that did not result in the filesystem blocking to
		-- read from disk, as a percentage of the total
		-- number of calls received for that procedure,
		-- since the last boot

	tv2cpNulls                      OBJECT-TYPE
	SYNTAX                          Integer32 (0..100)
        MAX-ACCESS                      read-only
        STATUS                          current
	DESCRIPTION
			"The number of NFS Version 2 calls received
			 for the NFSPROC_NULL (Do Nothing) procedure,
			 that did not result in the filesystem
			 blocking to read from disk, as a percentage
			 of the total number of calls received for
			 this procedure, since the last boot."
	::= { tv2CachedPerCent 1 }

	tv2cpGetattrs                   OBJECT-TYPE
	SYNTAX                          Integer32 (0..100)
        MAX-ACCESS                      read-only
        STATUS                          current
	DESCRIPTION
			"The number of NFS Version 2 calls received
			 for the NFSPROC_GETATTR (Get File Attributes)
			 procedure, that did not result in the
			 filesystem blocking to read from disk, as a
			 percentage of the total number of calls
			 received for this procedure, since the last boot."
	::= { tv2CachedPerCent 2 }

	tv2cpSetattrs                   OBJECT-TYPE
	SYNTAX                          Integer32 (0..100)
        MAX-ACCESS                      read-only
        STATUS                          current
	DESCRIPTION
			"The number of NFS Version 2 calls received
			 for the NFSPROC_SETATTR (Set File Attributes)
			 procedure, that did not result in the
			 filesystem blocking to read from disk, as a
			 percentage of the total number of calls
			 received for this procedure, since the last boot."
	::= { tv2CachedPerCent 3 }

	tv2cpRoots                      OBJECT-TYPE
	SYNTAX                          Integer32 (0..100)
        MAX-ACCESS                      read-only
        STATUS                          current
	DESCRIPTION
			"The number of NFS Version 2 calls received
			 for the NFSPROC_ROOT (Get Filesystem Root)
			 procedure, that did not result in the
			 filesystem blocking to read from disk, as a
			 percentage of the total number of calls
			 received for this procedure, since the last boot."
	::= { tv2CachedPerCent 4 }

	tv2cpLookups                    OBJECT-TYPE
	SYNTAX                          Integer32 (0..100)
        MAX-ACCESS                      read-only
        STATUS                          current
	DESCRIPTION
			"The number of NFS Version 2 calls received
			 for the NFSPROC_LOOKUP (Look Up File Name)
			 procedure, that did not result in the
			 filesystem blocking to read from disk, as a
			 percentage of the total number of calls
			 received for this procedure, since the last boot."
	::= { tv2CachedPerCent 5 }

	tv2cpReadlinks                  OBJECT-TYPE
	SYNTAX                          Integer32 (0..100)
        MAX-ACCESS                      read-only
        STATUS                          current
	DESCRIPTION
			"The number of NFS Version 2 calls received
			 for the NFSPROC_READLINK (Read From Symbolic
			 Link) procedure, that did not result in the
			 filesystem blocking to read from disk, as a
			 percentage of the total number of calls
			 received for this procedure, since the last boot."
	::= { tv2CachedPerCent 6 }

	tv2cpReads                      OBJECT-TYPE
	SYNTAX                          Integer32 (0..100)
        MAX-ACCESS                      read-only
        STATUS                          current
	DESCRIPTION
			"The number of NFS Version 2 calls received
			 for the NFSPROC_READ (Read From File)
			 procedure, that did not result in the
			 filesystem blocking to read from disk, as a
			 percentage of the total number of calls
			 received for this procedure, since the last boot."
	::= { tv2CachedPerCent 7 }

	tv2cpWrcaches                   OBJECT-TYPE
	SYNTAX                          Integer32 (0..100)
        MAX-ACCESS                      read-only
        STATUS                          current
	DESCRIPTION
			"The number of NFS Version 2 calls received
			 for the NFSPROC_WRITECACHE (Write to Cache)
			 procedure, that did not result in the
			 filesystem blocking to read from disk, as a
			 percentage of the total number of calls
			 received for this procedure, since the last boot."
	::= { tv2CachedPerCent 8 }

	tv2cpWrites                     OBJECT-TYPE
	SYNTAX                          Integer32 (0..100)
        MAX-ACCESS                      read-only
        STATUS                          current
	DESCRIPTION
			"The number of NFS Version 2 calls received
			 for the NFSPROC_WRITE (Write to File)
			 procedure, that did not result in the
			 filesystem blocking to read from disk, as a
			 percentage of the total number of calls
			 received for this procedure, since the last boot."
	::= { tv2CachedPerCent 9 }

	tv2cpCreates                    OBJECT-TYPE
	SYNTAX                          Integer32 (0..100)
        MAX-ACCESS                      read-only
        STATUS                          current
	DESCRIPTION
			"The number of NFS Version 2 calls received
			 for the NFSPROC_CREATE (Create File)
			 procedure, that did not result in the
			 filesystem blocking to read from disk, as a
			 percentage of the total number of calls
			 received for this procedure, since the last boot."
	::= { tv2CachedPerCent 10 }

	tv2cpRemoves                    OBJECT-TYPE
	SYNTAX                          Integer32 (0..100)
        MAX-ACCESS                      read-only
        STATUS                          current
	DESCRIPTION
			"The number of NFS Version 2 calls received
			 for the NFSPROC_REMOVE (Remove File)
			 procedure, that did not result in the
			 filesystem blocking to read from disk, as a
			 percentage of the total number of calls
			 received for this procedure, since the last boot."
	::= { tv2CachedPerCent 11 }

	tv2cpRenames                    OBJECT-TYPE
	SYNTAX                          Integer32 (0..100)
        MAX-ACCESS                      read-only
        STATUS                          current
	DESCRIPTION
			"The number of NFS Version 2 calls received
			 for the NFSPROC_RENAME (Rename File)
			 procedure, that did not result in the
			 filesystem blocking to read from disk, as a
			 percentage of the total number of calls
			 received for this procedure, since the last boot."
	::= { tv2CachedPerCent 12 }

	tv2cpLinks                      OBJECT-TYPE
	SYNTAX                          Integer32 (0..100)
        MAX-ACCESS                      read-only
        STATUS                          current
	DESCRIPTION
			"The number of NFS Version 2 calls received
			 for the NFSPROC_LINK (Create Link to File)
			 procedure, that did not result in the
			 filesystem blocking to read from disk, as a
			 percentage of the total number of calls
			 received for this procedure, since the last boot."
	::= { tv2CachedPerCent 13 }

	tv2cpSymlinks                   OBJECT-TYPE
	SYNTAX                          Integer32 (0..100)
        MAX-ACCESS                      read-only
        STATUS                          current
	DESCRIPTION
			"The number of NFS Version 2 calls received
			 for the NFSPROC_SYMLINK (Create Symbolic
			 Link) procedure, that did not result in the
			 filesystem blocking to read from disk, as a
			 percentage of the total number of calls
			 received for this procedure, since the last boot."
	::= { tv2CachedPerCent 14 }

	tv2cpMkdirs                     OBJECT-TYPE
	SYNTAX                          Integer32 (0..100)
        MAX-ACCESS                      read-only
        STATUS                          current
	DESCRIPTION
			"The number of NFS Version 2 calls received
			 for the NFSPROC_MKDIR (Create Directory)
			 procedure, that did not result in the
			 filesystem blocking to read from disk, as a
			 percentage of the total number of calls
			 received for this procedure, since the last boot."
	::= { tv2CachedPerCent 15 }

	tv2cpRmdirs                     OBJECT-TYPE
	SYNTAX                          Integer32 (0..100)
        MAX-ACCESS                      read-only
        STATUS                          current
	DESCRIPTION
			"The number of NFS Version 2 calls received
			 for the NFSPROC_RMDIR (Remove Directory)
			 procedure, that did not result in the
			 filesystem blocking to read from disk, as a
			 percentage of the total number of calls
			 received for this procedure, since the last boot."
	::= { tv2CachedPerCent 16 }

	tv2cpReaddirs                   OBJECT-TYPE
	SYNTAX                          Integer32 (0..100)
        MAX-ACCESS                      read-only
        STATUS                          current
	DESCRIPTION
			"The number of NFS Version 2 calls received
			 for the NFSPROC_READDIR (Read From Directory)
			 procedure, that did not result in the
			 filesystem blocking to read from disk, as a
			 percentage of the total number of calls
			 received for this procedure, since the last boot."
	::= { tv2CachedPerCent 17 }

	tv2cpStatfss                    OBJECT-TYPE
	SYNTAX                          Integer32 (0..100)
        MAX-ACCESS                      read-only
        STATUS                          current
	DESCRIPTION
			"The number of NFS Version 2 calls received
			 for the NFSPROC_STATFS (Get Filesystem
			 Attributes) procedure, that did not result
			 in the filesystem blocking to read from
			 disk, as a percentage of the total number
			 of calls received for this procedure,
			 since the last boot."
	::= { tv2CachedPerCent 18 }


	-- the tnfsV3 group

		-- this group contains statistics for NFS
		-- Version 3 calls processed since the last boot

	tv3Calls		OBJECT IDENTIFIER ::= { tnfsV3 1 }

	tv3Percent		OBJECT IDENTIFIER ::= { tnfsV3 2 }

	tv3CachedCalls		OBJECT IDENTIFIER ::= { tnfsV3 3 }

	tv3CachedPerCent	OBJECT IDENTIFIER ::= { tnfsV3 4 }


	-- the tv3Calls group

		-- this group contains statistics for the number of
		-- calls received for each NFS Version 3 procedure
		-- since the last boot

	tv3cNulls                       OBJECT-TYPE
	SYNTAX                          Counter32
        MAX-ACCESS                      read-only
        STATUS                          current
	DESCRIPTION
			"The number of NFS Version 3 calls received
			 for the NFSPROC3_NULL (Do Nothing) procedure,
			 since the last boot."
	::= { tv3Calls 1 }

	tv3cGetattrs                    OBJECT-TYPE
	SYNTAX                          Counter32
        MAX-ACCESS                      read-only
        STATUS                          current
	DESCRIPTION
			"The number of NFS Version 3 calls received
			 for the NFSPROC3_GETATTR (Get File Attributes)
			 procedure, since the last boot."
	::= { tv3Calls 2 }

	tv3cSetattrs                    OBJECT-TYPE
	SYNTAX                          Counter32
        MAX-ACCESS                      read-only
        STATUS                          current
	DESCRIPTION
			"The number of NFS Version 3 calls received
			 for the NFSPROC3_SETATTR (Set File Attributes)
			 procedure, since the last boot."
	::= { tv3Calls 3 }

	tv3cLookups                     OBJECT-TYPE
	SYNTAX                          Counter32
        MAX-ACCESS                      read-only
        STATUS                          current
	DESCRIPTION
			"The number of NFS Version 3 calls received
			 for the NFSPROC3_LOOKUP (Lookup Filename)
			 procedure, since the last boot."
	::= { tv3Calls 4 }

	tv3cAccesss                     OBJECT-TYPE
	SYNTAX                          Counter32
        MAX-ACCESS                      read-only
        STATUS                          current
	DESCRIPTION
			"The number of NFS Version 3 calls received
			 for the NFSPROC3_ACCESS (Check Access Permission)
			 procedure, since the last boot."
	::= { tv3Calls 5 }

	tv3cReadlinks                   OBJECT-TYPE
	SYNTAX                          Counter32
        MAX-ACCESS                      read-only
        STATUS                          current
	DESCRIPTION
			"The number of NFS Version 3 calls received
			 for the NFSPROC3_READLINK (Read from Symbolic
			 Link) procedure, since the last boot."
	::= { tv3Calls 6 }

	tv3cReads                       OBJECT-TYPE
	SYNTAX                          Counter32
        MAX-ACCESS                      read-only
        STATUS                          current
	DESCRIPTION
			"The number of NFS Version 3 calls received
			 for the NFSPROC3_READ (Read From File)
			 procedure, since the last boot."
	::= { tv3Calls 7 }

	tv3cWrites                      OBJECT-TYPE
	SYNTAX                          Counter32
        MAX-ACCESS                      read-only
        STATUS                          current
	DESCRIPTION
			"The number of NFS Version 3 calls received
			 for the NFSPROC3_WRITE (Write to File)
			 procedure, since the last boot."
	::= { tv3Calls 8 }

	tv3cCreates                     OBJECT-TYPE
	SYNTAX                          Counter32
        MAX-ACCESS                      read-only
        STATUS                          current
	DESCRIPTION
			"The number of NFS Version 3 calls received
			 for the NFSPROC3_CREATE (Create a File)
			 procedure, since the last boot."
	::= { tv3Calls 9 }

	tv3cMkdirs                      OBJECT-TYPE
	SYNTAX                          Counter32
        MAX-ACCESS                      read-only
        STATUS                          current
	DESCRIPTION
			"The number of NFS Version 3 calls received
			 for the NFSPROC3_MKDIR (Create a Directory)
			 procedure, since the last boot."
	::= { tv3Calls 10 }

	tv3cSymlinks                    OBJECT-TYPE
	SYNTAX                          Counter32
        MAX-ACCESS                      read-only
        STATUS                          current
	DESCRIPTION
			"The number of NFS Version 3 calls received
			 for the NFSPROC3_SYMLINK (Create a Symbolic
			 Link) procedure, since the last boot."
	::= { tv3Calls 11 }

	tv3cMknods                      OBJECT-TYPE
	SYNTAX                          Counter32
        MAX-ACCESS                      read-only
        STATUS                          current
	DESCRIPTION
			"The number of NFS Version 3 calls received
			 for the NFSPROC3_MKNOD (Create a Special
			 Device) procedure, since the last boot."
	::= { tv3Calls 12 }

	tv3cRemoves                     OBJECT-TYPE
	SYNTAX                          Counter32
        MAX-ACCESS                      read-only
        STATUS                          current
	DESCRIPTION
			"The number of NFS Version 3 calls received
			 for the NFSPROC3_REMOVE (Remove a File)
			 procedure, since the last boot."
	::= { tv3Calls 13 }

	tv3cRmdirs                      OBJECT-TYPE
	SYNTAX                          Counter32
        MAX-ACCESS                      read-only
        STATUS                          current
	DESCRIPTION
			"The number of NFS Version 3 calls received
			 for the NFSPROC3_RMDIR (Remove a Directory)
			 procedure, since the last boot."
	::= { tv3Calls 14 }

	tv3cRenames                     OBJECT-TYPE
	SYNTAX                          Counter32
        MAX-ACCESS                      read-only
        STATUS                          current
	DESCRIPTION
			"The number of NFS Version 3 calls received
			 for the NFSPROC3_RENAME (Rename a File or
			 Directory) procedure, since the last boot."
	::= { tv3Calls 15 }

	tv3cLinks                       OBJECT-TYPE
	SYNTAX                          Counter32
        MAX-ACCESS                      read-only
        STATUS                          current
	DESCRIPTION
			"The number of NFS Version 3 calls received
			 for the NFSPROC3_LINK (Create Link to an
			 Object) procedure, since the last boot."
	::= { tv3Calls 16 }

	tv3cReaddirs                    OBJECT-TYPE
	SYNTAX                          Counter32
        MAX-ACCESS                      read-only
        STATUS                          current
	DESCRIPTION
			"The number of NFS Version 3 calls received
			 for the NFSPROC3_READDIR (Read From Directory)
			 procedure, since the last boot."
	::= { tv3Calls 17 }

	tv3cReaddirPluss                OBJECT-TYPE
	SYNTAX                          Counter32
        MAX-ACCESS                      read-only
        STATUS                          current
	DESCRIPTION
			"The number of NFS Version 3 calls received
			 for the NFSPROC3_READDIRPLUS (Extended Read
			 from Directory) procedure, since the last boot."
	::= { tv3Calls 18 }

	tv3cFsstats                     OBJECT-TYPE
	SYNTAX                          Counter32
        MAX-ACCESS                      read-only
        STATUS                          current
	DESCRIPTION
			"The number of NFS Version 3 calls received
			 for the NFSPROC3_FSSTAT (Get Dynamic File
			 System Information) procedure, since the
			 last boot."
	::= { tv3Calls 19 }

	tv3cFsinfos                     OBJECT-TYPE
	SYNTAX                          Counter32
        MAX-ACCESS                      read-only
        STATUS                          current
	DESCRIPTION
			"The number of NFS Version 3 calls received
			 for the NFSPROC3_FSINFO (Get Static File System
			 Information) procedure, since the last boot."
	::= { tv3Calls 20 }

	tv3cPathconfs                   OBJECT-TYPE
	SYNTAX                          Counter32
        MAX-ACCESS                      read-only
        STATUS                          current
	DESCRIPTION
			"The number of NFS Version 3 calls received
			 for the NFSPROC3_PATHCONF (Retrieve POSIX
			 Information) procedure, since the last boot."
	::= { tv3Calls 21 }

	tv3cCommits                     OBJECT-TYPE
	SYNTAX                          Counter32
        MAX-ACCESS                      read-only
        STATUS                          current
	DESCRIPTION
			"The number of NFS Version 3 calls received
			 for the NFSPROC3_COMMIT (Commit Cached Data on
			 a Server to Stable Storage) procedure, since
			 the last boot."
	::= { tv3Calls 22 }



	-- the tv3Percent group

		-- this group contains statistics for the number of
		-- calls received for each NFS Version 3 procedure,
		-- as a percentage of total NFS calls received,
		-- since the last boot

	tv3pNulls                       OBJECT-TYPE
	SYNTAX                          Integer32 (0..100)
        MAX-ACCESS                      read-only
        STATUS                          current
	DESCRIPTION
			"The number of NFS Version 3 calls received
			 for the NFSPROC3_NULL (Do Nothing) procedure,
			 as a percentage of the total NFS calls
			 received, since the last boot."
	::= { tv3Percent 1 }

	tv3pGetattrs                    OBJECT-TYPE
	SYNTAX                          Integer32 (0..100)
        MAX-ACCESS                      read-only
        STATUS                          current
	DESCRIPTION
			"The number of NFS Version 3 calls received
			 for the NFSPROC3_GETATTR (Get File Attributes)
			 procedure, as a percentage of the total NFS
			 calls received, since the last boot."
	::= { tv3Percent 2 }

	tv3pSetattrs                    OBJECT-TYPE
	SYNTAX                          Integer32 (0..100)
        MAX-ACCESS                      read-only
        STATUS                          current
	DESCRIPTION
			"The number of NFS Version 3 calls received
			 for the NFSPROC3_SETATTR (Set File Attributes)
			 procedure, as a percentage of the total NFS
			 calls received, since the last boot."
	::= { tv3Percent 3 }

	tv3pLookups                     OBJECT-TYPE
	SYNTAX                          Integer32 (0..100)
        MAX-ACCESS                      read-only
        STATUS                          current
	DESCRIPTION
			"The number of NFS Version 3 calls received
			 for the NFSPROC3_LOOKUP (Lookup Filename)
			 procedure, as a percentage of the total NFS
			 calls received, since the last boot."
	::= { tv3Percent 4 }

	tv3pAccesss                     OBJECT-TYPE
	SYNTAX                          Integer32 (0..100)
        MAX-ACCESS                      read-only
        STATUS                          current
	DESCRIPTION
			"The number of NFS Version 3 calls received
			 for the NFSPROC3_ACCESS (Check Access
			 Permission) procedure, as a percentage of
			 the total NFS calls received, since the last boot."
	::= { tv3Percent 5 }

	tv3pReadlinks                   OBJECT-TYPE
	SYNTAX                          Integer32 (0..100)
        MAX-ACCESS                      read-only
        STATUS                          current
	DESCRIPTION
			"The number of NFS Version 3 calls received
			 for the NFSPROC3_READLINK (Read from Symbolic
			 Link) procedure, as a percentage of the total
			 NFS calls received, since the last boot."
	::= { tv3Percent 6 }

	tv3pReads                       OBJECT-TYPE
	SYNTAX                          Integer32 (0..100)
        MAX-ACCESS                      read-only
        STATUS                          current
	DESCRIPTION
			"The number of NFS Version 3 calls received
			 for the NFSPROC3_READ (Read From File)
			 procedure, as a percentage of the total NFS
			 calls received, since the last boot."
	::= { tv3Percent 7 }

	tv3pWrites                      OBJECT-TYPE
	SYNTAX                          Integer32 (0..100)
        MAX-ACCESS                      read-only
        STATUS                          current
	DESCRIPTION
			"The number of NFS Version 3 calls received
			 for the NFSPROC3_WRITE (Write to File)
			 procedure, as a percentage of the total NFS
			 calls received, since the last boot."
	::= { tv3Percent 8 }

	tv3pCreates                     OBJECT-TYPE
	SYNTAX                          Integer32 (0..100)
        MAX-ACCESS                      read-only
        STATUS                          current
	DESCRIPTION
			"The number of NFS Version 3 calls received
			 for the NFSPROC3_CREATE (Create a File)
			 procedure, as a percentage of the total NFS
			 calls received, since the last boot."
	::= { tv3Percent 9 }

	tv3pMkdirs                      OBJECT-TYPE
	SYNTAX                          Integer32 (0..100)
        MAX-ACCESS                      read-only
        STATUS                          current
	DESCRIPTION
			"The number of NFS Version 3 calls received
			 for the NFSPROC3_MKDIR (Create a Directory)
			 procedure, as a percentage of the total NFS
			 calls received, since the last boot."
	::= { tv3Percent 10 }

	tv3pSymlinks                    OBJECT-TYPE
	SYNTAX                          Integer32 (0..100)
        MAX-ACCESS                      read-only
        STATUS                          current
	DESCRIPTION
			"The number of NFS Version 3 calls received
			 for the NFSPROC3_SYMLINK (Create a Symbolic
			 Link) procedure, as a percentage of the total
			 NFS calls received, since the last boot."
	::= { tv3Percent 11 }

	tv3pMknods                      OBJECT-TYPE
	SYNTAX                          Integer32 (0..100)
        MAX-ACCESS                      read-only
        STATUS                          current
	DESCRIPTION
			"The number of NFS Version 3 calls received
			 for the NFSPROC3_MKNOD (Create a Special
			 Device) procedure, as a percentage of the
			 total NFS calls received, since the last boot."
	::= { tv3Percent 12 }

	tv3pRemoves                     OBJECT-TYPE
	SYNTAX                          Integer32 (0..100)
        MAX-ACCESS                      read-only
        STATUS                          current
	DESCRIPTION
			"The number of NFS Version 3 calls received
			 for the NFSPROC3_REMOVE (Remove a File)
			 procedure, as a percentage of the total NFS
			 calls received, since the last boot."
	::= { tv3Percent 13 }

	tv3pRmdirs                      OBJECT-TYPE
	SYNTAX                          Integer32 (0..100)
        MAX-ACCESS                      read-only
        STATUS                          current
	DESCRIPTION
			"The number of NFS Version 3 calls received
			 for the NFSPROC3_RMDIR (Remove a Directory)
			 procedure, as a percentage of the total NFS
			 calls received, since the last boot."
	::= { tv3Percent 14 }

	tv3pRenames                     OBJECT-TYPE
	SYNTAX                          Integer32 (0..100)
        MAX-ACCESS                      read-only
        STATUS                          current
	DESCRIPTION
			"The number of NFS Version 3 calls received
			 for the NFSPROC3_RENAME (Rename a File or
			 Directory) procedure, as a percentage of
			 the total NFS calls received, since the
			 last boot."
	::= { tv3Percent 15 }

	tv3pLinks                       OBJECT-TYPE
	SYNTAX                          Integer32 (0..100)
        MAX-ACCESS                      read-only
        STATUS                          current
	DESCRIPTION
			"The number of NFS Version 3 calls received
			 for the NFSPROC3_LINK (Create Link to an
			 Object) procedure, as a percentage of
			 the total NFS calls received, since the
			 last boot."
	::= { tv3Percent 16 }

	tv3pReaddirs                    OBJECT-TYPE
	SYNTAX                          Integer32 (0..100)
        MAX-ACCESS                      read-only
        STATUS                          current
	DESCRIPTION
			"The number of NFS Version 3 calls received
			 for the NFSPROC3_READDIR (Read From Directory)
			 procedure, as a percentage of the total NFS
			 calls received, since the last boot."
	::= { tv3Percent 17 }

	tv3pReaddirPluss                OBJECT-TYPE
	SYNTAX                          Integer32 (0..100)
        MAX-ACCESS                      read-only
        STATUS                          current
	DESCRIPTION
			"The number of NFS Version 3 calls received
			 for the NFSPROC3_READDIRPLUS (Extended Read
			 from Directory) procedure, as a percentage
			 of the total NFS calls received, since the
			 last boot."
	::= { tv3Percent 18 }

	tv3pFsstats                     OBJECT-TYPE
	SYNTAX                          Integer32 (0..100)
        MAX-ACCESS                      read-only
        STATUS                          current
	DESCRIPTION
			"The number of NFS Version 3 calls received
			 for the NFSPROC3_FSSTAT (Get Dynamic File
			 System Information) procedure, as a percentage
			 of the total NFS calls received, since the
			 last boot."
	::= { tv3Percent 19 }

	tv3pFsinfos                     OBJECT-TYPE
	SYNTAX                          Integer32 (0..100)
        MAX-ACCESS                      read-only
        STATUS                          current
	DESCRIPTION
			"The number of NFS Version 3 calls received
			 for the NFSPROC3_FSINFO (Get Static File System
			 Information) procedure, as a percentage of the
			 total NFS calls received, since the last boot."
	::= { tv3Percent 20 }

	tv3pPathconfs                   OBJECT-TYPE
	SYNTAX                          Integer32 (0..100)
        MAX-ACCESS                      read-only
        STATUS                          current
	DESCRIPTION
			"The number of NFS Version 3 calls received
			 for the NFSPROC3_PATHCONF (Retrieve POSIX
			 Information) procedure, as a percentage of the
			 total NFS calls received, since the last boot."
	::= { tv3Percent 21 }

	tv3pCommits                     OBJECT-TYPE
	SYNTAX                          Integer32 (0..100)
        MAX-ACCESS                      read-only
        STATUS                          current
	DESCRIPTION
			"The number of NFS Version 3 calls received
			 for the NFSPROC3_COMMIT (Commit Cached Data on
			 a Server to Stable Storage) procedure, as a
			 percentage of the total NFS calls received,
			 since the last boot."
	::= { tv3Percent 22 }



	-- the tv3CachedCalls group

		-- this group contains statistics for the number of
		-- calls received for each NFS Version 3 procedure,
		-- that did not result in the filesystem blocking to
		-- read from disk, since the last boot

	tv3ccNulls                      OBJECT-TYPE
	SYNTAX                          Counter32
        MAX-ACCESS                      read-only
        STATUS                          current
	DESCRIPTION
			"The number of NFS Version 3 calls received
			 for the NFSPROC3_NULL (Do Nothing) procedure,
			 that did not result in the filesystem blocking
			 to read from disk, since the last boot."
	::= { tv3CachedCalls 1 }

	tv3ccGetattrs                   OBJECT-TYPE
	SYNTAX                          Counter32
        MAX-ACCESS                      read-only
        STATUS                          current
	DESCRIPTION
			"The number of NFS Version 3 calls received
			 for the NFSPROC3_GETATTR (Get File Attributes)
			 procedure, that did not result in the filesystem
			 blocking to read from disk, since the last boot."
	::= { tv3CachedCalls 2 }

	tv3ccSetattrs                   OBJECT-TYPE
	SYNTAX                          Counter32
        MAX-ACCESS                      read-only
        STATUS                          current
	DESCRIPTION
			"The number of NFS Version 3 calls received
			 for the NFSPROC3_SETATTR (Set File Attributes)
			 procedure, that did not result in the filesystem
			 blocking to read from disk, since the last boot."
	::= { tv3CachedCalls 3 }

	tv3ccLookups                    OBJECT-TYPE
	SYNTAX                          Counter32
        MAX-ACCESS                      read-only
        STATUS                          current
	DESCRIPTION
			"The number of NFS Version 3 calls received
			 for the NFSPROC3_LOOKUP (Lookup Filename)
			 procedure, that did not result in the filesystem
			 blocking to read from disk, since the last boot."
	::= { tv3CachedCalls 4 }

	tv3ccAccesss                    OBJECT-TYPE
	SYNTAX                          Counter32
        MAX-ACCESS                      read-only
        STATUS                          current
	DESCRIPTION
			"The number of NFS Version 3 calls received
			 for the NFSPROC3_ACCESS (Check Access Permission)
			 procedure, that did not result in the filesystem
			 blocking to read from disk, since the last boot."
	::= { tv3CachedCalls 5 }

	tv3ccReadlinks                  OBJECT-TYPE
	SYNTAX                          Counter32
        MAX-ACCESS                      read-only
        STATUS                          current
	DESCRIPTION
			"The number of NFS Version 3 calls received
			 for the NFSPROC3_READLINK (Read from Symbolic
			 Link) procedure, that did not result in the
			 filesystem blocking to read from disk, since
			 the last boot."
	::= { tv3CachedCalls 6 }

	tv3ccReads                      OBJECT-TYPE
	SYNTAX                          Counter32
        MAX-ACCESS                      read-only
        STATUS                          current
	DESCRIPTION
			"The number of NFS Version 3 calls received
			 for the NFSPROC3_READ (Read From File)
			 procedure, that did not result in the filesystem
			 blocking to read from disk, since the last boot."
	::= { tv3CachedCalls 7 }

	tv3ccWrites                     OBJECT-TYPE
	SYNTAX                          Counter32
        MAX-ACCESS                      read-only
        STATUS                          current
	DESCRIPTION
			"The number of NFS Version 3 calls received
			 for the NFSPROC3_WRITE (Write to File)
			 procedure, that did not result in the filesystem
			 blocking to read from disk, since the last boot."
	::= { tv3CachedCalls 8 }

	tv3ccCreates                    OBJECT-TYPE
	SYNTAX                          Counter32
        MAX-ACCESS                      read-only
        STATUS                          current
	DESCRIPTION
			"The number of NFS Version 3 calls received
			 for the NFSPROC3_CREATE (Create a File)
			 procedure, that did not result in the filesystem
			 blocking to read from disk, since the last boot."
	::= { tv3CachedCalls 9 }

	tv3ccMkdirs                     OBJECT-TYPE
	SYNTAX                          Counter32
        MAX-ACCESS                      read-only
        STATUS                          current
	DESCRIPTION
			"The number of NFS Version 3 calls received
			 for the NFSPROC3_MKDIR (Create a Directory)
			 procedure, that did not result in the filesystem
			 blocking to read from disk, since the last boot."
	::= { tv3CachedCalls 10 }

	tv3ccSymlinks                   OBJECT-TYPE
	SYNTAX                          Counter32
        MAX-ACCESS                      read-only
        STATUS                          current
	DESCRIPTION
			"The number of NFS Version 3 calls received
			 for the NFSPROC3_SYMLINK (Create a Symbolic
			 Link) procedure, that did not result in the
			 filesystem blocking to read from disk, since
			 the last boot."
	::= { tv3CachedCalls 11 }

	tv3ccMknods                     OBJECT-TYPE
	SYNTAX                          Counter32
        MAX-ACCESS                      read-only
        STATUS                          current
	DESCRIPTION
			"The number of NFS Version 3 calls received
			 for the NFSPROC3_MKNOD (Create a Special
			 Device) procedure, that did not result in the
			 filesystem blocking to read from disk, since
			 the last boot."
	::= { tv3CachedCalls 12 }

	tv3ccRemoves                    OBJECT-TYPE
	SYNTAX                          Counter32
        MAX-ACCESS                      read-only
        STATUS                          current
	DESCRIPTION
			"The number of NFS Version 3 calls received
			 for the NFSPROC3_REMOVE (Remove a File)
			 procedure, that did not result in the
			 filesystem blocking to read from disk,
			 since the last boot."
	::= { tv3CachedCalls 13 }

	tv3ccRmdirs                     OBJECT-TYPE
	SYNTAX                          Counter32
        MAX-ACCESS                      read-only
        STATUS                          current
	DESCRIPTION
			"The number of NFS Version 3 calls received
			 for the NFSPROC3_RMDIR (Remove a Directory)
			 procedure, that did not result in the
			 filesystem blocking to read from disk,
			 since the last boot."
	::= { tv3CachedCalls 14 }

	tv3ccRenames                    OBJECT-TYPE
	SYNTAX                          Counter32
        MAX-ACCESS                      read-only
        STATUS                          current
	DESCRIPTION
			"The number of NFS Version 3 calls received
			 for the NFSPROC3_RENAME (Rename a File or
			 Directory) procedure, that did not result in
			 the filesystem blocking to read from disk,
			 since the last boot."
	::= { tv3CachedCalls 15 }

	tv3ccLinks                      OBJECT-TYPE
	SYNTAX                          Counter32
        MAX-ACCESS                      read-only
        STATUS                          current
	DESCRIPTION
			"The number of NFS Version 3 calls received
			 for the NFSPROC3_LINK (Create Link to an
			 Object) procedure, that did not result in
			 the filesystem blocking to read from disk,
			 since the last boot."
	::= { tv3CachedCalls 16 }

	tv3ccReaddirs                   OBJECT-TYPE
	SYNTAX                          Counter32
        MAX-ACCESS                      read-only
        STATUS                          current
	DESCRIPTION
			"The number of NFS Version 3 calls received
			 for the NFSPROC3_READDIR (Read From
			 Directory) procedure, that did not result in
			 the filesystem blocking to read from disk,
			 since the last boot."
	::= { tv3CachedCalls 17 }

	tv3ccReaddirPluss               OBJECT-TYPE
	SYNTAX                          Counter32
        MAX-ACCESS                      read-only
        STATUS                          current
	DESCRIPTION
			"The number of NFS Version 3 calls received
			 for the NFSPROC3_READDIRPLUS (Extended Read
			 from Directory) procedure, that did not result in
			 the filesystem blocking to read from disk,
			 since the last boot."
	::= { tv3CachedCalls 18 }

	tv3ccFsstats                    OBJECT-TYPE
	SYNTAX                          Counter32
        MAX-ACCESS                      read-only
        STATUS                          current
	DESCRIPTION
			"The number of NFS Version 3 calls received
			 for the NFSPROC3_FSSTAT (Get Dynamic File
			 System Information) procedure, that did not
			 result in the filesystem blocking to read
			 from disk, since the last boot."
	::= { tv3CachedCalls 19 }

	tv3ccFsinfos                    OBJECT-TYPE
	SYNTAX                          Counter32
        MAX-ACCESS                      read-only
        STATUS                          current
	DESCRIPTION
			"The number of NFS Version 3 calls received
			 for the NFSPROC3_FSINFO (Get Static File
			 System Information) procedure, that did not
			 result in the filesystem blocking to read
			 from disk, since the last boot."
	::= { tv3CachedCalls 20 }

	tv3ccPathconfs                  OBJECT-TYPE
	SYNTAX                          Counter32
        MAX-ACCESS                      read-only
        STATUS                          current
	DESCRIPTION
			"The number of NFS Version 3 calls received
			 for the NFSPROC3_PATHCONF (Retrieve POSIX
			 Information) procedure, that did not result
			 in the filesystem blocking to read from disk,
			 since the last boot."
	::= { tv3CachedCalls 21 }

	tv3ccCommits                    OBJECT-TYPE
	SYNTAX                          Counter32
        MAX-ACCESS                      read-only
        STATUS                          current
	DESCRIPTION
			"The number of NFS Version 3 calls received
			 for the NFSPROC3_COMMIT (Commit Cached Data on
			 a Server to Stable Storage) procedure, that did
			 not result in the filesystem blocking to read
			 from disk, since the last boot."
	::= { tv3CachedCalls 22 }



	-- the tv3CachedPerCent group

		-- this group contains statistics for the number of
		-- calls received for each NFS Version 3 procedure,
		-- that did not result in the filesystem blocking to
		-- read from disk, as a percentage of the total
		-- number of calls received for that procedure,
		-- since the last boot

	tv3cpNulls                      OBJECT-TYPE
	SYNTAX                          Integer32 (0..100)
        MAX-ACCESS                      read-only
        STATUS                          current
	DESCRIPTION
			"The number of NFS Version 3 calls received
			 for the NFSPROC3_NULL (Do Nothing) procedure,
			 that did not result in the filesystem
			 blocking to read from disk, as a percentage
			 of the total number of calls received for
			 this procedure, since the last boot."
	::= { tv3CachedPerCent 1 }

	tv3cpGetattrs                   OBJECT-TYPE
	SYNTAX                          Integer32 (0..100)
        MAX-ACCESS                      read-only
        STATUS                          current
	DESCRIPTION
			"The number of NFS Version 3 calls received
			 for the NFSPROC3_GETATTR (Get File Attributes)
			 procedure, that did not result in the filesystem
			 blocking to read from disk, as a percentage
			 of the total number of calls received for
			 this procedure, since the last boot."
	::= { tv3CachedPerCent 2 }

	tv3cpSetattrs                   OBJECT-TYPE
	SYNTAX                          Integer32 (0..100)
        MAX-ACCESS                      read-only
        STATUS                          current
	DESCRIPTION
			"The number of NFS Version 3 calls received
			 for the NFSPROC3_SETATTR (Set File Attributes)
			 procedure, that did not result in the filesystem
			 blocking to read from disk, as a percentage
			 of the total number of calls received for
			 this procedure, since the last boot."
	::= { tv3CachedPerCent 3 }

	tv3cpLookups                    OBJECT-TYPE
	SYNTAX                          Integer32 (0..100)
        MAX-ACCESS                      read-only
        STATUS                          current
	DESCRIPTION
			"The number of NFS Version 3 calls received
			 for the NFSPROC3_LOOKUP (Lookup Filename)
			 procedure, that did not result in the filesystem
			 blocking to read from disk, as a percentage
			 of the total number of calls received for
			 this procedure, since the last boot."
	::= { tv3CachedPerCent 4 }

	tv3cpAccesss                    OBJECT-TYPE
	SYNTAX                          Integer32 (0..100)
        MAX-ACCESS                      read-only
        STATUS                          current
	DESCRIPTION
			"The number of NFS Version 3 calls received
			 for the NFSPROC3_ACCESS (Check Access Permission)
			 procedure, that did not result in the filesystem
			 blocking to read from disk, as a percentage
			 of the total number of calls received for
			 this procedure, since the last boot."
	::= { tv3CachedPerCent 5 }

	tv3cpReadlinks                  OBJECT-TYPE
	SYNTAX                          Integer32 (0..100)
        MAX-ACCESS                      read-only
        STATUS                          current
	DESCRIPTION
			"The number of NFS Version 3 calls received
			 for the NFSPROC3_READLINK (Read from Symbolic
			 Link) procedure, that did not result in the
			 filesystem blocking to read from disk, as a
			 percentage of the total number of calls
			 received for this procedure, since the last
			 last boot."
	::= { tv3CachedPerCent 6 }

	tv3cpReads                      OBJECT-TYPE
	SYNTAX                          Integer32 (0..100)
        MAX-ACCESS                      read-only
        STATUS                          current
	DESCRIPTION
			"The number of NFS Version 3 calls received
			 for the NFSPROC3_READ (Read From File)
			 procedure, that did not result in the
			 filesystem blocking to read from disk, as a
			 percentage of the total number of calls
			 received for this procedure, since the last boot."
	::= { tv3CachedPerCent 7 }

	tv3cpWrites                     OBJECT-TYPE
	SYNTAX                          Integer32 (0..100)
        MAX-ACCESS                      read-only
        STATUS                          current
	DESCRIPTION
			"The number of NFS Version 3 calls received
			 for the NFSPROC3_WRITE (Write to File)
			 procedure, that did not result in the
			 filesystem blocking to read from disk, as a
			 percentage of the total number of calls
			 received for this procedure, since the last boot."
	::= { tv3CachedPerCent 8 }

	tv3cpCreates                    OBJECT-TYPE
	SYNTAX                          Integer32 (0..100)
        MAX-ACCESS                      read-only
        STATUS                          current
	DESCRIPTION
			"The number of NFS Version 3 calls received
			 for the NFSPROC3_CREATE (Create a File)
			 procedure, that did not result in the
			 filesystem blocking to read from disk, as a
			 percentage of the total number of calls
			 received for this procedure, since the last boot."
	::= { tv3CachedPerCent 9 }

	tv3cpMkdirs                     OBJECT-TYPE
	SYNTAX                          Integer32 (0..100)
        MAX-ACCESS                      read-only
        STATUS                          current
	DESCRIPTION
			"The number of NFS Version 3 calls received
			 for the NFSPROC3_MKDIR (Create a Directory)
			 procedure, that did not result in the
			 filesystem blocking to read from disk, as a
			 percentage of the total number of calls
			 received for this procedure, since the last boot."
	::= { tv3CachedPerCent 10 }

	tv3cpSymlinks                   OBJECT-TYPE
	SYNTAX                          Integer32 (0..100)
        MAX-ACCESS                      read-only
        STATUS                          current
	DESCRIPTION
			"The number of NFS Version 3 calls received
			 for the NFSPROC3_SYMLINK (Create a Symbolic
			 Link) procedure, that did not result in the
			 filesystem blocking to read from disk, as a
			 percentage of the total number of calls
			 received for this procedure, since the last boot."
	::= { tv3CachedPerCent 11 }

	tv3cpMknods                     OBJECT-TYPE
	SYNTAX                          Integer32 (0..100)
        MAX-ACCESS                      read-only
        STATUS                          current
	DESCRIPTION
			"The number of NFS Version 3 calls received
			 for the NFSPROC3_MKNOD (Create a Special
			 Device) procedure, that did not result in the
			 filesystem blocking to read from disk, as a
			 percentage of the total number of calls
			 received for this procedure, since the last boot."
	::= { tv3CachedPerCent 12 }

	tv3cpRemoves                    OBJECT-TYPE
	SYNTAX                          Integer32 (0..100)
        MAX-ACCESS                      read-only
        STATUS                          current
	DESCRIPTION
			"The number of NFS Version 3 calls received
			 for the NFSPROC3_REMOVE (Remove a File)
			 procedure, that did not result in the
			 filesystem blocking to read from disk, as a
			 percentage of the total number of calls
			 received for this procedure, since the last boot."
	::= { tv3CachedPerCent 13 }

	tv3cpRmdirs                     OBJECT-TYPE
	SYNTAX                          Integer32 (0..100)
        MAX-ACCESS                      read-only
        STATUS                          current
	DESCRIPTION
			"The number of NFS Version 3 calls received
			 for the NFSPROC3_RMDIR (Remove a Directory)
			 procedure, that did not result in the
			 filesystem blocking to read from disk, as a
			 percentage of the total number of calls
			 received for this procedure, since the last boot."
	::= { tv3CachedPerCent 14 }

	tv3cpRenames                    OBJECT-TYPE
	SYNTAX                          Integer32 (0..100)
        MAX-ACCESS                      read-only
        STATUS                          current
	DESCRIPTION
			"The number of NFS Version 3 calls received
			 for the NFSPROC3_RENAME (Rename a File or
			 Directory) procedure, that did not result in
			 the filesystem blocking to read from disk,
			 as a percentage of the total number of calls
			 received for this procedure, since the last boot."
	::= { tv3CachedPerCent 15 }

	tv3cpLinks                      OBJECT-TYPE
	SYNTAX                          Integer32 (0..100)
        MAX-ACCESS                      read-only
        STATUS                          current
	DESCRIPTION
			"The number of NFS Version 3 calls received
			 for the NFSPROC3_LINK (Create Link to an
			 Object) procedure, that did not result in
			 the filesystem blocking to read from disk,
			 as a percentage of the total number of calls
			 received for this procedure, since the last boot."
	::= { tv3CachedPerCent 16 }

	tv3cpReaddirs                   OBJECT-TYPE
	SYNTAX                          Integer32 (0..100)
        MAX-ACCESS                      read-only
        STATUS                          current
	DESCRIPTION
			"The number of NFS Version 3 calls received
			 for the NFSPROC3_READDIR (Read From Directory)
			 procedure, that did not result in the
			 filesystem blocking to read from disk, as a
			 percentage of the total number of calls
			 received for this procedure, since the last boot."
	::= { tv3CachedPerCent 17 }

	tv3cpReaddirPluss               OBJECT-TYPE
	SYNTAX                          Integer32 (0..100)
        MAX-ACCESS                      read-only
        STATUS                          current
	DESCRIPTION
			"The number of NFS Version 3 calls received
			 for the NFSPROC3_READIRPLUS (Extended Read
			 from Directory) procedure, that did not result
			 in the filesystem blocking to read from disk,
			 as a percentage of the total number of calls
			 received for this procedure, since the last boot."
	::= { tv3CachedPerCent 18 }

	tv3cpFsstats                    OBJECT-TYPE
	SYNTAX                          Integer32 (0..100)
        MAX-ACCESS                      read-only
        STATUS                          current
	DESCRIPTION
			"The number of NFS Version 3 calls received
			 for the NFSPROC3_FSSTAT (Get Dynamic File
			 System Information) procedure, that did not
			 result in the filesystem blocking to read from
			 disk, as a percentage of the total number of
			 calls received for this procedure, since the
			 last boot."
	::= { tv3CachedPerCent 19 }

	tv3cpFsinfos                    OBJECT-TYPE
	SYNTAX                          Integer32 (0..100)
        MAX-ACCESS                      read-only
        STATUS                          current
	DESCRIPTION
			"The number of NFS Version 3 calls received
			 for the NFSPROC3_FSINFO (Get Static File System
			 Information) procedure, that did not result
			 in the filesystem blocking to read from disk,
			 as a percentage of the total number of calls
			 received for this procedure, since the last boot."
	::= { tv3CachedPerCent 20 }

	tv3cpPathconfs                  OBJECT-TYPE
	SYNTAX                          Integer32 (0..100)
        MAX-ACCESS                      read-only
        STATUS                          current
	DESCRIPTION
			"The number of NFS Version 3 calls received
			 for the NFSPROC3_PATHCONF (Retrieve POSIX
			 Information) procedure, that did not result
			 in the filesystem blocking to read from disk,
			 as a percentage of the total number of calls
			 received for this procedure, since the last boot."
	::= { tv3CachedPerCent 21 }

	tv3cpCommits                    OBJECT-TYPE
	SYNTAX                          Integer32 (0..100)
        MAX-ACCESS                      read-only
        STATUS                          current
	DESCRIPTION
			"The number of NFS Version 3 calls received
			 for the NFSPROC3_COMMIT (Commit Cached Data on
			 a Server to Stable Storage) procedure, that
			 did not result in the filesystem blocking to
			 read from disk, as a percentage of the total
			 number of calls received for this procedure,
			 since the last boot."
	::= { tv3CachedPerCent 22 }


	-- the treplyCache group

		-- this group contains statistics related to the
		-- Reply Cache processing, since the last boot

	trcInProgressHits               OBJECT-TYPE
	SYNTAX                          Counter32
        MAX-ACCESS                      read-only
        STATUS                          current
	DESCRIPTION
			"The number of NFS requests that were dropped, for
			 calls already in progress, since the last boot."
	::= { treplyCache 1 }

	trcDelayHits                    OBJECT-TYPE
	SYNTAX                          Counter32
        MAX-ACCESS                      read-only
        STATUS                          deprecated
	DESCRIPTION
			"The number of NFS requests that were dropped,
			 for replies already generated within a short
			 interval, since the last boot. These stats are
			 deprecated. A value of zero will always be
			 returned for these stats."
	::= { treplyCache 2 }

	trcMisses                       OBJECT-TYPE
	SYNTAX                          Counter32
        MAX-ACCESS                      read-only
        STATUS                          current
	DESCRIPTION
			"The number of NFS requests received for which
			 there were no corresponding entries already in
			 the Reply Cache, since the last boot."
	::= { treplyCache 3 }

	trcNonIdemDoneHits              OBJECT-TYPE
	SYNTAX                          Counter32
        MAX-ACCESS                      read-only
        STATUS                          current
	DESCRIPTION
			"The number of NFS requests received that
			 resulted in replies being replayed from
			 the Reply Cache, since the last boot."
	::= { treplyCache 4 }

	trcNonIdemNotDoneHits           OBJECT-TYPE
	SYNTAX                          Counter32
        MAX-ACCESS                      read-only
        STATUS                          current
	DESCRIPTION
			"The number of NFS requests received for calls
			 that resulted in this request being processed
			 as a new request even when a corresponding
			 entry existed in the Reply Cache, since the
			 last boot."
	::= { treplyCache 5 }

	trcTcpInProgressHits            OBJECT-TYPE
	SYNTAX                          Counter32
        MAX-ACCESS                      read-only
        STATUS                          current
	DESCRIPTION
			"The number of NFS requests that were dropped
			 for the TCP protocol, for calls already in
			 progress, since the last boot."
	::= { treplyCache 6 }

	trcTcpDelayHits                 OBJECT-TYPE
	SYNTAX                          Counter32
        MAX-ACCESS                      read-only
        STATUS                          deprecated
	DESCRIPTION
			"The number of NFS requests that were dropped
			 for the TCP protocol, for replies already
			 generated within a short interval, since the
			 last boot. These stats are deprecated. A value
			 of zero will always be returned for these stats."
	::= { treplyCache 7 }

	trcTcpMisses                    OBJECT-TYPE
	SYNTAX                          Counter32
        MAX-ACCESS                      read-only
        STATUS                          current
	DESCRIPTION
			"The number of NFS requests received for the
			 TCP protocol for which there were no corresponding
			 entries already in the Reply Cache, since the
			 last boot."
	::= { treplyCache 8 }

	trcTcpNonIdemDoneHits           OBJECT-TYPE
	SYNTAX                          Counter32
        MAX-ACCESS                      read-only
        STATUS                          current
	DESCRIPTION
			"The number of NFS requests received for the
			 TCP protocol that resulted in replies being
			 replayed from the Reply Cache, since the
			 last boot."
	::= { treplyCache 9 }

	trcTcpNonIdemNotDoneHits        OBJECT-TYPE
	SYNTAX                          Counter32
        MAX-ACCESS                      read-only
        STATUS                          current
	DESCRIPTION
			"The number of NFS requests received for the
			 TCP protocol for calls that resulted in this
			 request being processed as a new request even
			 when a corresponding entry existed in the Reply
			 Cache, since the last boot."
	::= { treplyCache 10 }

	trcUdpInProgressHits            OBJECT-TYPE
	SYNTAX                          Counter32
        MAX-ACCESS                      read-only
        STATUS                          current
	DESCRIPTION
			"The number of NFS requests that were dropped
			 for the UDP protocol, for calls already in
			 progress, since the last boot."
	::= { treplyCache 11 }

	trcUdpDelayHits                 OBJECT-TYPE
	SYNTAX                          Counter32
        MAX-ACCESS                      read-only
        STATUS                          deprecated
	DESCRIPTION
			"The number of NFS requests that were dropped
			 for the UDP protocol, for replies already
			 generated within a short interval, since the
			 last boot. These stats are deprecated. A value
			 of zero will always be returned for these stats."
	::= { treplyCache 12 }

	trcUdpMisses                    OBJECT-TYPE
	SYNTAX                          Counter32
        MAX-ACCESS                      read-only
        STATUS                          current
	DESCRIPTION
			"The number of NFS requests received for the
			 UDP protocol for which there were no corresponding
			 entries already in the Reply Cache, since the
			 last boot."
	::= { treplyCache 13 }

	trcUdpNonIdemDoneHits           OBJECT-TYPE
	SYNTAX                          Counter32
        MAX-ACCESS                      read-only
        STATUS                          current
	DESCRIPTION
			"The number of NFS requests received for the
			 UDP protocol that resulted in replies being
			 replayed from the Reply Cache, since the
			 last boot."
	::= { treplyCache 14 }

	trcUdpNonIdemNotDoneHits        OBJECT-TYPE
	SYNTAX                          Counter32
        MAX-ACCESS                      read-only
        STATUS                          current
	DESCRIPTION
			"The number of NFS requests received for the
			 UDP protocol for calls that resulted in this
			 request being processed as a new request even
			 when a corresponding entry existed in the Reply
			 Cache, since the last boot."
	::= { treplyCache 15 }

	-- the tnfsrwStats group

		-- this group contains statistics for the sizes of
                -- NFS version 2 and 3 read and write calls since
		-- last boot.

	tv2ReadStats            OBJECT IDENTIFIER ::= { tnfsrwStats 1 }

	tv2WriteStats           OBJECT IDENTIFIER ::= { tnfsrwStats 2 }

	tv3ReadStats            OBJECT IDENTIFIER ::= { tnfsrwStats 3 }

	tv3WriteStats           OBJECT IDENTIFIER ::= { tnfsrwStats 4 }


	-- the tv2ReadStats group

		-- this group contains statistics for the sizes of
		-- NFS version 2 read calls since last boot.

	tv2Read512Calls                 OBJECT-TYPE
	SYNTAX                          Counter32
        MAX-ACCESS                      read-only
        STATUS                          current
	DESCRIPTION
			"The number of NFS Version 2 read calls
			received by the server since last boot
			with request sizes between 0-511 bytes."
	::= { tv2ReadStats 1 }

	tv2Read1KCalls                  OBJECT-TYPE
	SYNTAX                          Counter32
        MAX-ACCESS                      read-only
        STATUS                          current
	DESCRIPTION
			"The number of NFS Version 2 read calls
			received by the server since last boot
			with request sizes between 512-1023 bytes."
	::= { tv2ReadStats 2 }

	tv2Read2KCalls                  OBJECT-TYPE
	SYNTAX                          Counter32
        MAX-ACCESS                      read-only
        STATUS                          current
	DESCRIPTION
			"The number of NFS Version 2 read calls
			received by the server since last boot
			with request sizes between 1K-2047 bytes."
	::= { tv2ReadStats 3 }


	tv2Read4KCalls                  OBJECT-TYPE
	SYNTAX                          Counter32
        MAX-ACCESS                      read-only
        STATUS                          current
	DESCRIPTION
			"The number of NFS Version 2 read calls
			received by the server since last boot
			with request sizes between 2K-4095 bytes."
	::= { tv2ReadStats 4 }

	tv2Read8KCalls                  OBJECT-TYPE
	SYNTAX                          Counter32
        MAX-ACCESS                      read-only
        STATUS                          current
	DESCRIPTION
			"The number of NFS Version 2 read calls
			received by the server since last boot
			with request sizes between 4K-8191 bytes."
	::= { tv2ReadStats 5 }

	tv2Read16KCalls                 OBJECT-TYPE
	SYNTAX                          Counter32
        MAX-ACCESS                      read-only
        STATUS                          current
	DESCRIPTION
			"The number of NFS Version 2 read calls
			received by the server since last boot
			with request sizes between 8K-16383 bytes."
	::= { tv2ReadStats 6 }

	tv2Read32KCalls                 OBJECT-TYPE
	SYNTAX                          Counter32
        MAX-ACCESS                      read-only
        STATUS                          current
	DESCRIPTION
			"The number of NFS Version 2 read calls
			received by the server since last boot
			with request sizes between 16K-32767 bytes."
	::= { tv2ReadStats 7 }

	tv2Read64KCalls                 OBJECT-TYPE
	SYNTAX                          Counter32
        MAX-ACCESS                      read-only
        STATUS                          current
	DESCRIPTION
			"The number of NFS Version 2 read calls
			received by the server since last boot
			with request sizes between 32K-65535 bytes."
	::= { tv2ReadStats 8 }

	tv2Read128KCalls                OBJECT-TYPE
	SYNTAX                          Counter32
        MAX-ACCESS                      read-only
        STATUS                          current
	DESCRIPTION
			"The number of NFS Version 2 read calls
			received by the server since last boot
			with request sizes between 64K-131071 bytes."
	::= { tv2ReadStats 9 }


	-- the tv2WriteStats group

		-- this group contains statistics for the sizes of
		-- NFS version 2 write calls since last boot.

	tv2Write512Calls                OBJECT-TYPE
	SYNTAX                          Counter32
        MAX-ACCESS                      read-only
        STATUS                          current
	DESCRIPTION
			"The number of NFS Version 2 write calls
			received by the server since last boot
			with request sizes between 0-511 bytes."
	::= { tv2WriteStats 1 }

	tv2Write1KCalls                 OBJECT-TYPE
	SYNTAX                          Counter32
        MAX-ACCESS                      read-only
        STATUS                          current
	DESCRIPTION
			"The number of NFS Version 2 write calls
			received by the server since last boot
			with request sizes between 512-1023 bytes."
	::= { tv2WriteStats 2 }

	tv2Write2KCalls                 OBJECT-TYPE
	SYNTAX                          Counter32
        MAX-ACCESS                      read-only
        STATUS                          current
	DESCRIPTION
			"The number of NFS Version 2 write calls
			received by the server since last boot
			with request sizes between 1K-2047 bytes."
	::= { tv2WriteStats 3 }


	tv2Write4KCalls                 OBJECT-TYPE
	SYNTAX                          Counter32
        MAX-ACCESS                      read-only
        STATUS                          current
	DESCRIPTION
			"The number of NFS Version 2 write calls
			received by the server since last boot
			with request sizes between 2K-4095 bytes."
	::= { tv2WriteStats 4 }

	tv2Write8KCalls                 OBJECT-TYPE
	SYNTAX                          Counter32
        MAX-ACCESS                      read-only
        STATUS                          current
	DESCRIPTION
			"The number of NFS Version 2 write calls
			received by the server since last boot
			with request sizes between 4K-8191 bytes."
	::= { tv2WriteStats 5 }

	tv2Write16KCalls                OBJECT-TYPE
	SYNTAX                          Counter32
        MAX-ACCESS                      read-only
        STATUS                          current
	DESCRIPTION
			"The number of NFS Version 2 write calls
			received by the server since last boot
			with request sizes between 8K-16383 bytes."
	::= { tv2WriteStats 6 }

	tv2Write32KCalls                OBJECT-TYPE
	SYNTAX                          Counter32
        MAX-ACCESS                      read-only
        STATUS                          current
	DESCRIPTION
			"The number of NFS Version 2 write calls
			received by the server since last boot
			with request sizes between 16K-32767 bytes."
	::= { tv2WriteStats 7 }

	tv2Write64KCalls                OBJECT-TYPE
	SYNTAX                          Counter32
        MAX-ACCESS                      read-only
        STATUS                          current
	DESCRIPTION
			"The number of NFS Version 2 write calls
			received by the server since last boot
			with request sizes between 32K-65535 bytes."
	::= { tv2WriteStats 8 }

	tv2Write128KCalls               OBJECT-TYPE
	SYNTAX                          Counter32
        MAX-ACCESS                      read-only
        STATUS                          current
	DESCRIPTION
			"The number of NFS Version 2 write calls
			received by the server since last boot
			with request sizes between 64K-131071 bytes."
	::= { tv2WriteStats 9 }


	-- the tv3ReadStats group

		-- this group contains statistics for the sizes of
		-- NFS version 3 read calls since last boot.

	tv3Read512Calls                 OBJECT-TYPE
	SYNTAX                          Counter32
        MAX-ACCESS                      read-only
        STATUS                          current
	DESCRIPTION
			"The number of NFS Version 3 read calls
			received by the server since last boot
			with request sizes between 0-511 bytes."
	::= { tv3ReadStats 1 }

	tv3Read1KCalls                  OBJECT-TYPE
	SYNTAX                          Counter32
        MAX-ACCESS                      read-only
        STATUS                          current
	DESCRIPTION
			"The number of NFS Version 3 read calls
			received by the server since last boot
			with request sizes between 512-1023 bytes."
	::= { tv3ReadStats 2 }

	tv3Read2KCalls                  OBJECT-TYPE
	SYNTAX                          Counter32
        MAX-ACCESS                      read-only
        STATUS                          current
	DESCRIPTION
			"The number of NFS Version 3 read calls
			received by the server since last boot
			with request sizes between 1K-2047 bytes."
	::= { tv3ReadStats 3 }


	tv3Read4KCalls                  OBJECT-TYPE
	SYNTAX                          Counter32
        MAX-ACCESS                      read-only
        STATUS                          current
	DESCRIPTION
			"The number of NFS Version 3 read calls
			received by the server since last boot
			with request sizes between 2K-4095 bytes."
	::= { tv3ReadStats 4 }

	tv3Read8KCalls                  OBJECT-TYPE
	SYNTAX                          Counter32
        MAX-ACCESS                      read-only
        STATUS                          current
	DESCRIPTION
			"The number of NFS Version 3 read calls
			received by the server since last boot
			with request sizes between 4K-8191 bytes."
	::= { tv3ReadStats 5 }

	tv3Read16KCalls                 OBJECT-TYPE
	SYNTAX                          Counter32
        MAX-ACCESS                      read-only
        STATUS                          current
	DESCRIPTION
			"The number of NFS Version 3 read calls
			received by the server since last boot
			with request sizes between 8K-16383 bytes."
	::= { tv3ReadStats 6 }

	tv3Read32KCalls                 OBJECT-TYPE
	SYNTAX                          Counter32
        MAX-ACCESS                      read-only
        STATUS                          current
	DESCRIPTION
			"The number of NFS Version 3 read calls
			received by the server since last boot
			with request sizes between 16K-32767 bytes."
	::= { tv3ReadStats 7 }

	tv3Read64KCalls                 OBJECT-TYPE
	SYNTAX                          Counter32
        MAX-ACCESS                      read-only
        STATUS                          current
	DESCRIPTION
			"The number of NFS Version 3 read calls
			received by the server since last boot
			with request sizes between 32K-65535 bytes."
	::= { tv3ReadStats 8 }

	tv3Read128KCalls                OBJECT-TYPE
	SYNTAX                          Counter32
        MAX-ACCESS                      read-only
        STATUS                          current
	DESCRIPTION
			"The number of NFS Version 3 read calls
			received by the server since last boot
			with request sizes between 64K-131071 bytes."
	::= { tv3ReadStats 9 }


	-- the tv3WriteStats group

		-- this group contains statistics for the sizes of
		-- NFS version 3 write calls since last boot.

	tv3Write512Calls                OBJECT-TYPE
	SYNTAX                          Counter32
        MAX-ACCESS                      read-only
        STATUS                          current
	DESCRIPTION
			"The number of NFS Version 3 write calls
			received by the server since last boot
			with request sizes between 0-511 bytes."
	::= { tv3WriteStats 1 }

	tv3Write1KCalls                 OBJECT-TYPE
	SYNTAX                          Counter32
        MAX-ACCESS                      read-only
        STATUS                          current
	DESCRIPTION
			"The number of NFS Version 3 write calls
			received by the server since last boot
			with request sizes between 512-1023 bytes."
	::= { tv3WriteStats 2 }

	tv3Write2KCalls                 OBJECT-TYPE
	SYNTAX                          Counter32
        MAX-ACCESS                      read-only
        STATUS                          current
	DESCRIPTION
			"The number of NFS Version 3 write calls
			received by the server since last boot
			with request sizes between 1K-2047 bytes."
	::= { tv3WriteStats 3 }

	tv3Write4KCalls                 OBJECT-TYPE
	SYNTAX                          Counter32
        MAX-ACCESS                      read-only
        STATUS                          current
	DESCRIPTION
			"The number of NFS Version 3 write calls
			received by the server since last boot
			with request sizes between 2K-4095 bytes."
	::= { tv3WriteStats 4 }

	tv3Write8KCalls                 OBJECT-TYPE
	SYNTAX                          Counter32
        MAX-ACCESS                      read-only
        STATUS                          current
	DESCRIPTION
			"The number of NFS Version 3 write calls
			received by the server since last boot
			with request sizes between 4K-8191 bytes."
	::= { tv3WriteStats 5 }

	tv3Write16KCalls                OBJECT-TYPE
	SYNTAX                          Counter32
        MAX-ACCESS                      read-only
        STATUS                          current
	DESCRIPTION
			"The number of NFS Version 3 write calls
			received by the server since last boot
			with request sizes between 8K-16383 bytes."
	::= { tv3WriteStats 6 }

	tv3Write32KCalls                OBJECT-TYPE
	SYNTAX                          Counter32
        MAX-ACCESS                      read-only
        STATUS                          current
	DESCRIPTION
			"The number of NFS Version 3 write calls
			received by the server since last boot
			with request sizes between 16K-32767 bytes."
	::= { tv3WriteStats 7 }

	tv3Write64KCalls                OBJECT-TYPE
	SYNTAX                          Counter32
        MAX-ACCESS                      read-only
        STATUS                          current
	DESCRIPTION
			"The number of NFS Version 3 write calls
			received by the server since last boot
			with request sizes between 32K-65535 bytes."
	::= { tv3WriteStats 8 }

	tv3Write128KCalls               OBJECT-TYPE
	SYNTAX                          Counter32
        MAX-ACCESS                      read-only
        STATUS                          current
	DESCRIPTION
			"The number of NFS Version 3 write calls
			received by the server since last boot
			with request sizes between 64K-131071 bytes."
	::= { tv3WriteStats 9 }


	-- -- -- -- -- -- -- -- -- -- -- -- -- -- -- -- -- --
	-- the nfsOptions group
	-- -- -- -- -- -- -- -- -- -- -- -- -- -- -- -- -- --

	nfsIsLicensed                   OBJECT-TYPE
	SYNTAX                          INTEGER {
                                             false(1),
                                             true(2)
                                        }
        MAX-ACCESS                      read-only
        STATUS                          current
	DESCRIPTION
			"Whether the nfs protocol is licensed on the
			 filer."
	::= { nfsOptions 1 }


	-- -- -- -- -- --  --
	-- the quota group --
	-- -- -- -- -- --  --

	quotaState                      OBJECT-TYPE
	SYNTAX                          INTEGER {
                                             quotaStateOff(1),
                                             quotaStateOn(2),
                                             quotaStateInit(3)
                                        }
        MAX-ACCESS                      read-only
        STATUS                          deprecated
	DESCRIPTION
			"Indicates whether the root volume's quotas are ON,
			 OFF or initializing.  This object is deprecated -
			 use qvStateTable.qvStateStat instead."
	::= { quota 1 }

	quotaInitPercent                OBJECT-TYPE
	SYNTAX                          Integer32 (0..100)
        MAX-ACCESS                      read-only
        STATUS                          deprecated
	DESCRIPTION
			"Indicates percentage of root volume quota
			 computation done while quotas are in initializing
			 state. This object is deprecated - use
			 qvStateTable.qvInitPercent instead."
	::= { quota 2 }


	-- the old volume-unaware quota report table.  DEPRECATED

	qrTable                         OBJECT-TYPE
	SYNTAX                          SEQUENCE OF QrEntry
        MAX-ACCESS                      not-accessible
        STATUS                          deprecated
	DESCRIPTION
			"Provide a report of the current file and
			 space consumption for each user or group with
			 a quota in /etc/quotas.  All quotas are displayed
			 regardless of volume, and no volume information
			 is given.  This table is deprecated - use qrVTable
			 instead."
	::= { quota 3 }

	qrEntry                         OBJECT-TYPE
	SYNTAX                          QrEntry
        MAX-ACCESS                      not-accessible
        STATUS                          deprecated
	DESCRIPTION
			"Provide a report of the current file and
			 space consumption for a referenced entry
			 with a quota in the file /etc/quotas.
			 All quotas are displayed regardless of volume,
			 and no volume information is given.  This object is
			 deprecated - use qrVEntry instead."

	INDEX	{ qrIndex }
	::= { qrTable 1 }

	QrEntry ::=
	    SEQUENCE {
		qrIndex
		    Integer32,
		qrType
		    INTEGER,
		qrId
		    Integer32,
		qrKBytesUsed
		    Integer32,
		qrKBytesLimit
		    Integer32,
		qrFilesUsed
		    Integer32,
		qrFileLimit
		    Integer32,
		qrPathName
		    DisplayString
	    }

	qrIndex                         OBJECT-TYPE
	SYNTAX                          Integer32 (1..2147483647)
        MAX-ACCESS                      read-only
        STATUS                          deprecated
	DESCRIPTION
			"A number that identifies this entry in the
			 file /etc/quotas."
	::= { qrEntry 1 }

	qrType                          OBJECT-TYPE
	SYNTAX                          INTEGER {
                                             qrTypeUser(1),
                                             qrTypeGroup(2),
					     qrTypeTree(3),
                                             qrTypeUnknown(4)
                                        }
        MAX-ACCESS                      read-only
        STATUS                          deprecated
	DESCRIPTION
			"Identifies the kind of quota for this qrEntry."
	::= { qrEntry 2 }

	qrId                            OBJECT-TYPE
	SYNTAX                          Integer32
        MAX-ACCESS                      read-only
        STATUS                          deprecated
	DESCRIPTION
			"The UID (user's numerical ID) or the GID (numerical
			 ID of  the  group  that a user belongs to), as
			 applicable, associated with this qrEntry."
	::= { qrEntry 3 }

	qrKBytesUsed                    OBJECT-TYPE
	SYNTAX                          Integer32
        MAX-ACCESS                      read-only
        STATUS                          deprecated
	DESCRIPTION
			"The current number of KBytes used for this
			 qrEntry."
	::= { qrEntry 4 }

	qrKBytesLimit                   OBJECT-TYPE
	SYNTAX                          Integer32
        MAX-ACCESS                      read-only
        STATUS                          deprecated
	DESCRIPTION
			"The limit of KBytes that can be used for this
			 qrEntry."
	::= { qrEntry 5 }

	qrFilesUsed                     OBJECT-TYPE
	SYNTAX                          Integer32
        MAX-ACCESS                      read-only
        STATUS                          deprecated
	DESCRIPTION
			"The current number of files used for this
			 qrEntry."
	::= { qrEntry 6 }

	qrFileLimit                     OBJECT-TYPE
	SYNTAX                          Integer32
        MAX-ACCESS                      read-only
        STATUS                          deprecated
	DESCRIPTION
			"The limit of files that can be used for this
			 qrEntry."
	::= { qrEntry 7 }

	qrPathName                      OBJECT-TYPE
	SYNTAX                          DisplayString
        MAX-ACCESS                      read-only
        STATUS                          deprecated
	DESCRIPTION
			"A textual string that contains the path
			 corresponding to this qrEntry."
	::= { qrEntry 8 }

	-- quota volume state table

	qvStateTable                    OBJECT-TYPE
	SYNTAX                          SEQUENCE OF QvStateEntry
        MAX-ACCESS                      not-accessible
        STATUS                          current
	DESCRIPTION
			"Provide a report of the current quota state of
			each volume in the system."
	::= { quota 4 }

	qvStateEntry                    OBJECT-TYPE
	SYNTAX                          QvStateEntry
        MAX-ACCESS                      not-accessible
        STATUS                          current
	DESCRIPTION
			"Provide a report of the current quota state of
			each volume in the system."
	INDEX	{ qvStateVolume }
	::= { qvStateTable 1 }

	QvStateEntry ::=
	    SEQUENCE {
		qvStateVolume
		    Integer32,
		qvStateName
		    DisplayString,
		qvStateStat
		    INTEGER,
		qvStateInitPercent
		    Integer32,
		qvStateVserver
		    DisplayString
	    }

	qvStateVolume                   OBJECT-TYPE
	SYNTAX                          Integer32 (1..2147483647)
        MAX-ACCESS                      read-only
        STATUS                          current
	DESCRIPTION
			"A number that identifies this volume.  The mapping
       			 of this number to actual volumes may change if
			 volumes are added or deleted.  Use qvStateName to
			 unambiguously identify a volume.  The mapping
			 established by this object is the same as
			 the mapping of qrVVolume (below) to actual volumes.
			 For instance, if a qvStateVolume value of '5'
			 represents the volume 'vol2', a value of '5'
			 in qrVVolume also represents the volume 'vol2'."
	::= { qvStateEntry 1 }

	qvStateName                     OBJECT-TYPE
	SYNTAX                          DisplayString
        MAX-ACCESS                      read-only
        STATUS                          current
	DESCRIPTION
			"Indicates the name of this volume."
	::= { qvStateEntry 2 }

	qvStateStat                     OBJECT-TYPE
	SYNTAX                          INTEGER {
                                             quotaStateOff(1),
                                             quotaStateOn(2),
                                             quotaStateInit(3),
					     quotaStateCorrupt(4)
                                        }
        MAX-ACCESS                      read-only
        STATUS                          current
	DESCRIPTION
			"Indicates whether quotas are ON, OFF,
			 initializing or corrupted"
	::= { qvStateEntry 3 }

	qvStateInitPercent              OBJECT-TYPE
	SYNTAX                          Integer32 (0..100)
        MAX-ACCESS                      read-only
        STATUS                          current
	DESCRIPTION
			"Indicates percentage of quota computation done
			 while quotas are in initializing state."
	::= { qvStateEntry 4 }

	qvStateVserver                  OBJECT-TYPE
	SYNTAX                          DisplayString
        MAX-ACCESS                      read-only
        STATUS                          current
	DESCRIPTION
			"Indicates the vserver to which the volume belongs.
			 Name from the cluster interfaces.
                         Only applicable to cluster-mode volume."
	::= { qvStateEntry 5 }


	-- multi-volume-aware quota table
	-- THIS IS DEPRECATED, please use qrV2Table instead

	qrVTable                        OBJECT-TYPE
	SYNTAX                          SEQUENCE OF QrVEntry
        MAX-ACCESS                      not-accessible
        STATUS                          deprecated
	DESCRIPTION
			"Provide a report of the current file and
			 space consumption for each user or group with
			 a quota in /etc/quotas."
	::= { quota 5 }


	qrVEntry                        OBJECT-TYPE
	SYNTAX                          QrVEntry
        MAX-ACCESS                      not-accessible
        STATUS                          deprecated
	DESCRIPTION
			"Provide a report of the current file and
			 space consumption for a referenced entry
			 with a quota in the file /etc/quotas.  Indices
			 select the volume of the quota and the quota entry
			 itself."
	INDEX	{ qrVVolume, qrVIndex }
	::= { qrVTable 1 }

	QrVEntry ::=
	    SEQUENCE {
		qrVIndex
		    Integer32,
		qrVType
		    INTEGER,
		qrVId
		    Integer32,
		qrVKBytesUsed
		    Integer32,
		qrVKBytesLimit
		    Integer32,
		qrVFilesUsed
		    Integer32,
		qrVFileLimit
		    Integer32,
		qrVPathName
		    DisplayString,
		qrVVolume
		    Integer32,
		qrVTree
		    DisplayString,
		qrVIdType
		    INTEGER,
                qrVSid
                    DisplayString,
	        qrVKBytesThreshold
                    Integer32,
		qrVKBytesLimitSoft
		    Integer32,
		qrVFileLimitSoft
		    Integer32
	    }

	qrVIndex                        OBJECT-TYPE
	SYNTAX                          Integer32 (1..2147483647)
        MAX-ACCESS                      read-only
        STATUS                          deprecated
	DESCRIPTION
			"A number that identifies this entry in the
			 file /etc/quotas in the given volume."
	::= { qrVEntry 1 }

	qrVType                         OBJECT-TYPE
	SYNTAX                          INTEGER {
                                             qrVTypeUser(1),
                                             qrVTypeGroup(2),
					     qrVTypeTree(3),
					     qrVTypeUserDefault(4),
					     qrVTypeGroupDefault(5),
                                             qrVTypeUnknown(6)
                                        }
        MAX-ACCESS                      read-only
        STATUS                          deprecated
	DESCRIPTION
			"Identifies the kind of quota for this qrVEntry."
	::= { qrVEntry 2 }

	qrVId                           OBJECT-TYPE
	SYNTAX                          Integer32
        MAX-ACCESS                      read-only
        STATUS                          deprecated
	DESCRIPTION
			"The UID (user's numerical ID) or the GID (numerical
			 ID of  the  group  that a user belongs to), as
			 applicable, associated with this qrVEntry. Check
                         the qrVIdType field to see if this field is valid."
	::= { qrVEntry 3 }

	qrVKBytesUsed                   OBJECT-TYPE
	SYNTAX                          Integer32
        MAX-ACCESS                      read-only
        STATUS                          deprecated
	DESCRIPTION
			"The current number of KBytes used for this
			 qrVEntry."
	::= { qrVEntry 4 }

	qrVKBytesLimit                  OBJECT-TYPE
	SYNTAX                          Integer32
        MAX-ACCESS                      read-only
        STATUS                          deprecated
	DESCRIPTION
			"The limit of KBytes that can be used for this
			 qrVEntry."
	::= { qrVEntry 5 }

	qrVFilesUsed                    OBJECT-TYPE
	SYNTAX                          Integer32
        MAX-ACCESS                      read-only
        STATUS                          deprecated
	DESCRIPTION
			"The current number of files used for this
			 qrVEntry."
	::= { qrVEntry 6 }

	qrVFileLimit                    OBJECT-TYPE
	SYNTAX                          Integer32
        MAX-ACCESS                      read-only
        STATUS                          deprecated
	DESCRIPTION
			"The limit of files that can be used for this
			 qrVEntry."
	::= { qrVEntry 7 }

	qrVPathName                     OBJECT-TYPE
	SYNTAX                          DisplayString
        MAX-ACCESS                      read-only
        STATUS                          deprecated
	DESCRIPTION
			"A textual string that contains the path
			 corresponding to this qrVEntry."
	::= { qrVEntry 8 }

	qrVVolume                       OBJECT-TYPE
	SYNTAX                          Integer32 (1..2147483647)
        MAX-ACCESS                      read-only
        STATUS                          deprecated
	DESCRIPTION
			"A number that identifies the volume for which
			this quota is in effect on.  The volume that this
			value represents can be determined by checking
			the value of qvStateName (above) with
			qvStateVolume set to the value found here."
	::= { qrVEntry 9 }

        qrVTree                         OBJECT-TYPE
	SYNTAX                          DisplayString
        MAX-ACCESS                      read-only
        STATUS                          deprecated
        DESCRIPTION
			"A string that indicates which qtree this quota
			belongs to."
	::= { qrVEntry 10 }

        qrVIdType                       OBJECT-TYPE
	SYNTAX                          INTEGER {
                                             qrVIdValid(1),
                                             qrVSidValid(2)
                                        }
        MAX-ACCESS                      read-only
        STATUS                          deprecated
        DESCRIPTION
                        "A value that indicates which ID field is valid."
        ::= { qrVEntry 11}

	qrVSid                          OBJECT-TYPE
	SYNTAX                          DisplayString
        MAX-ACCESS                      read-only
        STATUS                          deprecated
	DESCRIPTION
			"The one or more IDs associated with this qrVEntry.
                         If the qrVentry is associated with a Windows ID, the
			 text form of the Windows ID (the SID) is here. If
			 the qrVEntry is associated with more than one id,
			 this contains a blank separated list of those IDs.
                         Check the qrVIdType field to see if this field is
                         valid."
	::= { qrVEntry 12 }

        qrVKBytesThreshold              OBJECT-TYPE
	SYNTAX                          Integer32
        MAX-ACCESS                      read-only
        STATUS                          deprecated
        DESCRIPTION
                        "A number of KBytes that when used by this entry
			 produces a warning message."
        ::= { qrVEntry 13 }

        qrVKBytesLimitSoft              OBJECT-TYPE
	SYNTAX                          Integer32
        MAX-ACCESS                      read-only
        STATUS                          deprecated
        DESCRIPTION
			"The limit of KBytes that can be used for this
			 qrVEntry before a warning message and SNMP
			 trap is produced."
        ::= { qrVEntry 14 }

        qrVFileLimitSoft                OBJECT-TYPE
	SYNTAX                          Integer32
        MAX-ACCESS                      read-only
        STATUS                          deprecated
        DESCRIPTION
			"The limit of files that can be used for this
			 qrVEntry before a warning message and SNMP
			 trap is produced."
        ::= { qrVEntry 15 }

	--
	-- multi-volume-aware quota table with 64 bit values (V2)
	--

	qrV2Table                       OBJECT-TYPE
	SYNTAX                          SEQUENCE OF QrV2Entry
        MAX-ACCESS                      not-accessible
        STATUS                          current
	DESCRIPTION
			"Provide a report of the current file and
			 space consumption for each user or group with
			 a quota in /etc/quotas."
	::= { quota 6 }


	qrV2Entry                       OBJECT-TYPE
	SYNTAX                          QrV2Entry
        MAX-ACCESS                      not-accessible
        STATUS                          current
	DESCRIPTION
			"Provide a report of the current file and
			 space consumption for a referenced entry
			 with a quota in the file /etc/quotas.  Indices
			 select the volume of the quota and the quota entry
			 itself."
	INDEX	{ qrV2Volume, qrV2Index }
	::= { qrV2Table 1 }

	QrV2Entry ::=
	    SEQUENCE {
		qrV2Index
		    Integer32,
		qrV2Type
		    INTEGER,
		qrV2Id
		    Integer32,
		qrV2HighKBytesUsed
		    Integer32,
		qrV2LowKBytesUsed
		    Integer32,
                qrV2QuotaUnlimited
		    INTEGER,
		qrV2HighKBytesLimit
		    Integer32,
		qrV2LowKBytesLimit
		    Integer32,
		qrV2FilesUsed
		    Integer32,
                qrV2FileQuotaUnlimited
		    INTEGER,
		qrV2FileLimit
		    Integer32,
		qrV2PathName
		    FilesystemPathString,
		qrV2Volume
		    Integer32,
		qrV2Tree
		    FileOrDirectoryString,
		qrV2IdType
		    INTEGER,
                qrV2Sid
                    DisplayString,
                qrV2ThresholdUnlimited
		    INTEGER,
	        qrV2HighKBytesThreshold
                    Integer32,
	        qrV2LowKBytesThreshold
                    Integer32,
                qrV2SoftQuotaUnlimited
		    INTEGER,
		qrV2HighKBytesSoftLimit
		    Integer32,
		qrV2LowKBytesSoftLimit
		    Integer32,
		qrV2SoftFileQuotaUnlimited
		    INTEGER,
		qrV2SoftFileLimit
		    Integer32,
		qrV264KBytesUsed
		    Counter64,
		qrV264KBytesLimit
		    Counter64,
	        qrV264KBytesThreshold
                    Counter64,
		qrV264KBytesSoftLimit
		    Counter64,
		qrV2VolumeName
		    DisplayString,
		qrV2Vserver
		    DisplayString
	    }

	qrV2Index                       OBJECT-TYPE
	SYNTAX                          Integer32 (1..2147483647)
        MAX-ACCESS                      read-only
        STATUS                          current
	DESCRIPTION
			"A number that identifies this entry in the
			 file /etc/quotas in the given volume."
	::= { qrV2Entry 1 }

	qrV2Type                        OBJECT-TYPE
	SYNTAX                          INTEGER {
                                             qrV2TypeUser(1),
                                             qrV2TypeGroup(2),
					     qrV2TypeTree(3),
					     qrV2TypeUserDefault(4),
					     qrV2TypeGroupDefault(5),
                                             qrV2TypeUnknown(6),
					     qrV2TypeTreeDefault(7)
                                        }
        MAX-ACCESS                      read-only
        STATUS                          current
	DESCRIPTION
			"Identifies the kind of quota for this qrV2Entry."
	::= { qrV2Entry 2 }

	qrV2Id                          OBJECT-TYPE
	SYNTAX                          Integer32
        MAX-ACCESS                      read-only
        STATUS                          current
	DESCRIPTION
			"The UID (user's numerical ID) or the GID (numerical
			 ID of  the  group  that a user belongs to), as
			 applicable, associated with this qrV2Entry. Check
                         the qrV2IdType field to see if this field is valid."
	::= { qrV2Entry 3 }

	qrV2HighKBytesUsed              OBJECT-TYPE
	SYNTAX                          Integer32
        MAX-ACCESS                      read-only
        STATUS                          deprecated
	DESCRIPTION
			"The current number of KBytes used for this
			 qrV2Entry. This object returns the most significant
			 32 bits of the 64 bit unsigned integer. This object
			 is deprecated - Use qrV264KBytesUsed instead."
	::= { qrV2Entry 4 }

	qrV2LowKBytesUsed               OBJECT-TYPE
	SYNTAX                          Integer32
        MAX-ACCESS                      read-only
        STATUS                          deprecated
	DESCRIPTION
			"The current number of KBytes used for this
			 qrV2Entry. This object returns the least significant
			 32 bits of the 64 bit unsigned integer. This object
			 is deprecated - Use qrV264KBytesUsed instead."
	::= { qrV2Entry 5 }

	qrV2QuotaUnlimited              OBJECT-TYPE
	SYNTAX                          INTEGER {
                                             false(1),
                                             true(2)
                                        }
        MAX-ACCESS                      read-only
        STATUS                          current
	DESCRIPTION
			"This flag designates whether or not the
			size based quota limit for this qrV2Entry is unlimited.
			If false(1) then qrV2*KBytesLimit OID's are valid,
			if true(2) then qrV2*KBytesLimit OID's are unused
			and will return 0."
	::= { qrV2Entry 6 }

	qrV2HighKBytesLimit             OBJECT-TYPE
	SYNTAX                          Integer32
        MAX-ACCESS                      read-only
        STATUS                          deprecated
	DESCRIPTION
			"The limit of KBytes that can be used for this
			 qrV2Entry. This object returns the most significant
			 32 bits of the 64 bit unsigned integer. This will
			 return 0 if qrV2QuotaUnlimited is true. This object
			 is deprecated - Use qrV264KBytesLimit instead."
	::= { qrV2Entry 7 }

	qrV2LowKBytesLimit              OBJECT-TYPE
	SYNTAX                          Integer32
        MAX-ACCESS                      read-only
        STATUS                          deprecated
	DESCRIPTION
			"The limit of KBytes that can be used for this
			 qrV2Entry. This object returns the least significant
			 32 bits of the 64 bit unsigned integer. This will
			 return 0 if qrV2QuotaUnlimited is true. This object
			 is deprecated - Use qrV264KBytesLimit instead."
	::= { qrV2Entry 8 }

	qrV2FilesUsed                   OBJECT-TYPE
	SYNTAX                          Integer32
        MAX-ACCESS                      read-only
        STATUS                          current
	DESCRIPTION
			"The current number of files used for this
			 qrV2Entry."
	::= { qrV2Entry 9 }

	qrV2FileQuotaUnlimited          OBJECT-TYPE
	SYNTAX                          INTEGER {
                                             false(1),
                                             true(2)
                                        }
        MAX-ACCESS                      read-only
        STATUS                          current
	DESCRIPTION
			"This flag designates whether or not the
			file based quota limit for this qrV2Entry is unlimited.
			If false(1) then qrV2FileLimit is valid, if true(2)
			qrV2FileLimit will return 0."
	::= { qrV2Entry 10 }


	qrV2FileLimit                   OBJECT-TYPE
	SYNTAX                          Integer32
        MAX-ACCESS                      read-only
        STATUS                          current
	DESCRIPTION
			"The limit of files that can be used for this
			 qrV2Entry."
	::= { qrV2Entry 11 }

	qrV2PathName                    OBJECT-TYPE
	SYNTAX                          FilesystemPathString
        MAX-ACCESS                      read-only
        STATUS                          current
	DESCRIPTION
			"A textual string that contains the path
			 corresponding to this qrV2Entry."
	::= { qrV2Entry 12 }

	qrV2Volume                      OBJECT-TYPE
	SYNTAX                          Integer32 (1..2147483647)
        MAX-ACCESS                      read-only
        STATUS                          current
	DESCRIPTION
			"A number that identifies the volume for which
			this quota is in effect on.  The volume that this
			value represents can be determined by checking
			the value of qvStateName (above) with
			qvStateVolume set to the value found here."
	::= { qrV2Entry 13 }

        qrV2Tree                        OBJECT-TYPE
	SYNTAX                          FileOrDirectoryString
        MAX-ACCESS                      read-only
        STATUS                          current
        DESCRIPTION
			"A string that indicates which qtree this quota
			belongs to."
	::= { qrV2Entry 14 }

        qrV2IdType                      OBJECT-TYPE
	SYNTAX                          INTEGER {
                                             qrV2IdValid(1),
                                             qrV2SidValid(2)
                                        }
        MAX-ACCESS                      read-only
        STATUS                          current
        DESCRIPTION
                        "A value that indicates which ID field is valid."
        ::= { qrV2Entry 15 }

	qrV2Sid                         OBJECT-TYPE
	SYNTAX                          DisplayString
        MAX-ACCESS                      read-only
        STATUS                          current
	DESCRIPTION
			"The one or more IDs associated with this qrV2Entry.
                         If the qrV2entry is associated with a Windows ID, the
			 text form of the Windows ID (the SID) is here. If
			 the qrV2Entry is associated with more than one id,
			 this contains a blank separated list of those IDs.
                         Check the qrV2IdType field to see if this field is
                         valid."
	::= { qrV2Entry 16 }

	qrV2ThresholdUnlimited          OBJECT-TYPE
	SYNTAX                          INTEGER {
                                             false(1),
                                             true(2)
                                        }
        MAX-ACCESS                      read-only
        STATUS                          current
	DESCRIPTION
			"This flag designates whether or not the
			size based threshold limit for this qrV2Entry is
			unlimited. If false(1) then qrV2*KBytesThreshold OID's
			are valid, if true(2) then qrV2*KBytesThreshold OID's
			are unused and will return 0."
	::= { qrV2Entry 17 }

        qrV2HighKBytesThreshold         OBJECT-TYPE
	SYNTAX                          Integer32
        MAX-ACCESS                      read-only
        STATUS                          deprecated
        DESCRIPTION
       			 "A number of KBytes that when used by this entry
			 produces a warning message. This object returns the
			 most significant 32 bits of the 64 bit unsigned
			 integer. This will return 0 if qrV2ThresholdUnlimited
			 is true. This object is deprecated - Use
			 qrV264KBytesThreshold instead."
        ::= { qrV2Entry 18 }

        qrV2LowKBytesThreshold          OBJECT-TYPE
	SYNTAX                          Integer32
        MAX-ACCESS                      read-only
        STATUS                          deprecated
        DESCRIPTION
       			 "A number of KBytes that when used by this entry
			 produces a warning message. This object returns the
			 least significant 32 bits of the 64 bit unsigned
			 integer. This will return 0 if qrV2ThresholdUnlimited
			 is true. This object is deprecated - Use
			 qrV264KBytesThreshold instead."
        ::= { qrV2Entry 19 }

	qrV2SoftQuotaUnlimited          OBJECT-TYPE
	SYNTAX                          INTEGER {
                                             false(1),
                                             true(2)
                                        }
        MAX-ACCESS                      read-only
        STATUS                          current
	DESCRIPTION
			"This flag designates whether or not the
			size based soft quota limit for this qrV2Entry is
			unlimited. If false(1) then qrV2*KBytesSoftLimit OID's
			are valid, if true(2) the qrV2*KBytesSoftLimit OID's
			are unused and will return 0."
	::= { qrV2Entry 20 }

        qrV2HighKBytesSoftLimit         OBJECT-TYPE
	SYNTAX                          Integer32
        MAX-ACCESS                      read-only
        STATUS                          deprecated
        DESCRIPTION
			"The limit of KBytes that can be used for this
			 qrV2Entry before a warning message and SNMP
			 trap is produced. This object returns the most
			 significant 32 bits of the 64 bit unsigned integer.
			 This object is deprecated - Use qrV264KBytesSoftLimit
			 instead."
        ::= { qrV2Entry 21 }

        qrV2LowKBytesSoftLimit          OBJECT-TYPE
	SYNTAX                          Integer32
        MAX-ACCESS                      read-only
        STATUS                          deprecated
        DESCRIPTION
			"The limit of KBytes that can be used for this
			 qrV2Entry before a warning message and SNMP
			 trap is produced. This object returns the least
			 significant 32 bits of the 64 bit unsigned integer.
			 This object is deprecated - Use qrV264KBytesSoftLimit
			 instead."
        ::= { qrV2Entry 22 }

	qrV2SoftFileQuotaUnlimited      OBJECT-TYPE
	SYNTAX                          INTEGER {
                                             false(1),
                                             true(2)
                                        }
        MAX-ACCESS                      read-only
        STATUS                          current
	DESCRIPTION
			"This flag designates whether or not the
			file based soft quota limit for this qrV2Entry is
			unlimited. If false(1) then qrV2SoftFileLimit is valid,
			if true(2) qrV2SoftFileLimit is unused and will
			return 0."
	::= { qrV2Entry 23 }

        qrV2SoftFileLimit               OBJECT-TYPE
	SYNTAX                          Integer32
        MAX-ACCESS                      read-only
        STATUS                          current
        DESCRIPTION
			"The limit of files that can be used for this
			 qrV2Entry before a warning message and SNMP
			 trap is produced. This will return 0 if
			 qrV2SoftFileQuotaUnlimited is true."
        ::= { qrV2Entry 24 }

	qrV264KBytesUsed                OBJECT-TYPE
	SYNTAX                          Counter64
        MAX-ACCESS                      read-only
        STATUS                          current
	DESCRIPTION
			"The current number of KBytes used for this
			 qrV2Entry. This object returns all of the 64 bit
			 unsigned integer."

	::= { qrV2Entry 25 }

	qrV264KBytesLimit               OBJECT-TYPE
	SYNTAX                          Counter64
        MAX-ACCESS                      read-only
        STATUS                          current
	DESCRIPTION
			"The limit of KBytes that can be used for this
			 qrV2Entry. This object returns all of the 64
			 bit unsigned integer. This will return 0 if
			 qrV2QuotaUnlimited is true."
	::= { qrV2Entry 26 }

        qrV264KBytesThreshold           OBJECT-TYPE
	SYNTAX                          Counter64
        MAX-ACCESS                      read-only
        STATUS                          current
        DESCRIPTION
                        "A number of KBytes that when used by this entry
			 produces a warning message. This object returns the
			 all of the 64 bit unsigned integer. This will return
			 0 if qrV2ThresholdUnlimited is true."
        ::= { qrV2Entry 27 }

        qrV264KBytesSoftLimit           OBJECT-TYPE
	SYNTAX                          Counter64
        MAX-ACCESS                      read-only
        STATUS                          current
        DESCRIPTION
			"The limit of KBytes that can be used for this
			 qrV2Entry before a warning message and SNMP
			 trap is produced. This object returns all of the
			 64 bit unsigned integer."
        ::= { qrV2Entry 28 }

	qrV2VolumeName                  OBJECT-TYPE
	SYNTAX                          DisplayString
        MAX-ACCESS                      read-only
        STATUS                          current
	DESCRIPTION
			"Indicates the name of the volume to which this quota
			 belongs to."
	::= { qrV2Entry 29 }

	qrV2Vserver                     OBJECT-TYPE
	SYNTAX                          DisplayString
        MAX-ACCESS                      read-only
        STATUS                          current
	DESCRIPTION
			"Indicates the vserver to which the volume belongs.
			 Name from the cluster interfaces.
			 Only applicable to cluster-mode volume."
	::= { qrV2Entry 30 }

	--
	-- quota table with 64 bit index (index-high,index-low) (V3)
	--

	qrV3Table                       OBJECT-TYPE
	SYNTAX                          SEQUENCE OF QrV3Entry
        MAX-ACCESS                      not-accessible
        STATUS                          current
	DESCRIPTION
			"Provide a report of the current file and
			 space consumption for each user, group,
                         or qtree, as well as configured limits."
	::= { quota 7 }


	qrV3Entry                       OBJECT-TYPE
	SYNTAX                          QrV3Entry
        MAX-ACCESS                      not-accessible
        STATUS                          current
	DESCRIPTION
			"Provide a report of the current file and
			 space consumption for the referenced user,
			 group, or qtree.  Field qrV3Volume identifies
                         the volume, and the combination of
                         qrV3IndexHigh and qrV3IndexLow indentify
                         a particular record within that volume."
	INDEX	{ qrV3Volume, qrV3IndexHigh, qrV3IndexLow }
	::= { qrV3Table 1 }

	QrV3Entry ::=
	    SEQUENCE {
		qrV3Volume
		    Unsigned32,
		qrV3IndexHigh
		    Unsigned32,
		qrV3IndexLow
		    Unsigned32,
		qrV3Vserver
		    DisplayString,
		qrV3VolumeName
		    DisplayString,
		qrV3Type
		    INTEGER,
		qrV3IdType
		    INTEGER,
		qrV3Id
		    Unsigned32,
                qrV3Sid
                    DisplayString,
		qrV3PathName
		    FilesystemPathString,
		qrV3Tree
		    FileOrDirectoryString,
		qrV3KBytesUsed
		    Counter64,
                qrV3QuotaUnlimited
		    INTEGER,
		qrV3KBytesLimit
		    Counter64,
		qrV3FilesUsed
		    Unsigned32,
                qrV3FileQuotaUnlimited
		    INTEGER,
		qrV3FileLimit
		    Unsigned32,
                qrV3SoftQuotaUnlimited
		    INTEGER,
		qrV3KBytesSoftLimit
		    Counter64,
		qrV3SoftFileQuotaUnlimited
		    INTEGER,
		qrV3SoftFileLimit
		    Unsigned32,
                qrV3ThresholdUnlimited
		    INTEGER,
	        qrV3KBytesThreshold
                    Counter64,
		qrV364FilesUsed
                    Counter64,
		qrV364FileLimit
                    Counter64,
		qrV364SoftFileLimit
                    Counter64
	    }

	qrV3Volume                      OBJECT-TYPE
	SYNTAX                          Unsigned32 (1..4294967295)
        MAX-ACCESS                      read-only
        STATUS                          current
	DESCRIPTION
			"A number that identifies the volume for which
			this quota applies. The volume that this
			value represents can be determined by checking
			the value of qvStateName (above) with
			qvStateVolume set to the value found here."
	::= { qrV3Entry 1 }

	qrV3IndexHigh                   OBJECT-TYPE
	SYNTAX                          Unsigned32 (1..4294967295)
        MAX-ACCESS                      read-only
        STATUS                          current
	DESCRIPTION
			"A number that identifies this entry
			 within the volume. This is the most
                         significant 32 bits of a 64 bit record
                         identifier."
	::= { qrV3Entry 2 }

	qrV3IndexLow                    OBJECT-TYPE
	SYNTAX                          Unsigned32 (1..4294967295)
        MAX-ACCESS                      read-only
        STATUS                          current
	DESCRIPTION
			"A number that identifies this entry
			 within the volume. This is the least
                         significant 32 bits of a 64 bit record
                         identifier."
	::= { qrV3Entry 3 }

	qrV3Vserver                     OBJECT-TYPE
	SYNTAX                          DisplayString
        MAX-ACCESS                      read-only
        STATUS                          current
	DESCRIPTION
			"Indicates the vserver to which the volume belongs.
			 Name from the cluster interfaces."
	::= { qrV3Entry 4 }

	qrV3VolumeName                  OBJECT-TYPE
	SYNTAX                          DisplayString
        MAX-ACCESS                      read-only
        STATUS                          current
	DESCRIPTION
			"Indicates the name of the volume to which this
                         quota belongs."
	::= { qrV3Entry 5 }

	qrV3Type                        OBJECT-TYPE
	SYNTAX                          INTEGER {
                                             qrV3TypeUser(1),
                                             qrV3TypeGroup(2),
					     qrV3TypeTree(3),
					     qrV3TypeUserDefault(4),
					     qrV3TypeGroupDefault(5),
                                             qrV3TypeUnknown(6),
					     qrV3TypeTreeDefault(7)
                                        }
        MAX-ACCESS                      read-only
        STATUS                          current
	DESCRIPTION
			"Identifies the kind of quota for this qrV3Entry."
	::= { qrV3Entry 6 }

        qrV3IdType                      OBJECT-TYPE
	SYNTAX                          INTEGER {
                                             qrV3IdValid(1),
                                             qrV3SidValid(2)
                                        }
        MAX-ACCESS                      read-only
        STATUS                          current
        DESCRIPTION
                        "A value that indicates which ID field is valid."
        ::= { qrV3Entry 7 }

	qrV3Id                          OBJECT-TYPE
	SYNTAX                          Unsigned32
        MAX-ACCESS                      read-only
        STATUS                          current
	DESCRIPTION
			"Depending on qrV3Type, this is either the UID
			 (user's numerical ID), the GID (numerical ID
			 of  the  group  that a user belongs to), or the
			 TID (numerical qtree id) associated with this
			 qrV3Entry. For qrV3TypeUser records, check the
			 qrV3IdType field to see if this field is valid."
	::= { qrV3Entry 8 }

	qrV3Sid                         OBJECT-TYPE
	SYNTAX                          DisplayString
        MAX-ACCESS                      read-only
        STATUS                          current
	DESCRIPTION
			"The one or more IDs associated with this qrV3Entry.
                         If the qrV3entry is associated with a Windows ID, the
			 text form of the Windows ID (the SID) is here. If
			 the qrV3Entry is associated with more than one id,
			 this contains a blank separated list of those IDs.
                         Check the qrV3IdType field to see if this field is
                         valid."
	::= { qrV3Entry 9 }

	qrV3PathName                    OBJECT-TYPE
	SYNTAX                          FilesystemPathString
        MAX-ACCESS                      read-only
        STATUS                          current
	DESCRIPTION
			"A textual string that contains the path
			 corresponding to this qrV3Entry."
	::= { qrV3Entry 10 }

        qrV3Tree                        OBJECT-TYPE
	SYNTAX                          FileOrDirectoryString
        MAX-ACCESS                      read-only
        STATUS                          current
        DESCRIPTION
			"A string that indicates which qtree this quota
			belongs to."
	::= { qrV3Entry 11 }

	qrV3KBytesUsed                  OBJECT-TYPE
	SYNTAX                          Counter64
        MAX-ACCESS                      read-only
        STATUS                          current
	DESCRIPTION
			"The current number of KBytes used for this
			 qrV3Entry."

	::= { qrV3Entry 12 }

	qrV3QuotaUnlimited              OBJECT-TYPE
	SYNTAX                          INTEGER {
                                             false(1),
                                             true(2)
                                        }
        MAX-ACCESS                      read-only
        STATUS                          current
	DESCRIPTION
			"This flag designates whether or not the
			size based quota limit for this qrV3Entry is unlimited.
			If false(1) then qrV3KBytesLimit OID's are valid,
			if true(2) then qrV3KBytesLimit OID's are unused
			and will return 0."
	::= { qrV3Entry 13 }

	qrV3KBytesLimit                 OBJECT-TYPE
	SYNTAX                          Counter64
        MAX-ACCESS                      read-only
        STATUS                          current
	DESCRIPTION
			"The limit of KBytes that can be used for this
			 qrV3Entry. This will return 0 if
			 qrV3QuotaUnlimited is true."
	::= { qrV3Entry 14 }

	qrV3FilesUsed                   OBJECT-TYPE
	SYNTAX                          Unsigned32
        MAX-ACCESS                      read-only
        STATUS                          deprecated
	DESCRIPTION
			"The current number of files used for this
			 qrV3Entry. This object is deprecated in
                         favor of qrV364FilesUsed."
	::= { qrV3Entry 15 }

	qrV3FileQuotaUnlimited          OBJECT-TYPE
	SYNTAX                          INTEGER {
                                             false(1),
                                             true(2)
                                        }
        MAX-ACCESS                      read-only
        STATUS                          current
	DESCRIPTION
			"This flag designates whether or not the
			file based quota limit for this qrV3Entry is unlimited.
			If false(1) then qrV3FileLimit is valid, if true(2)
			qrV3FileLimit will return 0."
	::= { qrV3Entry 16 }

	qrV3FileLimit                   OBJECT-TYPE
	SYNTAX                          Unsigned32
        MAX-ACCESS                      read-only
        STATUS                          deprecated
	DESCRIPTION
			"The limit of files that can be used for this
			 qrV3Entry. This object is deprecated in
                         favor of qrV364FileLimit."
	::= { qrV3Entry 17 }

	qrV3SoftQuotaUnlimited          OBJECT-TYPE
	SYNTAX                          INTEGER {
                                             false(1),
                                             true(2)
                                        }
        MAX-ACCESS                      read-only
        STATUS                          current
	DESCRIPTION
			"This flag designates whether or not the
			size based soft quota limit for this qrV3Entry is
			unlimited. If false(1) then qrV3KBytesSoftLimit OID's
			are valid, if true(2) the qrV3KBytesSoftLimit OID's
			are unused and will return 0."
	::= { qrV3Entry 18 }

        qrV3KBytesSoftLimit             OBJECT-TYPE
	SYNTAX                          Counter64
        MAX-ACCESS                      read-only
        STATUS                          current
        DESCRIPTION
			"The limit of KBytes that can be used for this
			 qrV3Entry before a warning message and SNMP
			 trap is produced."
        ::= { qrV3Entry 19 }

	qrV3SoftFileQuotaUnlimited      OBJECT-TYPE
	SYNTAX                          INTEGER {
                                             false(1),
                                             true(2)
                                        }
        MAX-ACCESS                      read-only
        STATUS                          current
	DESCRIPTION
			"This flag designates whether or not the
			file based soft quota limit for this qrV3Entry is
			unlimited. If false(1) then qrV3SoftFileLimit is valid,
			if true(2) qrV3SoftFileLimit is unused and will
			return 0."
	::= { qrV3Entry 20 }

        qrV3SoftFileLimit               OBJECT-TYPE
	SYNTAX                          Unsigned32
        MAX-ACCESS                      read-only
        STATUS                          deprecated
        DESCRIPTION
			"The limit of files that can be used for this
			 qrV3Entry before a warning message and SNMP
			 trap is produced. This will return 0 if
			 qrV3SoftFileQuotaUnlimited is true. This object
			 is deprecated in favor of qrV364SoftFileLimit."
        ::= { qrV3Entry 21 }

	qrV3ThresholdUnlimited          OBJECT-TYPE
	SYNTAX                          INTEGER {
                                             false(1),
                                             true(2)
                                        }
        MAX-ACCESS                      read-only
        STATUS                          current
	DESCRIPTION
			"This flag designates whether or not the
			size based threshold limit for this qrV3Entry is
			unlimited. If false(1) then qrV3KBytesThreshold OID's
			are valid, if true(2) then qrV3KBytesThreshold OID's
			are unused and will return 0."
	::= { qrV3Entry 22 }

        qrV3KBytesThreshold             OBJECT-TYPE
	SYNTAX                          Counter64
        MAX-ACCESS                      read-only
        STATUS                          current
        DESCRIPTION
                        "A number of KBytes that when used by this entry
			 produces a warning message. This will return
			 0 if qrV3ThresholdUnlimited is true."
        ::= { qrV3Entry 23 }

	qrV364FilesUsed                 OBJECT-TYPE
	SYNTAX                          Counter64
        MAX-ACCESS                      read-only
        STATUS                          current
	DESCRIPTION
			"The current number of files used for this
			 qrV3Entry."
	::= { qrV3Entry 24 }

	qrV364FileLimit                 OBJECT-TYPE
	SYNTAX                          Counter64
        MAX-ACCESS                      read-only
        STATUS                          current
	DESCRIPTION
			"The limit of files that can be used for this
			 qrV3Entry."
	::= { qrV3Entry 25 }

        qrV364SoftFileLimit             OBJECT-TYPE
	SYNTAX                          Counter64
        MAX-ACCESS                      read-only
        STATUS                          current
        DESCRIPTION
			"The limit of files that can be used for this
			 qrV3Entry before a warning message and SNMP
			 trap is produced. This will return 0 if
			 qrV3SoftFileQuotaUnlimited is true."
        ::= { qrV3Entry 26 }

	-- -- -- -- -- -- -- --  --
	-- the file system group --
	-- -- -- -- -- -- -- --  --

	filesysMaxfilesAvail            OBJECT-TYPE
	SYNTAX                          Integer32
        MAX-ACCESS                      read-only
        STATUS                          deprecated
	DESCRIPTION
				"The count of the maximum number of
				 files allowable on the root volume.  This
				 object is deprecated - use
				 dfEntry.dfMaxFilesAvail instead."
	::= { filesys 1 }

	filesysMaxfilesUsed             OBJECT-TYPE
	SYNTAX                          Integer32
        MAX-ACCESS                      read-only
        STATUS                          deprecated
	DESCRIPTION
				"The count of the number of files
				 currently in use on the root volume.
				 This object is deprecated - use
				 dfEntry.dfMaxFilesUsed instead."
	::= { filesys 2 }

	filesysMaxfilesPossible         OBJECT-TYPE
	SYNTAX                          Integer32
        MAX-ACCESS                      read-only
        STATUS                          deprecated
	DESCRIPTION
				"The largest value to which the
				 filesysMaxfilesAvail parameter above can
				 be increased by reconfiguration on the
				 root volume.  This object is deprecated -
				 use dfEntry.dfMaxFilesPossible."
	::= { filesys 3 }

	dfTable                         OBJECT-TYPE
	SYNTAX                          SEQUENCE OF DfEntry
        MAX-ACCESS                      not-accessible
        STATUS                          current
	DESCRIPTION
				"Provide a report of the available disk space
				 on the file systems. The tables shows the
				 available disk space for volumes as well as
				 aggregates.
				 For node volumes and aggregates, only online
				 volumes and aggregates are reported. For
				 cluster volumes and aggregates, the
				 dfStateOnline is set and the value for
				 other fields are undefined when volumes
				 and aggregates are not online."

	::= { filesys 4 }

	snapshot OBJECT IDENTIFIER ::= { filesys 5 }

	-- the display file system table

	dfEntry                         OBJECT-TYPE
	SYNTAX                          DfEntry
        MAX-ACCESS                      not-accessible
        STATUS                          current
	DESCRIPTION
			"Provide a report of the available disk space on
			 the referenced file system.
			 For entries returned from the cluster interfaces
			 only, if the dfRowInfo is not set to
			 'available', the values reported for other
			 fields may not be valid."

	INDEX      { dfIndex }
	::= { dfTable 1 }

	DfEntry ::=
	    SEQUENCE {
		dfIndex
		    Integer32,
		dfFileSys
		    DisplayString,
		dfKBytesTotal
		    Integer32,
		dfKBytesUsed
		    Integer32,
		dfKBytesAvail
		    Integer32,
		dfPerCentKBytesCapacity
		    Integer32,
		dfInodesUsed
		    Integer32,
		dfInodesFree
		    Integer32,
		dfPerCentInodeCapacity
		    Integer32,
		dfMountedOn
		    DisplayString,
		dfMaxFilesAvail
		    Integer32,
		dfMaxFilesUsed
		    Integer32,
		dfMaxFilesPossible
		    Integer32,
		dfHighTotalKBytes
		    Integer32,
		dfLowTotalKBytes
		    Integer32,
		dfHighUsedKBytes
		    Integer32,
		dfLowUsedKBytes
		    Integer32,
		dfHighAvailKBytes
		    Integer32,
		dfLowAvailKBytes
		    Integer32,
		dfStatus
		    INTEGER,
		dfMirrorStatus
		    INTEGER,
		dfPlexCount
		    Integer32,
		dfType
		    INTEGER,
		dfHighSisSharedKBytes
		    Integer32,
		dfLowSisSharedKBytes
		    Integer32,
		dfHighSisSavedKBytes
		    Integer32,
		dfLowSisSavedKBytes
		    Integer32,
		dfPerCentSaved
		    Integer32,
		df64TotalKBytes
		    Counter64,
		df64UsedKBytes
		    Counter64,
		df64AvailKBytes
		    Counter64,
		df64SisSharedKBytes
		    Counter64,
		df64SisSavedKBytes
		    Counter64,
		dfVserver
		    DisplayString,
		dfStateOnline
		    Boolean,
		dfRowInfo
		    INTEGER,
		df64CompressSaved
		    Counter64,
		dfCompressSavedPercent
		    Integer32,
		df64DedupeSaved
		    Counter64,
		dfDedupeSavedPercent
		    Integer32,
		df64TotalSaved
		    Counter64,
		dfTotalSavedPercent
		    Integer32,
		df64TotalReservedKBytes
		    Counter64
	    }

	dfIndex                         OBJECT-TYPE
	SYNTAX                          Integer32 (1..2147483647)
        MAX-ACCESS                      read-only
        STATUS                          current
	DESCRIPTION
			"A number that identifies this entry for the
			 referenced file system."
	::= { dfEntry 1 }

	dfFileSys                       OBJECT-TYPE
	SYNTAX                          DisplayString
        MAX-ACCESS                      read-only
        STATUS                          current
	DESCRIPTION
			"The name for the referenced file system."
	::= { dfEntry 2 }

	dfKBytesTotal                   OBJECT-TYPE
	SYNTAX                          Integer32
        MAX-ACCESS                      read-only
        STATUS                          deprecated
	DESCRIPTION
			"The total capacity in KBytes for the
			 referenced file system."
	::= { dfEntry 3 }

	dfKBytesUsed                    OBJECT-TYPE
	SYNTAX                          Integer32
        MAX-ACCESS                      read-only
        STATUS                          deprecated
	DESCRIPTION
			"The total disk space in KBytes that is in use
			 on the referenced file system."
	::= { dfEntry 4 }

	dfKBytesAvail                   OBJECT-TYPE
	SYNTAX                          Integer32
        MAX-ACCESS                      read-only
        STATUS                          deprecated
	DESCRIPTION
			"The total disk space in KBytes that is
			 free for use on the referenced file system."
	::= { dfEntry 5 }

	dfPerCentKBytesCapacity         OBJECT-TYPE
	SYNTAX                          Integer32
        MAX-ACCESS                      read-only
        STATUS                          current
	DESCRIPTION
				"The percentage of disk space currently
				 in use on the referenced file system."
	::= { dfEntry 6 }

	dfInodesUsed                    OBJECT-TYPE
	SYNTAX                          Integer32
        MAX-ACCESS                      read-only
        STATUS                          current
	DESCRIPTION
				"The total number of inodes in use on the
				 referenced file system."
	::= { dfEntry 7 }

	dfInodesFree                    OBJECT-TYPE
	SYNTAX                          Integer32
        MAX-ACCESS                      read-only
        STATUS                          current
	DESCRIPTION
				"The total number of inodes that are
				 available for use on the referenced
				 file system."
	::= { dfEntry 8 }

	dfPerCentInodeCapacity          OBJECT-TYPE
	SYNTAX                          Integer32
        MAX-ACCESS                      read-only
        STATUS                          current
	DESCRIPTION
				"The percentage of disk space currently
				 in use based on inode counts, on the
				 referenced file system."
	::= { dfEntry 9 }

	dfMountedOn                     OBJECT-TYPE
	SYNTAX                          DisplayString
        MAX-ACCESS                      read-only
        STATUS                          current
	DESCRIPTION
				"The name of the file on which this file
				 system is mounted."
	::= { dfEntry 10 }

	dfMaxFilesAvail                 OBJECT-TYPE
	SYNTAX                          Integer32
        MAX-ACCESS                      read-only
        STATUS                          current
	DESCRIPTION
				"The count of the maximum number of
				 files allowable on the referenced file
				 system."
	::= { dfEntry 11 }

	dfMaxFilesUsed                  OBJECT-TYPE
	SYNTAX                          Integer32
        MAX-ACCESS                      read-only
        STATUS                          current
	DESCRIPTION
				"The count of the number of files
				 currently in use on the referenced file
				 system."
	::= { dfEntry 12 }

	dfMaxFilesPossible              OBJECT-TYPE
	SYNTAX                          Integer32
        MAX-ACCESS                      read-only
        STATUS                          current
	DESCRIPTION
				"The largest value to which the
				 filesysMaxfilesAvail parameter above can
				 be increased by reconfiguration on the
				 referenced file system."
	::= { dfEntry 13 }

	dfHighTotalKBytes               OBJECT-TYPE
	SYNTAX                          Integer32
        MAX-ACCESS                      read-only
        STATUS                          deprecated
	DESCRIPTION
				"The total capacity in KBytes for the
				 referenced file system.  This object returns
				 the most significant 32 bits of the 64 bit
				 unsigned integer. This object is deprecated -
				 Use df64TotalKBytes instead."
	::= { dfEntry 14 }

	dfLowTotalKBytes                OBJECT-TYPE
	SYNTAX                          Integer32
        MAX-ACCESS                      read-only
        STATUS                          deprecated
	DESCRIPTION
				"The total capacity in KBytes for the
				 referenced file system.  This object returns
				 the least significant 32 bits of the 64 bit
				 unsigned integer. This object is deprecated -
				 Use df64TotalKBytes instead."
	::= { dfEntry 15 }

	dfHighUsedKBytes                OBJECT-TYPE
	SYNTAX                          Integer32
        MAX-ACCESS                      read-only
        STATUS                          deprecated
	DESCRIPTION
				"The total disk space in KBytes that is in use
				 on the referenced file system.  This object
				 returns the most significant 32 bits of the
				 64 bit unsigned integer. This object is
				 deprecated - Use df64UsedKBytes instead."
	::= { dfEntry 16 }

	dfLowUsedKBytes                 OBJECT-TYPE
	SYNTAX                          Integer32
        MAX-ACCESS                      read-only
        STATUS                          deprecated
	DESCRIPTION
				"The total disk space in KBytes that is in use
				 on the referenced file system.  This object
				 returns the least significant 32 bits of the
				 64 bit unsigned integer. This object is
				 deprecated - Use df64UsedKBytes instead."
	::= { dfEntry 17 }

	dfHighAvailKBytes               OBJECT-TYPE
	SYNTAX                          Integer32
        MAX-ACCESS                      read-only
        STATUS                          deprecated
	DESCRIPTION
				"The total disk space in KBytes that is free
				 for use on the referenced file system.
				 This object returns the most significant
				 32 bits of the 64 bit unsigned integer.
				 This object is deprecated - Use df64AvailKBytes
				 instead."
	::= { dfEntry 18 }

	dfLowAvailKBytes                OBJECT-TYPE
	SYNTAX                          Integer32
        MAX-ACCESS                      read-only
        STATUS                          deprecated
	DESCRIPTION
				"The total disk space in KBytes that is free
				 for use on the referenced file system.
				 This object returns the least significant
				 32 bits of the 64 bit unsigned integer.
				 This object is deprecated - Use df64AvailKBytes
				 instead."
	::= { dfEntry 19 }


        dfStatus                        OBJECT-TYPE
	SYNTAX                          INTEGER {
                                             unmounted(1),
                                             mounted(2),
					     frozen(3),
					     destroying(4),
					     creating(5),
					     mounting(6),
					     unmounting(7),
					     nofsinfo(8),
					     replaying(9),
                                             replayed(10)
                                        }
        MAX-ACCESS                      read-only
        STATUS                          current
        DESCRIPTION
                                "The status of the file system."
        ::= { dfEntry 20 }

        dfMirrorStatus                  OBJECT-TYPE
	SYNTAX                          INTEGER {
                                             invalid(1),
                                             uninitialized(2),
					     needcpcheck(3),
					     cpcheckwait(4),
					     unmirrored(5),
					     normal(6),
					     degraded(7),
					     resyncing(8),
					     failed(9),
                                             limbo(10)
                                        }
        MAX-ACCESS                      read-only
        STATUS                          current
        DESCRIPTION
                                "Overall mirror status of the file system."
        ::= { dfEntry 21 }

        dfPlexCount                     OBJECT-TYPE
	SYNTAX                          Integer32
        MAX-ACCESS                      read-only
        STATUS                          current
        DESCRIPTION
                                "Number of plexes in this file system."
        ::= { dfEntry 22 }

        dfType                          OBJECT-TYPE
	SYNTAX                          INTEGER {
                                             flexibleVolume(2),
                                             aggregate(3),
                                             stripedAggregate(4),
                                             stripedVolume(5)
                                        }
        MAX-ACCESS                      read-only
        STATUS                          current
        DESCRIPTION
                                "Indicates the type of container."
        ::= { dfEntry 23 }

	dfHighSisSharedKBytes           OBJECT-TYPE
	SYNTAX                          Integer32
        MAX-ACCESS                      read-only
        STATUS                          deprecated
	DESCRIPTION
				"The total amount of data in KBytes that is
				 shared by more than one instance on the
				 referenced file system.  This object returns
				 the most significant 32 bits of the 64 bit
				 unsigned integer. This object is deprecated -
				 Use df64SisSharedKBytes instead."
	::= { dfEntry 24 }

	dfLowSisSharedKBytes            OBJECT-TYPE
	SYNTAX                          Integer32
        MAX-ACCESS                      read-only
        STATUS                          deprecated
	DESCRIPTION
				"The total amount of data in KBytes that is
				 shared by more than one instance on the
				 referenced file system.  This object returns
				 the least significant 32 bits of the 64 bit
				 unsigned integer. This object is deprecated -
				 Use df64SisSharedKBytes instead."
	::= { dfEntry 25 }

	dfHighSisSavedKBytes            OBJECT-TYPE
	SYNTAX                          Integer32
        MAX-ACCESS                      read-only
        STATUS                          deprecated
	DESCRIPTION
				"The total disk space in KBytes that is saved
				 by storing only one copy of the duplicated
				 blocks on the referenced file system.  The
				 object returns the most significant 32 bits
				 of the 64 bit unsigned integer. This object is
				 deprecated - Use df64SisSavedKBytes instead."
	::= { dfEntry 26 }

	dfLowSisSavedKBytes             OBJECT-TYPE
	SYNTAX                          Integer32
        MAX-ACCESS                      read-only
        STATUS                          deprecated
	DESCRIPTION
				"The total disk space in KBytes that is saved
				 by storing only one copy of the duplicated
				 blocks on the referenced file system.  The
				 object returns the least significant 32 bits
				 of the 64 bit unsigned integer. This object is
				 deprecated - Use df64SisSavedKBytes instead."
	::= { dfEntry 27 }

	dfPerCentSaved                  OBJECT-TYPE
	SYNTAX                          Integer32
        MAX-ACCESS                      read-only
        STATUS                          current
	DESCRIPTION
				"The percentage of disk space saved by
				 eliminating the duplicated blocks on the
				 referenced file system."
	::= { dfEntry 28 }

	df64TotalKBytes                 OBJECT-TYPE
	SYNTAX                          Counter64
        MAX-ACCESS                      read-only
        STATUS                          current
	DESCRIPTION
				"The total capacity in KBytes for the
				 referenced file system.  This object returns
				 all of the 64 bit unsigned integer."
	::= { dfEntry 29 }

	df64UsedKBytes                  OBJECT-TYPE
	SYNTAX                          Counter64
        MAX-ACCESS                      read-only
        STATUS                          current
	DESCRIPTION
				"The total disk space in KBytes that is in use
				 on the referenced file system.  This object
				 returns all of the 64 bit unsigned integer."
	::= { dfEntry 30 }

	df64AvailKBytes                 OBJECT-TYPE
	SYNTAX                          Counter64
        MAX-ACCESS                      read-only
        STATUS                          current
	DESCRIPTION
				"The total disk space in KBytes that is free
				 for use on the referenced file system.
				 This object returns all of the 64 bit
				 unsigned integer."
	::= { dfEntry 31 }

	df64SisSharedKBytes             OBJECT-TYPE
	SYNTAX                          Counter64
        MAX-ACCESS                      read-only
        STATUS                          current
	DESCRIPTION
				"The total amount of data in KBytes that is
				 shared by more than one instance on the
				 referenced file system.  This object returns
				 all of the 64 bit unsigned integer."
	::= { dfEntry 32 }

	df64SisSavedKBytes              OBJECT-TYPE
	SYNTAX                          Counter64
        MAX-ACCESS                      read-only
        STATUS                          current
	DESCRIPTION
				"The total disk space in KBytes that is saved
				 by storing only one copy of the duplicated
				 blocks on the referenced file system.  The
				 object returns all of the 64 bit unsigned
				 integer."
	::= { dfEntry 33 }

	dfVserver                       OBJECT-TYPE
	SYNTAX                          DisplayString
	MAX-ACCESS                      read-only
	STATUS                          current
	DESCRIPTION		"Name of the vserver to which the volume belongs.
				For aggregate and aggregate snapshot it will be
				an empty string.

				This field is returned only from the cluster interfaces."

	::= { dfEntry 34 }

	dfStateOnline                   OBJECT-TYPE
	SYNTAX                          Boolean
	MAX-ACCESS                      read-only
	STATUS                          current
	DESCRIPTION		"The state of the cluster aggregates and
				 volumes. If this is not true, all the
				 values for the fields of this table are
				 undefined.

				 This field is returned only from the cluster interfaces."

	::= { dfEntry 35 }

        dfRowInfo                       OBJECT-TYPE
	SYNTAX                          INTEGER {
					    available(1),
					    partiallyAvailable(2)
					}

        MAX-ACCESS                      read-only
        STATUS                          current
        DESCRIPTION
			"Volume or aggregate and its snapshot
			is 'available' or 'partiallyAvailable'.
			This field is returned only from the cluster interfaces.
			Possible values for this field are:

			'available'
			Indicates a normal case when everything went
			fine while fetching the values for the fields
			of this table and all values returned
			are valid.

			'partiallyAvailable'
			Indicates something went wrong while fetching
			the values for the fields of this table and
			not all values are valid.

			For fields that could not be fetched, default
			values are set. For integers it is -1, for
			counters 0, and for string it is null."
        ::= { dfEntry 36 }

	df64CompressSaved		OBJECT-TYPE
	SYNTAX				Counter64
	MAX-ACCESS			read-only
	STATUS				current
	DESCRIPTION
			"Provides the compression savings in a volume
			 in KBytes. This is only returned for volumes."

	::= { dfEntry 37 }

	dfCompressSavedPercent		OBJECT-TYPE
	SYNTAX				Integer32 (0..100)
	MAX-ACCESS			read-only
	STATUS				current
	DESCRIPTION
			"Provides the percentage of compression
			 savings in a volume, which is
			 ((compr_saved/(compr_saved + used)) * 100).
			 This is only returned for volumes."

	::= { dfEntry 38 }

	df64DedupeSaved			OBJECT-TYPE
	SYNTAX				Counter64
	MAX-ACCESS			read-only
	STATUS				current
	DESCRIPTION
			"Provides the deduplication savings in a volume
			 in KBytes. This is only returned for volumes."

	::= { dfEntry 39 }

	dfDedupeSavedPercent		OBJECT-TYPE
	SYNTAX				Integer32 (0..100)
	MAX-ACCESS			read-only
	STATUS				current
	DESCRIPTION
			"Provides the percentage of deduplication
			 savings in a volume, which is
			 ((dedup_saved/(dedup_saved + used)) * 100).
			 This is only returned for volumes."


	::= { dfEntry 40 }

	df64TotalSaved			OBJECT-TYPE
	SYNTAX				Counter64
	MAX-ACCESS			read-only
	STATUS				current
	DESCRIPTION
			"Provides the total savings due to deduplication
			 & compression in a volume in KBytes. This is
			 only returned for volumes."

	::= { dfEntry 41 }

	dfTotalSavedPercent		OBJECT-TYPE
	SYNTAX				Integer32 (0..100)
	MAX-ACCESS			read-only
	STATUS				current
	DESCRIPTION
			"Provides the percentage of total savings
			 due to deduplication & compression in a
			 volume, which is
			 ((total_saved/(total_saved + used)) * 100).
			 This is only returned for volumes."

	::= { dfEntry 42 }

	df64TotalReservedKBytes		OBJECT-TYPE
	SYNTAX                          Counter64
	MAX-ACCESS                      read-only
	STATUS                          current
	DESCRIPTION
			"The total disk space in KBytes that is
			 reserved on the referenced file system."


	::= { dfEntry 43 }

	-- the old single-volume snapshot table.  DEPRECATED

	slTable                         OBJECT-TYPE
	SYNTAX                          SEQUENCE OF SlEntry
        MAX-ACCESS                      not-accessible
        STATUS                          deprecated
	DESCRIPTION
			"Provide a report of the snapshots on the
			 root volume.  This table is deprecated - use
			 slVTable instead."
	::= { snapshot 1 }

	slEntry                         OBJECT-TYPE
	SYNTAX                          SlEntry
        MAX-ACCESS                      not-accessible
        STATUS                          deprecated
	DESCRIPTION
			"Provide a report on a given snapshot on the
			 root volume.  This object is deprecated - use
			 slVEntry instead."
	INDEX	{ slIndex }
	::= { slTable 1 }

	SlEntry ::=
	    SEQUENCE {
		slIndex
		    Integer32,
		slMonth
		    INTEGER,
		slDay
		    Integer32,
		slHour
		    Integer32,
		slMinutes
		    Integer32,
		slName
		    DisplayString
	    }

	slIndex                         OBJECT-TYPE
	SYNTAX                          Integer32 (1..2147483647)
        MAX-ACCESS                      read-only
        STATUS                          deprecated
	DESCRIPTION
			"A number that identifies this entry for the
			 referenced file system."
	::= { slEntry 1 }

	slMonth                         OBJECT-TYPE
	SYNTAX                          INTEGER {
                                             january(1),
                                             february(2),
					     march(3),
					     april(4),
					     may(5),
					     june(6),
					     july(7),
					     august(8),
					     september(9),
					     october(10),
					     november(11),
                                             december(12)
                                        }
        MAX-ACCESS                      read-only
        STATUS                          deprecated
	DESCRIPTION
			"The month in which the snapshot was created."
	::= { slEntry 2 }

	slDay                           OBJECT-TYPE
	SYNTAX                          Integer32 (1..31)
        MAX-ACCESS                      read-only
        STATUS                          deprecated
	DESCRIPTION
			"The day on which the snapshot was created."
	::= { slEntry 3 }

	slHour                          OBJECT-TYPE
	SYNTAX                          Integer32 (0..23)
        MAX-ACCESS                      read-only
        STATUS                          deprecated
	DESCRIPTION
			"The hour in which the snapshot was created."
	::= { slEntry 4 }

	slMinutes                       OBJECT-TYPE
	SYNTAX                          Integer32 (0..59)
        MAX-ACCESS                      read-only
        STATUS                          deprecated
	DESCRIPTION
			"The minute in which the snapshot was created."
	::= { slEntry 5 }

	slName                          OBJECT-TYPE
	SYNTAX                          DisplayString
        MAX-ACCESS                      read-only
        STATUS                          deprecated
	DESCRIPTION
			"The name of the referenced snapshot."
	::= { slEntry 6 }


	-- The multivolume / aggregate snapshot table.

	slVTable                        OBJECT-TYPE
	SYNTAX                          SEQUENCE OF SlVEntry
        MAX-ACCESS                      not-accessible
        STATUS                          current
	DESCRIPTION
			"Provide a report of the snapshots on the
			 file systems."
	::= { snapshot 2 }

	slVEntry                        OBJECT-TYPE
	SYNTAX                          SlVEntry
        MAX-ACCESS                      not-accessible
        STATUS                          current
	DESCRIPTION
			"Provide a report on a given snapshot on the
			 file system.  Indices select the volume of
			 the snapshot and the snapshot entry itself."
	INDEX	{ slVVolume, slVIndex }
	::= { slVTable 1 }

	SlVEntry ::=
	    SEQUENCE {
		slVIndex
		    Integer32,
		slVMonth
		    INTEGER,
		slVDay
		    Integer32,
		slVHour
		    Integer32,
		slVMinutes
		    Integer32,
		slVName
		    DisplayString,
		slVVolume
		    Integer32,
		slVNumber
		    Integer32,
		slVVolumeName
		    DisplayString,
		slVType
		    INTEGER
	    }

	slVIndex                        OBJECT-TYPE
	SYNTAX                          Integer32 (1..2147483647)
        MAX-ACCESS                      read-only
        STATUS                          current
	DESCRIPTION
			"A number that identifies this entry for the
			 referenced file system."
	::= { slVEntry 1 }

	slVMonth                        OBJECT-TYPE
	SYNTAX                          INTEGER {
                                             january(1),
                                             february(2),
					     march(3),
					     april(4),
					     may(5),
					     june(6),
					     july(7),
					     august(8),
					     september(9),
					     october(10),
					     november(11),
                                             december(12)
                                        }
        MAX-ACCESS                      read-only
        STATUS                          current
	DESCRIPTION
			"The month in which the snapshot was created."
	::= { slVEntry 2 }

	slVDay                          OBJECT-TYPE
	SYNTAX                          Integer32 (1..31)
        MAX-ACCESS                      read-only
        STATUS                          current
	DESCRIPTION
			"The day on which the snapshot was created."
	::= { slVEntry 3 }

	slVHour                         OBJECT-TYPE
	SYNTAX                          Integer32 (0..23)
        MAX-ACCESS                      read-only
        STATUS                          current
	DESCRIPTION
			"The hour in which the snapshot was created."
	::= { slVEntry 4 }

	slVMinutes                      OBJECT-TYPE
	SYNTAX                          Integer32 (0..59)
        MAX-ACCESS                      read-only
        STATUS                          current
	DESCRIPTION
			"The minute in which the snapshot was created."
	::= { slVEntry 5 }

	slVName                         OBJECT-TYPE
	SYNTAX                          DisplayString
        MAX-ACCESS                      read-only
        STATUS                          current
	DESCRIPTION
			"The name of the referenced snapshot."
	::= { slVEntry 6 }

	slVVolume                       OBJECT-TYPE
	SYNTAX                          Integer32 (1..2147483647)
        MAX-ACCESS                      read-only
        STATUS                          current
	DESCRIPTION
			"A number that identifies the volume  / aggregate that
			 contains this snapshot."
	::= { slVEntry 7 }

	slVNumber                       OBJECT-TYPE
	SYNTAX                          Integer32
        MAX-ACCESS                      read-only
        STATUS                          current
	DESCRIPTION
			"Number of snapshots for this volume / aggregate."
	::= { slVEntry 8 }

	slVVolumeName                   OBJECT-TYPE
	SYNTAX                          DisplayString
        MAX-ACCESS                      read-only
        STATUS                          current
	DESCRIPTION
			"The name of the volume / aggregate. This does not
			 have a /vol/ prefix."

	::= { slVEntry 9 }

	slVType                         OBJECT-TYPE
	SYNTAX                          INTEGER {
                                             flexibleVolume(2),
                                             aggregate(3)
                                        }
        MAX-ACCESS                      read-only
        STATUS                          current
	DESCRIPTION
			"Indicates the type of container for this
			 snapshot."

	::= { slVEntry 10 }


	-- The snapshot content table.

	slQTable                        OBJECT-TYPE
	SYNTAX                          SEQUENCE OF SlQEntry
        MAX-ACCESS                      not-accessible
        STATUS                          current
	DESCRIPTION
			"Provide a report of the snapshots and their contents
			on the file systems."
	::= { snapshot 3 }

	slQEntry                        OBJECT-TYPE
	SYNTAX                          SlQEntry
        MAX-ACCESS                      not-accessible
        STATUS                          current
	DESCRIPTION
			"Provide a report on a given snapshot for a given
			qtree on the file system.  Indices select the volume
			and qtree of the snapshot and the snapshot entry
			itself."

	INDEX	{ slQVolume, slQQtree, slQIndex }
	::= { slQTable 1 }

	SlQEntry ::=
	    SEQUENCE {
		slQIndex
		    Integer32,
		slQVolume
		    Integer32,
		slQQtree
		    Integer32,
		slQSnapshotName
		    DisplayString,
    	        slQSnapshotTime
		    Integer32,
		slQQtreeName
		    FileOrDirectoryString,
  	        slQQtreeContent
		    INTEGER,
		slQSource
		    OCTET STRING,
		slQSourceTime
		    Integer32,
		slQVolumeName
		    DisplayString
	    }

	slQIndex                        OBJECT-TYPE
	SYNTAX                          Integer32 (1..2147483647)
        MAX-ACCESS                      read-only
        STATUS                          current
	DESCRIPTION
			"A number that identifies this entry for the
			 referenced file system."
	::= { slQEntry 1 }

	slQVolume                       OBJECT-TYPE
	SYNTAX                          Integer32 (1..2147483647)
        MAX-ACCESS                      read-only
        STATUS                          current
	DESCRIPTION
			"A number that identifies the volume that contains
			this snapshot."
	::= { slQEntry 2 }

	slQQtree                        OBJECT-TYPE
	SYNTAX                          Integer32 (1..2147483647)
        MAX-ACCESS                      read-only
        STATUS                          current
	DESCRIPTION
			"A number that identifies the qtree that contains
			this snapshot."
	::= { slQEntry 3 }

	slQSnapshotName                 OBJECT-TYPE
	SYNTAX                          DisplayString
        MAX-ACCESS                      read-only
        STATUS                          current
	DESCRIPTION
			"The name of the referenced snapshot."
	::= { slQEntry 4 }

	slQSnapshotTime                 OBJECT-TYPE
	SYNTAX                          Integer32
        MAX-ACCESS                      read-only
        STATUS                          current
	DESCRIPTION
			"Time of the snapshot on the system. The time in
			seconds since January 1, 1970."
	::= { slQEntry 5 }

	slQQtreeName                    OBJECT-TYPE
	SYNTAX                          FileOrDirectoryString
        MAX-ACCESS                      read-only
        STATUS                          current
	DESCRIPTION
			"A string that indicates which qtree is in this
			snapshot"
	::= { slQEntry 6 }

        slQQtreeContent                 OBJECT-TYPE
	SYNTAX                          INTEGER {
                                             replica(1),
                                             transitioning(2),
                                             original(3)
                                        }
        MAX-ACCESS                      read-only
        STATUS                          current
	DESCRIPTION
	                "The content of the qtree tree"
	::= { slQEntry 7 }

	slQSource                       OBJECT-TYPE
	SYNTAX                          OCTET STRING
        MAX-ACCESS                      read-only
        STATUS                          current
	DESCRIPTION
	    		"The source of this qtree for a replicated qtree.
			'-' for an original qtree."
	::= { slQEntry 8 }

	slQSourceTime                   OBJECT-TYPE
	SYNTAX                          Integer32
        MAX-ACCESS                      read-only
        STATUS                          current
	DESCRIPTION
			"Time of the source snapshot for a replicated qtree.
			Time of the current snapshot for an original qtree.
			The time in seconds since January 1, 1970. 0 if the
			qtree is in a transitioning stage"

	::= { slQEntry 9 }

	slQVolumeName                   OBJECT-TYPE
	SYNTAX                          DisplayString
        MAX-ACCESS                      read-only
        STATUS                          current
	DESCRIPTION
			"The name of the volume. This does not have a /vol/
			prefix."
	::= { slQEntry 10 }


	dfNumber                        OBJECT-TYPE
	SYNTAX                          Integer32
        MAX-ACCESS                      read-only
        STATUS                          current
	DESCRIPTION
			"Number of entries in the dfTable table."

	::= { filesys 6 }

	-- -- -- -- -- -- -- -- -- -- -- --
	-- file system status information --
	-- -- -- -- -- -- -- -- -- -- -- --

	fsStatus OBJECT IDENTIFIER ::= { filesys 7 }

	fsOverallStatus                 OBJECT-TYPE
	SYNTAX                          INTEGER {
                                             ok(1),
                                             nearlyFull(2),
                                             full(3)
                                        }
        MAX-ACCESS                      read-only
        STATUS                          current
	DESCRIPTION
			"An indication of overall file system
			health.  'ok' indicates that all file systems
			have adequate space.  'nearlyFull' means
			that one or more is nearly full (more than
			95% full). 'full' means that one or more
			are more than 98% full."
	::= { fsStatus 1 }

	fsStatusMessage                 OBJECT-TYPE
	SYNTAX                          DisplayString
        MAX-ACCESS                      read-only
        STATUS                          current
	DESCRIPTION
			"A string indicating any file systems which
			are full or nearly full."
	::= { fsStatus 2 }

	fsMaxUsedBytesPerCent           OBJECT-TYPE
	SYNTAX                          Integer32 (0..100)
        MAX-ACCESS                      read-only
        STATUS                          current
	DESCRIPTION
			"The percentage of space currently in use or
			reserved by the fullest file system."
	::= { fsStatus 3 }

	fsMaxUsedInodesPerCent          OBJECT-TYPE
	SYNTAX                          Integer32 (0..100)
        MAX-ACCESS                      read-only
        STATUS                          current
	DESCRIPTION
			"The percentage of inodes currently in use
			by the fullest file system."
	::= { fsStatus 4 }

	-- -- -- -- -- -- -- -- -- -- -- -- -- -- -- -- -- -- --
	--
	--  All volumes, including those offline and those
	--  owned by the cluster partner.
	--
	-- -- -- -- -- -- -- -- -- -- -- -- -- -- -- -- -- -- --

	volTable                        OBJECT-TYPE
	SYNTAX                          SEQUENCE OF VolEntry
        MAX-ACCESS                      not-accessible
        STATUS                          current
	DESCRIPTION
			"List the volumes defined on the system,
			including offline volumes."

	::= { filesys 8 }

	volEntry                        OBJECT-TYPE
	SYNTAX                          VolEntry
        MAX-ACCESS                      not-accessible
        STATUS                          current
	DESCRIPTION
			"Provide details about a particular volume.
			 For entries returned only from the cluster
			 interfaces, if the volRowInfo is not set to
			 'available', the values reported by other
			 fields of this table may not be valid."

	INDEX	{ volIndex }
	::= { volTable 1 }

	VolEntry ::=
	    SEQUENCE {
		volIndex	Integer32,
		volName		DisplayString,
		volFSID		DisplayString,
		volOwningHost	INTEGER,
		volState	DisplayString,
		volStatus	DisplayString,
		volOptions	OCTET STRING,
		volUUID		DisplayString,
		volAggrName	DisplayString,
		volType		INTEGER,
		volClone	INTEGER,
		volCloneOf	DisplayString,
		volCloneSnap	DisplayString,
		volVserver	DisplayString,
		volMSID		DisplayString,
		volDSID		DisplayString,
		volSpaceGuaranteeEnabled	INTEGER,
		volSpaceGuarantee		INTEGER,
		volLanguage	DisplayString,
		volLanguageCode	DisplayString,
		volCloneChildrenList	DisplayString,
		volJunctionPathActive	Boolean,
		volJunctionPath		DisplayString,
		volJunctionPathSource	DisplayString,
		volRowInfo		INTEGER,
		volNvfail		Boolean,
		volInNvfailedState	Boolean,
		volInstanceUUID		DisplayString,
		volProvenanceUUID	DisplayString,
		volDrForceNvfail        Boolean
	    }

	volIndex                        OBJECT-TYPE
	SYNTAX                          Integer32 (1..2048)
        MAX-ACCESS                      read-only
        STATUS                          current
	DESCRIPTION
			"A number that identifies this volume.  The
			volIndex is not related to any other table
			defined in this MIB, and may change as
			volumes are created and destroyed."
	::= { volEntry 1 }

	volName                         OBJECT-TYPE
	SYNTAX                          DisplayString
        MAX-ACCESS                      read-only
        STATUS                          current
	DESCRIPTION
			"Name of the volume.  This includes no /vol/
			prefix."
	::= { volEntry 2 }

	volFSID                         OBJECT-TYPE
	SYNTAX                          DisplayString
        MAX-ACCESS                      read-only
        STATUS                          current
	DESCRIPTION
			"Unique identifier for this volume."
	::= { volEntry 3 }

	volOwningHost                   OBJECT-TYPE
	SYNTAX                          INTEGER {
                                             local(1),
                                             partner(2)
                                        }
        MAX-ACCESS                      read-only
        STATUS                          current
	DESCRIPTION
			"Indication of which host owns this volume.
			 This field is not supported in a cluster."
	::= { volEntry 4 }

	volState                        OBJECT-TYPE
	SYNTAX                          DisplayString
        MAX-ACCESS                      read-only
        STATUS                          current
	DESCRIPTION
			"State of the volume, such as 'online' or
			'offline'."
	::= { volEntry 5 }

	volStatus                       OBJECT-TYPE
	SYNTAX                          DisplayString
        MAX-ACCESS                      read-only
        STATUS                          current
	DESCRIPTION
			"Status of the volume, such as 'normal' or
			'reconstructing'. May include several values
			separated by comma and space."
	::= { volEntry 6 }

	volOptions                      OBJECT-TYPE
	SYNTAX                          OCTET STRING (SIZE (0..1024))
        MAX-ACCESS                      read-only
        STATUS                          current
	DESCRIPTION
			"Options associated with the volume, such
			as 'root' and 'nosnapdir=off'. May include
			several values separated by comma."
	::= { volEntry 7 }

	volUUID                         OBJECT-TYPE
	SYNTAX                          DisplayString
        MAX-ACCESS                      read-only
        STATUS                          current
	DESCRIPTION
			"A unique id associated with the volume."
	::= { volEntry 8 }

	volAggrName                     OBJECT-TYPE
	SYNTAX                          DisplayString
        MAX-ACCESS                      read-only
        STATUS                          current
	DESCRIPTION
			"Name of the aggregate this flexible volume is a
			part of."
	::= { volEntry 9 }

	volType                         OBJECT-TYPE
	SYNTAX                          INTEGER {
                                             flexible(2),
                                             striped(3),
                                             asis(4),
                                             snaplock(5)
                                        }
        MAX-ACCESS                      read-only
        STATUS                          current
	DESCRIPTION
			"Type of this volume."
	::= { volEntry 10 }

	volClone                        OBJECT-TYPE
	SYNTAX                          INTEGER {
                                             false(1),
                                             true(2)
                                        }
        MAX-ACCESS                      read-only
        STATUS                          current
	DESCRIPTION
			"True indicates flexible volume is a clone."
	::= { volEntry 11 }

	volCloneOf                      OBJECT-TYPE
	SYNTAX                          DisplayString
        MAX-ACCESS                      read-only
        STATUS                          current
	DESCRIPTION
			"Name of flexible volume this flexible volume is
			a clone of."
	::= { volEntry 12 }

	volCloneSnap                    OBJECT-TYPE
	SYNTAX                          DisplayString
        MAX-ACCESS                      read-only
        STATUS                          current
	DESCRIPTION
			"Name of original cloned snapshot."
	::= { volEntry 13 }

	volVserver                      OBJECT-TYPE
	SYNTAX                          DisplayString
        MAX-ACCESS                      read-only
        STATUS                          current
	DESCRIPTION
			"Vserver to which the volume belongs.
			Name from the cluster interfaces.
			Only applicable to cluster-mode volume."
	::= { volEntry 14 }

	volMSID                         OBJECT-TYPE
	SYNTAX                          DisplayString
        MAX-ACCESS                      read-only
        STATUS                          current
	DESCRIPTION
			"The volume's Mirror Set ID. MSIDs are formatted
			as 10-character strings composed of 8 hex
			characters prefixed with '0x'.
			Only applicable to cluster-mode volume."
	::= { volEntry 15 }

	volDSID                         OBJECT-TYPE
	SYNTAX                          DisplayString
        MAX-ACCESS                      read-only
        STATUS                          current
	DESCRIPTION
			"The volume's Data Set ID. DSIDs are formatted
			as 10-character strings composed of 8 hex
			characters prefixed with '0x'.
			Only applicable to cluster-mode volume."
	::= { volEntry 16 }

	volSpaceGuaranteeEnabled        OBJECT-TYPE
	SYNTAX                          INTEGER {
                                             false(1),
                                             true(2)
                                        }
        MAX-ACCESS                      read-only
        STATUS                          current
	DESCRIPTION
			"Whether or not the space guarantee style
			associated with the volume is currently in
			effect. This field does not appear if the
			flexible volume is restricted or offline."
	::= { volEntry 17 }

	volSpaceGuarantee               OBJECT-TYPE
	SYNTAX                          INTEGER {
                                             none(0),
                                             file(1),
                                             volume(2)
                                        }
        MAX-ACCESS                      read-only
        STATUS                          current
	DESCRIPTION
			"The space guarantee style associated with the
			volume, such as 'volume', etc. This field does
			not appear if the flexible volume is
			restricted or offline."
	::= { volEntry 18 }

	volLanguage                     OBJECT-TYPE
	SYNTAX                          DisplayString
        MAX-ACCESS                      read-only
        STATUS                          current
	DESCRIPTION
			"The language currently set for the volume. For
			example, 'English '."
	::= { volEntry 19 }

	volLanguageCode                 OBJECT-TYPE
	SYNTAX                          DisplayString
        MAX-ACCESS                      read-only
        STATUS                          current
	DESCRIPTION
			"The language code currently set for the volume.
			For example, 'en'."
	::= { volEntry 20 }

	volCloneChildrenList            OBJECT-TYPE
	SYNTAX                          DisplayString
        MAX-ACCESS                      read-only
        STATUS                          current
	DESCRIPTION
			"A comma separated list of all volume's child clones."
	::= { volEntry 21 }

	volJunctionPathActive           OBJECT-TYPE
	SYNTAX                          Boolean
        MAX-ACCESS                      read-only
        STATUS                          current
	DESCRIPTION
			"Indicates if a Junction Path is active on this volume.
			This field is returned only from the cluster interfaces."
	::= { volEntry 22 }

	volJunctionPath                 OBJECT-TYPE
	SYNTAX                          DisplayString
        MAX-ACCESS                      read-only
        STATUS                          current
	DESCRIPTION
			"The mount path for the volume, relative to the root
			volume. This field is returned only from the cluster
			interfaces."
	::= { volEntry 23 }

	volJunctionPathSource           OBJECT-TYPE
	SYNTAX                          DisplayString
        MAX-ACCESS                      read-only
        STATUS                          current
	DESCRIPTION
			"Source directory of the Junction Path for this volume.
			This field is returned only from the cluster interfaces.

			Two possible values are
			  'LSM volume' for Load Share Mirror volumes
			  'RW volume'  for Read-Write volumes."
	::= { volEntry 24 }

        volRowInfo                      OBJECT-TYPE
        SYNTAX                          INTEGER {
                                             available(1),
                                             partiallyAvailable(2)
                                        }
        MAX-ACCESS                      read-only
        STATUS                          current
        DESCRIPTION
                "Volume is 'available' or 'partiallyAvailable'.
                This field is returned only from the cluster interfaces.

                Two possible values are:
                'available'
                     Indicates a normal case when everything went
                     fine while fetching the values for the fields
                     of this table and all values returned
                     are valid.

               'partiallyAvailable'
                     Indicates something went wrong while fetching
                     the values of the fields for this table and
                     not all values are valid.

               For fields that could not be fetched, default
               values are set. For integers it is -1, for
               counters 0, and for string it is null."

	::= { volEntry 25 }
	volNvfail                       OBJECT-TYPE
	SYNTAX                          Boolean
        MAX-ACCESS                      read-only
        STATUS                          current
	DESCRIPTION
			"Indicates whether nvfail option is enabled
			 on this volume."

	::= { volEntry 26 }
	volInNvfailedState              OBJECT-TYPE
	SYNTAX                          Boolean
        MAX-ACCESS                      read-only
        STATUS                          current
	DESCRIPTION
			"Indicates whether the volume is in nvfailed state.
			 This is only applicable to cluster-mode volumes."

	::= { volEntry 27 }

	volInstanceUUID                 OBJECT-TYPE
	SYNTAX                          DisplayString
        MAX-ACCESS                      read-only
        STATUS                          current
	DESCRIPTION
			"A unique id associated with the volume that moves
			 with the volume when the volume is migrated."

	::= { volEntry 28 }

	volProvenanceUUID               OBJECT-TYPE
	SYNTAX                          DisplayString
        MAX-ACCESS                      read-only
        STATUS                          current
	DESCRIPTION
			"A unique id associated with the volume that identifies
			 the source of the volume content."

        ::= { volEntry 29 }

        volDrForceNvfail                OBJECT-TYPE
        SYNTAX                          Boolean
        MAX-ACCESS                      read-only
        STATUS                          current
        DESCRIPTION
			"Indicates whether dr-force-nvfail option is enabled
			 on this volume. If true, volume would be put in a
			 special state called 'in-nvfailed-state' by switchover
			 operation. The option has no effect for negotiated or
			 an automatic switchover operation. The protocol
			 access on the volume in 'in-nvfailed-state' is
			 blocked. This will cause the client applications to
			 crash and thus prevent access to data on the volume.
			 To get out of this situation, admin needs to manually
			 clear the 'in-nvfailed-state' on the volume. By
			 default, dr-force-nvfail option value is false."

        ::= { volEntry 30 }

        volNumber                      OBJECT-TYPE
        SYNTAX                          Integer32 (0..2048)
        MAX-ACCESS                      read-only
        STATUS                          current
        DESCRIPTION
			"Number of volumes in the volTable."

	::= { filesys 9 }

        qtreeTable                      OBJECT-TYPE
	SYNTAX                          SEQUENCE OF QtreeEntry
        MAX-ACCESS                      not-accessible
        STATUS                          current
	DESCRIPTION
			"Provide a list of the qtrees on the system."

	::= { filesys 10 }

	qtreeEntry                      OBJECT-TYPE
	SYNTAX                          QtreeEntry
        MAX-ACCESS                      not-accessible
        STATUS                          current
	DESCRIPTION
	                "Provide details about a particular qtree."

	INDEX   { qtreeVolume, qtreeIndex }
        ::= { qtreeTable 1 }

        QtreeEntry ::=
	    SEQUENCE {
		qtreeIndex		     Integer32,
		qtreeVolume		     Integer32,
		qtreeVolumeName		     DisplayString,
		qtreeId			     Integer32,
		qtreeName		     FileOrDirectoryString,
		qtreeStyle		     INTEGER,
		qtreeStatus		     INTEGER,
		qtreeOplock		     INTEGER,
		qtreeVserver		     DisplayString,
		qtreeExportPolicy            DisplayString,
		qtreeIsExportPolicyInherited Boolean,
		qtreeMode                    Unsigned32,
		qtreeQosPolicyGroup          DisplayString
	    }

	qtreeIndex                      OBJECT-TYPE
	SYNTAX                          Integer32 (1..2147483647)
        MAX-ACCESS                      read-only
        STATUS                          current
	DESCRIPTION
			"Index into the qtree table."

	::= { qtreeEntry 1 }

	qtreeVolume                     OBJECT-TYPE
	SYNTAX                          Integer32 (1..2147483647)
        MAX-ACCESS                      read-only
        STATUS                          current
	DESCRIPTION
	                "A number that identifies the volume that contains
			this qtree."

	::= { qtreeEntry 2 }

	qtreeVolumeName                 OBJECT-TYPE
	SYNTAX                          DisplayString
        MAX-ACCESS                      read-only
        STATUS                          current
	DESCRIPTION
			"The name of the volume that contains this qtree.
			This includes no /vol/prefix."

	::= { qtreeEntry 3 }

	qtreeId                         OBJECT-TYPE
	SYNTAX                          Integer32
        MAX-ACCESS                      read-only
        STATUS                          current
	DESCRIPTION
			"The Id number of the qtree."

	::= { qtreeEntry 4 }

	qtreeName                       OBJECT-TYPE
	SYNTAX                          FileOrDirectoryString
        MAX-ACCESS                      read-only
        STATUS                          current
	DESCRIPTION
	                "The name of the qtree."

	::= { qtreeEntry 5 }

	qtreeStyle                      OBJECT-TYPE
	SYNTAX                          INTEGER {
                                             unix(1),
                                             ntfs(2),
                                             mixed(3)
                                        }
        MAX-ACCESS                      read-only
        STATUS                          current
        DESCRIPTION
	                "The security style of the qtree."

        ::= { qtreeEntry 6 }

	qtreeStatus                     OBJECT-TYPE
	SYNTAX                          INTEGER {
                                             normal(1)
                                        }
        MAX-ACCESS                      read-only
        STATUS                          current
        DESCRIPTION
	                "The status of the qtree."

	::= { qtreeEntry 7 }

	qtreeOplock                     OBJECT-TYPE
	SYNTAX                          INTEGER {
                                             enabled(1),
                                             disabled(2)
                                        }
        MAX-ACCESS                      read-only
        STATUS                          current
        DESCRIPTION
                        "An indication of whether the oplocks is enabled or not
			for this qtree."

	::= { qtreeEntry 8 }

        qtreeVserver                    OBJECT-TYPE
	SYNTAX                          DisplayString
	MAX-ACCESS                      read-only
	STATUS                          current
	DESCRIPTION
	                 "Indicates the vserver to which the volume belongs.
			  Name from the cluster interfaces.
			  Only applicable to cluster-mode volume."

	::= { qtreeEntry 9 }

        qtreeExportPolicy               OBJECT-TYPE
	SYNTAX                          DisplayString
	MAX-ACCESS                      read-only
	STATUS                          current
	DESCRIPTION
	                 "Indicates the export policy assigned to the qtree."

	::= { qtreeEntry 10 }

        qtreeIsExportPolicyInherited    OBJECT-TYPE
	SYNTAX                          Boolean
	MAX-ACCESS                      read-only
	STATUS                          current
	DESCRIPTION
	                 "Indicates the export policy assigned to the qtree is
			  inherited from the parent volume."

	::= { qtreeEntry 11 }

        qtreeMode                       OBJECT-TYPE
        SYNTAX                          Unsigned32
        MAX-ACCESS                      read-only
        STATUS                          current
        DESCRIPTION
                        "The file permission bits of the qtree."

	::= { qtreeEntry 12 }

        qtreeQosPolicyGroup             OBJECT-TYPE
        SYNTAX                          DisplayString
        MAX-ACCESS                      read-only
        STATUS                          current
        DESCRIPTION
                        "Indicates the qos policy group assigned to the qtree."

	::= { qtreeEntry 13 }

        -- -- -- -- -- -- -- -- -- -- -- -- -- -- -- -- -- -- --
        --
        --  All aggregates, including those offline and those
        --  owned by the cluster partner.
        --
        -- -- -- -- -- -- -- -- -- -- -- -- -- -- -- -- -- -- --

        aggrTable                       OBJECT-TYPE
	SYNTAX                          SEQUENCE OF AggrEntry
        MAX-ACCESS                      not-accessible
        STATUS                          current
        DESCRIPTION
                        "List the aggregates defined on the system,
                        including offline aggregates."

        ::= { filesys 11 }

        aggrEntry                       OBJECT-TYPE
	SYNTAX                          AggrEntry
        MAX-ACCESS                      not-accessible
        STATUS                          current
        DESCRIPTION
                        "Provide details about a particular aggregate.
                        For entries returned only from the cluster
                        interfaces, if the aggrRowInfo is not set to
                        'available', the values reported by other
                        fields of this table may not be valid."

        INDEX   { aggrIndex }
        ::= { aggrTable 1 }

        AggrEntry ::=
            SEQUENCE {
                aggrIndex       Integer32,
                aggrName        DisplayString,
                aggrFSID        DisplayString,
                aggrOwningHost  INTEGER,
                aggrState       DisplayString,
                aggrStatus      DisplayString,
                aggrOptions     DisplayString,
                aggrUUID        DisplayString,
                aggrFlexvollist OCTET STRING,
                aggrType        INTEGER,
                aggrRaidType    DisplayString,
                aggrHAType      INTEGER,
                aggrOwners      DisplayString,
                aggrRowInfo     INTEGER,
                aggrVolumeFootprints            Counter64,
                aggrVolumeFootprintsPercent     Integer32,
                aggrFilesystemMetadata	        Counter64,
                aggrFilesystemMetadataPercent   Integer32
            }

        aggrIndex                       OBJECT-TYPE
	SYNTAX                          Integer32 (1..2048)
        MAX-ACCESS                      read-only
        STATUS                          current
        DESCRIPTION
                        "A number that identifies this aggregate.  The
                        aggrIndex is not related to any other table
                        defined in this MIB, and may change as
                        aggregates are created and destroyed."
        ::= { aggrEntry 1 }

        aggrName                        OBJECT-TYPE
	SYNTAX                          DisplayString
        MAX-ACCESS                      read-only
        STATUS                          current
        DESCRIPTION
                        "Name of the aggregate.  This includes no /vol/
                        prefix."
        ::= { aggrEntry 2 }

        aggrFSID                        OBJECT-TYPE
	SYNTAX                          DisplayString
        MAX-ACCESS                      read-only
        STATUS                          current
        DESCRIPTION
                        "Unique identifier for this aggregate."
        ::= { aggrEntry 3 }

        aggrOwningHost                  OBJECT-TYPE
	SYNTAX                          INTEGER {
                                             local(1),
                                             partner(2)
                                        }
        MAX-ACCESS                      read-only
        STATUS                          current
        DESCRIPTION
                        "Indication of which host owns this aggregate.
                         This field is not supported in a cluster."
        ::= { aggrEntry 4 }

        aggrState                       OBJECT-TYPE
	SYNTAX                          DisplayString
        MAX-ACCESS                      read-only
        STATUS                          current
        DESCRIPTION
                        "State of the aggregate, such as 'online' or
                        'offline'."
        ::= { aggrEntry 5 }

        aggrStatus                      OBJECT-TYPE
	SYNTAX                          DisplayString
        MAX-ACCESS                      read-only
        STATUS                          current
        DESCRIPTION
                        "Status of the aggregate, such as 'normal' or
                        'reconstructing'. May include several values
                        separated by comma and space."
        ::= { aggrEntry 6 }

        aggrOptions                     OBJECT-TYPE
	SYNTAX                          DisplayString
        MAX-ACCESS                      read-only
        STATUS                          current
        DESCRIPTION
                        "Options associated with the aggregate."
        ::= { aggrEntry 7 }

        aggrUUID                        OBJECT-TYPE
	SYNTAX                          DisplayString
        MAX-ACCESS                      read-only
        STATUS                          current
        DESCRIPTION
                        "A unique id associated with the aggregate."
        ::= { aggrEntry 8 }

        aggrFlexvollist                 OBJECT-TYPE
	SYNTAX                          OCTET STRING (SIZE (0..1024))
        MAX-ACCESS                      read-only
        STATUS                          current
        DESCRIPTION
                        "List of all the flexible volumes within this
                        aggregate.
                        This field is not supported in a cluster."
        ::= { aggrEntry 9 }

        aggrType                        OBJECT-TYPE
	SYNTAX                          INTEGER {
                                             unknown(0),
                                             aggregate(2),
                                             striped(3)
                                        }
        MAX-ACCESS                      read-only
        STATUS                          current
        DESCRIPTION
                        "Type of this container, containers
                        containing flexible volumes are aggregate."
        ::= { aggrEntry 10 }

        aggrRaidType                    OBJECT-TYPE
	SYNTAX                          DisplayString
        MAX-ACCESS                      read-only
        STATUS                          current
        DESCRIPTION
                        "Type of raid protection of the aggregate, such as
                        'raid0', 'mirrored raid0', 'raid4', 'mirrored raid4',
                        'raid_dp', 'mirrored raid_dp'."
        ::= { aggrEntry 11 }

        aggrHAType                      OBJECT-TYPE
	SYNTAX                          INTEGER {
                                             none(0),
                                             cfo(1),
                                             sfo(2)
                                        }
        MAX-ACCESS                      read-only
        STATUS                          current
        DESCRIPTION
                        "Aggregate failover type, such as 'cfo' for
                        cluster failover, 'sfo' for storage failover.
                        This is set to 'none' if aggregate failover
			type is not known."
        ::= { aggrEntry 12 }

        aggrOwners                      OBJECT-TYPE
	SYNTAX                          DisplayString
        MAX-ACCESS                      read-only
        STATUS                          current
        DESCRIPTION
                        "Current owner(s) or the node(s) to which the
                        aggregate belongs to. In case of striped
                        aggregates, this will be a comma separated list
                        of nodes to which the aggregate belongs to."

        ::= { aggrEntry 13 }

        aggrRowInfo                     OBJECT-TYPE
        SYNTAX                          INTEGER {
                                           available(1),
                                           partiallyAvailable(2)
                                         }
        MAX-ACCESS                      read-only
        STATUS                          current
        DESCRIPTION
                        "Aggregate is 'available' or 'partiallyAvailable'.
                        This OID is available only from the cluster
			management interfaces.

                        Two possible values are:
                        'available' :
                          Indicates a normal case when everything went
                          fine while fetching the values of the fields
                          for this table and all values returned
                          are valid.

                        'partiallyAvailable' :
                          Indicates something went wrong while fetching
                          the values of the fields for this table and
                          not all the values are valid.

                        For fields that could not be fetched, default
                        values are set. For integers it is -1, for
                        counters 0, and for string it is null."

        ::= { aggrEntry 14 }

        aggrVolumeFootprints            OBJECT-TYPE
        SYNTAX                          Counter64
        MAX-ACCESS                      read-only
        STATUS                          deprecated
        DESCRIPTION
                        "Footprint of data and metadata inside
                        volumes belonging to the Aggregate.
			This field is deprecated in Data ONTAP 8.3
			and later - use the volume-footprints
			field of the aggr-space-get-iter ZAPI
			instead."
        ::= { aggrEntry 15 }

        aggrVolumeFootprintsPercent     OBJECT-TYPE
        SYNTAX                          Integer32 (0..100)
        MAX-ACCESS                      read-only
        STATUS                          deprecated
        DESCRIPTION
                        "Footprint of data and metadata inside
                        volumes belonging to the aggregate as a
                        percentage of aggregate size.
			This field is deprecated in Data ONTAP 8.3
			and later - use the volume-footprints-percent
			field of the aggr-space-get-iter ZAPI
			instead."
        ::= { aggrEntry 16 }

        aggrFilesystemMetadata          OBJECT-TYPE
        SYNTAX                          Counter64
        MAX-ACCESS                      read-only
        STATUS                          deprecated
        DESCRIPTION
                        "Metadata of the Aggregate.
			This field is deprecated in Data ONTAP 8.3
			and later - use the aggregate-metadata
			field of the aggr-space-get-iter ZAPI
			instead."
        ::= { aggrEntry 17 }

        aggrFilesystemMetadataPercent   OBJECT-TYPE
        SYNTAX                          Integer32 (0..100)
        MAX-ACCESS                      read-only
        STATUS				deprecated
        DESCRIPTION
                        "Metadata of the Aggregate as a
                        percentage of Aggregate size.
			This field is deprecated in Data ONTAP 8.3
			and later - use the aggregate-metadata-percent
			field of the aggr-space-get-iter ZAPI instead."
        ::= { aggrEntry 18 }

        aggrNumber                      OBJECT-TYPE
	SYNTAX                          Integer32 (0..2048)
        MAX-ACCESS                      read-only
        STATUS                          current
        DESCRIPTION
                        "Number of aggregates in the aggrTable."

        ::= { filesys 12 }

	volMoveStatusTable 		OBJECT-TYPE
	SYNTAX 				SEQUENCE OF VolMoveStatusEntry
	MAX-ACCESS 			not-accessible
	STATUS 				current
	DESCRIPTION
			"Status of Vol Move operation"
	::= { filesys 13 }

	volMoveStatusEntry 		OBJECT-TYPE
	SYNTAX 				VolMoveStatusEntry
	MAX-ACCESS 			not-accessible
	STATUS 				current
	DESCRIPTION
			"Provide movement details of a particular volume"

	INDEX    { volMoveIndex }
	::= { volMoveStatusTable 1}

	VolMoveStatusEntry ::=
	    SEQUENCE {
		volMoveIndex		INTEGER,
		volMoveSrcName 		DisplayString,
		volMoveDstaggrName 	DisplayString,
		volMoveCOattempts 	Integer32,
		volMoveCOtime		Integer32,
		volMoveState 		DisplayString
	}

	volMoveIndex	 		OBJECT-TYPE
	SYNTAX 				INTEGER (1..10)
	MAX-ACCESS 			read-only
	STATUS 				current
	DESCRIPTION
			"A number that identifies this volume. The volIndex is
			 not related to any other table defined in this MIB, and
			 may change as volumes are created and destroyed."
	::= { volMoveStatusEntry 1}

	volMoveSrcName 			OBJECT-TYPE
	SYNTAX 				DisplayString
	MAX-ACCESS			read-only
	STATUS 				current
	DESCRIPTION
			"Name of the vol move source volume.
			 This will not have the /vol/ prefix."
	::= { volMoveStatusEntry 2}

        volMoveDstaggrName              OBJECT-TYPE
        SYNTAX                          DisplayString
        MAX-ACCESS                      read-only
        STATUS                          current
        DESCRIPTION
                        "Name of the vol move destination aggregate"
        ::= { volMoveStatusEntry 3}

        volMoveCOattempts               OBJECT-TYPE
        SYNTAX                          Integer32
        MAX-ACCESS                      read-only
        STATUS                          current
        DESCRIPTION
                        "Maximum Cutover attempts for specified vol move operation"
        ::= { volMoveStatusEntry 4}

        volMoveCOtime                       OBJECT-TYPE
        SYNTAX                          Integer32
        MAX-ACCESS                      read-only
        STATUS                          current
        DESCRIPTION
                        "Maximum Cutover time for specified vol move operation"
        ::= { volMoveStatusEntry 5}

        volMoveState                    OBJECT-TYPE
        SYNTAX                          DisplayString
        MAX-ACCESS                      read-only
        STATUS                          current
        DESCRIPTION
                        "State of the vol move operation"
        ::= { volMoveStatusEntry 6}

	-- -- -- -- -- -- --
	-- the RAID group --
	-- -- -- -- -- -- --

	-- Old root volume raid table.  DEPRECATED

	raidTable                       OBJECT-TYPE
	SYNTAX                          SEQUENCE OF RaidEntry
        MAX-ACCESS                      not-accessible
        STATUS                          deprecated
	DESCRIPTION
			"Display RAID configuration information for the
			 root volume.  This table is deprecated - use
			 raidVTable instead."
	::= { raid 1 }

	raidEntry                       OBJECT-TYPE
	SYNTAX                          RaidEntry
        MAX-ACCESS                      not-accessible
        STATUS                          deprecated
	DESCRIPTION
			"Display RAID configuration information for
			 the referenced disk drive.  This only works for
			 disks contained within the root volume, and will
			 include spare drives.  This object is
			 deprecated - use raidVEntry instead."
	INDEX	{ raidIndex }
	::= { raidTable 1 }

	RaidEntry ::=
	    SEQUENCE {
		raidIndex
		    Integer32,
		raidDiskName
		    DisplayString,
		raidStatus
		    INTEGER,
		raidDiskId
		    Integer32,
		raidScsiAdapter
		    DisplayString,
		raidScsiId
		    Integer32,
		raidUsedMb
		    Integer32,
		raidUsedBlocks
		    Integer32,
		raidTotalMb
		    Integer32,
		raidTotalBlocks
		    Integer32,
		raidCompletionPerCent
		    Integer32
	    }

	raidIndex                       OBJECT-TYPE
	SYNTAX                          Integer32 (1..2147483647)
        MAX-ACCESS                      read-only
        STATUS                          deprecated
	DESCRIPTION
			"A number that identifies this entry for the
			 referenced disk drive."
	::= { raidEntry 1 }

	raidDiskName                    OBJECT-TYPE
	SYNTAX                          DisplayString
        MAX-ACCESS                      read-only
        STATUS                          deprecated
	DESCRIPTION
			"The name identifying the referenced disk drive."
	::= { raidEntry 2 }

	raidStatus                      OBJECT-TYPE
	SYNTAX                          INTEGER {
                                             active(1),
                                             reconstructionInProgress(2),
					     parityReconstructionInProgress(3),
					     parityVerificationInProgress(4),
					     scrubbingInProgress(5),
					     failed(6),
					     addingSpare(7),
					     spare(8),
					     prefailed(9),
                                             offline(10)
                                        }
        MAX-ACCESS                      read-only
        STATUS                          deprecated
	DESCRIPTION
			"The status of the referenced disk drive."
	::= { raidEntry 3 }

	raidDiskId                      OBJECT-TYPE
	SYNTAX                          Integer32
        MAX-ACCESS                      read-only
        STATUS                          deprecated
	DESCRIPTION
			"The disk identifier for the referenced disk
			 drive."
	::= { raidEntry 4 }

	raidScsiAdapter                 OBJECT-TYPE
	SYNTAX                          DisplayString
        MAX-ACCESS                      read-only
        STATUS                          deprecated
	DESCRIPTION
			"The identifier of the SCSI adapter for the
			 referenced disk drive."
	::= { raidEntry 5 }

	raidScsiId                      OBJECT-TYPE
	SYNTAX                          Integer32 (0..100)
        MAX-ACCESS                      read-only
        STATUS                          deprecated
	DESCRIPTION
			"The identifier for the referenced disk drive
			 on the referenced SCSI adapter."
	::= { raidEntry 6 }

	raidUsedMb                      OBJECT-TYPE
	SYNTAX                          Integer32
        MAX-ACCESS                      read-only
        STATUS                          deprecated
	DESCRIPTION
			"The number of MBytes currently in use on
			 the referenced disk drive."
	::= { raidEntry 7 }

	raidUsedBlocks                  OBJECT-TYPE
	SYNTAX                          Integer32
        MAX-ACCESS                      read-only
        STATUS                          deprecated
	DESCRIPTION
			"The number of Blocks currently in use on
			 the referenced disk drive."
	::= { raidEntry 8 }

	raidTotalMb                     OBJECT-TYPE
	SYNTAX                          Integer32
        MAX-ACCESS                      read-only
        STATUS                          deprecated
	DESCRIPTION
			"The number of MBytes physically available
			 on the referenced disk drive."
	::= { raidEntry 9 }

	raidTotalBlocks                 OBJECT-TYPE
	SYNTAX                          Integer32
        MAX-ACCESS                      read-only
        STATUS                          deprecated
	DESCRIPTION
			"The number of Blocks physically available
			 on the referenced disk drive."
	::= { raidEntry 10 }

	raidCompletionPerCent           OBJECT-TYPE
	SYNTAX                          Integer32 (0..100)
        MAX-ACCESS                      read-only
        STATUS                          deprecated
	DESCRIPTION
			 "In the case when reconstruction/adding a
			  spare, verification or scrubbing is in progress,
			  the percent of such reconstruction, verification
			  or scrubbing that has been completed on the
			  referenced disk drive."
	::= { raidEntry 11 }


	-- Multivolume raidTable.


 	raidVTable                      OBJECT-TYPE
	SYNTAX                          SEQUENCE OF RaidVEntry
        MAX-ACCESS                      not-accessible
        STATUS                          current
	DESCRIPTION
			"Display RAID configuration information."
	::= { raid 2 }

	raidVEntry                      OBJECT-TYPE
	SYNTAX                          RaidVEntry
        MAX-ACCESS                      not-accessible
        STATUS                          current
	DESCRIPTION
			"Display RAID configuration information for
			 the referenced aggregate, raid group, and disk drive."
	INDEX	{ raidVVol, raidVGroup, raidVIndex }
	::= { raidVTable 1 }

	RaidVEntry ::=
	    SEQUENCE {
		raidVIndex
		    Integer32,
		raidVDiskName
		    DisplayString,
		raidVStatus
		    INTEGER,
		raidVDiskId
		    Integer32,
		raidVScsiAdapter
		    DisplayString,
		raidVScsiId
		    Integer32,
		raidVUsedMb
		    Integer32,
		raidVUsedBlocks
		    Integer32,
		raidVTotalMb
		    Integer32,
		raidVTotalBlocks
		    Integer32,
		raidVCompletionPerCent
		    Integer32,
		raidVVol
		    Integer32,
		raidVGroup
		    Integer32,
		raidVDiskNumber
		    Integer32,
		raidVGroupNumber
		    Integer32,
		raidVDiskPort
		    INTEGER,
		raidVSecondaryDiskName
		    DisplayString,
		raidVSecondaryDiskPort
		    INTEGER,
		raidVShelf
		    Integer32,
		raidVBay
		    Integer32,
                raidVPlex
                    Integer32,
                raidVPlexGroup
                    Integer32,
                raidVPlexNumber
                    Integer32,
                raidVPlexName
                    DisplayString,
                raidVSectorSize
                    Integer32,
		raidVDiskSerialNumber
		    DisplayString,
		raidVDiskVendor
		    DisplayString,
		raidVDiskModel
		    DisplayString,
		raidVDiskFirmwareRevision
		    DisplayString,
		raidVDiskRPM
		    DisplayString,
		raidVDiskType
		    DisplayString,
		raidVDiskPool
		    DisplayString,
		raidVDiskCopyDestDiskName
		    DisplayString,
		raidVDiskUID
		    DisplayString,
		raidV64UsedBlocks
		    Counter64,
		raidV64TotalBlocks
		    Counter64,
		raidVCarrierID
		    DisplayString
	    }

	raidVIndex                      OBJECT-TYPE
	SYNTAX                          Integer32 (1..2147483647)
        MAX-ACCESS                      read-only
        STATUS                          current
	DESCRIPTION
			"A number that identifies this disk drive within
			 the given aggregate and RAID group."
	::= { raidVEntry 1 }

	raidVDiskName                   OBJECT-TYPE
	SYNTAX                          DisplayString
        MAX-ACCESS                      read-only
        STATUS                          current
	DESCRIPTION
			"The name identifying the referenced disk drive."
	::= { raidVEntry 2 }

	raidVStatus                     OBJECT-TYPE
	SYNTAX                          INTEGER {
                                             active(1),
                                             reconstructionInProgress(2),
					     parityReconstructionInProgress(3),
					     parityVerificationInProgress(4),
					     scrubbingInProgress(5),
					     failed(6),
					     prefailed(9),
                                             offline(10)
                                        }
        MAX-ACCESS                      read-only
        STATUS                          current
	DESCRIPTION
			"The status of the referenced disk drive."
	::= { raidVEntry 3 }

	raidVDiskId                     OBJECT-TYPE
	SYNTAX                          Integer32
        MAX-ACCESS                      read-only
        STATUS                          deprecated
	DESCRIPTION
			"The disk identifier for the referenced disk
			 drive. This OID is not available from the
			 Cluster management interfaces. This object is deprecated."
	::= { raidVEntry 4 }

	raidVScsiAdapter                OBJECT-TYPE
	SYNTAX                          DisplayString
        MAX-ACCESS                      read-only
        STATUS                          deprecated
	DESCRIPTION
			"The identifier of the SCSI adapter for the
			 referenced disk drive. This OID is not available
			 from the Cluster management interfaces. This object is deprecated."
	::= { raidVEntry 5 }

	raidVScsiId                     OBJECT-TYPE
	SYNTAX                          Integer32 (0..100)
        MAX-ACCESS                      read-only
        STATUS                          deprecated
	DESCRIPTION
			"The identifier for the referenced disk drive
			 on the referenced SCSI adapter. This OID is
			 not available from the Cluster management interfaces.
			 This object is deprecated."
	::= { raidVEntry 6 }

	raidVUsedMb                     OBJECT-TYPE
	SYNTAX                          Integer32
        MAX-ACCESS                      read-only
        STATUS                          current
	DESCRIPTION
			"The number of MBytes currently in use on
			 the referenced disk drive."
	::= { raidVEntry 7 }

	raidVUsedBlocks                 OBJECT-TYPE
	SYNTAX                          Integer32
        MAX-ACCESS                      read-only
        STATUS                          deprecated
	DESCRIPTION
			"The number of Blocks currently in use on
			 the referenced disk drive. This object is deprecated.
			 Use raidV64UsedBlocks object instead."
	::= { raidVEntry 8 }

	raidVTotalMb                    OBJECT-TYPE
	SYNTAX                          Integer32
        MAX-ACCESS                      read-only
        STATUS                          current
	DESCRIPTION
			"The number of MBytes physically available
			 on the referenced disk drive."
	::= { raidVEntry 9 }

	raidVTotalBlocks                OBJECT-TYPE
	SYNTAX                          Integer32
        MAX-ACCESS                      read-only
        STATUS                          deprecated
	DESCRIPTION
			"The number of Blocks physically available
			 on the referenced disk drive. This object is deprecated.
			 Use raidV64TotalBlocks object instead."
	::= { raidVEntry 10 }

	raidVCompletionPerCent          OBJECT-TYPE
	SYNTAX                          Integer32 (0..100)
        MAX-ACCESS                      read-only
        STATUS                          current
	DESCRIPTION
			 "In the case when rapid raid recovery, disk copy,
			  reconstruction/adding a spare, verification or
			  scrubbing is in progress, the percent of such
			  copy, reconstruction, verification or scrubbing
			  that has been completed on the referenced disk
			  drive."
	::= { raidVEntry 11 }

	raidVVol                        OBJECT-TYPE
	SYNTAX                          Integer32 (1..2147483647)
        MAX-ACCESS                      read-only
        STATUS                          current
	DESCRIPTION
			"A number that identifies the aggregate that this entry
			 belongs to.  The first aggregate is '1'."
	::= { raidVEntry 12 }

	raidVGroup                      OBJECT-TYPE
	SYNTAX                          Integer32 (1..2147483647)
        MAX-ACCESS                      read-only
        STATUS                          current
	DESCRIPTION
			"A number that identifies the RAID group within the
			 given aggregate that this entry belongs to.  The
			 first RAID group is '1', and number across all plexes."
	::= { raidVEntry 13 }

	raidVDiskNumber                 OBJECT-TYPE
	SYNTAX                          Integer32
        MAX-ACCESS                      read-only
        STATUS                          current
	DESCRIPTION
			"The number of disks within this RAID group."
	::= { raidVEntry 14 }

	raidVGroupNumber                OBJECT-TYPE
	SYNTAX                          Integer32
        MAX-ACCESS                      read-only
        STATUS                          current
	DESCRIPTION
			"The number of RAID groups within this aggregate."
	::= { raidVEntry 15 }

	raidVDiskPort                   OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the primary path to the disk.
			For a dual-ported disk, values of portA and portB
			indicate which port is being used.
			If the disk only has a single port, the value
			is portSingle, and if the port is not active,
			the value is portNone. This OID is not available
			from the Cluster management interfaces.
			This object is deprecated."
	::= { raidVEntry 16 }

	raidVSecondaryDiskName          OBJECT-TYPE
	SYNTAX                          DisplayString
        MAX-ACCESS                      read-only
        STATUS                          deprecated
	DESCRIPTION
			"The name identifying the secondary path to
			the referenced disk drive. This OID is not
			available from the Cluster management interfaces.
			This object is deprecated."
	::= { raidVEntry 17 }

	raidVSecondaryDiskPort          OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the secondary path to the disk.
			For a dual-ported disk, values of portA and portB
			indicate which port is being used.
			If the disk only has a single port, the value
			is portSingle, and if the port is not active,
			the value is portNone. This OID is not available from
			the Cluster management interfaces. This object is deprecated."
	::= { raidVEntry 18 }

	raidVShelf                      OBJECT-TYPE
	SYNTAX                          Integer32
        MAX-ACCESS                      read-only
        STATUS                          current
	DESCRIPTION
			"Number identifying the shelf where the disk
			is located."
	::= { raidVEntry 19 }

	raidVBay                        OBJECT-TYPE
	SYNTAX                          Integer32
        MAX-ACCESS                      read-only
        STATUS                          current
	DESCRIPTION
			"Number identifying the disk bay within
			the shelf where the disk is located."
	::= { raidVEntry 20 }


        raidVPlex                       OBJECT-TYPE
	SYNTAX                          Integer32
        MAX-ACCESS                      read-only
        STATUS                          current
        DESCRIPTION
                        "A number that identifies the plex within the
                         given aggregate that this entry belongs to.  The
                         first plex is '1'."
        ::= { raidVEntry 21 }

        raidVPlexGroup                  OBJECT-TYPE
	SYNTAX                          Integer32
        MAX-ACCESS                      read-only
        STATUS                          current
        DESCRIPTION
                        "A number that identifies the RAID group within
                         the given plex that this entry belongs to.  The
                         first RAID group is '1'."
        ::= { raidVEntry 22 }

	raidVPlexNumber                 OBJECT-TYPE
	SYNTAX                          Integer32 (1..2)
        MAX-ACCESS                      read-only
        STATUS                          current
	DESCRIPTION
			"The number of plexes within this aggregate.
                        This number is always 1 or 2."
	::= { raidVEntry 23 }

        raidVPlexName                   OBJECT-TYPE
	SYNTAX                          DisplayString
        MAX-ACCESS                      read-only
        STATUS                          current
	DESCRIPTION
			"A name that identifies the plex that this entry
			 belongs to.  A plex name can be anything, but
                         is usually a string like 'plex0' or 'plex1'."
        ::= { raidVEntry 24 }

        raidVSectorSize                 OBJECT-TYPE
	SYNTAX                          Integer32
        MAX-ACCESS                      read-only
        STATUS                          current
        DESCRIPTION
                        "A number that specifies bytes per sector
                         for this entry.  Values are '512' or '520'."
        ::= { raidVEntry 25 }

	raidVDiskSerialNumber           OBJECT-TYPE
	SYNTAX                          DisplayString
        MAX-ACCESS                      read-only
        STATUS                          current
	DESCRIPTION
		"Serial number of the referenced disk drive."
	::= { raidVEntry 26 }

	raidVDiskVendor                 OBJECT-TYPE
	SYNTAX                          DisplayString
        MAX-ACCESS                      read-only
        STATUS                          current
	DESCRIPTION
		"The vendor of the referenced disk drive."
	::= { raidVEntry 27 }

	raidVDiskModel                  OBJECT-TYPE
	SYNTAX                          DisplayString
        MAX-ACCESS                      read-only
        STATUS                          current
	DESCRIPTION
		"Model string of the referenced disk drive."
	::= { raidVEntry 28 }

	raidVDiskFirmwareRevision       OBJECT-TYPE
	SYNTAX                          DisplayString
        MAX-ACCESS                      read-only
        STATUS                          current
	DESCRIPTION
		"Firmware revision number of the referenced disk drive."
	::= { raidVEntry 29 }

	raidVDiskRPM                    OBJECT-TYPE
	SYNTAX                          DisplayString
        MAX-ACCESS                      read-only
        STATUS                          current
	DESCRIPTION
		"RPM of the referenced disk drive."
	::= { raidVEntry 30 }

	raidVDiskType                   OBJECT-TYPE
	SYNTAX                          DisplayString
        MAX-ACCESS                      read-only
        STATUS                          current
	DESCRIPTION
		"Interface type of the referenced disk drive. e.g SCSI,
		 or ATA."
	::= { raidVEntry 31 }

	raidVDiskPool                   OBJECT-TYPE
	SYNTAX                          DisplayString
        MAX-ACCESS                      read-only
        STATUS                          current
	DESCRIPTION
		"A name that identifies the disk pool that this entry
		 belongs to."
	::= { raidVEntry 32 }

	raidVDiskCopyDestDiskName       OBJECT-TYPE
	SYNTAX                          DisplayString
        MAX-ACCESS                      read-only
        STATUS                          current
	DESCRIPTION
		"When raidVStatus value is prefailed, this string identifies
		 the name of the disk which is the copy target of the
		 referenced prefailed disk."
	::= { raidVEntry 33 }

	raidVDiskUID			OBJECT-TYPE
	SYNTAX                          DisplayString
        MAX-ACCESS                      read-only
        STATUS                          current
	DESCRIPTION
		"Unique identifier for the disk. The maximum length is 90 characters."
	::= { raidVEntry 34 }

	raidV64UsedBlocks               OBJECT-TYPE
	SYNTAX                          Counter64
        MAX-ACCESS                      read-only
        STATUS                          current
	DESCRIPTION
		"The number of Blocks currently in use on the referenced disk drive.
		 This object returns all of the 64 bit unsigned integer."
	::= { raidVEntry 35 }

	raidV64TotalBlocks              OBJECT-TYPE
	SYNTAX                          Counter64
        MAX-ACCESS                      read-only
        STATUS                          current
	DESCRIPTION
		"The number of Blocks physically available on the referenced disk drive.
		 This object returns all of the 64 bit unsigned integer."
	::= { raidVEntry 36 }

	raidVCarrierID			OBJECT-TYPE
	SYNTAX				DisplayString
	MAX-ACCESS			read-only
	STATUS				current
	DESCRIPTION
		"Unique identifier of the disk carrier."
	::= { raidVEntry 37 }

	-- Spare disk table.

	spareTable                      OBJECT-TYPE
	SYNTAX                          SEQUENCE OF SpareEntry
        MAX-ACCESS                      not-accessible
        STATUS                          current
	DESCRIPTION
			"Display spare disk configuration information."
	::= { raid 3 }

	spareEntry                      OBJECT-TYPE
	SYNTAX                          SpareEntry
        MAX-ACCESS                      not-accessible
        STATUS                          current
	DESCRIPTION
			"Display configuration information for
			 the referenced spare disk drive."
	INDEX	{ spareIndex }
	::= { spareTable 1 }

	SpareEntry ::=
	    SEQUENCE {
		spareIndex
		    Integer32,
		spareDiskName
		    DisplayString,
		spareStatus
		    INTEGER,
		spareDiskId
		    Integer32,
		spareScsiAdapter
		    DisplayString,
		spareScsiId
		    Integer32,
		spareTotalMb
		    Integer32,
		spareTotalBlocks
		    Integer32,
		spareDiskPort
		    INTEGER,
		spareSecondaryDiskName
		    DisplayString,
		spareSecondaryDiskPort
		    INTEGER,
		spareShelf
		    Integer32,
		spareBay
		    Integer32,
		sparePool
		    DisplayString,
		spareSectorSize
		    Integer32,
		spareDiskSerialNumber
		    DisplayString,
		spareDiskVendor
		    DisplayString,
		spareDiskModel
		    DisplayString,
		spareDiskFirmwareRevision
		    DisplayString,
		spareDiskRPM
		    DisplayString,
		spareDiskType
		    DisplayString,
		spareDiskUID
		    DisplayString,
		spare64TotalBlocks
		    Counter64,
		spareCarrierID
		    DisplayString,
		spareOwnerNode
		    DisplayString,
		spareDrawer
		    Integer32,
		spareDrawerSlot
		    Integer32
	    }

	spareIndex                      OBJECT-TYPE
	SYNTAX                          Integer32 (1..2147483647)
        MAX-ACCESS                      read-only
        STATUS                          current
	DESCRIPTION
			"A number that identifies this entry for the
			 referenced disk drive in the list of spare disk
			 drives."
	::= { spareEntry 1 }

	spareDiskName                   OBJECT-TYPE
	SYNTAX                          DisplayString
        MAX-ACCESS                      read-only
        STATUS                          current
	DESCRIPTION
			"The name identifying the referenced spare disk
			 drive."
	::= { spareEntry 2 }

	spareStatus                     OBJECT-TYPE
	SYNTAX                          INTEGER {
                                             spare(1),
                                             addingspare(2),
					     bypassed(3),
					     unknown(4),
                                             offline(10)
                                        }
        MAX-ACCESS                      read-only
        STATUS                          current
	DESCRIPTION
			"The status of the referenced spare disk drive."
	::= { spareEntry 3 }

	spareDiskId                     OBJECT-TYPE
	SYNTAX                          Integer32
        MAX-ACCESS                      read-only
        STATUS                          deprecated
	DESCRIPTION
			"The disk identifier for the referenced spare disk
			 drive. This OID is not available from the Cluster
			 management interfaces. This object is deprecated."
	::= { spareEntry 4 }

	spareScsiAdapter                OBJECT-TYPE
	SYNTAX                          DisplayString
        MAX-ACCESS                      read-only
        STATUS                          deprecated
	DESCRIPTION
			"The identifier of the SCSI adapter for the
			 referenced spare disk drive. This OID is not
			 available from the Cluster management interfaces.
			 This object is deprecated."
	::= { spareEntry 5 }

	spareScsiId                     OBJECT-TYPE
	SYNTAX                          Integer32 (0..100)
        MAX-ACCESS                      read-only
        STATUS                          deprecated
	DESCRIPTION
			"The identifier for the referenced spare disk drive
			 on the referenced SCSI adapter. This OID is not
			 available from the Cluster management interfaces.
			 This object is deprecated."
	::= { spareEntry 6 }

	spareTotalMb                    OBJECT-TYPE
	SYNTAX                          Integer32
        MAX-ACCESS                      read-only
        STATUS                          current
	DESCRIPTION
			"The number of MBytes physically available
			 on the referenced spare disk drive."
	::= { spareEntry 7 }

	spareTotalBlocks                OBJECT-TYPE
	SYNTAX                          Integer32
        MAX-ACCESS                      read-only
        STATUS                          deprecated
	DESCRIPTION
			"The number of Blocks physically available
			 on the referenced spare disk drive. This object is deprecated.
			 Use spare64TotalBlocks object instead."
	::= { spareEntry 8 }

	spareDiskPort                   OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the primary path to the disk.
			For a dual-ported disk, values of portA and portB
			indicate which port is being used.
			If the disk only has a single port, the value
			is portSingle, and if the port is not active,
			the value is portNone. This OID is not available
			from the Cluster management interfaces.
			This object is deprecated."
	::= { spareEntry 9 }

	spareSecondaryDiskName          OBJECT-TYPE
	SYNTAX                          DisplayString
        MAX-ACCESS                      read-only
        STATUS                          deprecated
	DESCRIPTION
			"The name identifying the secondary path to
			the referenced disk drive. This OID is not
			available from the Cluster management interfaces.
			This object is deprecated."
	::= { spareEntry 10 }

	spareSecondaryDiskPort          OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the secondary path to the disk.
			For a dual-ported disk, values of portA and portB
			indicate which port is being used.
			If the disk only has a single port, the value
			is portSingle, and if the port is not active,
			the value is portNone. This OID is not available from
			the Cluster management interfaces. This object is deprecated."
	::= { spareEntry 11 }

	spareShelf                      OBJECT-TYPE
	SYNTAX                          Integer32
        MAX-ACCESS                      read-only
        STATUS                          current
	DESCRIPTION
			"Number identifying the shelf where the disk
			is located."
	::= { spareEntry 12 }

	spareBay                        OBJECT-TYPE
	SYNTAX                          Integer32
        MAX-ACCESS                      read-only
        STATUS                          current
	DESCRIPTION
			"Number identifying the disk bay within
			the shelf where the disk is located."
	::= { spareEntry 13 }

        sparePool                       OBJECT-TYPE
	SYNTAX                          DisplayString
        MAX-ACCESS                      read-only
        STATUS                          current
        DESCRIPTION
                        "A name that identifies the disk pool that this
                         entry belongs to."
        ::= { spareEntry 14 }

        spareSectorSize                 OBJECT-TYPE
	SYNTAX                          Integer32
        MAX-ACCESS                      read-only
        STATUS                          current
        DESCRIPTION
                        "A number that specifies bytes per sector
                         for this entry.  Values are '512' or '520'."
        ::= { spareEntry 15 }

	spareDiskSerialNumber           OBJECT-TYPE
	SYNTAX                          DisplayString
        MAX-ACCESS                      read-only
        STATUS                          current
	DESCRIPTION
		"Serial number of the referenced disk drive."
	::= { spareEntry 16 }

	spareDiskVendor                 OBJECT-TYPE
	SYNTAX                          DisplayString
        MAX-ACCESS                      read-only
        STATUS                          current
	DESCRIPTION
		"The vendor of the referenced disk drive."
	::= { spareEntry 17 }

	spareDiskModel                  OBJECT-TYPE
	SYNTAX                          DisplayString
        MAX-ACCESS                      read-only
        STATUS                          current
	DESCRIPTION
		"Model string of the referenced disk drive."
	::= { spareEntry 18 }

	spareDiskFirmwareRevision       OBJECT-TYPE
	SYNTAX                          DisplayString
        MAX-ACCESS                      read-only
        STATUS                          current
	DESCRIPTION
		"Firmware revision number of the referenced disk drive."
	::= { spareEntry 19 }

	spareDiskRPM                    OBJECT-TYPE
	SYNTAX                          DisplayString
        MAX-ACCESS                      read-only
        STATUS                          current
	DESCRIPTION
		"RPM of the referenced disk drive."
	::= { spareEntry 20 }

	spareDiskType                   OBJECT-TYPE
	SYNTAX                          DisplayString
        MAX-ACCESS                      read-only
        STATUS                          current
	DESCRIPTION
		"Interface type of the referenced disk drive. e.g SCSI,
		 or ATA."
	::= { spareEntry 21 }

	spareDiskUID			OBJECT-TYPE
	SYNTAX				DisplayString
	MAX-ACCESS			read-only
	STATUS				current
	DESCRIPTION
		"External unique identifier for the disk.
		The Maximum length is 90 characters."
	::= { spareEntry 22 }

	spare64TotalBlocks              OBJECT-TYPE
	SYNTAX                          Counter64
        MAX-ACCESS                      read-only
        STATUS                          current
	DESCRIPTION
			"The number of Blocks physically available
			 on the referenced spare disk drive. This
			 object returns all of the 64 bit unsigned integer."
	::= { spareEntry 23 }

	spareCarrierID			OBJECT-TYPE
	SYNTAX				DisplayString
	MAX-ACCESS			read-only
	STATUS				current
	DESCRIPTION
		"Unique identifier of the disk carrier."
	::= { spareEntry 24 }

	spareOwnerNode			OBJECT-TYPE
	SYNTAX				DisplayString
	MAX-ACCESS			read-only
	STATUS				current
	DESCRIPTION
	        "Owner node of the spare disk."
	::= { spareEntry 25 }

    spareDrawer                     OBJECT-TYPE
	SYNTAX                          Integer32
    MAX-ACCESS                      read-only
    STATUS                          current
    DESCRIPTION
			"Used for shelves with drawers. Number
			identifying the physical drawer where
			the disk is located."
        ::= { spareEntry 26 }

    spareDrawerSlot                 OBJECT-TYPE
	SYNTAX                          Integer32
    MAX-ACCESS                      read-only
    STATUS                          current
    DESCRIPTION
			"Used for shelves with drawers. Identifies which
			slot in the drawer this disk is located."
        ::= { spareEntry 27 }

	-- Disk summaries

	diskSummary	OBJECT IDENTIFIER ::= { raid 4 }

	diskTotalCount                  OBJECT-TYPE
	SYNTAX                          Integer32
        MAX-ACCESS                      read-only
        STATUS                          current
	DESCRIPTION
			"The total number of disks on the system."

	::= { diskSummary 1 }

	diskActiveCount                 OBJECT-TYPE
	SYNTAX                          Integer32
        MAX-ACCESS                      read-only
        STATUS                          current
	DESCRIPTION
			"The number of disks which are currently active,
			including parity disks."

	::= { diskSummary 2 }

	diskReconstructingCount         OBJECT-TYPE
	SYNTAX                          Integer32
        MAX-ACCESS                      read-only
        STATUS                          current
	DESCRIPTION
			"The number of disks which are
			currently being reconstructed."

	::= { diskSummary 3 }

	diskReconstructingParityCount   OBJECT-TYPE
	SYNTAX                          Integer32
        MAX-ACCESS                      read-only
        STATUS                          current
	DESCRIPTION
			"The number of parity disks which are
			currently being reconstructed."

	::= { diskSummary 4 }

	diskVerifyingParityCount        OBJECT-TYPE
	SYNTAX                          Integer32
        MAX-ACCESS                      read-only
        STATUS                          current
	DESCRIPTION
			"The number of disks which are
			currently being verified."

	::= { diskSummary 5 }

	diskScrubbingCount              OBJECT-TYPE
	SYNTAX                          Integer32
        MAX-ACCESS                      read-only
        STATUS                          current
	DESCRIPTION
			"The number of disks which are
			currently being scrubbed."

	::= { diskSummary 6 }

	diskFailedCount                 OBJECT-TYPE
	SYNTAX                          Integer32
        MAX-ACCESS                      read-only
        STATUS                          current
	DESCRIPTION
			"The number of disks which are
			currently broken."

	::= { diskSummary 7 }

	diskSpareCount                  OBJECT-TYPE
	SYNTAX                          Integer32
        MAX-ACCESS                      read-only
        STATUS                          current
	DESCRIPTION
			"The number of available spare disks."

	::= { diskSummary 8 }

	diskAddingSpareCount            OBJECT-TYPE
	SYNTAX                          Integer32
        MAX-ACCESS                      read-only
        STATUS                          current
	DESCRIPTION
			"The number of spare disks which are
			currently being added into a RAID group."

	::= { diskSummary 9 }

	diskFailedMessage               OBJECT-TYPE
	SYNTAX                          DisplayString
        MAX-ACCESS                      read-only
        STATUS                          current
	DESCRIPTION
			"If diskFailedCount is non-zero, this is
			a string describing the failed disk or
			disks.  Each failed disk is described with
			a sentence like

			Disk on adapter 8a, shelf 1, bay 0, failed.

			or

			Disk on stack 3, shelf 2, bay 2, failed."

	::= { diskSummary 10 }

        diskPrefailedCount              OBJECT-TYPE
	SYNTAX                          Integer32
        MAX-ACCESS                      read-only
        STATUS                          current
        DESCRIPTION
			"The number of disks which are prefailed and marked
			  for rapid raid recovery."

        ::= { diskSummary 11 }

	raidVNumber                     OBJECT-TYPE
	SYNTAX                          Integer32
        MAX-ACCESS                      read-only
        STATUS                          current
	DESCRIPTION
			"Number of entries in the raidVTable table.
			 This is the total number of aggregates in the system."

	::= { raid 5 }

	spareNumber                     OBJECT-TYPE
	SYNTAX                          Integer32
        MAX-ACCESS                      read-only
        STATUS                          current
	DESCRIPTION
			"Number of entries in the spareTable table."

	::= { raid 6 }

	otherDiskNumber                 OBJECT-TYPE
	SYNTAX                          Integer32
        MAX-ACCESS                      read-only
        STATUS                          current
	DESCRIPTION
			"Number of entries in the otherDiskTable table."

	::= { raid 7 }

	raidPNumber                     OBJECT-TYPE
	SYNTAX                          Integer32
        MAX-ACCESS                      read-only
        STATUS                          current
	DESCRIPTION
			"Number of entries in the raidPTable table.
			 This is the total number of aggregates in the system."

	::= { raid 8 }

	-- Other (out-of-service) disk table.

	otherDiskTable                  OBJECT-TYPE
	SYNTAX                          SEQUENCE OF OtherDiskEntry
        MAX-ACCESS                      not-accessible
        STATUS                          current
	DESCRIPTION
			"Display out-of-service disk configuration information."
	::= { raid 9 }

	otherDiskEntry                  OBJECT-TYPE
	SYNTAX                          OtherDiskEntry
        MAX-ACCESS                      not-accessible
        STATUS                          current
	DESCRIPTION
			"Display configuration information for
			 the referenced disk drive."
	INDEX	{ otherDiskIndex }
	::= { otherDiskTable 1 }

	OtherDiskEntry ::=
	    SEQUENCE {
		otherDiskIndex
		    Integer32,
		otherDiskDiskName
		    DisplayString,
		otherDiskStatus
		    INTEGER,
		otherDiskDiskId
		    Integer32,
		otherDiskScsiAdapter
		    DisplayString,
		otherDiskScsiId
		    Integer32,
		otherDiskTotalMb
		    Integer32,
		otherDiskTotalBlocks
		    Integer32,
		otherDiskDiskPort
		    INTEGER,
		otherDiskSecondaryDiskName
		    DisplayString,
		otherDiskSecondaryDiskPort
		    INTEGER,
		otherDiskShelf
		    Integer32,
		otherDiskBay
		    Integer32,
		otherDiskPool
		    DisplayString,
		otherDiskSectorSize
		    Integer32,
		otherDiskSerialNumber
		    DisplayString,
		otherDiskVendor
		    DisplayString,
		otherDiskModel
		    DisplayString,
		otherDiskFirmwareRevision
		    DisplayString,
		otherDiskRPM
		    DisplayString,
		otherDiskType
		    DisplayString,
		otherDisk64TotalBlocks
		    Counter64,
		otherDiskCarrierID
		    DisplayString,
		otherDiskDrawer
		    Integer32,
		otherDiskDrawerSlot
		    Integer32
	    }

	otherDiskIndex                  OBJECT-TYPE
	SYNTAX                          Integer32 (1..2147483647)
        MAX-ACCESS                      read-only
        STATUS                          current
	DESCRIPTION
			"A number that identifies this entry for the
			 referenced disk drive in the list of out-of-service
			 disk drives. Out-of-service disks include all disks
                         that are not in service in a raid group or available
                         as a spare disk."
	::= { otherDiskEntry 1 }

	otherDiskDiskName               OBJECT-TYPE
	SYNTAX                          DisplayString
        MAX-ACCESS                      read-only
        STATUS                          current
	DESCRIPTION
			"The name identifying the referenced disk
			 drive."
	::= { otherDiskEntry 2 }

	otherDiskStatus                 OBJECT-TYPE
	SYNTAX                          INTEGER {
                                             broken(1),
                                             bypassed(2),
                                             unknown(3)
                                        }
        MAX-ACCESS                      read-only
        STATUS                          current
	DESCRIPTION
			"The status of the referenced disk drive."
	::= { otherDiskEntry 3 }

	otherDiskDiskId                 OBJECT-TYPE
	SYNTAX                          Integer32
        MAX-ACCESS                      read-only
        STATUS                          deprecated
	DESCRIPTION
			"The disk identifier for the referenced disk
			 drive. This OID is not available from the Cluster
			 management interfaces. This object is deprecated."
	::= { otherDiskEntry 4 }

	otherDiskScsiAdapter            OBJECT-TYPE
	SYNTAX                          DisplayString
        MAX-ACCESS                      read-only
        STATUS                          deprecated
	DESCRIPTION
			"The identifier of the SCSI adapter for the
			 referenced disk drive. This OID is not available
			 from the Cluster management interfaces.
			 This object is deprecated."
	::= { otherDiskEntry 5 }

	otherDiskScsiId                 OBJECT-TYPE
	SYNTAX                          Integer32 (0..100)
        MAX-ACCESS                      read-only
        STATUS                          deprecated
	DESCRIPTION
			"The identifier for the referenced disk drive
			 on the referenced SCSI adapter. This OID is
			 not available from the Cluster management interfaces.
			 This object is deprecated."
	::= { otherDiskEntry 6 }

	otherDiskTotalMb                OBJECT-TYPE
	SYNTAX                          Integer32
        MAX-ACCESS                      read-only
        STATUS                          current
	DESCRIPTION
			"The number of MBytes physically available
			 on the referenced disk drive."
	::= { otherDiskEntry 7 }

	otherDiskTotalBlocks            OBJECT-TYPE
	SYNTAX                          Integer32
        MAX-ACCESS                      read-only
        STATUS                          deprecated
	DESCRIPTION
			"The number of Blocks physically available
			 on the referenced disk drive. This object is deprecated.
			 Use otherDisk64TotalBlocks object instead."
	::= { otherDiskEntry 8 }

	otherDiskDiskPort               OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the primary path to the disk.
			For a dual-ported disk, values of portA and portB
			indicate which port is being used.
			If the disk only has a single port, the value
			is portSingle, and if the port is not active,
			the value is portNone. This OID is not available
			from the Cluster management interfaces.
			This object is deprecated."
	::= { otherDiskEntry 9 }

	otherDiskSecondaryDiskName      OBJECT-TYPE
	SYNTAX                          DisplayString
        MAX-ACCESS                      read-only
        STATUS                          deprecated
	DESCRIPTION
			"The name identifying the secondary path to
			the referenced disk drive. This OID is not available
			from the Cluster management interfaces.
			This object is deprecated."
	::= { otherDiskEntry 10 }

	otherDiskSecondaryDiskPort      OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the secondary path to the disk.
			For a dual-ported disk, values of portA and portB
			indicate which port is being used.
			If the disk only has a single port, the value
			is portSingle, and if the port is not active,
			the value is portNone. This OID is not available
			from the Cluster management interfaces.
			This object is deprecated."
	::= { otherDiskEntry 11 }

	otherDiskShelf                  OBJECT-TYPE
	SYNTAX                          Integer32
        MAX-ACCESS                      read-only
        STATUS                          current
	DESCRIPTION
			"Number identifying the shelf where the disk
			is located."
	::= { otherDiskEntry 12 }

	otherDiskBay                    OBJECT-TYPE
	SYNTAX                          Integer32
        MAX-ACCESS                      read-only
        STATUS                          current
	DESCRIPTION
			"Number identifying the disk bay within
			the shelf where the disk is located."
	::= { otherDiskEntry 13 }

        otherDiskPool                   OBJECT-TYPE
	SYNTAX                          DisplayString
        MAX-ACCESS                      read-only
        STATUS                          current
        DESCRIPTION
                        "A name that identifies the disk pool that this
                         entry belongs to."
        ::= { otherDiskEntry 14 }

        otherDiskSectorSize             OBJECT-TYPE
	SYNTAX                          Integer32
        MAX-ACCESS                      read-only
        STATUS                          current
        DESCRIPTION
                        "A number that specifies bytes per sector
                         for this entry.  Values are '512' or '520'."
        ::= { otherDiskEntry 15 }

	otherDiskSerialNumber           OBJECT-TYPE
	SYNTAX                          DisplayString
        MAX-ACCESS                      read-only
        STATUS                          current
	DESCRIPTION
		"Serial number of the referenced disk drive."
	::= { otherDiskEntry 16 }

	otherDiskVendor                 OBJECT-TYPE
	SYNTAX                          DisplayString
        MAX-ACCESS                      read-only
        STATUS                          current
	DESCRIPTION
		"The vendor of the referenced disk drive."
	::= { otherDiskEntry 17 }

	otherDiskModel                  OBJECT-TYPE
	SYNTAX                          DisplayString
        MAX-ACCESS                      read-only
        STATUS                          current
	DESCRIPTION
		"Model string of the referenced disk drive."
	::= { otherDiskEntry 18 }

	otherDiskFirmwareRevision       OBJECT-TYPE
	SYNTAX                          DisplayString
        MAX-ACCESS                      read-only
        STATUS                          current
	DESCRIPTION
		"Firmware revision number of the referenced disk drive."
	::= { otherDiskEntry 19 }

	otherDiskRPM                    OBJECT-TYPE
	SYNTAX                          DisplayString
        MAX-ACCESS                      read-only
        STATUS                          current
	DESCRIPTION
		"RPM of the referenced disk drive."
	::= { otherDiskEntry 20 }

	otherDiskType                   OBJECT-TYPE
	SYNTAX                          DisplayString
        MAX-ACCESS                      read-only
        STATUS                          current
	DESCRIPTION
		"Interface type of the referenced disk drive. e.g SCSI,
		 or ATA."
	::= { otherDiskEntry 21 }

	otherDisk64TotalBlocks          OBJECT-TYPE
	SYNTAX                          Counter64
        MAX-ACCESS                      read-only
        STATUS                          current
	DESCRIPTION
			"The number of Blocks physically available
			 on the referenced disk drive. This object
			returns all of the 64 bit unsigned integer."
	::= { otherDiskEntry 22 }

	otherDiskCarrierID		OBJECT-TYPE
	SYNTAX				DisplayString
	MAX-ACCESS			read-only
	STATUS				current
	DESCRIPTION
		"Unique identifier of the disk carrier."
	::= { otherDiskEntry 23 }


	otherDiskDrawer                  OBJECT-TYPE
	SYNTAX                          Integer32
	MAX-ACCESS                      read-only
	STATUS                          current
	DESCRIPTION
			"Used for shelves with drawers. Number
			identifying the physical drawer where
			the disk is located."
	::= { otherDiskEntry 24 }

	otherDiskDrawerSlot                  OBJECT-TYPE
	SYNTAX                          Integer32
	MAX-ACCESS                      read-only
	STATUS                          current
	DESCRIPTION
			"Used for shelves with drawers. Identifies which
			slot in the drawer this disk is located."
	::= { otherDiskEntry 25 }

	-- Multivolume and multiplex raidTable.

	raidPTable                      OBJECT-TYPE
	SYNTAX                          SEQUENCE OF RaidPEntry
        MAX-ACCESS                      not-accessible
        STATUS                          current
	DESCRIPTION
			"Display RAID configuration information."
	::= { raid 10 }

	raidPEntry                      OBJECT-TYPE
	SYNTAX                          RaidPEntry
        MAX-ACCESS                      not-accessible
        STATUS                          current
	DESCRIPTION
			"Display RAID configuration information for
			 the referenced aggregate, plex, raid group, and disk drive."
	INDEX	{ raidPVol, raidPPlex, raidPGroup, raidPIndex }
	::= { raidPTable 1 }

	RaidPEntry ::=
	    SEQUENCE {
		raidPIndex
		    Integer32,
		raidPStatus
		    INTEGER,
		raidPVol
		    Integer32,
                raidPPlex
                    Integer32,
		raidPGroup
		    Integer32,
		raidPPlexNumber
		    Integer32,
		raidPGroupNumber
		    Integer32,
		raidPDiskNumber
		    Integer32,
                raidPPlexName
                    DisplayString,
		raidPDiskName
		    DisplayString,
		raidPDiskPort
		    INTEGER,
		raidPSecondaryDiskName
		    DisplayString,
		raidPSecondaryDiskPort
		    INTEGER,
		raidPScsiAdapter
		    DisplayString,
		raidPScsiId
		    Integer32,
		raidPDiskId
		    Integer32,
		raidPShelf
		    Integer32,
		raidPBay
		    Integer32,
                raidPSectorSize
                    Integer32,
		raidPUsedMb
		    Integer32,
		raidPUsedBlocks
		    Integer32,
		raidPTotalMb
		    Integer32,
		raidPTotalBlocks
		    Integer32,
		raidPCompletionPerCent
		    Integer32,
		raidPDiskSerialNumber
		    DisplayString,
		raidPDiskVendor
		    DisplayString,
		raidPDiskModel
		    DisplayString,
		raidPDiskFirmwareRevision
		    DisplayString,
		raidPDiskRPM
		    DisplayString,
		raidPDiskType
		    DisplayString,
		raidPDiskPool
		    DisplayString,
		raidPDiskCopyDestDiskName
		    DisplayString,
		raidP64UsedBlocks
		    Counter64,
		raidP64TotalBlocks
		    Counter64,
		raidPCarrierID
		    DisplayString
	    }

	raidPIndex                      OBJECT-TYPE
	SYNTAX                          Integer32 (1..2147483647)
        MAX-ACCESS                      read-only
        STATUS                          current
	DESCRIPTION
			"A number that identifies this disk drive within
			 the given aggregate and RAID group."
	::= { raidPEntry 1 }

	raidPStatus                     OBJECT-TYPE
	SYNTAX                          INTEGER {
                                             active(1),
                                             reconstructionInProgress(2),
					     parityReconstructionInProgress(3),
					     parityVerificationInProgress(4),
					     scrubbingInProgress(5),
					     failed(6),
					     prefailed(9),
                                             offline(10)
                                        }
        MAX-ACCESS                      read-only
        STATUS                          current
	DESCRIPTION
			"The status of the referenced disk drive."
	::= { raidPEntry 2 }

	raidPVol                        OBJECT-TYPE
	SYNTAX                          Integer32 (1..2147483647)
        MAX-ACCESS                      read-only
        STATUS                          current
	DESCRIPTION
			"A number that identifies the aggregate that this entry
			 belongs to. The first aggregate is '1'."
	::= { raidPEntry 3 }

	raidPPlex                       OBJECT-TYPE
	SYNTAX                          Integer32 (1..2147483647)
        MAX-ACCESS                      read-only
        STATUS                          current
	DESCRIPTION
			"A number that identifies the plex that this entry
			 belongs to. The first plex is '1'."
	::= { raidPEntry 4 }

	raidPGroup                      OBJECT-TYPE
	SYNTAX                          Integer32 (1..2147483647)
        MAX-ACCESS                      read-only
        STATUS                          current
	DESCRIPTION
			"A number that identifies the RAID group within the
			 given plex that this entry belongs to. The
			 first RAID group is '1'."
	::= { raidPEntry 5 }

	raidPPlexNumber                 OBJECT-TYPE
	SYNTAX                          Integer32 (1..2)
        MAX-ACCESS                      read-only
        STATUS                          current
	DESCRIPTION
			"The number of plexes within this aggregate.
                        This number is always 1 or 2."
	::= { raidPEntry 6 }

	raidPGroupNumber                OBJECT-TYPE
	SYNTAX                          Integer32
        MAX-ACCESS                      read-only
        STATUS                          current
	DESCRIPTION
			"The number of RAID groups within this plex."
	::= { raidPEntry 7 }

	raidPDiskNumber                 OBJECT-TYPE
	SYNTAX                          Integer32 (1..100)
        MAX-ACCESS                      read-only
        STATUS                          current
	DESCRIPTION
			"The number of disks within this RAID group."
	::= { raidPEntry 8 }

	raidPPlexName                   OBJECT-TYPE
	SYNTAX                          DisplayString
        MAX-ACCESS                      read-only
        STATUS                          current
	DESCRIPTION
			"A name that identifies the plex that this entry
			 belongs to.  A plex name can be anything, but
                         is usually a string like 'plex0' or 'plex1'."
	::= { raidPEntry 9 }

	raidPDiskName                   OBJECT-TYPE
	SYNTAX                          DisplayString
        MAX-ACCESS                      read-only
        STATUS                          current
	DESCRIPTION
			"The name identifying the referenced disk drive."
	::= { raidPEntry 10 }

	raidPDiskPort                   OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the primary path to the disk.
			For a dual-ported disk, values of portA and portB
			indicate which port is being used.
			If the disk only has a single port, the value
			is portSingle, and if the port is not active,
			the value is portNone. This OID is not available
			from the Cluster management interfaces.
			This object is deprecated."
	::= { raidPEntry 11 }

	raidPSecondaryDiskName          OBJECT-TYPE
	SYNTAX                          DisplayString
        MAX-ACCESS                      read-only
        STATUS                          deprecated
	DESCRIPTION
			"The name identifying the secondary path to
			the referenced disk drive. This OID is not
			available from the Cluster management interfaces.
			This object is deprecated."
	::= { raidPEntry 12 }

	raidPSecondaryDiskPort          OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the secondary path to the disk.
			For a dual-ported disk, values of portA and portB
			indicate which port is being used.
			If the disk only has a single port, the value
			is portSingle, and if the port is not active,
			the value is portNone. This OID is not available
			from the Cluster management interfaces.
			This object is deprecated."
	::= { raidPEntry 13 }

	raidPScsiAdapter                OBJECT-TYPE
	SYNTAX                          DisplayString
        MAX-ACCESS                      read-only
        STATUS                          deprecated
	DESCRIPTION
			"The identifier of the SCSI adapter for the
			 referenced disk drive. This OID is not available
			 from the Cluster management interfaces.
			 This object is deprecated."
	::= { raidPEntry 14 }

	raidPScsiId                     OBJECT-TYPE
	SYNTAX                          Integer32 (0..100)
        MAX-ACCESS                      read-only
        STATUS                          deprecated
	DESCRIPTION
			"The identifier for the referenced disk drive
			 on the referenced SCSI adapter. This OID is
			 not available from the Cluster management interfaces.
			 This object is deprecated."
	::= { raidPEntry 15 }

	raidPDiskId                     OBJECT-TYPE
	SYNTAX                          Integer32
        MAX-ACCESS                      read-only
        STATUS                          deprecated
	DESCRIPTION
			"The disk identifier for the referenced disk
			 drive. This OID is not available from the
			 Cluster management interfaces.
			 This object is deprecated."
	::= { raidPEntry 16 }

	raidPShelf                      OBJECT-TYPE
	SYNTAX                          Integer32
        MAX-ACCESS                      read-only
        STATUS                          current
	DESCRIPTION
			"Number identifying the shelf where the disk
			is located."
	::= { raidPEntry 17 }

	raidPBay                        OBJECT-TYPE
	SYNTAX                          Integer32
        MAX-ACCESS                      read-only
        STATUS                          current
	DESCRIPTION
			"Number identifying the disk bay within
			the shelf where the disk is located."
	::= { raidPEntry 18 }


        raidPSectorSize                 OBJECT-TYPE
	SYNTAX                          Integer32
        MAX-ACCESS                      read-only
        STATUS                          current
        DESCRIPTION
                        "A number that specifies bytes per sector
                         for this entry.  Values are '512' or '520'."
        ::= { raidPEntry 19 }

	raidPUsedMb                     OBJECT-TYPE
	SYNTAX                          Integer32
        MAX-ACCESS                      read-only
        STATUS                          current
	DESCRIPTION
			"The number of MBytes currently in use on
			 the referenced disk drive."
	::= { raidPEntry 20 }

	raidPUsedBlocks                 OBJECT-TYPE
	SYNTAX                          Integer32
        MAX-ACCESS                      read-only
        STATUS                          deprecated
	DESCRIPTION
			"The number of Blocks currently in use on
			 the referenced disk drive. This object is deprecated.
			 Use raidP64UsedBlocks object instead."
	::= { raidPEntry 21 }

	raidPTotalMb                    OBJECT-TYPE
	SYNTAX                          Integer32
        MAX-ACCESS                      read-only
        STATUS                          current
	DESCRIPTION
			"The number of MBytes physically available
			 on the referenced disk drive."
	::= { raidPEntry 22 }

	raidPTotalBlocks                OBJECT-TYPE
	SYNTAX                          Integer32
        MAX-ACCESS                      read-only
        STATUS                          deprecated
	DESCRIPTION
			"The number of Blocks physically available
			 on the referenced disk drive. This object is deprecated.
			 Use raidP64TotalBlocks object instead."
	::= { raidPEntry 23 }

	raidPCompletionPerCent          OBJECT-TYPE
	SYNTAX                          Integer32 (0..100)
        MAX-ACCESS                      read-only
        STATUS                          current
	DESCRIPTION
			 "In the case when rapid raid recovery, disk copy,
			  reconstruction or adding a spare, verification or
			  scrubbing is in progress, the percent of such copy,
			  reconstruction, verification or scrubbing that has
			  been completed on the referenced disk drive."
	::= { raidPEntry 24 }

	raidPDiskSerialNumber           OBJECT-TYPE
	SYNTAX                          DisplayString
        MAX-ACCESS                      read-only
        STATUS                          current
	DESCRIPTION
		"Serial number of the referenced disk drive."
	::= { raidPEntry 25 }

	raidPDiskVendor                 OBJECT-TYPE
	SYNTAX                          DisplayString
        MAX-ACCESS                      read-only
        STATUS                          current
	DESCRIPTION
		"The vendor of the referenced disk drive."
	::= { raidPEntry 26 }

	raidPDiskModel                  OBJECT-TYPE
	SYNTAX                          DisplayString
        MAX-ACCESS                      read-only
        STATUS                          current
	DESCRIPTION
		"Model string of the referenced disk drive."
	::= { raidPEntry 27 }

	raidPDiskFirmwareRevision       OBJECT-TYPE
	SYNTAX                          DisplayString
        MAX-ACCESS                      read-only
        STATUS                          current
	DESCRIPTION
		"Firmware revision number of the referenced disk drive."
	::= { raidPEntry 28 }

	raidPDiskRPM                    OBJECT-TYPE
	SYNTAX                          DisplayString
        MAX-ACCESS                      read-only
        STATUS                          current
	DESCRIPTION
		"RPM of the referenced disk drive."
	::= { raidPEntry 29 }

	raidPDiskType                   OBJECT-TYPE
	SYNTAX                          DisplayString
        MAX-ACCESS                      read-only
        STATUS                          current
	DESCRIPTION
		"Interface type of the referenced disk drive. e.g SCSI,
		 or ATA."
	::= { raidPEntry 30 }

	raidPDiskPool                   OBJECT-TYPE
	SYNTAX                          DisplayString
        MAX-ACCESS                      read-only
        STATUS                          current
	DESCRIPTION
		"A name that identifies the disk pool that this entry
		 belongs to."
	::= { raidPEntry 31 }

	raidPDiskCopyDestDiskName       OBJECT-TYPE
	SYNTAX                          DisplayString
        MAX-ACCESS                      read-only
        STATUS                          current
	DESCRIPTION
		"When raidPStatus value is prefailed, this string identifies
		 the name of the disk which is the copy target of the
		 referenced prefailed disk."
	::= { raidPEntry 32 }

	raidP64UsedBlocks               OBJECT-TYPE
	SYNTAX                          Counter64
        MAX-ACCESS                      read-only
        STATUS                          current
	DESCRIPTION
			"The number of Blocks currently in use on
			 the referenced disk drive. This object returns
			 all of the 64 bit unsigned integer."
	::= { raidPEntry 33 }

	raidP64TotalBlocks              OBJECT-TYPE
	SYNTAX                          Counter64
        MAX-ACCESS                      read-only
        STATUS                          current
	DESCRIPTION
			"The number of Blocks physically available on
			 the referenced disk drive. This object returns
			 all of the 64 bit unsigned integer."
	::= { raidPEntry 34 }

	raidPCarrierID			OBJECT-TYPE
	SYNTAX				DisplayString
	MAX-ACCESS			read-only
	STATUS				current
	DESCRIPTION
		"Unique identifier of the disk carrier."
	::= { raidPEntry 35 }

	-- RAID Plex table.

        plexTable                       OBJECT-TYPE
	SYNTAX                          SEQUENCE OF PlexEntry
        MAX-ACCESS                      not-accessible
        STATUS                          current
        DESCRIPTION
                    "A table containing plex specific information."
        ::= {raid 11}

        -- display plexes

        plexEntry                       OBJECT-TYPE
	SYNTAX                          PlexEntry
        MAX-ACCESS                      not-accessible
        STATUS                          current
        DESCRIPTION
                        "Provide a report on file system plexes."
        INDEX           { plexIndex }
        ::= { plexTable 1 }

        PlexEntry ::=
            SEQUENCE {
                plexIndex
                    Integer32,
                plexName
                    DisplayString,
                plexVolName
                    DisplayString,
                plexStatus
                    INTEGER,
                plexPercentResyncing
                    Integer32
            }

        plexIndex                       OBJECT-TYPE
	SYNTAX                          Integer32 (1..2147483647)
        MAX-ACCESS                      read-only
        STATUS                          current
        DESCRIPTION
                        "A number that identifies this entry for the
                         referenced plex."
        ::= { plexEntry 1 }

        plexName                        OBJECT-TYPE
	SYNTAX                          DisplayString
        MAX-ACCESS                      read-only
        STATUS                          current
        DESCRIPTION
                        "The identifier of the plex."
        ::= { plexEntry 2 }

        plexVolName                     OBJECT-TYPE
	SYNTAX                          DisplayString
        MAX-ACCESS                      read-only
        STATUS                          current
        DESCRIPTION
                        "The aggregate to which this plex belongs."
        ::= { plexEntry 3 }

        plexStatus                      OBJECT-TYPE
	SYNTAX                          INTEGER {
                                             offline(1),
                                             resyncing(2),
                                             online(3)
                                        }
        MAX-ACCESS                      read-only
        STATUS                          current
        DESCRIPTION
                        "The status of the plex."
        ::= { plexEntry 4 }

        plexPercentResyncing            OBJECT-TYPE
	SYNTAX                          Integer32
        MAX-ACCESS                      read-only
        STATUS                          current
        DESCRIPTION
                             "If the plex is resyncing, the percent
                              completion of the resync."
        ::= { plexEntry 5 }

	--out-of-dateDisks

	outOfDateDiskCount              OBJECT-TYPE
	SYNTAX                          Integer32
        MAX-ACCESS                      read-only
        STATUS                          current
	DESCRIPTION
			"Number of entries in the outOfDateDiskTable table."

	::= { raid 12 }

	-- out-of-date disk table.

	outOfDateDiskTable              OBJECT-TYPE
	SYNTAX                          SEQUENCE OF OutOfDateDiskEntry
        MAX-ACCESS                      not-accessible
        STATUS                          current
	DESCRIPTION
			"Display out-of-date disk information."
	::= { raid 13 }

	outOfDateDiskEntry              OBJECT-TYPE
	SYNTAX                          OutOfDateDiskEntry
        MAX-ACCESS                      not-accessible
        STATUS                          current
	DESCRIPTION
			"Display information for the referenced
			 out-of-date disk."
	INDEX	{ outOfDateDiskIndex }
	::= { outOfDateDiskTable 1 }

	OutOfDateDiskEntry ::=
	    SEQUENCE {
		outOfDateDiskIndex
		    Integer32,
		outOfDateDiskDiskName
		    DisplayString,
		outOfDateDiskDiskId
		    Integer32,
		outOfDateDiskScsiAdapter
		    DisplayString,
		outOfDateDiskScsiId
		    Integer32,
		outOfDateDiskTotalMb
		    Integer32,
		outOfDateDiskTotalBlocks
		    Integer32,
		outOfDateDiskDiskPort
		    INTEGER,
		outOfDateDiskSecondaryDiskName
		    DisplayString,
		outOfDateDiskSecondaryDiskPort
		    INTEGER,
		outOfDateDiskShelf
		    Integer32,
		outOfDateDiskBay
		    Integer32,
		outOfDateDiskPool
		    DisplayString,
		outOfDateDiskSectorSize
		    Integer32,
		outOfDateDiskSerialNumber
		    DisplayString,
		outOfDateDiskVendor
		    DisplayString,
		outOfDateDiskModel
		    DisplayString,
		outOfDateDiskFirmwareRevision
		    DisplayString,
		outOfDateDiskRPM
		    DisplayString,
		outOfDateDiskType
		    DisplayString,
		outOfDateDisk64TotalBlocks
		    Counter64,
		outOfDateDiskCarrierID
		    DisplayString,
		outOfDateDiskDrawer
		    Integer32,
		outOfDateDiskDrawerSlot
		    Integer32
	    }

	outOfDateDiskIndex              OBJECT-TYPE
	SYNTAX                          Integer32 (1..2147483647)
        MAX-ACCESS                      read-only
        STATUS                          current
	DESCRIPTION
			"A number that identifies this entry for the
			 referenced disk drive in the list of out-of-date
			 disk drives."
	::= { outOfDateDiskEntry 1 }

	outOfDateDiskDiskName           OBJECT-TYPE
	SYNTAX                          DisplayString
        MAX-ACCESS                      read-only
        STATUS                          current
	DESCRIPTION
			"The name identifying the referenced disk
			 drive."
	::= { outOfDateDiskEntry 2 }

	outOfDateDiskDiskId             OBJECT-TYPE
	SYNTAX                          Integer32
        MAX-ACCESS                      read-only
        STATUS                          deprecated
	DESCRIPTION
			"The disk identifier for the referenced disk
			 drive. This OID is not available from the
			 Cluster management interfaces.
			 This object is deprecated."
	::= { outOfDateDiskEntry 3 }

	outOfDateDiskScsiAdapter        OBJECT-TYPE
	SYNTAX                          DisplayString
        MAX-ACCESS                      read-only
        STATUS                          deprecated
	DESCRIPTION
			"The identifier of the SCSI adapter for the
			 referenced disk drive. This OID is not available
			 from the Cluster management interfaces.
			 This object is deprecated."
	::= { outOfDateDiskEntry 4 }

	outOfDateDiskScsiId             OBJECT-TYPE
	SYNTAX                          Integer32 (0..100)
        MAX-ACCESS                      read-only
        STATUS                          deprecated
	DESCRIPTION
			"The identifier for the referenced disk drive
			 on the referenced SCSI adapter. This OID is not
			 available from the Cluster management interfaces.
			 This object is deprecated."
	::= { outOfDateDiskEntry 5 }

	outOfDateDiskTotalMb            OBJECT-TYPE
	SYNTAX                          Integer32
        MAX-ACCESS                      read-only
        STATUS                          current
	DESCRIPTION
			"The number of MBytes physically available
			 on the referenced disk drive."
	::= { outOfDateDiskEntry 6 }

	outOfDateDiskTotalBlocks        OBJECT-TYPE
	SYNTAX                          Integer32
        MAX-ACCESS                      read-only
        STATUS                          deprecated
	DESCRIPTION
			"The number of Blocks physically available
			 on the referenced disk drive. This object is deprecated.
			 Use outOfDateDisk64TotalBlocks object instead."
	::= { outOfDateDiskEntry 7 }

	outOfDateDiskDiskPort           OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the primary path to the disk.
			For a dual-ported disk, values of portA and portB
			indicate which port is being used.
			If the disk only has a single port, the value
			is portSingle, and if the port is not active,
			the value is portNone. This OID is not available
			from the Cluster management interfaces.
			This object is deprecated."
	::= { outOfDateDiskEntry 8 }

	outOfDateDiskSecondaryDiskName  OBJECT-TYPE
	SYNTAX                          DisplayString
        MAX-ACCESS                      read-only
        STATUS                          deprecated
	DESCRIPTION
			"The name identifying the secondary path to
			the referenced disk drive. This OID is not available
			from the Cluster management interfaces.
			This object is deprecated"
	::= { outOfDateDiskEntry 9 }

	outOfDateDiskSecondaryDiskPort  OBJECT-TYPE
	SYNTAX                          INTEGER {
                                             portA(1),
                                             portB(2),
					     portSingle(3),
                                             portNone(4)
                                        }
        MAX-ACCESS                      read-only
        STATUS                          deprecated
	DESCRIPTION
			"A number that indicates which port of the
			disk is being used by the secondary path to the disk.
			For a dual-ported disk, values of portA and portB
			indicate which port is being used.
			If the disk only has a single port, the value
			is portSingle, and if the port is not active,
			the value is portNone. This OID is not available
			from the Cluster management interfaces.
			This object is deprecated."
	::= { outOfDateDiskEntry 10 }

	outOfDateDiskShelf              OBJECT-TYPE
	SYNTAX                          Integer32
        MAX-ACCESS                      read-only
        STATUS                          current
	DESCRIPTION
			"Number identifying the shelf where the disk
			is located."
	::= { outOfDateDiskEntry 11 }

	outOfDateDiskBay                OBJECT-TYPE
	SYNTAX                          Integer32
        MAX-ACCESS                      read-only
        STATUS                          current
	DESCRIPTION
			"Number identifying the disk bay within
			the shelf where the disk is located."
	::= { outOfDateDiskEntry 12 }

        outOfDateDiskPool               OBJECT-TYPE
	SYNTAX                          DisplayString
        MAX-ACCESS                      read-only
        STATUS                          current
        DESCRIPTION
                        "A name that identifies the disk pool that this
                         entry belongs to."
        ::= { outOfDateDiskEntry 13 }

        outOfDateDiskSectorSize         OBJECT-TYPE
	SYNTAX                          Integer32
        MAX-ACCESS                      read-only
        STATUS                          current
        DESCRIPTION
                        "A number that specifies bytes per sector
                         for this entry.  Values are '512' or '520'."
        ::= { outOfDateDiskEntry 14 }

	outOfDateDiskSerialNumber       OBJECT-TYPE
	SYNTAX                          DisplayString
        MAX-ACCESS                      read-only
        STATUS                          current
	DESCRIPTION
		"Serial number of the referenced disk drive."
	::= { outOfDateDiskEntry 15 }

	outOfDateDiskVendor             OBJECT-TYPE
	SYNTAX                          DisplayString
        MAX-ACCESS                      read-only
        STATUS                          current
	DESCRIPTION
		"The vendor of the referenced disk drive."
	::= { outOfDateDiskEntry 16 }

	outOfDateDiskModel              OBJECT-TYPE
	SYNTAX                          DisplayString
        MAX-ACCESS                      read-only
        STATUS                          current
	DESCRIPTION
		"Model string of the referenced disk drive."
	::= { outOfDateDiskEntry 17 }

	outOfDateDiskFirmwareRevision   OBJECT-TYPE
	SYNTAX                          DisplayString
        MAX-ACCESS                      read-only
        STATUS                          current
	DESCRIPTION
		"Firmware revision number of the referenced disk drive."
	::= { outOfDateDiskEntry 18 }

	outOfDateDiskRPM                OBJECT-TYPE
	SYNTAX                          DisplayString
        MAX-ACCESS                      read-only
        STATUS                          current
	DESCRIPTION
		"RPM of the referenced disk drive."
	::= { outOfDateDiskEntry 19 }

	outOfDateDiskType               OBJECT-TYPE
	SYNTAX                          DisplayString
        MAX-ACCESS                      read-only
        STATUS                          current
	DESCRIPTION
		"Interface type of the referenced disk drive. e.g SCSI,
		 or ATA."
	::= { outOfDateDiskEntry 20 }

	outOfDateDisk64TotalBlocks        OBJECT-TYPE
	SYNTAX                            Counter64
        MAX-ACCESS                        read-only
        STATUS                            current
	DESCRIPTION
			"The number of Blocks physically available
			 on the referenced disk drive. This object
			 returns all of the 64 bit unsigned integer."
	::= { outOfDateDiskEntry 21 }

	outOfDateDiskCarrierID		OBJECT-TYPE
	SYNTAX				DisplayString
	MAX-ACCESS			read-only
	STATUS				current
	DESCRIPTION
		"Unique identifier of the disk carrier."
	::= { outOfDateDiskEntry 22 }

	outOfDateDiskDrawer             OBJECT-TYPE
	SYNTAX                          Integer32
        MAX-ACCESS                      read-only
        STATUS                          current
	DESCRIPTION
			"Used for shelves with drawers. Number
			identifying the physical drawer where
			the disk is located."
	::= { outOfDateDiskEntry 23 }

	outOfDateDiskDrawerSlot         OBJECT-TYPE
	SYNTAX                          Integer32
        MAX-ACCESS                      read-only
        STATUS                          current
	DESCRIPTION
			"Used for shelves with drawers. Identifies which
			slot in the drawer this disk is located."
	::= { outOfDateDiskEntry 24 }

	-- -- -- -- -- -- -- -- -- -- -- -- -- -- -- -- -- --
	-- -- -- -- -- -- -- -- -- -- -- -- -- -- -- -- -- --
	-- the CIFS group    --
	-- -- -- -- -- -- -- -- -- -- -- -- -- -- -- -- -- --
	-- -- -- -- -- -- -- -- -- -- -- -- -- -- -- -- -- --


	cifsOptions	OBJECT IDENTIFIER ::= { cifs 1 }

	cifsInfo	OBJECT IDENTIFIER ::= { cifs 2 }

	cifsStats	OBJECT IDENTIFIER ::= { cifs 3 }

	cifsMisc	OBJECT IDENTIFIER ::= { cifs 4 }

	-- -- -- -- -- -- -- -- -- -- -- -- -- -- -- -- -- --
	-- the cifsOptions group
	-- -- -- -- -- -- -- -- -- -- -- -- -- -- -- -- -- --

	cifsIsEnabled                   OBJECT-TYPE
	SYNTAX                          INTEGER {
                                             false(1),
                                             true(2)
                                        }
        MAX-ACCESS                      read-only
        STATUS                          current
	DESCRIPTION
			"Whether the CIFS protocol is active on the
			 filer."
	::= { cifsOptions 1 }

	cifsIsLoginEnabled              OBJECT-TYPE
	SYNTAX                          INTEGER {
                                             false(1),
                                             true(2)
                                        }
        MAX-ACCESS                      read-only
        STATUS                          current
	DESCRIPTION
			"Whether new CIFS connections to the filer
			 are currently allowed."
	::= { cifsOptions 2 }


	cifsHostName                    OBJECT-TYPE
	SYNTAX                          DisplayString
        MAX-ACCESS                      read-only
        STATUS                          current
	DESCRIPTION
			"The host name used by the CIFS protocol on this
			 filer."
	::= { cifsOptions 3 }


	cifsAltNames                    OBJECT-TYPE
	SYNTAX                          DisplayString
        MAX-ACCESS                      read-only
        STATUS                          current
	DESCRIPTION
			"Alternate names recognized by the filer."
	::= { cifsOptions 4 }


	cifsDomainJoined                OBJECT-TYPE
	SYNTAX                          INTEGER {
                                             false(1),
                                             true(2)
                                        }
        MAX-ACCESS                      read-only
        STATUS                          current
	DESCRIPTION
			"Has the filer joined an NT domain?
			 If this value is true, cifsDomainName
			 will contain the name of the domain.
			 Otherwise, the filer may have joined
			 a WorkGroup, and cifsWGName will contain
			 the name of the WorkGroup. "
        ::= { cifsOptions 5 }


 	cifsDomainName                  OBJECT-TYPE
	SYNTAX                          DisplayString
        MAX-ACCESS                      read-only
        STATUS                          current
	DESCRIPTION
			"The domain name used by the CIFS
			 protocol on this filer."
	::= { cifsOptions 6 }


	cifsWGName                      OBJECT-TYPE
	SYNTAX                          DisplayString
        MAX-ACCESS                      read-only
        STATUS                          current
	DESCRIPTION
			"The workgroup name (if any) used by
			 the CIFS protocol on this filer."
	::= { cifsOptions 7 }


	cifsDCName                      OBJECT-TYPE
	SYNTAX                          DisplayString
        MAX-ACCESS                      read-only
        STATUS                          current
	DESCRIPTION
			"The name of the Domain Controller used by
			 this filer to authenticate users and file
			 requests."
	::= { cifsOptions 8 }


	cifsIsWinsEnabled               OBJECT-TYPE
	SYNTAX                          INTEGER {
                                             false(1),
                                             true(2)
                                        }
        MAX-ACCESS                      read-only
        STATUS                          current
	DESCRIPTION
			"True if WINS name resolution is enabled
			 on the filer."
	::= { cifsOptions 9 }


	cifsWinsServers                 OBJECT-TYPE
	SYNTAX                          DisplayString
        MAX-ACCESS                      read-only
        STATUS                          current
	DESCRIPTION
			"The name(s) of the WINS servers registered
			 with the filer."
	::= { cifsOptions 10 }


	cifsSecurityModel               OBJECT-TYPE
	SYNTAX                          INTEGER {
                                             unix(1),
                                             pc(2)
                                        }
        MAX-ACCESS                      read-only
        STATUS                          current
	DESCRIPTION
			"Which type of authentication semantics
			 (Unix or PC) are in use for PC access to
			 Unix files on the filer. If Unix semantics
			 are in use, no ACL on a Unix file is ever
			 checked. If PC semantics are in use, the
			 share level ACL on the share containing the
			 file is used for authentication instead of
			 the group portion of the permissions on
			 the file."
	::= { cifsOptions 11 }


	cifsPCGenericUser               OBJECT-TYPE
	SYNTAX                          DisplayString
        MAX-ACCESS                      read-only
        STATUS                          current
	DESCRIPTION
			"The name of the generic PC user, if any.  This
			 username is used for CIFS access by Unix users
			 who have not authenticated through CIFS or NT."
	::= { cifsOptions 12 }


	cifsOplocksEnabled              OBJECT-TYPE
	SYNTAX                          INTEGER {
                                             notEnabled(1),
                                             enabled(2)
                                        }
        MAX-ACCESS                      read-only
        STATUS                          current
	DESCRIPTION
			"Whether oplocks are enabled on the filer."
	::= { cifsOptions 15 }


	cifsLevel2OplocksEnabled        OBJECT-TYPE
	SYNTAX                          INTEGER {
                                             notEnabled(1),
                                             enabled(2)
                                        }
        MAX-ACCESS                      read-only
        STATUS                          current
	DESCRIPTION
			"Whether level 2 oplocks are enabled on the filer."
	::= { cifsOptions 16 }


	cifsPreserveCase                OBJECT-TYPE
	SYNTAX                          INTEGER {
                                             noPreserveCase(1),
                                             preserveCase(2)
                                        }
        MAX-ACCESS                      read-only
        STATUS                          current
	DESCRIPTION
			"If this option is set to preserve-case
			 (the default), all filename references
			 will be case preserving.  Otherwise,
			 they are forced to lowercase."
	::= { cifsOptions 17 }


	cifsSymlinksEnabled             OBJECT-TYPE
	SYNTAX                          INTEGER {
                                             notEnabled(1),
                                             enabled(2)
                                        }
        MAX-ACCESS                      read-only
        STATUS                          current
	DESCRIPTION
			"If this option is enabled, CIFS accesses will
			 follow symbolic links using Unix semantics."
	::= { cifsOptions 19 }


	cifsSymlinkCycleProtEnabled     OBJECT-TYPE
	SYNTAX                          INTEGER {
                                             notEnabled(1),
                                             enabled(2)
                                        }
        MAX-ACCESS                      read-only
        STATUS                          current
	DESCRIPTION
			"If this option is enabled, CIFS accesses will
			 through symbolic links will check for cycles
			 in the link graph."
	::= { cifsOptions 20 }


	cifsIsLicensed                  OBJECT-TYPE
	SYNTAX                          INTEGER {
                                             false(1),
                                             true(2)
                                        }
        MAX-ACCESS                      read-only
        STATUS                          current
	DESCRIPTION
			"Whether the CIFS protocol is licensed on the
			 filer."
	::= { cifsOptions 21 }

	cifsPerClientStatsEnabled       OBJECT-TYPE
	SYNTAX                          INTEGER {
                                             false(1),
                                             true(2)
                                        }
        MAX-ACCESS                      read-only
        STATUS                          current
	DESCRIPTION
			"True when cifs.per_client_stats are
			 being collected."
	::= { cifsOptions 22 }

	-- -- -- -- -- -- -- -- -- -- -- -- -- -- -- -- -- --
	-- the cifsInfo group
	-- -- -- -- -- -- -- -- -- -- -- -- -- -- -- -- -- --

	cifsStatus                      OBJECT-TYPE
	SYNTAX                          Integer32
        MAX-ACCESS                      read-only
        STATUS                          current
	DESCRIPTION
			"Encoding of CIFS startup state on the filer."
              ::= { cifsInfo 1 }

	cifsNeedPW                      OBJECT-TYPE
	SYNTAX                          Integer32
        MAX-ACCESS                      read-only
        STATUS                          current
	DESCRIPTION
			"Does the administrative password need
			 to be set before start?"
	::= { cifsInfo 2 }

	cifsTimeToShutdown              OBJECT-TYPE
	SYNTAX                          Integer32
        MAX-ACCESS                      read-only
        STATUS                          current
	DESCRIPTION
			"Time remaining until CIFS shutdown"
	::= { cifsInfo 3 }


 	cifsMaxConnections              OBJECT-TYPE
	SYNTAX                          Integer32
        MAX-ACCESS                      read-only
        STATUS                          current
	DESCRIPTION
			"The maximum number of simultaneous CIFS
			 connections allowed on the filer."
	::= { cifsInfo 4 }

	cifsMaxTrees                    OBJECT-TYPE
	SYNTAX                          Integer32
        MAX-ACCESS                      read-only
        STATUS                          current
	DESCRIPTION
			"The maximum number of simultaneous CIFS
			 trees allowed on the filer."
	::= { cifsInfo 5 }

	cifsMaxShares                   OBJECT-TYPE
	SYNTAX                          Integer32
        MAX-ACCESS                      read-only
        STATUS                          current
	DESCRIPTION
			"The maximum number of simultaneous CIFS
			 shares allowed on the filer."
	::= { cifsInfo 6 }

	cifsMaxFiles                    OBJECT-TYPE
	SYNTAX                          Integer32
        MAX-ACCESS                      read-only
        STATUS                          current
	DESCRIPTION
			"The maximum number of concurrently open CIFS
			 files and directories allowed on the filer."
	::= { cifsInfo 7 }


	cifsMaxACLs                     OBJECT-TYPE
	SYNTAX                          Integer32
        MAX-ACCESS                      read-only
        STATUS                          current
	DESCRIPTION
			"This object is deprecated, and always has a
			 value of 0."
	::= { cifsInfo 8 }


	cifsConnectedUsers              OBJECT-TYPE
	SYNTAX                          Counter32
        MAX-ACCESS                      read-only
        STATUS                          current
	DESCRIPTION
			"The current number of CIFS users on the
			 filer."
	::= { cifsInfo 9 }

	cifsNTrees                      OBJECT-TYPE
	SYNTAX                          Counter32
        MAX-ACCESS                      read-only
        STATUS                          current
	DESCRIPTION
			"The current number of CIFS trees on the
			 filer."
	::= { cifsInfo 10 }

	cifsNShares                     OBJECT-TYPE
	SYNTAX                          Counter32
        MAX-ACCESS                      read-only
        STATUS                          current
	DESCRIPTION
			"The current number of CIFS shares on the
			 filer."
	::= { cifsInfo 11 }

	cifsNSessions                   OBJECT-TYPE
	SYNTAX                          Counter32
        MAX-ACCESS                      read-only
        STATUS                          current
	DESCRIPTION
			"The current number of active CIFS sessions
			 on the filer."
	::= { cifsInfo 12 }

	cifsNOpenFiles                  OBJECT-TYPE
	SYNTAX                          Counter32
        MAX-ACCESS                      read-only
        STATUS                          current
	DESCRIPTION
			"The number of open CIFS files and directories
			 on the filer."
	::= { cifsInfo 13 }

	cifsNOpenDirs                   OBJECT-TYPE
	SYNTAX                          Counter32
        MAX-ACCESS                      read-only
        STATUS                          current
	DESCRIPTION
			"The number of open CIFS directories on the
			 filer."
	::= { cifsInfo 14 }


	cifsNOplockBreakWaits           OBJECT-TYPE
	SYNTAX                          Counter32
        MAX-ACCESS                      read-only
        STATUS                          current
	DESCRIPTION
			"The number of open files waiting for oplock
			 break messages to be sent."
	::= { cifsInfo 16 }


	cifsNOplockAckWaits             OBJECT-TYPE
	SYNTAX                          Counter32
        MAX-ACCESS                      read-only
        STATUS                          current
	DESCRIPTION
			"The number of open files waiting for
			 acknowledgements to oplock break messages."
	::= { cifsInfo 17 }

	cifsSuspectOps                  OBJECT-TYPE
	SYNTAX                          Integer32
        MAX-ACCESS                      read-only
        STATUS                          current
	DESCRIPTION
			"A smoothed average of the number of events
			 per second of the type frequently seen
			 during virus attacks."
	::= { cifsInfo 18 }

	cifsNDomainControllers          OBJECT-TYPE
	SYNTAX                          Integer32
        MAX-ACCESS                      read-only
        STATUS                          current
	DESCRIPTION
			"The number of Domain Controllers found."
	::= { cifsInfo 19 }

	-- -- -- -- -- -- -- -- -- -- -- -- -- -- -- -- -- --
	-- the cifsStats group
	-- -- -- -- -- -- -- -- -- -- -- -- -- -- -- -- -- --

		-- this group contains cifs statistics since the last
		-- time the statistics were cleared

	cifsServ	 OBJECT IDENTIFIER ::= { cifsStats 1 }

	-- cifsPerClient OBJECT IDENTIFIER ::= { cifsStats 2 }

		-- no per-client stats are kept as of the 5.3 release


	-- -- -- -- -- -- -- -- -- -- -- -- -- -- -- -- -- --
	-- the cifsServ group
	-- -- -- -- -- -- -- -- -- -- -- -- -- -- -- -- -- --

		-- this group contains statistics for CIFS
		-- status, and calls processed since the last
		-- time the statistics were cleared

	cifsOps		OBJECT IDENTIFIER ::= { cifsServ 1 }

	cifsReqs	OBJECT IDENTIFIER ::= { cifsServ 2 }

	cifsPercent	OBJECT IDENTIFIER ::= { cifsServ 3 }

	cifsObsReqs	OBJECT IDENTIFIER ::= { cifsServ 4 }

	cifsObsPercent	OBJECT IDENTIFIER ::= { cifsServ 5 }

	-- -- -- -- -- -- -- -- -- -- -- -- -- -- -- -- -- --
	-- the cifsOps group
	-- -- -- -- -- -- -- -- -- -- -- -- -- -- -- -- -- --

	cifsTotalOps                    OBJECT-TYPE
	SYNTAX                          Counter32
        MAX-ACCESS                      read-only
        STATUS                          current
	DESCRIPTION
			"The number of CIFS operations done by the filer,
			 since the last time the statistics were cleared."
	::= { cifsOps 1 }

	cifsTotalCalls                  OBJECT-TYPE
	SYNTAX                          Counter32
        MAX-ACCESS                      read-only
        STATUS                          current
	DESCRIPTION
			"The total number of CIFS calls received, since
			 the last time the statistics were cleared.  This
			 is the number of cifsTotalOps plus the number of
			 miscellaneous operations that are not logged
			 which were received in that time period."
	::= { cifsOps 2 }

	cifsBadCalls                    OBJECT-TYPE
	SYNTAX                          Counter32
        MAX-ACCESS                      read-only
        STATUS                          current
	DESCRIPTION
			"The total number of received CIFS calls rejected,
			 since the last time the statistics were cleared."
	::= { cifsOps 3 }


	cifsGetAttrs                    OBJECT-TYPE
	SYNTAX                          Counter32
        MAX-ACCESS                      read-only
        STATUS                          current
	DESCRIPTION
			"The total number of CIFS operations to get
			 the attributes on a file or directory, since
			 the last time the statistics were reset."
        ::= { cifsOps 4 }


	cifsReads                       OBJECT-TYPE
	SYNTAX                          Counter32
        MAX-ACCESS                      read-only
        STATUS                          current
	DESCRIPTION
			"The total number of CIFS Read operations on
			 a file or directory, since the last time the
			 statistics were reset."
	::= { cifsOps 5 }


	cifsWrites                      OBJECT-TYPE
	SYNTAX                          Counter32
        MAX-ACCESS                      read-only
        STATUS                          current
	DESCRIPTION
			"The total number of CIFS write operations on
			 a file or directory, since the last time the
			 statistics were reset."
	::= { cifsOps 6 }


	cifsLocks                       OBJECT-TYPE
	SYNTAX                          Counter32
        MAX-ACCESS                      read-only
        STATUS                          current
	DESCRIPTION
			"The number of CIFS file locking requests
			 since the last time the statistics were reset."
	::= { cifsOps 7 }


	cifsOpens                       OBJECT-TYPE
	SYNTAX                          Counter32
        MAX-ACCESS                      read-only
        STATUS                          current
	DESCRIPTION
			"The number of calls, via CIFS, to open
			 a file or directory, since the last time
			 the statistics were reset."
	::= { cifsOps 8 }


 	cifsDirOps                      OBJECT-TYPE
	SYNTAX                          Counter32
        MAX-ACCESS                      read-only
        STATUS                          current
 	DESCRIPTION
			"The number of CIFS directory operations,
			 since the last time the statistics were reset."
        ::= { cifsOps 9 }


 	cifsOthers                      OBJECT-TYPE
	SYNTAX                          Counter32
        MAX-ACCESS                      read-only
        STATUS                          current
 	DESCRIPTION
			"The number of CIFS operations, since the
			 last time the statistics were reset, that
			 don't fall into the categories for GetAttr,
			 SetAttr, Read, Write, Lock, DirOp and Open."
        ::= { cifsOps 10 }

	cifsSetAttrs			OBJECT-TYPE
	SYNTAX				Counter32
	MAX-ACCESS			read-only
	STATUS				current
	DESCRIPTION
			"The total number of CIFS operations to set
			 the attributes on a file or directory, since
			 the last time the statistics were reset."
        ::= { cifsOps 11 }

 	-- -- -- -- -- -- -- -- -- -- -- -- -- -- -- -- -- --
	-- the cifsReqs group
	-- -- -- -- -- -- -- -- -- -- -- -- -- -- -- -- -- --

		-- this group contains statistics for the number of
		-- calls received for each CIFS SMB request
		-- since the last time the statistics were cleared

	smbNegProts                     OBJECT-TYPE
	SYNTAX                          Counter32
        MAX-ACCESS                      read-only
        STATUS                          current
	DESCRIPTION
			"The number of SMB NEGOTIATE requests,
			 since the last time the statistics were cleared."
	::= { cifsReqs 1 }

	smbSessionSetupAndXs            OBJECT-TYPE
	SYNTAX                          Counter32
        MAX-ACCESS                      read-only
        STATUS                          current
	DESCRIPTION
			"The number of SMB SESSION_SETUP_ANDX requests,
			 since the last time the statistics were cleared."
	::= { cifsReqs 2 }

	smbLogoffAndXs                  OBJECT-TYPE
	SYNTAX                          Counter32
        MAX-ACCESS                      read-only
        STATUS                          current
	DESCRIPTION
			"The number of SMB LOGOFF_ANDX requests,
			 since the last time the statistics were cleared."
	::= { cifsReqs 3 }

	smbTreeConnectAndXs             OBJECT-TYPE
	SYNTAX                          Counter32
        MAX-ACCESS                      read-only
        STATUS                          current
	DESCRIPTION
			"The number of SMB TREE_CONNECT_ANDX requests,
			 since the last time the statistics were cleared."
	::= { cifsReqs 4 }

	smbTreeDisconnects              OBJECT-TYPE
	SYNTAX                          Counter32
        MAX-ACCESS                      read-only
        STATUS                          current
	DESCRIPTION
			"The number of SMB TREE_DISCONNECT requests,
			 since the last time the statistics were cleared."
	::= { cifsReqs 5 }

	smbTrans2QueryFSInfos           OBJECT-TYPE
	SYNTAX                          Counter32
        MAX-ACCESS                      read-only
        STATUS                          current
	DESCRIPTION
			"The number of SMB TRANS2_QUERY_FS_INFORMATION
			 requests, since the last time the statistics
			 were cleared."
	::= { cifsReqs 6 }

	smbEchos                        OBJECT-TYPE
	SYNTAX                          Counter32
        MAX-ACCESS                      read-only
        STATUS                          current
	DESCRIPTION
			"The number of SMB ECHO requests,
			 since the last time the statistics were cleared."
	::= { cifsReqs 7 }

	smbNTCancels                    OBJECT-TYPE
	SYNTAX                          Counter32
        MAX-ACCESS                      read-only
        STATUS                          current
	DESCRIPTION
			"The number of SMB NT_CANCEL requests, since the
			 last time the statistics were cleared."
	::= { cifsReqs 8 }

	smbNTCreateAndXs                OBJECT-TYPE
	SYNTAX                          Counter32
        MAX-ACCESS                      read-only
        STATUS                          current
	DESCRIPTION
			"The number of SMB NT_CREATE_ANDX requests,
			 since the last time the statistics were cleared."
	::= { cifsReqs 9 }

	smbNTTransactCreates            OBJECT-TYPE
	SYNTAX                          Counter32
        MAX-ACCESS                      read-only
        STATUS                          current
	DESCRIPTION
			"The number of SMB NT_TRANSACT_CREATE requests,
			 since the last time the statistics were cleared."
	::= { cifsReqs 10 }

	smbCreateTemporaries            OBJECT-TYPE
	SYNTAX                          Counter32
        MAX-ACCESS                      read-only
        STATUS                          current
	DESCRIPTION
			"The SMB CREATE_TEMPORARY operation is not presently
			 supported, so this value should always be zero."
	::= { cifsReqs 11 }

	smbReadAndXs                    OBJECT-TYPE
	SYNTAX                          Counter32
        MAX-ACCESS                      read-only
        STATUS                          current
	DESCRIPTION
			"The number of SMB READ_ANDX requests,
			 since the last time the statistics were cleared."
	::= { cifsReqs 12 }

	smbWriteAndXs                   OBJECT-TYPE
	SYNTAX                          Counter32
        MAX-ACCESS                      read-only
        STATUS                          current
	DESCRIPTION
			"The number of SMB WRITE_ANDX requests,
			 since the last time the statistics were cleared."
	::= { cifsReqs 13 }

	smbLockingAndXs                 OBJECT-TYPE
	SYNTAX                          Counter32
        MAX-ACCESS                      read-only
        STATUS                          current
	DESCRIPTION
			"The number of SMB LOCKING_ANDX requests,
			 since the last time the statistics were cleared."
	::= { cifsReqs 14 }

	smbSeeks                        OBJECT-TYPE
	SYNTAX                          Counter32
        MAX-ACCESS                      read-only
        STATUS                          current
	DESCRIPTION
			"The number of SMB SEEK requests,
			 since the last time the statistics were cleared."
	::= { cifsReqs 15 }

	smbFlushes                      OBJECT-TYPE
	SYNTAX                          Counter32
        MAX-ACCESS                      read-only
        STATUS                          current
	DESCRIPTION
			"The number of SMB FLUSH requests,
			 since the last time the statistics were cleared."
	::= { cifsReqs 16 }

	smbCloses                       OBJECT-TYPE
	SYNTAX                          Counter32
        MAX-ACCESS                      read-only
        STATUS                          current
	DESCRIPTION
			"The number of SMB CLOSE requests,
			 since the last time the statistics were cleared."
	::= { cifsReqs 17 }

	smbDeletes                      OBJECT-TYPE
	SYNTAX                          Counter32
        MAX-ACCESS                      read-only
        STATUS                          current
	DESCRIPTION
			"The number of SMB DELETE requests,
			 since the last time the statistics were cleared."
	::= { cifsReqs 18 }

	smbRenames                      OBJECT-TYPE
	SYNTAX                          Counter32
        MAX-ACCESS                      read-only
        STATUS                          current
	DESCRIPTION
			"The number of SMB RENAME requests,
			 since the last time the statistics were cleared."
	::= { cifsReqs 19 }

	smbMoves                        OBJECT-TYPE
	SYNTAX                          Counter32
        MAX-ACCESS                      read-only
        STATUS                          current
	DESCRIPTION
			"The SMB MOVE request is not presently supported,
			 so this value should always be zero."
	::= { cifsReqs 20 }

	smbCopies                       OBJECT-TYPE
	SYNTAX                          Counter32
        MAX-ACCESS                      read-only
        STATUS                          current
	DESCRIPTION
			"The SMB COPY request is not presently supported,
			 so this value should always be zero."
	::= { cifsReqs 21 }

	smbTrans2QueryPathInfos         OBJECT-TYPE
	SYNTAX                          Counter32
        MAX-ACCESS                      read-only
        STATUS                          current
	DESCRIPTION
			"The number of SMB TRANS2_QUERY_PATH_INFORMATION
			 requests, since the last time the statistics
			 were cleared."
	::= { cifsReqs 22 }

	smbTrans2QueryFileInfos         OBJECT-TYPE
	SYNTAX                          Counter32
        MAX-ACCESS                      read-only
        STATUS                          current
	DESCRIPTION
			"The number of SMB TRANS2_QUERY_FILE_INFORMATION
			 requests, since the last time the statistics
			 were cleared."
	::= { cifsReqs 23 }

	smbTrans2SetPathInfos           OBJECT-TYPE
	SYNTAX                          Counter32
        MAX-ACCESS                      read-only
        STATUS                          current
	DESCRIPTION
			"The number of SMB TRANS2_SET_PATH_INFORMATION
			 requests, since the last time the statistics
			 were cleared."
	::= { cifsReqs 24 }

	smbTrans2SetFileInfos           OBJECT-TYPE
	SYNTAX                          Counter32
        MAX-ACCESS                      read-only
        STATUS                          current
	DESCRIPTION
			"The number of SMB TRANS2_SET_FILE_INFORMATION
			 requests, since the last time the statistics
			 were cleared."
	::= { cifsReqs 25 }

	smbDeleteDirs                   OBJECT-TYPE
	SYNTAX                          Counter32
        MAX-ACCESS                      read-only
        STATUS                          current
	DESCRIPTION
			"The number of SMB DELETE_DIRECTORY requests,
			 since the last time the statistics were cleared."
	::= { cifsReqs 26 }

	smbCheckDirs                    OBJECT-TYPE
	SYNTAX                          Counter32
        MAX-ACCESS                      read-only
        STATUS                          current
	DESCRIPTION
			"The SMB COPY request is not presently supported,
			 so this value should always be zero."
	::= { cifsReqs 27 }

	smbTrans2FindFirst2s            OBJECT-TYPE
	SYNTAX                          Counter32
        MAX-ACCESS                      read-only
        STATUS                          current
	DESCRIPTION
			"The number of SMB TRANS2_FIND_FIRST2 requests,
			 since the last time the statistics were cleared."
	::= { cifsReqs 28 }

	smbTrans2FindNext2s             OBJECT-TYPE
	SYNTAX                          Counter32
        MAX-ACCESS                      read-only
        STATUS                          current
	DESCRIPTION
			"The number of SMB TRANS2_FIND_NEXT2 requests,
			 since the last time the statistics were cleared."
	::= { cifsReqs 29 }

	smbFindClose2s                  OBJECT-TYPE
	SYNTAX                          Counter32
        MAX-ACCESS                      read-only
        STATUS                          current
	DESCRIPTION
			"The number of SMB FIND_CLOSE2 requests,
			 since the last time the statistics were cleared."
	::= { cifsReqs 30 }

	smbNTTransactNotifyChgs         OBJECT-TYPE
	SYNTAX                          Counter32
        MAX-ACCESS                      read-only
        STATUS                          current
	DESCRIPTION
			"The number of SMB NT_TRANSACT_NOTIFY_CHANGE
			 requests, since the last time the statistics
			 were cleared."
	::= { cifsReqs 31 }

	smbTrans2GetDFSReferrals        OBJECT-TYPE
	SYNTAX                          Counter32
        MAX-ACCESS                      read-only
        STATUS                          current
	DESCRIPTION
			"The SMB TRANS2_GET_DFS_REFERRAL request is
			 not presently supported, so this value should
			 always be zero."
	::= { cifsReqs 32 }

	smbTrans2ReportDFSIncs          OBJECT-TYPE
	SYNTAX                          Counter32
        MAX-ACCESS                      read-only
        STATUS                          current
	DESCRIPTION
			"The SMB TRANS2_REPORT_DFS_INCONSISTENCY request is
			 not presently supported, so this value should
			 always be zero."
	::= { cifsReqs 33 }

	smbOpenPrintFiles               OBJECT-TYPE
	SYNTAX                          Counter32
        MAX-ACCESS                      read-only
        STATUS                          current
	DESCRIPTION
			"The SMB OPEN_PRINT_FILE request is not supported,
			 so this value should always be zero."
	::= { cifsReqs 34 }

	smbGetPrintQueues               OBJECT-TYPE
	SYNTAX                          Counter32
        MAX-ACCESS                      read-only
        STATUS                          current
	DESCRIPTION
			"The SMB GET_PRINT_QUEUE request is not supported,
			 so this value should always be zero."
	::= { cifsReqs 35 }

	smbNTTransactIoctls             OBJECT-TYPE
	SYNTAX                          Counter32
        MAX-ACCESS                      read-only
        STATUS                          current
	DESCRIPTION
			"The number of SMB NT_TRANSACT_IOCTL requests,
			 since the last time the statistics were cleared."
	::= { cifsReqs 36 }

	smbNTTransactQuerySecDescs      OBJECT-TYPE
	SYNTAX                          Counter32
        MAX-ACCESS                      read-only
        STATUS                          current
	DESCRIPTION
			"The number of SMB NT_TRANSACT_QUERY_SECURITY_DESC
			 requests, since the last time the statistics
			 were cleared."
	::= { cifsReqs 37 }

	smbNTTransactSetSecDescs        OBJECT-TYPE
	SYNTAX                          Counter32
        MAX-ACCESS                      read-only
        STATUS                          current
	DESCRIPTION
			"The number of SMB NT_TRANSACT_SET_SECURITY_DESC
			 requests, since the last time the statistics
			 were cleared."
	::= { cifsReqs 38 }


	smbTrans2CreateDirs             OBJECT-TYPE
	SYNTAX                          Counter32
        MAX-ACCESS                      read-only
        STATUS                          current
	DESCRIPTION
			"The number of SMB TRANS2_CREATE_DIRECTORY
			 requests, since the last time the statistics
			 were cleared."
	::= { cifsReqs 39 }


	smbNTCancelCNs                  OBJECT-TYPE
	SYNTAX                          Counter32
        MAX-ACCESS                      read-only
        STATUS                          current
	DESCRIPTION
			"The number of SMB NT_CANCEL requests against
			 change notifications since the last time
			 the statistics were cleared."
	::= { cifsReqs 40 }

	smbNTCancelOthers               OBJECT-TYPE
	SYNTAX                          Counter32
        MAX-ACCESS                      read-only
        STATUS                          current
	DESCRIPTION
			"The number of SMB NT_CANCEL requests against
			 operations other than change notifications,
			 since the last time the statistics
			 were cleared."
	::= { cifsReqs 41 }

	smb2Echos			OBJECT-TYPE
	SYNTAX				Counter32
	MAX-ACCESS			read-only
	STATUS				current
	DESCRIPTION
			"The number of SMB2 ECHO requests,
			since the last time the statistics were cleared."
	::= { cifsReqs 42 }

	smb2NegProts			OBJECT-TYPE
	SYNTAX				Counter32
	MAX-ACCESS			read-only
	STATUS				current
	DESCRIPTION
			"The number of SMB2 NEGOTIATE requests,
			 since the last time the statistics were cleared."
	::= { cifsReqs 43 }

	smb2SessionSetups		OBJECT-TYPE
	SYNTAX				Counter32
	MAX-ACCESS			read-only
	STATUS				current
	DESCRIPTION
			"The number of SMB2 SESSION_SETUP requests,
			 since the last time the statistics were cleared."
	::= { cifsReqs 44 }

	smb2Logoffs			OBJECT-TYPE
	SYNTAX				Counter32
	MAX-ACCESS			read-only
	STATUS				current
	DESCRIPTION
			"The number of SMB2 LOGOFF requests,
			 since the last time the statistics were cleared."
	::= { cifsReqs 45 }

	smb2TreeConnects		OBJECT-TYPE
	SYNTAX				Counter32
	MAX-ACCESS			read-only
	STATUS				current
	DESCRIPTION
			"The number of SMB2 TREE_CONNECT requests,
			 since the last time the statistics were cleared."
	::= { cifsReqs 46 }

	smb2TreeDisconnects		OBJECT-TYPE
	SYNTAX				Counter32
	MAX-ACCESS			read-only
	STATUS				current
	DESCRIPTION
			"The number of SMB2 TREE_DISCONNECT requests,
			 since the last time the statistics were cleared."
	::= { cifsReqs 47 }


	smb2Cancels			OBJECT-TYPE
	SYNTAX				Counter32
	MAX-ACCESS			read-only
	STATUS				current
	DESCRIPTION
			"The number of SMB2 CANCEL requests,
			 since the last time the statistics were cleared."
	::= { cifsReqs 48 }

	smb2Creates			OBJECT-TYPE
	SYNTAX				Counter32
	MAX-ACCESS			read-only
	STATUS				current
	DESCRIPTION
			"The number of SMB2 CREATE requests,
			 since the last time the statistics were cleared."
	::= { cifsReqs 49 }

	smb2IpcCreates			OBJECT-TYPE
	SYNTAX				Counter32
	MAX-ACCESS			read-only
	STATUS				current
	DESCRIPTION
			"The number of SMB2 IPC CREATE requests,
			 since the last time the statistics were cleared."
	::= { cifsReqs 50 }

	smb2Reads			OBJECT-TYPE
	SYNTAX				Counter32
	MAX-ACCESS			read-only
	STATUS				current
	DESCRIPTION
			"The number of SMB2 READ requests,
			 since the last time the statistics were cleared."
	::= { cifsReqs 51 }

	smb2Writes			OBJECT-TYPE
	SYNTAX				Counter32
	MAX-ACCESS			read-only
	STATUS				current
	DESCRIPTION
			"The number of SMB2 WRITE requests,
			 since the last time the statistics were cleared."
	::= { cifsReqs 52 }

	smb2IpcReads			OBJECT-TYPE
	SYNTAX				Counter32
	MAX-ACCESS			read-only
	STATUS				current
	DESCRIPTION
			"The number of SMB2 IPC READ requests,
			 since the last time the statistics were cleared."
	::= { cifsReqs 53 }

	smb2IpcWrites			OBJECT-TYPE
	SYNTAX				Counter32
	MAX-ACCESS			read-only
	STATUS				current
	DESCRIPTION
			"The number of SMB2 IPC WRITE requests,
			 since the last time the statistics were cleared."
	::= { cifsReqs 54 }

	smb2Locks			OBJECT-TYPE
	SYNTAX				Counter32
	MAX-ACCESS			read-only
	STATUS				current
	DESCRIPTION
			"The number of SMB2 LOCK requests,
			 since the last time the statistics were cleared."
	::= { cifsReqs 55 }

	smb2UnLocks			OBJECT-TYPE
	SYNTAX				Counter32
	MAX-ACCESS			read-only
	STATUS				current
	DESCRIPTION
			"The number of SMB2 UNLOCK requests,
			 since the last time the statistics were cleared."
	::= { cifsReqs 56 }

	smb2OplkBrkAck			OBJECT-TYPE
	SYNTAX				Counter32
	MAX-ACCESS			read-only
	STATUS				current
	DESCRIPTION
			"The number of SMB2 Oplock Break Acknowledgements,
			 since the last time the statistics were cleared."

	::= { cifsReqs 57 }

	smb2Flushs			OBJECT-TYPE
	SYNTAX				Counter32
	MAX-ACCESS			read-only
	STATUS				current
	DESCRIPTION
			"The number of SMB2 FLUSH requests,
			 since the last time the statistics were cleared."
	::= { cifsReqs 58 }

	smb2Closes			OBJECT-TYPE
	SYNTAX				Counter32
	MAX-ACCESS			read-only
	STATUS				current
	DESCRIPTION
			"The number of SMB2 CLOSE requests,
			 since the last time the statistics were cleared."
	::= { cifsReqs 59 }

	smb2QueryFileBasicInfos		OBJECT-TYPE
	SYNTAX				Counter32
	MAX-ACCESS			read-only
	STATUS				current
	DESCRIPTION
			"The number of SMB2 QUERY_FILE_BASIC_INFO
			 requests, since the last time the statistics
			 were cleared."
	::= { cifsReqs 60 }


	smb2QueryFileStandardInfos	OBJECT-TYPE
	SYNTAX				Counter32
	MAX-ACCESS			read-only
	STATUS				current
	DESCRIPTION
			"The number of SMB2 QUERY_FILE_STANDARD_INFO
			 requests, since the last time the statistics
			 were cleared."
	::= { cifsReqs 61 }

	smb2QueryFileInternalInfos	OBJECT-TYPE
	SYNTAX				Counter32
	MAX-ACCESS			read-only
	STATUS				current
	DESCRIPTION
			"The number of SMB2 QUERY_FILE_INT_INFO
			 requests, since the last time the statistics
			 were cleared."
	::= { cifsReqs 62 }

	smb2QueryFileEAInfos		OBJECT-TYPE
	SYNTAX				Counter32
	MAX-ACCESS			read-only
	STATUS				current
	DESCRIPTION
			"The number of SMB2 QUERY_FILE_EA_INFO
			 requests, since the last time the statistics
			 were cleared."
	::= { cifsReqs 63 }

	smb2QueryFileFullEAInfos	OBJECT-TYPE
	SYNTAX				Counter32
	MAX-ACCESS			read-only
	STATUS				current
	DESCRIPTION
			"The number of SMB2 QUERY_FILE_FULL_EA_INFO
			 requests, since the last time the statistics
			 were cleared."
	::= { cifsReqs 64 }

	smb2QueryFileModeInfos		OBJECT-TYPE
	SYNTAX				Counter32
	MAX-ACCESS			read-only
	STATUS				current
	DESCRIPTION
			"The number of SMB2 QUERY_FILE_MODE_INFO
			 requests, since the last time the statistics
			 were cleared."
	::= { cifsReqs 65 }

	smb2QueryFileAltNames		OBJECT-TYPE
	SYNTAX				Counter32
	MAX-ACCESS			read-only
	STATUS				current
	DESCRIPTION
			"The number of SMB2 QUERY_FILE_ALT_NAME_INFO_
			 requests, since the last time the statistics
			 were cleared."
	::= { cifsReqs 66 }

	smb2QueryFileStreamInfos	OBJECT-TYPE
	SYNTAX				Counter32
	MAX-ACCESS			read-only
	STATUS				current
	DESCRIPTION
			"The number of SMB2 QUERY_FILE_STREAM_INFO_
			 requests, since the last time the statistics
			 were cleared."
	::= { cifsReqs 67 }

	smb2QueryFileNetOpenInfos	OBJECT-TYPE
	SYNTAX				Counter32
	MAX-ACCESS			read-only
	STATUS				current
	DESCRIPTION
			"The number of SMB2 QUERY_FILE_NET_OPEN_INFO
			 requests, since the last time the statistics
			 were cleared."
	::= { cifsReqs 68 }

	smb2QueryFileAttrTagInfos	OBJECT-TYPE
	SYNTAX				Counter32
	MAX-ACCESS			read-only
	STATUS				current
	DESCRIPTION
			"The number of SMB2 QUERY_FILE_ATTR_TAG_INFO
			 requests, since the last time the statistics
			 were cleared."
	::= { cifsReqs 69 }

	smb2QueryFileUnsupporteds	OBJECT-TYPE
	SYNTAX				Counter32
	MAX-ACCESS			read-only
	STATUS				current
	DESCRIPTION
			"The number of SMB2 Unsupported QUERY_FILE_INFO
			 requests, since the last time the statistics
			 were cleared."
	::= { cifsReqs 70 }

	smb2QueryFileInvalids		OBJECT-TYPE
	SYNTAX				Counter32
	MAX-ACCESS			read-only
	STATUS				current
	DESCRIPTION
			"The number of SMB2 invalid QUERY_FILE_INFO
			 requests, since the last time the statistics
			 were cleared."
	::= { cifsReqs 71 }

	smb2QueryFsVolInfos		OBJECT-TYPE
	SYNTAX				Counter32
	MAX-ACCESS			read-only
	STATUS				current
	DESCRIPTION
			"The number of SMB2 QUERY_FS_VOLUME_INFO
			 requests, since the last time the statistics
			 were cleared."
	::= { cifsReqs 72 }

	smb2QueryFsSizeInfos		OBJECT-TYPE
	SYNTAX				Counter32
	MAX-ACCESS			read-only
	STATUS				current
	DESCRIPTION
			"The number of SMB2 QUERY_FS_SIZE_INFO
			 requests, since the last time the statistics
			 were cleared."
	::= { cifsReqs 73 }

	smb2QueryFsDeviceInfos		OBJECT-TYPE
	SYNTAX				Counter32
	MAX-ACCESS			read-only
	STATUS				current
	DESCRIPTION
			"The number of SMB2 QUERY_FS_DEVICE_INFO
			 requests, since the last time the statistics
			 were cleared."
	::= { cifsReqs 74 }

	smb2QueryFsAttrInfos		OBJECT-TYPE
	SYNTAX				Counter32
	MAX-ACCESS			read-only
	STATUS				current
	DESCRIPTION
			"The number of SMB2 QUERY_FS_ATTR_INFO
			 requests, since the last time the statistics
			 were cleared."
	::= { cifsReqs 75 }

	smb2QueryFsFullSizeInfos	OBJECT-TYPE
	SYNTAX				Counter32
	MAX-ACCESS			read-only
	STATUS				current
	DESCRIPTION
			"The number of SMB2 QUERY_FS_FULL_SIZE_INFO
			 requests, since the last time the statistics
			 were cleared."
	::= { cifsReqs 76 }

	smb2QueryFsObjectIdInfos	OBJECT-TYPE
	SYNTAX				Counter32
	MAX-ACCESS			read-only
	STATUS				current
	DESCRIPTION
			"The number of SMB2 QUERY_FS_OBJECT_ID_INFO
			 requests, since the last time the statistics
			 were cleared."
	::= { cifsReqs 77 }

	smb2QueryFsInvalids		OBJECT-TYPE
	SYNTAX				Counter32
	MAX-ACCESS			read-only
	STATUS				current
	DESCRIPTION
			"The number of SMB2 invalid QUERY_FS_INFO
			 requests, since the last time the statistics
			 were cleared."
	::= { cifsReqs 78 }

	smb2SetBasicInfos		OBJECT-TYPE
	SYNTAX				Counter32
	MAX-ACCESS			read-only
	STATUS				current
	DESCRIPTION
			"The number of SMB2 SET_BASIC_INFO
			 received, since the last time the statistics
			 were cleared."
	::= { cifsReqs 79 }

	smb2SetRenameInfos		OBJECT-TYPE
	SYNTAX				Counter32
	MAX-ACCESS			read-only
	STATUS				current
	DESCRIPTION
			"The number of SMB2 SET_FILE_RENAME_INFO
			 received, since the last time the statistics
			 were cleared."
	::= { cifsReqs 80 }

	smb2SetFileLinkInfos		OBJECT-TYPE
	SYNTAX				Counter32
	MAX-ACCESS			read-only
	STATUS				current
	DESCRIPTION
			"The number of SMB2 SET_FILE_LINK_INFO
			 received, since the last time the statistics
			 were cleared."
	::= { cifsReqs 81 }

	smb2SetFileDispInfos		OBJECT-TYPE
	SYNTAX				Counter32
	MAX-ACCESS			read-only
	STATUS				current
	DESCRIPTION
			"The number of SMB2 SET_FILE_DISP_INFO
			 received, since the last time the statistics
			 were cleared."
	::= { cifsReqs 82 }

	smb2SetFullEaInfos		OBJECT-TYPE
	SYNTAX				Counter32
	MAX-ACCESS			read-only
	STATUS				current
	DESCRIPTION
			"The number of SMB2 SET_FULL_EA_INFO
			 received, since the last time the statistics
			 were cleared."
	::= { cifsReqs 83 }

	smb2SetModeInfos		OBJECT-TYPE
	SYNTAX				Counter32
	MAX-ACCESS			read-only
	STATUS				current
	DESCRIPTION
			"The number of SMB2 SET_MODE_INFO
			 received, since the last time the statistics
			 were cleared."
	::= { cifsReqs 84 }

	smb2SetAllocInfos		OBJECT-TYPE
	SYNTAX				Counter32
	MAX-ACCESS			read-only
	STATUS				current
	DESCRIPTION
			"The number of SMB2 SET_ALLOC_INFO
			 received, since the last time the statistics
			 were cleared."
	::= { cifsReqs 85 }

	smb2SetEofInfos			OBJECT-TYPE
	SYNTAX				Counter32
	MAX-ACCESS			read-only
	STATUS				current
	DESCRIPTION
			"The number of SMB2 SET_EOF_INFO
			 received, since the last time the statistics
			 were cleared."
	::= { cifsReqs 86 }

	smb2SetInfoUnsupporteds		OBJECT-TYPE
	SYNTAX				Counter32
	MAX-ACCESS			read-only
	STATUS				current
	DESCRIPTION
			"The number of SMB2 Unsupported SET_INFO
			 received, since the last time the statistics
			 were cleared."
	::= { cifsReqs 87 }

	smb2SetInfoInvalids		OBJECT-TYPE
	SYNTAX				Counter32
	MAX-ACCESS			read-only
	STATUS				current
	DESCRIPTION
			"The number of invalid SMB2 SET_INFO
			 received, since the last time the statistics
			 were cleared."
	::= { cifsReqs 88 }

	smb2FsctlPipeTransceives	OBJECT-TYPE
	SYNTAX				Counter32
	MAX-ACCESS			read-only
	STATUS				current
	DESCRIPTION
			"The number of SMB2 FSCTL_PIPE_TRANSCEIVE
			 received, since the last time the statistics
			 were cleared."
	::= { cifsReqs 89 }

	smb2FsctlPipePeeks		OBJECT-TYPE
	SYNTAX				Counter32
	MAX-ACCESS			read-only
	STATUS				current
	DESCRIPTION
			"The number of SMB2 FSCTL_PIPE_PEEK
			 received, since the last time the statistics
			 were cleared."
	::= { cifsReqs 90 }

	smb2FsctlEnumSnapshotss		OBJECT-TYPE
	SYNTAX				Counter32
	MAX-ACCESS			read-only
	STATUS				current
	DESCRIPTION
			"The number of SMB2 FSCTL_ENUMERATE_SNAPSHOTS
			 received, since the last time the statistics
			 were cleared."
	::= { cifsReqs 91 }

	smb2FsctlDfsReferralss		OBJECT-TYPE
	SYNTAX				Counter32
	MAX-ACCESS			read-only
	STATUS				current
	DESCRIPTION
			"The number of SMB2 FSCTL_DFS_REFERRALS
			 received, since the last time the statistics
			 were cleared."
	::= { cifsReqs 92 }

	smb2FsctlSetSparses		OBJECT-TYPE
	SYNTAX				Counter32
	MAX-ACCESS			read-only
	STATUS				current
	DESCRIPTION
			"The number of SMB2 FSCTL_SET_SPARSE
			 received, since the last time the statistics
			 were cleared."
	::= { cifsReqs 93 }

	smb2FsctlSecureShares		OBJECT-TYPE
	SYNTAX				Counter32
	MAX-ACCESS			read-only
	STATUS				current
	DESCRIPTION
			"The number of SMB2 FSCTL_SECURE_SHARE
			 received, since the last time the statistics
			 were cleared."
	::= { cifsReqs 94 }

	smb2FsctlFileUnsupporteds	OBJECT-TYPE
	SYNTAX				Counter32
	MAX-ACCESS			read-only
	STATUS				current
	DESCRIPTION
			"The number of Unsupported SMB2 File FSCTL
			 received, since the last time the statistics
			 were cleared."
	::= { cifsReqs 95 }

	smb2FsctlIpcUnsupporteds	OBJECT-TYPE
	SYNTAX				Counter32
	MAX-ACCESS			read-only
	STATUS				current
	DESCRIPTION
			"The number of Unsupported SMB2 IPC FSCTL
			 received, since the last time the statistics
			 were cleared."
	::= { cifsReqs 96 }

	smb2QueryDirs			OBJECT-TYPE
	SYNTAX				Counter32
	MAX-ACCESS			read-only
	STATUS				current
	DESCRIPTION
			"The number of SMB2 QUERY_DIR
			 received, since the last time the statistics
			 were cleared."
	::= { cifsReqs 97 }

	smb2ChgNfys			OBJECT-TYPE
	SYNTAX				Counter32
	MAX-ACCESS			read-only
	STATUS				current
	DESCRIPTION
			"The number of SMB2 CHANGE_NOTIFY
			 received, since the last time the statistics
			 were cleared."
	::= { cifsReqs 98 }

	smb2QuerySecurityInfos		OBJECT-TYPE
	SYNTAX				Counter32
	MAX-ACCESS			read-only
	STATUS				current
	DESCRIPTION
			"The number of SMB2 QUERY_INFO SECURITY requests
			 received, since the last time the statistics
			 were cleared."
	::= { cifsReqs 99 }

	smb2SetSecurityInfos		OBJECT-TYPE
	SYNTAX				Counter32
	MAX-ACCESS			read-only
	STATUS				current
	DESCRIPTION
			"The number of SMB2 SET_INFO SECURITY requests
			 received, since the last time the statistics
			 were cleared."
	::= { cifsReqs 100 }

	smb2QueryFileAccessInfos	OBJECT-TYPE
	SYNTAX				Counter32
	MAX-ACCESS			read-only
	STATUS				current
	DESCRIPTION
			"The number of SMB2 QUERY_FILE_ACCESS_INFO
			 requests, since the last time the statistics
			 were cleared."
	::= { cifsReqs 101 }


	-- -- -- -- -- -- -- -- -- -- -- -- -- -- -- -- -- --
	-- the cifsObsReqs group
	-- (Obsolete SMB requests)
	-- -- -- -- -- -- -- -- -- -- -- -- -- -- -- -- -- --

	obsSmbClosePrintFiles           OBJECT-TYPE
	SYNTAX                          Counter32
        MAX-ACCESS                      read-only
        STATUS                          current
	DESCRIPTION
			"The number of SMB CLOSE_PRINT_FILE requests,
			 since the last time the statistics were cleared."
	::= { cifsObsReqs 1 }

	obsSmbCreates                   OBJECT-TYPE
	SYNTAX                          Counter32
        MAX-ACCESS                      read-only
        STATUS                          current
	DESCRIPTION
			"The number of SMB CREATE requests,
			 since the last time the statistics were cleared."
	::= { cifsObsReqs 2 }

	obsSmbCreateDirs                OBJECT-TYPE
	SYNTAX                          Counter32
        MAX-ACCESS                      read-only
        STATUS                          current
	DESCRIPTION
			"The number of SMB CREATE_DIRECTORY requests,
			 since the last time the statistics were cleared."
	::= { cifsObsReqs 3 }

	obsSmbCreateNews                OBJECT-TYPE
	SYNTAX                          Counter32
        MAX-ACCESS                      read-only
        STATUS                          current
	DESCRIPTION
			"The number of SMB CREATE_NEW requests,
			 since the last time the statistics were cleared."
	::= { cifsObsReqs 4 }

	obsSmbLockAndReads              OBJECT-TYPE
	SYNTAX                          Counter32
        MAX-ACCESS                      read-only
        STATUS                          current
	DESCRIPTION
			"The number of SMB LOCK_AND_READ requests,
			 since the last time the statistics were cleared."
	::= { cifsObsReqs 5 }

	obsSmbLockByteRanges            OBJECT-TYPE
	SYNTAX                          Counter32
        MAX-ACCESS                      read-only
        STATUS                          current
	DESCRIPTION
			"The number of SMB LOCK_BYTE_RANGE requests,
			 since the last time the statistics were cleared."
	::= { cifsObsReqs 6 }

	obsSmbOpens                     OBJECT-TYPE
	SYNTAX                          Counter32
        MAX-ACCESS                      read-only
        STATUS                          current
	DESCRIPTION
			"The number of SMB OPEN requests,
			 since the last time the statistics were cleared."
	::= { cifsObsReqs 7 }

	obsSmbOpenAndXs                 OBJECT-TYPE
	SYNTAX                          Counter32
        MAX-ACCESS                      read-only
        STATUS                          current
	DESCRIPTION
			"The number of SMB OPEN_ANDX requests,
			 since the last time the statistics were cleared."
	::= { cifsObsReqs 8 }

	obsSmbProcessExits              OBJECT-TYPE
	SYNTAX                          Counter32
        MAX-ACCESS                      read-only
        STATUS                          current
	DESCRIPTION
			"The number of SMB PROCESS_EXIT requests,
			 since the last time the statistics were cleared."
	::= { cifsObsReqs 9 }

	obsSmbQueryInfos                OBJECT-TYPE
	SYNTAX                          Counter32
        MAX-ACCESS                      read-only
        STATUS                          current
	DESCRIPTION
			"The number of SMB QUERY_INFORMATION requests,
			 since the last time the statistics were cleared."
	::= { cifsObsReqs 10 }

	obsSmbQueryInfo2s               OBJECT-TYPE
	SYNTAX                          Counter32
        MAX-ACCESS                      read-only
        STATUS                          current
	DESCRIPTION
			"The number of SMB QUERY_INFORMATION2 requests,
			 since the last time the statistics were cleared."
	::= { cifsObsReqs 11 }

	obsSmbReads                     OBJECT-TYPE
	SYNTAX                          Counter32
        MAX-ACCESS                      read-only
        STATUS                          current
	DESCRIPTION
			"The number of SMB READ requests,
			 since the last time the statistics were cleared."
	::= { cifsObsReqs 12 }

	obsSmbReadMPXs                  OBJECT-TYPE
	SYNTAX                          Counter32
        MAX-ACCESS                      read-only
        STATUS                          current
	DESCRIPTION
			"The SMB READ_MPX request is not supported,
			 so this value should always be zero."
	::= { cifsObsReqs 13 }

	obsSmbReadRaws                  OBJECT-TYPE
	SYNTAX                          Counter32
        MAX-ACCESS                      read-only
        STATUS                          current
	DESCRIPTION
			"The number of SMB READ_RAW requests,
			 since the last time the statistics were cleared."
	::= { cifsObsReqs 14 }

	obsSmbSearchs                   OBJECT-TYPE
	SYNTAX                          Counter32
        MAX-ACCESS                      read-only
        STATUS                          current
	DESCRIPTION
			"The number of SMB SEARCH requests,
			 since the last time the statistics were cleared."
	::= { cifsObsReqs 15 }

	obsSmbSetInfos                  OBJECT-TYPE
	SYNTAX                          Counter32
        MAX-ACCESS                      read-only
        STATUS                          current
	DESCRIPTION
			"The number of SMB SET_INFORMATION requests,
			 since the last time the statistics were cleared."
	::= { cifsObsReqs 16 }

	obsSmbSetInfo2s                 OBJECT-TYPE
	SYNTAX                          Counter32
        MAX-ACCESS                      read-only
        STATUS                          current
	DESCRIPTION
			"The number of SMB SET_INFORMATION2 requests,
			 since the last time the statistics were cleared."
	::= { cifsObsReqs 17 }

	obsSmbQueryInfoDisks            OBJECT-TYPE
	SYNTAX                          Counter32
        MAX-ACCESS                      read-only
        STATUS                          current
	DESCRIPTION
			"The number of SMB QUERY_INFORMATION_DISK
			 requests, since the last time the statistics
			 were cleared."
	::= { cifsObsReqs 18 }

	obsSmbTrans2Open2s              OBJECT-TYPE
	SYNTAX                          Counter32
        MAX-ACCESS                      read-only
        STATUS                          current
	DESCRIPTION
			"The number of SMB TRANS2_OPEN2 requests,
			 since the last time the statistics were cleared."
	::= { cifsObsReqs 19 }

	obsSmbTreeConnects              OBJECT-TYPE
	SYNTAX                          Counter32
        MAX-ACCESS                      read-only
        STATUS                          current
	DESCRIPTION
			"The number of SMB TREE_CONNECT requests,
			 since the last time the statistics were cleared."
	::= { cifsObsReqs 20 }

	obsSmbUnlockByteRanges          OBJECT-TYPE
	SYNTAX                          Counter32
        MAX-ACCESS                      read-only
        STATUS                          current
	DESCRIPTION
			"The number of SMB UNLOCK_BYTE_RANGE requests,
			 since the last time the statistics were cleared."
	::= { cifsObsReqs 21 }

	obsSmbWrites                    OBJECT-TYPE
	SYNTAX                          Counter32
        MAX-ACCESS                      read-only
        STATUS                          current
	DESCRIPTION
			"The number of SMB WRITE requests,
			 since the last time the statistics were cleared."
	::= { cifsObsReqs 22 }

	obsSmbWriteAndUnlocks           OBJECT-TYPE
	SYNTAX                          Counter32
        MAX-ACCESS                      read-only
        STATUS                          current
	DESCRIPTION
			"The number of SMB WRITE_AND_UNLOCK requests,
			 since the last time the statistics were cleared."
	::= { cifsObsReqs 23 }

	obsSmbWriteAndCloses            OBJECT-TYPE
	SYNTAX                          Counter32
        MAX-ACCESS                      read-only
        STATUS                          current
	DESCRIPTION
			"The number of SMB WRITE_AND_CLOSE requests,
			 since the last time the statistics were cleared."
	::= { cifsObsReqs 24 }

	obsSmbWriteMPXs                 OBJECT-TYPE
	SYNTAX                          Counter32
        MAX-ACCESS                      read-only
        STATUS                          current
	DESCRIPTION
			"The SMB WRITE_MPX request is not supported,
			 so this value should always be zero."
	::= { cifsObsReqs 25 }

	obsSmbWritePrintFiles           OBJECT-TYPE
	SYNTAX                          Counter32
        MAX-ACCESS                      read-only
        STATUS                          current
	DESCRIPTION
			"The SMB WRITE_PRINT_FILE request is not supported,
			 so this value should always be zero."
	::= { cifsObsReqs 26 }

	obsSmbWriteRaws                 OBJECT-TYPE
	SYNTAX                          Counter32
        MAX-ACCESS                      read-only
        STATUS                          current
	DESCRIPTION
			"The number of SMB WRITE_RAW requests,
			 since the last time the statistics were cleared."
	::= { cifsObsReqs 27 }



	-- -- -- -- -- -- -- -- -- -- -- -- -- -- -- -- -- --
	-- the cifsPercent group
	-- -- -- -- -- -- -- -- -- -- -- -- -- -- -- -- -- --

		-- this group contains statistics for the number of
		-- calls received for each CIFS SMB request
		-- as a percentage of total CIFS calls received,
		-- since the last time the statistics were cleared

	smbNegProtPct                   OBJECT-TYPE
	SYNTAX                          Integer32 (0..100)
        MAX-ACCESS                      read-only
        STATUS                          current
	DESCRIPTION
			"The number of SMB NEGOTIATE requests,
			 as a percentage of total CIFS calls received,
			 since the last time the statistics were cleared."
	::= { cifsPercent 1 }

	smbSessionSetupAndXPct          OBJECT-TYPE
	SYNTAX                          Integer32 (0..100)
        MAX-ACCESS                      read-only
        STATUS                          current
	DESCRIPTION
			"The number of SMB SESSION_SETUP_ANDX requests,
			 as a percentage of total CIFS calls received,
			 since the last time the statistics were cleared."
	::= { cifsPercent 2 }

	smbLogoffAndXPct                OBJECT-TYPE
	SYNTAX                          Integer32 (0..100)
        MAX-ACCESS                      read-only
        STATUS                          current
	DESCRIPTION
			"The number of SMB LOGOFF_ANDX requests,
			 as a percentage of total CIFS calls received,
			 since the last time the statistics were cleared."
	::= { cifsPercent 3 }

	smbTreeConnectAndXPct           OBJECT-TYPE
	SYNTAX                          Integer32 (0..100)
        MAX-ACCESS                      read-only
        STATUS                          current
	DESCRIPTION
			"The number of SMB TREE_CONNECT_ANDX requests,
			 as a percentage of total CIFS calls received,
			 since the last time the statistics were cleared."
	::= { cifsPercent 4 }

	smbTreeDisconnectAndXPct        OBJECT-TYPE
	SYNTAX                          Integer32 (0..100)
        MAX-ACCESS                      read-only
        STATUS                          current
	DESCRIPTION
			"The number of SMB TREE_DISCONNECT_ANDX requests,
			 as a percentage of total CIFS calls received,
			 since the last time the statistics were cleared."
	::= { cifsPercent 5 }

	smbTrans2QueryFSInfoPct         OBJECT-TYPE
	SYNTAX                          Integer32 (0..100)
        MAX-ACCESS                      read-only
        STATUS                          current
	DESCRIPTION
			"The number of SMB TRANS2_QUERY_FS_INFORMATION
			 requests, as a percentage of total CIFS calls
			 received, since the last time the statistics
			 were cleared."
	::= { cifsPercent 6 }

	smbEchoPct                      OBJECT-TYPE
	SYNTAX                          Integer32 (0..100)
        MAX-ACCESS                      read-only
        STATUS                          current
	DESCRIPTION
			"The number of SMB ECHO requests,
			 as a percentage of total CIFS calls received,
			 since the last time the statistics were cleared."
	::= { cifsPercent 7 }

	smbNTCancelPct                  OBJECT-TYPE
	SYNTAX                          Integer32 (0..100)
        MAX-ACCESS                      read-only
        STATUS                          current
	DESCRIPTION
			"The number of SMB NT_CANCEL requests,
			 as a percentage of total CIFS calls received,
			 since the last time the statistics were cleared."
	::= { cifsPercent 8 }

	smbCreateAndXPct                OBJECT-TYPE
	SYNTAX                          Integer32 (0..100)
        MAX-ACCESS                      read-only
        STATUS                          current
	DESCRIPTION
			"The number of SMB NT_CREATE_ANDX requests,
			 as a percentage of total CIFS calls received,
			 since the last time the statistics were cleared."
	::= { cifsPercent 9 }

	smbTransactCreatePct            OBJECT-TYPE
	SYNTAX                          Integer32 (0..100)
        MAX-ACCESS                      read-only
        STATUS                          current
	DESCRIPTION
			"The number of SMB NT_TRANSACT_CREATE requests,
			 as a percentage of total CIFS calls received,
			 since the last time the statistics were cleared."
	::= { cifsPercent 10 }

	smbCreateTemporaryPct           OBJECT-TYPE
	SYNTAX                          Integer32 (0..100)
        MAX-ACCESS                      read-only
        STATUS                          current
	DESCRIPTION
			"The number of SMB CREATE_TEMPORARY requests,
			 as a percentage of total CIFS calls received,
			 since the last time the statistics were cleared."
	::= { cifsPercent 11 }

	smbReadAndXPct                  OBJECT-TYPE
	SYNTAX                          Integer32 (0..100)
        MAX-ACCESS                      read-only
        STATUS                          current
	DESCRIPTION
			"The number of SMB READ_ANDX requests,
			 as a percentage of total CIFS calls received,
			 since the last time the statistics were cleared."
	::= { cifsPercent 12 }

	smbWriteAndXPct                 OBJECT-TYPE
	SYNTAX                          Integer32 (0..100)
        MAX-ACCESS                      read-only
        STATUS                          current
	DESCRIPTION
			"The number of SMB WRITE_ANDX requests,
			 as a percentage of total CIFS calls received,
			 since the last time the statistics were cleared."
	::= { cifsPercent 13 }

	smbLockingAndXPct               OBJECT-TYPE
	SYNTAX                          Integer32 (0..100)
        MAX-ACCESS                      read-only
        STATUS                          current
	DESCRIPTION
			"The number of SMB LOCKING_ANDX requests,
			 as a percentage of total CIFS calls received,
			 since the last time the statistics were cleared."
	::= { cifsPercent 14 }

	smbSeekPct                      OBJECT-TYPE
	SYNTAX                          Integer32 (0..100)
        MAX-ACCESS                      read-only
        STATUS                          current
	DESCRIPTION
			"The number of SMB SEEK requests,
			 as a percentage of total CIFS calls received,
			 since the last time the statistics were cleared."
	::= { cifsPercent 15 }

	smbFlushPct                     OBJECT-TYPE
	SYNTAX                          Integer32 (0..100)
        MAX-ACCESS                      read-only
        STATUS                          current
	DESCRIPTION
			"The number of SMB FLUSH requests,
			 as a percentage of total CIFS calls received,
			 since the last time the statistics were cleared."
	::= { cifsPercent 16 }

	smbClosePct                     OBJECT-TYPE
	SYNTAX                          Integer32 (0..100)
        MAX-ACCESS                      read-only
        STATUS                          current
	DESCRIPTION
			"The number of SMB CLOSE requests,
			 as a percentage of total CIFS calls received,
			 since the last time the statistics were cleared."
	::= { cifsPercent 17 }

	smbDeletePct                    OBJECT-TYPE
	SYNTAX                          Integer32 (0..100)
        MAX-ACCESS                      read-only
        STATUS                          current
	DESCRIPTION
			"The number of SMB DELETE requests,
			 as a percentage of total CIFS calls received,
			 since the last time the statistics were cleared."
	::= { cifsPercent 18 }

	smbRenamePct                    OBJECT-TYPE
	SYNTAX                          Integer32 (0..100)
        MAX-ACCESS                      read-only
        STATUS                          current
	DESCRIPTION
			"The number of SMB RENAME requests,
			 as a percentage of total CIFS calls received,
			 since the last time the statistics were cleared."
	::= { cifsPercent 19 }

	smbMovePct                      OBJECT-TYPE
	SYNTAX                          Integer32 (0..100)
        MAX-ACCESS                      read-only
        STATUS                          current
	DESCRIPTION
			"The number of SMB MOVE requests,
			 as a percentage of total CIFS calls received,
			 since the last time the statistics were cleared."
	::= { cifsPercent 20 }

	smbCopyPct                      OBJECT-TYPE
	SYNTAX                          Integer32 (0..100)
        MAX-ACCESS                      read-only
        STATUS                          current
	DESCRIPTION
			"The number of SMB COPY requests,
			 as a percentage of total CIFS calls received,
			 since the last time the statistics were cleared."
	::= { cifsPercent 21 }

	smbTrans2QueryPathInfoPct       OBJECT-TYPE
	SYNTAX                          Integer32 (0..100)
        MAX-ACCESS                      read-only
        STATUS                          current
	DESCRIPTION
			"The number of SMB TRANS2_QUERY_PATH_INFORMATION
			 requests, as a percentage of total CIFS calls
			 received, since the last time the statistics
			 were cleared."
	::= { cifsPercent 22 }

	smbTrans2QueryFileInfoPct       OBJECT-TYPE
	SYNTAX                          Integer32 (0..100)
        MAX-ACCESS                      read-only
        STATUS                          current
	DESCRIPTION
			"The number of SMB TRANS2_QUERY_FILE_INFORMATION
			 requests, as a percentage of total CIFS calls
			 received, since the last time the statistics
			 were cleared."
	::= { cifsPercent 23 }

	smbTrans2SetPathInfoPct         OBJECT-TYPE
	SYNTAX                          Integer32 (0..100)
        MAX-ACCESS                      read-only
        STATUS                          current
	DESCRIPTION
			"The number of SMB TRANS2_SET_PATH_INFORMATION
			 requests, as a percentage of total CIFS calls
			 received, since the last time the statistics
			 were cleared."
	::= { cifsPercent 24 }

	smbTrans2SetFileInfoPct         OBJECT-TYPE
	SYNTAX                          Integer32 (0..100)
        MAX-ACCESS                      read-only
        STATUS                          current
	DESCRIPTION
			"The number of SMB TRANS2_SET_FILE_INFORMATION
			 requests, as a percentage of total CIFS calls
			 received, since the last time the statistics
			 were cleared."
	::= { cifsPercent 25 }

	smbDeleteDirPct                 OBJECT-TYPE
	SYNTAX                          Integer32 (0..100)
        MAX-ACCESS                      read-only
        STATUS                          current
	DESCRIPTION
			"The number of SMB DELETE_DIRECTORY requests,
			 as a percentage of total CIFS calls received,
			 since the last time the statistics were cleared."
	::= { cifsPercent 26 }

	smbCheckDirPct                  OBJECT-TYPE
	SYNTAX                          Integer32 (0..100)
        MAX-ACCESS                      read-only
        STATUS                          current
	DESCRIPTION
			"The number of SMB CHECK_DIRECTORY requests,
			 as a percentage of total CIFS calls received,
			 since the last time the statistics were cleared."
	::= { cifsPercent 27 }


	smbTrans2FindFirst2Pct          OBJECT-TYPE
	SYNTAX                          Integer32 (0..100)
        MAX-ACCESS                      read-only
        STATUS                          current
	DESCRIPTION
			"The number of SMB TRANS2_FIND_FIRST2 requests,
			 as a percentage of total CIFS calls received,
			 since the last time the statistics were cleared."
	::= { cifsPercent 28 }

	smbTrans2FindNext2Pct           OBJECT-TYPE
	SYNTAX                          Integer32 (0..100)
        MAX-ACCESS                      read-only
        STATUS                          current
	DESCRIPTION
			"The number of SMB TRANS2_FIND_NEXT2 requests,
			 as a percentage of total CIFS calls received,
			 since the last time the statistics were cleared."
	::= { cifsPercent 29 }

	smbFindClose2Pct                OBJECT-TYPE
	SYNTAX                          Integer32 (0..100)
        MAX-ACCESS                      read-only
        STATUS                          current
	DESCRIPTION
			"The number of SMB FIND_CLOSE2 requests,
			 as a percentage of total CIFS calls received,
			 since the last time the statistics were cleared."
	::= { cifsPercent 30 }

	smbNTTransactNotifyChgPct       OBJECT-TYPE
	SYNTAX                          Integer32 (0..100)
        MAX-ACCESS                      read-only
        STATUS                          current
	DESCRIPTION
			"The number of SMB NT_TRANSACT_NOTIFY_CHANGE
			 requests, as a percentage of total CIFS calls
			 received, since the last time the statistics
			 were cleared."
	::= { cifsPercent 31 }

	smbTrans2GetDFSReferralPct      OBJECT-TYPE
	SYNTAX                          Integer32 (0..100)
        MAX-ACCESS                      read-only
        STATUS                          current
	DESCRIPTION
			"The number of SMB TRANS2_GET_DFS_REFERRAL
			 requests, as a percentage of total CIFS calls
			 received, since the last time the statistics
			 were cleared."
	::= { cifsPercent 32 }

	smbTrans2ReportDFSIncPct        OBJECT-TYPE
	SYNTAX                          Integer32 (0..100)
        MAX-ACCESS                      read-only
        STATUS                          current
	DESCRIPTION
			"The number of SMB TRANS2_REPORT_DFS_INCONSISTENCY
			 requests, as a percentage of total CIFS calls
			 received, since the last time the statistics
			 were cleared."
	::= { cifsPercent 33 }

	smbOpenPrintFilePct             OBJECT-TYPE
	SYNTAX                          Integer32 (0..100)
        MAX-ACCESS                      read-only
        STATUS                          current
	DESCRIPTION
			"The number of SMB OPEN_PRINT_FILE requests,
			 as a percentage of total CIFS calls received,
			 since the last time the statistics were cleared."
	::= { cifsPercent 34 }

	smbGetPrintQueuePct             OBJECT-TYPE
	SYNTAX                          Integer32 (0..100)
        MAX-ACCESS                      read-only
        STATUS                          current
	DESCRIPTION
			"The number of SMB GET_PRINT_QUEUE requests,
			 as a percentage of total CIFS calls received,
			 since the last time the statistics were cleared."
	::= { cifsPercent 35 }

	smbNTTransactIoctlPct           OBJECT-TYPE
	SYNTAX                          Integer32 (0..100)
        MAX-ACCESS                      read-only
        STATUS                          current
	DESCRIPTION
			"The number of SMB NT_TRANSACT_IOCTL requests,
			 as a percentage of total CIFS calls received,
			 since the last time the statistics were cleared."
	::= { cifsPercent 36 }

	smbNTTransactQuerySecDescPct    OBJECT-TYPE
	SYNTAX                          Integer32 (0..100)
        MAX-ACCESS                      read-only
        STATUS                          current
	DESCRIPTION
			"The number of SMB NT_TRANSACT_QUERY_SECURITY_DESC
			 requests, as a percentage of total CIFS calls
			 received, since the last time the statistics
			 were cleared."
	::= { cifsPercent 37 }

	smbNTTransactSetSecDescPct      OBJECT-TYPE
	SYNTAX                          Integer32 (0..100)
        MAX-ACCESS                      read-only
        STATUS                          current
	DESCRIPTION
			"The number of SMB NT_TRANSACT_SET_SECURITY_DESC
			 requests, as a percentage of total CIFS calls
			 received, since the last time the statistics
			 were cleared."
	::= { cifsPercent 38 }


	smbTrans2CreateDirPct           OBJECT-TYPE
	SYNTAX                          Integer32 (0..100)
        MAX-ACCESS                      read-only
        STATUS                          current
	DESCRIPTION
			"The number of SMB TRANS2_CREATE_DIRECTORY
			 requests, as a percentage of total CIFS calls
			 received, since the last time the statistics
			 were cleared."
	::= { cifsPercent 39 }


	smbNTCancelCNPct                OBJECT-TYPE
	SYNTAX                          Integer32 (0..100)
        MAX-ACCESS                      read-only
        STATUS                          current
	DESCRIPTION
			"The number of SMB NT_CANCEL requests against
			 change notifications, as a percentage of
			 total CIFS calls received, since the last
			 time the statistics were cleared."
	::= { cifsPercent 40 }

	smbNTCancelOtherPct             OBJECT-TYPE
	SYNTAX                          Integer32 (0..100)
        MAX-ACCESS                      read-only
        STATUS                          current
	DESCRIPTION
			"The number of SMB NT_CANCEL requests against
			 calls other than change notifications, as
			 a percentage of total CIFS calls received,
			 since the last time the statistics were
			 cleared."
	::= { cifsPercent 41 }

	smb2EchoPct			OBJECT-TYPE
	SYNTAX				Integer32 (0..100)
	MAX-ACCESS			read-only
	STATUS				current
	DESCRIPTION
			"The number of SMB2 ECHO requests,
			 as a percentage of total CIFS calls received,
			 since the last time the statistics were cleared."
	::= { cifsPercent 42 }

	smb2NegProtPct			OBJECT-TYPE
	SYNTAX				Integer32 (0..100)
	MAX-ACCESS			read-only
	STATUS				current
	DESCRIPTION
			"The number of SMB2 NEGOTIATE requests,
			 as a percentage of total CIFS calls received,
			 since the last time the statistics were cleared."
	::= { cifsPercent 43 }

	smb2SessionSetupPct		OBJECT-TYPE
	SYNTAX				Integer32 (0..100)
	MAX-ACCESS			read-only
	STATUS				current
	DESCRIPTION
			"The number of SMB2 SESSION_SETUP requests,
			 as a percentage of total CIFS calls received,
			 since the last time the statistics were cleared."
	::= { cifsPercent 44 }

	smb2LogoffPct			OBJECT-TYPE
	SYNTAX				Integer32 (0..100)
	MAX-ACCESS			read-only
	STATUS				current
	DESCRIPTION
			"The number of SMB2 LOGOFF requests,
			 as a percentage of total CIFS calls received,
			 since the last time the statistics were cleared."
	::= { cifsPercent 45 }

	smb2TreeConnectPct		OBJECT-TYPE
	SYNTAX				Integer32 (0..100)
	MAX-ACCESS			read-only
	STATUS				current
	DESCRIPTION
			"The number of SMB2 TREE_CONNECT requests,
			 as a percentage of total CIFS calls received,
			 since the last time the statistics were cleared."
	::= { cifsPercent 46 }

	smb2TreeDisconnectPct		OBJECT-TYPE
	SYNTAX				Integer32 (0..100)
	MAX-ACCESS			read-only
	STATUS				current
	DESCRIPTION
			"The number of SMB2 TREE_DISCONNECT requests,
			 as a percentage of total CIFS calls received,
			 since the last time the statistics were cleared."
	::= { cifsPercent 47 }


	smb2CancelPct			OBJECT-TYPE
	SYNTAX				Integer32 (0..100)
	MAX-ACCESS			read-only
	STATUS				current
	DESCRIPTION
			"The number of SMB2 CANCEL requests,
			 as a percentage of total CIFS calls received,
			 since the last time the statistics were cleared."
	::= { cifsPercent 48 }

	smb2CreatePct			OBJECT-TYPE
	SYNTAX				Integer32 (0..100)
	MAX-ACCESS			read-only
	STATUS				current
	DESCRIPTION
			"The number of SMB2 CREATE requests,
			 as a percentage of total CIFS calls received,
			 since the last time the statistics were cleared."
	::= { cifsPercent 49 }

	smb2IpcCreatePct		OBJECT-TYPE
	SYNTAX				Integer32 (0..100)
	MAX-ACCESS			read-only
	STATUS				current
	DESCRIPTION
			"The number of SMB2 IPC CREATE requests,
			 as a percentage of total CIFS calls received,
			 since the last time the statistics were cleared."
	::= { cifsPercent 50 }

	smb2ReadPct			OBJECT-TYPE
	SYNTAX				Integer32 (0..100)
	MAX-ACCESS			read-only
	STATUS				current
	DESCRIPTION
			"The number of SMB2 READ requests,
			 as a percentage of total CIFS calls received,
			 since the last time the statistics were cleared."
	::= { cifsPercent 51 }

	smb2WritePct			OBJECT-TYPE
	SYNTAX				Integer32 (0..100)
	MAX-ACCESS			read-only
	STATUS				current
	DESCRIPTION
			"The number of SMB2 WRITE requests,
			 as a percentage of total CIFS calls received,
			 since the last time the statistics were cleared."
	::= { cifsPercent 52 }

	smb2IpcReadPct			OBJECT-TYPE
	SYNTAX				Integer32 (0..100)
	MAX-ACCESS			read-only
	STATUS				current
	DESCRIPTION
			"The number of SMB2 IPC READ requests,
			 as a percentage of total CIFS calls received,
			 since the last time the statistics were cleared."
	::= { cifsPercent 53 }

	smb2IpcWritePct			OBJECT-TYPE
	SYNTAX				Integer32 (0..100)
	MAX-ACCESS			read-only
	STATUS				current
	DESCRIPTION
			"The number of SMB2 IPC WRITE requests,
			 as a percentage of total CIFS calls received,
			 since the last time the statistics were cleared."
	::= { cifsPercent 54 }

	smb2LockPct			OBJECT-TYPE
	SYNTAX				Integer32 (0..100)
	MAX-ACCESS			read-only
	STATUS				current
	DESCRIPTION
			"The number of SMB2 LOCK requests,
			 as a percentage of total CIFS calls received,
			 since the last time the statistics were cleared."
	::= { cifsPercent 55 }

	smb2UnLockPct			OBJECT-TYPE
	SYNTAX				Integer32 (0..100)
	MAX-ACCESS			read-only
	STATUS				current
	DESCRIPTION
			"The number of SMB2 UNLOCK requests,
			 as a percentage of total CIFS calls received,
			 since the last time the statistics were cleared."
	::= { cifsPercent 56 }

	smb2OplkBrkAckPct		OBJECT-TYPE
	SYNTAX				Integer32 (0..100)
	MAX-ACCESS			read-only
	STATUS				current
	DESCRIPTION
			"The number of SMB2 Oplock Break Acknowledgement,
			 as a percentage of total CIFS calls received,
			 since the last time the statistics were cleared."
	::= { cifsPercent 57 }

	smb2FlushPct			OBJECT-TYPE
	SYNTAX				Integer32 (0..100)
	MAX-ACCESS			read-only
	STATUS				current
	DESCRIPTION
			"The number of SMB2 FLUSH requests,
			 as a percentage of total CIFS calls received,
			 since the last time the statistics were cleared."
	::= { cifsPercent 58 }

	smb2ClosePct			OBJECT-TYPE
	SYNTAX				Integer32 (0..100)
	MAX-ACCESS			read-only
	STATUS				current
	DESCRIPTION
			"The number of SMB2 CLOSE requests,
			 as a percentage of total CIFS calls received,
			 since the last time the statistics were cleared."
	::= { cifsPercent 59 }

	smb2QueryFileBasicInfoPct	OBJECT-TYPE
	SYNTAX				Integer32 (0..100)
	MAX-ACCESS			read-only
	STATUS				current
	DESCRIPTION
			"The number of SMB2 QUERY_FILE_BASIC_INFO
			 requests, as a percentage of total CIFS calls
			 received, since the last time the statistics
			 were cleared."
	::= { cifsPercent 60 }


	smb2QueryFileStandardInfoPct	OBJECT-TYPE
	SYNTAX				Integer32 (0..100)
	MAX-ACCESS			read-only
	STATUS				current
	DESCRIPTION
			"The number of SMB2 QUERY_FILE_STANDARD_INFO
			 requests, as a percentage of total CIFS calls
			 received, since the last time the statistics
			 were cleared."
	::= { cifsPercent 61 }

	smb2QueryFileInternalInfoPct	OBJECT-TYPE
	SYNTAX				Integer32 (0..100)
	MAX-ACCESS			read-only
	STATUS				current
	DESCRIPTION
			"The number of SMB2 QUERY_FILE_INT_INFO
			 requests, as a percentage of total CIFS calls
			 received, since the last time the statistics
			 were cleared."
	::= { cifsPercent 62 }

	smb2QueryFileEAInfoPct		OBJECT-TYPE
	SYNTAX				Integer32 (0..100)
	MAX-ACCESS			read-only
	STATUS				current
	DESCRIPTION
			"The number of SMB2 QUERY_FILE_EA_INFO
			 requests, as a percentage of total CIFS calls
			 received, since the last time the statistics
			 were cleared."
	::= { cifsPercent 63 }

	smb2QueryFileFullEAInfoPct	OBJECT-TYPE
	SYNTAX				Integer32 (0..100)
	MAX-ACCESS			read-only
	STATUS				current
	DESCRIPTION
			"The number of SMB2 QUERY_FILE_FULL_EA_INFO
			 requests, as a percentage of total CIFS calls
			 received, since the last time the statistics
			 were cleared."
	::= { cifsPercent 64 }

	smb2QueryFileModeInfoPct	OBJECT-TYPE
	SYNTAX				Integer32 (0..100)
	MAX-ACCESS			read-only
	STATUS				current
	DESCRIPTION
			"The number of SMB2 QUERY_FILE_MODE_INFO
			 requests, as a percentage of total CIFS calls
			 received, since the last time the statistics
			 were cleared."
	::= { cifsPercent 65 }

	smb2QueryFileAltNamePct		OBJECT-TYPE
	SYNTAX				Integer32 (0..100)
	MAX-ACCESS			read-only
	STATUS				current
	DESCRIPTION
			"The number of SMB2 QUERY_FILE_ALT_NAME_INFO_
			 requests, as a percentage of total CIFS calls
			 received, since the last time the statistics
			 were cleared."
	::= { cifsPercent 66 }

	smb2QueryFileStreamInfoPct	OBJECT-TYPE
	SYNTAX				Integer32 (0..100)
	MAX-ACCESS			read-only
	STATUS				current
	DESCRIPTION
			"The number of SMB2 QUERY_FILE_STREAM_INFO_
			 requests, as a percentage of total CIFS calls
			 received, since the last time the statistics
			 were cleared."
	::= { cifsPercent 67 }

	smb2QueryFileNetOpenInfoPct	OBJECT-TYPE
	SYNTAX				Integer32 (0..100)
	MAX-ACCESS			read-only
	STATUS				current
	DESCRIPTION
			"The number of SMB2 QUERY_FILE_NET_OPEN_INFO
			 requests, as a percentage of total CIFS calls
			 received, since the last time the statistics
			 were cleared."
	::= { cifsPercent 68 }

	smb2QueryFileAttrTagInfoPct	OBJECT-TYPE
	SYNTAX				Integer32 (0..100)
	MAX-ACCESS			read-only
	STATUS				current
	DESCRIPTION
			"The number of SMB2 QUERY_FILE_ATTR_TAG_INFO
			 requests, as a percentage of total CIFS calls
			 received, since the last time the statistics
			 were cleared."
	::= { cifsPercent 69 }

	smb2QueryFileUnsupportedPct	OBJECT-TYPE
	SYNTAX				Integer32 (0..100)
	MAX-ACCESS			read-only
	STATUS				current
	DESCRIPTION
			"The number of SMB2 Unsupported QUERY_FILE_INFO
			 requests, as a percentage of total CIFS calls
			 received, since the last time the statistics
			 were cleared."
	::= { cifsPercent 70 }

	smb2QueryFileInvalidPct		OBJECT-TYPE
	SYNTAX				Integer32 (0..100)
	MAX-ACCESS			read-only
	STATUS				current
	DESCRIPTION
			"The number of SMB2 invalid QUERY_FILE_INFO
			 requests, as a percentage of total CIFS calls
			 received, since the last time the statistics
			 were cleared."
	::= { cifsPercent 71 }

	smb2QueryFsVolInfoPct		OBJECT-TYPE
	SYNTAX				Integer32 (0..100)
	MAX-ACCESS			read-only
	STATUS				current
	DESCRIPTION
			"The number of SMB2 QUERY_FS_VOLUME_INFO
			 requests, as a percentage of total CIFS calls
			 received, since the last time the statistics
			 were cleared."
	::= { cifsPercent 72 }

	smb2QueryFsSizeInfoPct		OBJECT-TYPE
	SYNTAX				Integer32 (0..100)
	MAX-ACCESS			read-only
	STATUS				current
	DESCRIPTION
			"The number of SMB2 QUERY_FS_SIZE_INFO
			 requests, as a percentage of total CIFS calls
			 received, since the last time the statistics
			 were cleared."
	::= { cifsPercent 73 }

	smb2QueryFsDeviceInfoPct	OBJECT-TYPE
	SYNTAX				Integer32 (0..100)
	MAX-ACCESS			read-only
	STATUS				current
	DESCRIPTION
			"The number of SMB2 QUERY_FS_DEVICE_INFO
			 requests, as a percentage of total CIFS calls
			 received, since the last time the statistics
			 were cleared."
	::= { cifsPercent 74 }

	smb2QueryFsAttrInfoPct		OBJECT-TYPE
	SYNTAX				Integer32 (0..100)
	MAX-ACCESS			read-only
	STATUS				current
	DESCRIPTION
			"The number of SMB2 QUERY_FS_ATTR_INFO
			 requests, as a percentage of total CIFS calls
			 received, since the last time the statistics
			 were cleared."
	::= { cifsPercent 75 }

	smb2QueryFsFullSizeInfoPct	OBJECT-TYPE
	SYNTAX				Integer32 (0..100)
	MAX-ACCESS			read-only
	STATUS				current
	DESCRIPTION
			"The number of SMB2 QUERY_FS_FULL_SIZE_INFO
			 requests, as a percentage of total CIFS calls
			 received, since the last time the statistics
			 were cleared."
	::= { cifsPercent 76 }

	smb2QueryFsObjectIdInfoPct	OBJECT-TYPE
	SYNTAX				Integer32 (0..100)
	MAX-ACCESS			read-only
	STATUS				current
	DESCRIPTION
			"The number of SMB2 QUERY_FS_OBJECT_ID_INFO
			 requests, as a percentage of total CIFS calls
			 received, since the last time the statistics
			 were cleared."
	::= { cifsPercent 77 }

	smb2QueryFsInvalidPct		OBJECT-TYPE
	SYNTAX				Integer32 (0..100)
	MAX-ACCESS			read-only
	STATUS				current
	DESCRIPTION
			"The number of SMB2 invalid QUERY_FS_INFO
			 requests, as a percentage of total CIFS calls
			 received, since the last time the statistics
			 were cleared."
	::= { cifsPercent 78 }

	smb2SetBasicInfoPct		OBJECT-TYPE
	SYNTAX				Integer32 (0..100)
	MAX-ACCESS			read-only
	STATUS				current
	DESCRIPTION
			"The number of SMB2 SET_BASIC_INFO
			 requests, as a percentage of total CIFS calls
			 received, since the last time the statistics
			 were cleared."
	::= { cifsPercent 79 }

	smb2SetRenameInfoPct		OBJECT-TYPE
	SYNTAX				Integer32 (0..100)
	MAX-ACCESS			read-only
	STATUS				current
	DESCRIPTION
			"The number of SMB2 SET_FILE_RENAME_INFO
			 requests, as a percentage of total CIFS calls
			 received, since the last time the statistics
			 were cleared."
	::= { cifsPercent 80 }

	smb2SetFileLinkInfoPct		OBJECT-TYPE
	SYNTAX				Integer32 (0..100)
	MAX-ACCESS			read-only
	STATUS				current
	DESCRIPTION
			"The number of SMB2 SET_FILE_LINK_INFO
			 requests, as a percentage of total CIFS calls
			 received, since the last time the statistics
			 were cleared."
	::= { cifsPercent 81 }

	smb2SetFileDispInfoPct		OBJECT-TYPE
	SYNTAX				Integer32 (0..100)
	MAX-ACCESS			read-only
	STATUS				current
	DESCRIPTION
			"The number of SMB2 SET_FILE_DISP_INFO
			 requests, as a percentage of total CIFS calls
			 received, since the last time the statistics
			 were cleared."
	::= { cifsPercent 82 }

	smb2SetFullEaInfoPct		OBJECT-TYPE
	SYNTAX				Integer32 (0..100)
	MAX-ACCESS			read-only
	STATUS				current
	DESCRIPTION
			"The number of SMB2 SET_FULL_EA_INFO
			 requests, as a percentage of total CIFS calls
			 received, since the last time the statistics
			 were cleared."
	::= { cifsPercent 83 }

	smb2SetModeInfoPct		OBJECT-TYPE
	SYNTAX				Integer32 (0..100)
	MAX-ACCESS			read-only
	STATUS				current
	DESCRIPTION
			"The number of SMB2 SET_MODE_INFO
			 requests, as a percentage of total CIFS calls
			 received, since the last time the statistics
			 were cleared."
	::= { cifsPercent 84 }

	smb2SetAllocInfoPct		OBJECT-TYPE
	SYNTAX				Integer32 (0..100)
	MAX-ACCESS			read-only
	STATUS				current
	DESCRIPTION
			"The number of SMB2 SET_ALLOC_INFO
			 requests, as a percentage of total CIFS calls
			 received, since the last time the statistics
			 were cleared."
	::= { cifsPercent 85 }

	smb2SetEofInfoPct		OBJECT-TYPE
	SYNTAX				Integer32 (0..100)
	MAX-ACCESS			read-only
	STATUS				current
	DESCRIPTION
			"The number of SMB2 SET_EOF_INFO
			 requests, as a percentage of total CIFS calls
			 received, since the last time the statistics
			 were cleared."
	::= { cifsPercent 86 }

	smb2SetInfoUnsupportedPct	OBJECT-TYPE
	SYNTAX				Integer32 (0..100)
	MAX-ACCESS			read-only
	STATUS				current
	DESCRIPTION
			"The number of SMB2 Unsupported SET_INFO
			 requests, as a percentage of total CIFS calls
			 received, since the last time the statistics
			 were cleared."
	::= { cifsPercent 87 }

	smb2SetInfoInvalidPct		OBJECT-TYPE
	SYNTAX				Integer32 (0..100)
	MAX-ACCESS			read-only
	STATUS				current
	DESCRIPTION
			"The number of invalid SMB2 SET_INFO
			 requests, as a percentage of total CIFS calls
			 received, since the last time the statistics
			 were cleared."
	::= { cifsPercent 88 }

	smb2FsctlPipeTransceivePct	OBJECT-TYPE
	SYNTAX				Integer32 (0..100)
	MAX-ACCESS			read-only
	STATUS				current
	DESCRIPTION
			"The number of SMB2 FSCTL_PIPE_TRANSCEIVE
			 requests, as a percentage of total CIFS calls
			 received, since the last time the statistics
			 were cleared."
	::= { cifsPercent 89 }

	smb2FsctlPipePeekPct		OBJECT-TYPE
	SYNTAX				Integer32 (0..100)
	MAX-ACCESS			read-only
	STATUS				current
	DESCRIPTION
			"The number of SMB2 FSCTL_PIPE_PEEK
			 requests, as a percentage of total CIFS calls
			 received, since the last time the statistics
			 were cleared."
	::= { cifsPercent 90 }

	smb2FsctlEnumSnapshotsPct	OBJECT-TYPE
	SYNTAX				Integer32 (0..100)
	MAX-ACCESS			read-only
	STATUS				current
	DESCRIPTION
			"The number of SMB2 FSCTL_ENUMERATE_SNAPSHOTS
			 requests, as a percentage of total CIFS calls
			 received, since the last time the statistics
			 were cleared."
	::= { cifsPercent 91 }

	smb2FsctlDfsReferralsPct	OBJECT-TYPE
	SYNTAX				Integer32 (0..100)
	MAX-ACCESS			read-only
	STATUS				current
	DESCRIPTION
			"The number of SMB2 FSCTL_DFS_REFERRALS
			 requests, as a percentage of total CIFS calls
			 received, since the last time the statistics
			 were cleared."
	::= { cifsPercent 92 }

	smb2FsctlSetSparsePct		OBJECT-TYPE
	SYNTAX				Integer32 (0..100)
	MAX-ACCESS			read-only
	STATUS				current
	DESCRIPTION
			"The number of SMB2 FSCTL_SET_SPARSE
			 requests, as a percentage of total CIFS calls
			 received, since the last time the statistics
			 were cleared."
	::= { cifsPercent 93 }

	smb2FsctlSecureSharePct		OBJECT-TYPE
	SYNTAX				Integer32 (0..100)
	MAX-ACCESS			read-only
	STATUS				current
	DESCRIPTION
			"The number of SMB2 FSCTL_SECURE_SHARE
			 requests, as a percentage of total CIFS calls
			 received, since the last time the statistics
			 were cleared."
	::= { cifsPercent 94 }

	smb2FsctlFileUnsupportedPct	OBJECT-TYPE
	SYNTAX				Integer32 (0..100)
	MAX-ACCESS			read-only
	STATUS				current
	DESCRIPTION
			"The number of Unsupported SMB2 File FSCTL
			 requests, as a percentage of total CIFS calls
			 received, since the last time the statistics
			 were cleared."
	::= { cifsPercent 95 }

	smb2FsctlIpcUnsupportedPct	OBJECT-TYPE
	SYNTAX				Integer32 (0..100)
	MAX-ACCESS			read-only
	STATUS				current
	DESCRIPTION
			"The number of Unsupported SMB2 IPC FSCTL
			 requests, as a percentage of total CIFS calls
			 received, since the last time the statistics
			 were cleared."
	::= { cifsPercent 96 }

	smb2QueryDirPct			OBJECT-TYPE
	SYNTAX				Integer32 (0..100)
	MAX-ACCESS			read-only
	STATUS				current
	DESCRIPTION
			"The number of SMB2 QUERY_DIR
			 requests, as a percentage of total CIFS calls
			 received, since the last time the statistics
			 were cleared."
	::= { cifsPercent 97 }

	-- -- -- -- -- -- -- -- -- -- -- -- -- -- -- -- -- --
	-- the obsPct group
	-- (Obsolete SMB requests)
	-- -- -- -- -- -- -- -- -- -- -- -- -- -- -- -- -- --

	obsSmbClosePrintFilePct         OBJECT-TYPE
	SYNTAX                          Integer32 (0..100)
        MAX-ACCESS                      read-only
        STATUS                          current
	DESCRIPTION
			"The number of SMB CLOSE_PRINT_FILE requests,
			 as a percentage of total CIFS calls received,
			 since the last time the statistics were cleared."
	::= { cifsObsPercent 1 }

	obsSmbCreatePct                 OBJECT-TYPE
	SYNTAX                          Integer32 (0..100)
        MAX-ACCESS                      read-only
        STATUS                          current
	DESCRIPTION
			"The number of SMB CREATE requests,
			 as a percentage of total CIFS calls received,
			 since the last time the statistics were cleared."
	::= { cifsObsPercent 2 }

	obsSmbCreateDirPct              OBJECT-TYPE
	SYNTAX                          Integer32 (0..100)
        MAX-ACCESS                      read-only
        STATUS                          current
	DESCRIPTION
			"The number of SMB CREATE_DIRECTORY requests,
			 as a percentage of total CIFS calls received,
			 since the last time the statistics were cleared."
	::= { cifsObsPercent 3 }

	obsSmbCreateNewPct              OBJECT-TYPE
	SYNTAX                          Integer32 (0..100)
        MAX-ACCESS                      read-only
        STATUS                          current
	DESCRIPTION
			"The number of SMB CREATE_NEW requests,
			 as a percentage of total CIFS calls received,
			 since the last time the statistics were cleared."
	::= { cifsObsPercent 4 }

	obsSmbLockAndReadPct            OBJECT-TYPE
	SYNTAX                          Integer32 (0..100)
        MAX-ACCESS                      read-only
        STATUS                          current
	DESCRIPTION
			"The number of SMB LOCK_AND_READ requests,
			 as a percentage of total CIFS calls received,
			 since the last time the statistics were cleared."
	::= { cifsObsPercent 5 }

	obsSmbLockByteRangePct          OBJECT-TYPE
	SYNTAX                          Integer32 (0..100)
        MAX-ACCESS                      read-only
        STATUS                          current
	DESCRIPTION
			"The number of SMB LOCK_BYTE_RANGE requests,
			 as a percentage of total CIFS calls received,
			 since the last time the statistics were cleared."
	::= { cifsObsPercent 6 }

	obsSmbOpenPct                   OBJECT-TYPE
	SYNTAX                          Integer32 (0..100)
        MAX-ACCESS                      read-only
        STATUS                          current
	DESCRIPTION
			"The number of SMB OPEN requests,
			 as a percentage of total CIFS calls received,
			 since the last time the statistics were cleared."
	::= { cifsObsPercent 7 }

	obsSmbOpenAndXPct               OBJECT-TYPE
	SYNTAX                          Integer32 (0..100)
        MAX-ACCESS                      read-only
        STATUS                          current
	DESCRIPTION
			"The number of SMB OPEN_ANDX requests,
			 as a percentage of total CIFS calls received,
			 since the last time the statistics were cleared."
	::= { cifsObsPercent 8 }

	obsSmbProcessExitPct            OBJECT-TYPE
	SYNTAX                          Integer32 (0..100)
        MAX-ACCESS                      read-only
        STATUS                          current
	DESCRIPTION
			"The number of SMB PROCESS_EXIT requests,
			 as a percentage of total CIFS calls received,
			 since the last time the statistics were cleared."
	::= { cifsObsPercent 9 }

	obsSmbQueryInfoPct              OBJECT-TYPE
	SYNTAX                          Integer32 (0..100)
        MAX-ACCESS                      read-only
        STATUS                          current
	DESCRIPTION
			"The number of SMB QUERY_INFORMATION requests,
			 as a percentage of total CIFS calls received,
			 since the last time the statistics were cleared."
	::= { cifsObsPercent 10 }

	obsSmbQueryInfo2Pct             OBJECT-TYPE
	SYNTAX                          Integer32 (0..100)
        MAX-ACCESS                      read-only
        STATUS                          current
	DESCRIPTION
			"The number of SMB QUERY_INFORMATION2 requests,
			 as a percentage of total CIFS calls received,
			 since the last time the statistics were cleared."
	::= { cifsObsPercent 11 }

	obsSmbReadPct                   OBJECT-TYPE
	SYNTAX                          Integer32 (0..100)
        MAX-ACCESS                      read-only
        STATUS                          current
	DESCRIPTION
			"The number of SMB READ requests,
			 as a percentage of total CIFS calls received,
			 since the last time the statistics were cleared."
	::= { cifsObsPercent 12 }

	obsSmbReadMPXPct                OBJECT-TYPE
	SYNTAX                          Integer32 (0..100)
        MAX-ACCESS                      read-only
        STATUS                          current
	DESCRIPTION
			"The number of SMB READ_MPX requests,
			 as a percentage of total CIFS calls received,
			 since the last time the statistics were cleared."
	::= { cifsObsPercent 13 }

	obsSmbReadRawPct                OBJECT-TYPE
	SYNTAX                          Integer32 (0..100)
        MAX-ACCESS                      read-only
        STATUS                          current
	DESCRIPTION
			"The number of SMB READ_RAW requests,
			 as a percentage of total CIFS calls received,
			 since the last time the statistics were cleared."
	::= { cifsObsPercent 14 }

	obsSmbSearchPct                 OBJECT-TYPE
	SYNTAX                          Integer32 (0..100)
        MAX-ACCESS                      read-only
        STATUS                          current
	DESCRIPTION
			"The number of SMB SEARCH requests,
			 as a percentage of total CIFS calls received,
			 since the last time the statistics were cleared."
	::= { cifsObsPercent 15 }

	obsSmbSetInfoPct                OBJECT-TYPE
	SYNTAX                          Integer32 (0..100)
        MAX-ACCESS                      read-only
        STATUS                          current
	DESCRIPTION
			"The number of SMB SET_INFORMATION requests,
			 as a percentage of total CIFS calls received,
			 since the last time the statistics were cleared."
	::= { cifsObsPercent 16 }

	obsSmbSetInfo2Pct               OBJECT-TYPE
	SYNTAX                          Integer32 (0..100)
        MAX-ACCESS                      read-only
        STATUS                          current
	DESCRIPTION
			"The number of SMB SET_INFORMATION2 requests,
			 as a percentage of total CIFS calls received,
			 since the last time the statistics were cleared."
	::= { cifsObsPercent 17 }

	obsSmbQueryInfoDiskPct          OBJECT-TYPE
	SYNTAX                          Integer32 (0..100)
        MAX-ACCESS                      read-only
        STATUS                          current
	DESCRIPTION
			"The number of SMB QUERY_INFORMATION_DISK
			 requests, as a percentage of total CIFS calls
			 received, since the last time the statistics
			 were cleared."
	::= { cifsObsPercent 18 }

	obsSmbTrans2Open2Pct            OBJECT-TYPE
	SYNTAX                          Integer32 (0..100)
        MAX-ACCESS                      read-only
        STATUS                          current
	DESCRIPTION
			"The number of SMB TRANS2_OPEN2 requests,
			 as a percentage of total CIFS calls received,
			 since the last time the statistics were cleared."
	::= { cifsObsPercent 19 }

	obsSmbTreeConnectPct            OBJECT-TYPE
	SYNTAX                          Integer32 (0..100)
        MAX-ACCESS                      read-only
        STATUS                          current
	DESCRIPTION
			"The number of SMB TREE_CONNECT requests,
			 as a percentage of total CIFS calls received,
			 since the last time the statistics were cleared."
	::= { cifsObsPercent 20 }

	obsSmbUnlockByteRangePct        OBJECT-TYPE
	SYNTAX                          Integer32 (0..100)
        MAX-ACCESS                      read-only
        STATUS                          current
	DESCRIPTION
			"The number of SMB UNLOCK_BYTE_RANGE requests,
			 as a percentage of total CIFS calls received,
			 since the last time the statistics were cleared."
	::= { cifsObsPercent 21 }

	obsSmbWritePct                  OBJECT-TYPE
	SYNTAX                          Integer32 (0..100)
        MAX-ACCESS                      read-only
        STATUS                          current
	DESCRIPTION
			"The number of SMB WRITE requests,
			 as a percentage of total CIFS calls received,
			 since the last time the statistics were cleared."
	::= { cifsObsPercent 22 }

	obsSmbWriteAndUnlockPct         OBJECT-TYPE
	SYNTAX                          Integer32 (0..100)
        MAX-ACCESS                      read-only
        STATUS                          current
	DESCRIPTION
			"The number of SMB WRITE_AND_UNLOCK requests,
			 as a percentage of total CIFS calls received,
			 since the last time the statistics were cleared."
	::= { cifsObsPercent 23 }

	obsSmbWriteAndClosePct          OBJECT-TYPE
	SYNTAX                          Integer32 (0..100)
        MAX-ACCESS                      read-only
        STATUS                          current
	DESCRIPTION
			"The number of SMB WRITE_AND_CLOSE requests,
			 as a percentage of total CIFS calls received,
			 since the last time the statistics were cleared."
	::= { cifsObsPercent 24 }

	obsSmbWriteMPXPct               OBJECT-TYPE
	SYNTAX                          Integer32 (0..100)
        MAX-ACCESS                      read-only
        STATUS                          current
	DESCRIPTION
			"The number of SMB WRITE_MPX requests,
			 as a percentage of total CIFS calls received,
			 since the last time the statistics were cleared."
	::= { cifsObsPercent 25 }

	obsSmbWritePrintFilePct         OBJECT-TYPE
	SYNTAX                          Integer32 (0..100)
        MAX-ACCESS                      read-only
        STATUS                          current
	DESCRIPTION
			"The number of SMB WRITE_PRINT_FILE requests,
			 as a percentage of total CIFS calls received,
			 since the last time the statistics were cleared."
	::= { cifsObsPercent 26 }

	obsSmbWriteRawPct               OBJECT-TYPE
	SYNTAX                          Integer32 (0..100)
        MAX-ACCESS                      read-only
        STATUS                          current
	DESCRIPTION
			"The number of SMB WRITE_RAW requests,
			 as a percentage of total CIFS calls received,
			 since the last time the statistics were cleared."
	::= { cifsObsPercent 27 }

	-- -- -- -- -- -- -- -- -- -- -- -- -- -- -- -- -- --
	-- the cifsMisc group
	-- These statistics are primarily of interest to
	-- NetApp developers.
	-- -- -- -- -- -- -- -- -- -- -- -- -- -- -- -- -- --

	cifsCancelLocks                 OBJECT-TYPE
	SYNTAX                          Counter32
        MAX-ACCESS                      read-only
        STATUS                          current
	DESCRIPTION
			"Undocumented"
	::= { cifsMisc 1 }

	cifsWaitLocks                   OBJECT-TYPE
	SYNTAX                          Counter32
        MAX-ACCESS                      read-only
        STATUS                          current
	DESCRIPTION
			"Undocumented"
	::= { cifsMisc 2 }

	cifsCopyToAligns                OBJECT-TYPE
	SYNTAX                          Counter32
        MAX-ACCESS                      read-only
        STATUS                          current
	DESCRIPTION
			"Undocumented"
	::= { cifsMisc 3 }

	cifsAlignedSmalls               OBJECT-TYPE
	SYNTAX                          Counter32
        MAX-ACCESS                      read-only
        STATUS                          current
	DESCRIPTION
			"Undocumented"
	::= { cifsMisc 4 }

	cifsAlignedLarges               OBJECT-TYPE
	SYNTAX                          Counter32
        MAX-ACCESS                      read-only
        STATUS                          current
	DESCRIPTION
			"Undocumented"
	::= { cifsMisc 5 }

	cifsAlignedSmallRels            OBJECT-TYPE
	SYNTAX                          Counter32
        MAX-ACCESS                      read-only
        STATUS                          current
	DESCRIPTION
			"Undocumented"
	::= { cifsMisc 6 }

	cifsAlignedLargeRels            OBJECT-TYPE
	SYNTAX                          Counter32
        MAX-ACCESS                      read-only
        STATUS                          current
	DESCRIPTION
			"Undocumented"
	::= { cifsMisc 7 }

	cifsMbufWaits                   OBJECT-TYPE
	SYNTAX                          Counter32
        MAX-ACCESS                      read-only
        STATUS                          current
	DESCRIPTION
			"Undocumented"
	::= { cifsMisc 8 }

	cifsNbtWaits                    OBJECT-TYPE
	SYNTAX                          Counter32
        MAX-ACCESS                      read-only
        STATUS                          current
	DESCRIPTION
			"Undocumented"
	::= { cifsMisc 9 }

	cifsCwaWaits                    OBJECT-TYPE
	SYNTAX                          Counter32
        MAX-ACCESS                      read-only
        STATUS                          current
	DESCRIPTION
			"Undocumented"
	::= { cifsMisc 10 }

	cifsMultipleVCs                 OBJECT-TYPE
	SYNTAX                          Counter32
        MAX-ACCESS                      read-only
        STATUS                          current
	DESCRIPTION
			"Undocumented"
	::= { cifsMisc 11 }

	cifsPDCUpcalls                  OBJECT-TYPE
	SYNTAX                          Counter32
        MAX-ACCESS                      read-only
        STATUS                          current
	DESCRIPTION
			"Undocumented"
	::= { cifsMisc 12 }

	cifsQueuedWriteRaws             OBJECT-TYPE
	SYNTAX                          Counter32
        MAX-ACCESS                      read-only
        STATUS                          current
	DESCRIPTION
			"Undocumented"
	::= { cifsMisc 13 }

	cifsNBTDisconnects              OBJECT-TYPE
	SYNTAX                          Counter32
        MAX-ACCESS                      read-only
        STATUS                          current
	DESCRIPTION
			"Undocumented"
	::= { cifsMisc 14 }

	cifsSMBDisconnects              OBJECT-TYPE
	SYNTAX                          Counter32
        MAX-ACCESS                      read-only
        STATUS                          current
	DESCRIPTION
			"Undocumented"
	::= { cifsMisc 15 }

	cifsDupDisconnects              OBJECT-TYPE
	SYNTAX                          Counter32
        MAX-ACCESS                      read-only
        STATUS                          current
	DESCRIPTION
			"Undocumented"
	::= { cifsMisc 16 }

	cifsOpLkBatchToL2s              OBJECT-TYPE
	SYNTAX                          Counter32
        MAX-ACCESS                      read-only
        STATUS                          current
	DESCRIPTION
			"Undocumented"
	::= { cifsMisc 17 }

	cifsOpLkBatchToNones            OBJECT-TYPE
	SYNTAX                          Counter32
        MAX-ACCESS                      read-only
        STATUS                          current
	DESCRIPTION
			"Undocumented"
	::= { cifsMisc 18 }

	cifsOpLkL2ToNones               OBJECT-TYPE
	SYNTAX                          Counter32
        MAX-ACCESS                      read-only
        STATUS                          current
	DESCRIPTION
			"Undocumented"
	::= { cifsMisc 19 }

	cifsOpLkNoBreakAcks             OBJECT-TYPE
	SYNTAX                          Counter32
        MAX-ACCESS                      read-only
        STATUS                          current
	DESCRIPTION
			"Undocumented"
	::= { cifsMisc 20 }

	cifsOpLkIgnoredAcks             OBJECT-TYPE
	SYNTAX                          Counter32
        MAX-ACCESS                      read-only
        STATUS                          current
	DESCRIPTION
			"Undocumented"
	::= { cifsMisc 21 }

	cifsOpLkMultiWaiters            OBJECT-TYPE
	SYNTAX                          Counter32
        MAX-ACCESS                      read-only
        STATUS                          current
	DESCRIPTION
			"Undocumented"
	::= { cifsMisc 22 }

	cifsSharingErrorRetries         OBJECT-TYPE
	SYNTAX                          Counter32
        MAX-ACCESS                      read-only
        STATUS                          current
	DESCRIPTION
			"Undocumented"
	::= { cifsMisc 23 }

	cifsOpLkWaiterTimedOuts         OBJECT-TYPE
	SYNTAX                          Counter32
        MAX-ACCESS                      read-only
        STATUS                          current
	DESCRIPTION
			"Undocumented"
	::= { cifsMisc 24 }

	cifsOpLkDelayedBreaks           OBJECT-TYPE
	SYNTAX                          Counter32
        MAX-ACCESS                      read-only
        STATUS                          current
	DESCRIPTION
			"Undocumented"
	::= { cifsMisc 25 }

	cifsOpLkEarlyNFSs               OBJECT-TYPE
	SYNTAX                          Counter32
        MAX-ACCESS                      read-only
        STATUS                          current
	DESCRIPTION
			"Undocumented"
	::= { cifsMisc 26 }

	cifsOpLkNFSWaiteds              OBJECT-TYPE
	SYNTAX                          Counter32
        MAX-ACCESS                      read-only
        STATUS                          current
	DESCRIPTION
			"Undocumented"
	::= { cifsMisc 27 }

	cifsMaxNFSBkWaiterCount         OBJECT-TYPE
	SYNTAX                          Integer32
        MAX-ACCESS                      read-only
        STATUS                          current
	DESCRIPTION
			"Undocumented"
	::= { cifsMisc 28 }

	cifsClearTextPasswd             OBJECT-TYPE
	SYNTAX                          INTEGER {
                                             no(1),
                                             yes(2)
                                        }
        MAX-ACCESS                      read-only
        STATUS                          current
	DESCRIPTION
				"This indicates whether the cifs clients are
				 using clear text passwords when authenticating
				 with the filer. If cifsDomainJoined is false and
				 this variable is also false, then the filer is
				 using NT Security from a local user list."
	::= { cifsMisc 29 }

	cifsSmb2MidUsedHash		OBJECT-TYPE
	SYNTAX				Counter32
	MAX-ACCESS			read-only
	STATUS				current
	DESCRIPTION
			"Undocumented"
	::= { cifsMisc 30 }

	cifsSmb2MidUnusedHash		OBJECT-TYPE
	SYNTAX				Counter32
	MAX-ACCESS			read-only
	STATUS				current
	DESCRIPTION
			"Undocumented"
	::= { cifsMisc 31 }

	cifsSmb2MidInvReject		OBJECT-TYPE
	SYNTAX				Counter32
	MAX-ACCESS			read-only
	STATUS				current
	DESCRIPTION
			"Undocumented"
	::= { cifsMisc 32 }

	cifsSmb2DurableCreateReceived	OBJECT-TYPE
	SYNTAX				Counter32
	MAX-ACCESS			read-only
	STATUS				current
	DESCRIPTION
			"Undocumented"
	::= { cifsMisc 33 }

	cifsSmb2DurableCreateSucceeded	OBJECT-TYPE
	SYNTAX				Counter32
	MAX-ACCESS			read-only
	STATUS				current
	DESCRIPTION
			"Undocumented"
	::= { cifsMisc 34 }

	cifsSmb2DurableReclaimReceived	OBJECT-TYPE
	SYNTAX				Counter32
	MAX-ACCESS			read-only
	STATUS				current
	DESCRIPTION
			"Undocumented"
	::= { cifsMisc 35 }

	cifsSmb2DurableReclaimSucceeded	OBJECT-TYPE
	SYNTAX				Counter32
	MAX-ACCESS			read-only
	STATUS				current
	DESCRIPTION
			"Undocumented"
	::= { cifsMisc 36 }

	cifsSmb2DurableHandlePreserved	OBJECT-TYPE
	SYNTAX				Counter32
	MAX-ACCESS			read-only
	STATUS				current
	DESCRIPTION
			"Undocumented"
	::= { cifsMisc 37 }

	cifsSmb2DurableHandlePurged	OBJECT-TYPE
	SYNTAX				Counter32
	MAX-ACCESS			read-only
	STATUS				current
	DESCRIPTION
			"Undocumented"
	::= { cifsMisc 38 }

	cifsSmb2DurableHandleExpired	OBJECT-TYPE
	SYNTAX				Counter32
	MAX-ACCESS			read-only
	STATUS				current
	DESCRIPTION
			"Undocumented"
	::= { cifsMisc 39 }

	cifsSmb2FileDirInfo		OBJECT-TYPE
	SYNTAX				Counter32
	MAX-ACCESS			read-only
	STATUS				current
	DESCRIPTION
			"Undocumented"
	::= { cifsMisc 40 }

	cifsSmb2FileFullDirInfo		OBJECT-TYPE
	SYNTAX				Counter32
	MAX-ACCESS			read-only
	STATUS				current
	DESCRIPTION
			"Undocumented"
	::= { cifsMisc 41 }

	cifsSmb2FileIdFullDirInfo	OBJECT-TYPE
	SYNTAX				Counter32
	MAX-ACCESS			read-only
	STATUS				current
	DESCRIPTION
			"Undocumented"
	::= { cifsMisc 42 }

	cifsSmb2FileBothDirInfo		OBJECT-TYPE
	SYNTAX				Counter32
	MAX-ACCESS			read-only
	STATUS				current
	DESCRIPTION
			"Undocumented"
	::= { cifsMisc 43 }

	cifsSmb2FileIdBothDirInfo	OBJECT-TYPE
	SYNTAX				Counter32
	MAX-ACCESS			read-only
	STATUS				current
	DESCRIPTION
			"Undocumented"
	::= { cifsMisc 44 }

	cifsSmb2FileNamesInfo		OBJECT-TYPE
	SYNTAX				Counter32
	MAX-ACCESS			read-only
	STATUS				current
	DESCRIPTION
			"Undocumented"
	::= { cifsMisc 45 }

	cifsSmb2FileDirUnsupported	OBJECT-TYPE
	SYNTAX				Counter32
	MAX-ACCESS			read-only
	STATUS				current
	DESCRIPTION
			"Undocumented"
	::= { cifsMisc 46 }

	cifsSmb2QueryInfo		OBJECT-TYPE
	SYNTAX				Counter32
	MAX-ACCESS			read-only
	STATUS				current
	DESCRIPTION
			"Undocumented"
	::= { cifsMisc 47 }

	cifsSmb2SetInfo			OBJECT-TYPE
	SYNTAX				Counter32
	MAX-ACCESS			read-only
	STATUS				current
	DESCRIPTION
			"Undocumented"
	::= { cifsMisc 48 }

	cifsSmb2Ioctl			OBJECT-TYPE
	SYNTAX				Counter32
	MAX-ACCESS			read-only
	STATUS				current
	DESCRIPTION
			"Undocumented"
	::= { cifsMisc 49 }

	cifsSmb2RelatedCompRequest	OBJECT-TYPE
	SYNTAX				Counter32
	MAX-ACCESS			read-only
	STATUS				current
	DESCRIPTION
			"Undocumented"
	::= { cifsMisc 50 }

	cifsSmb2UnRelatedCompRequest	OBJECT-TYPE
	SYNTAX				Counter32
	MAX-ACCESS			read-only
	STATUS				current
	DESCRIPTION
			"Undocumented"
	::= { cifsMisc 51 }

	cifsSmb2FileRequest		OBJECT-TYPE
	SYNTAX				Counter32
	MAX-ACCESS			read-only
	STATUS				current
	DESCRIPTION
			"Undocumented"
	::= { cifsMisc 52 }

	cifsSmb2PipeRequest		OBJECT-TYPE
	SYNTAX				Counter32
	MAX-ACCESS			read-only
	STATUS				current
	DESCRIPTION
			"Undocumented"
	::= { cifsMisc 53 }

	cifsSmb2Unsupported		OBJECT-TYPE
	SYNTAX				Counter32
	MAX-ACCESS			read-only
	STATUS				current
	DESCRIPTION
			"Undocumented"
	::= { cifsMisc 54 }

	cifsSmb2InvalidSignatures	OBJECT-TYPE
	SYNTAX				Counter32
	MAX-ACCESS			read-only
	STATUS				current
	DESCRIPTION
			"Number of CIFS SMB 2.0 messages received
			 with incorrect signature."
	::= { cifsMisc 55 }

	-- -- -- -- -- -- -- -- -- -- -- -- -- -- -- -- -- --
	-- -- -- -- -- -- -- -- -- -- -- -- -- -- -- -- -- --
	-- the netcache group --
	-- -- -- -- -- -- -- -- -- -- -- -- -- -- -- -- -- --
	-- -- -- -- -- -- -- -- -- -- -- -- -- -- -- -- -- --

	ncOptions	OBJECT IDENTIFIER ::= { netcache 1 }

	ncInfo		OBJECT IDENTIFIER ::= { netcache 2 }

	ncStats		OBJECT IDENTIFIER ::= { netcache 3 }

	-- -- -- -- -- -- -- -- -- -- -- -- -- -- -- -- -- --
	-- the netcache options group
	-- -- -- -- -- -- -- -- -- -- -- -- -- -- -- -- -- --

	ncIsEnabled                     OBJECT-TYPE
	SYNTAX                          INTEGER {
                                             false(1),
                                             true(2)
                                        }
        MAX-ACCESS                      read-only
        STATUS                          current
	DESCRIPTION
			"Whether Netcache is enabled on this system."
	::= { ncOptions 1 }

	ncIsLicensed                    OBJECT-TYPE
	SYNTAX                          INTEGER {
                                             false(1),
                                             true(2)
                                        }
        MAX-ACCESS                      read-only
        STATUS                          current
	DESCRIPTION
			"Whether Netcache is licensed on this system."
	::= { ncOptions 2 }

	-- -- -- -- -- -- -- -- -- -- -- -- -- -- -- -- -- --
	-- the dns options group
	-- -- -- -- -- -- -- -- -- -- -- -- -- -- -- -- -- --

	ncDnsOptions		OBJECT IDENTIFIER ::= { ncOptions 3 }

	ncDnsIsEnabled                  OBJECT-TYPE
	SYNTAX                          INTEGER {
                                             false(1),
                                             true(2)
                                        }
        MAX-ACCESS                      read-only
        STATUS                          current
	DESCRIPTION
			"Whether the Domain Name System (DNS)
			is enabled on this system."
	::= { ncDnsOptions 1 }

	-- -- -- -- -- -- -- -- -- -- -- -- -- -- -- -- -- --
	-- the http options group
	-- -- -- -- -- -- -- -- -- -- -- -- -- -- -- -- -- --

	ncHttpOptions		OBJECT IDENTIFIER ::= { ncOptions 4 }

	ncHttpIsEnabled                 OBJECT-TYPE
	SYNTAX                          INTEGER {
                                             false(1),
                                             true(2)
                                        }
        MAX-ACCESS                      read-only
        STATUS                          current
	DESCRIPTION
			"Whether HTTP is enabled on this system."
	::= { ncHttpOptions 1 }

	-- -- -- -- -- -- -- -- -- -- -- -- -- -- -- -- -- --
	-- the nntp options group
	-- -- -- -- -- -- -- -- -- -- -- -- -- -- -- -- -- --

	ncNntpOptions		OBJECT IDENTIFIER ::= { ncOptions 5 }

	ncNntpIsEnabled                 OBJECT-TYPE
	SYNTAX                          INTEGER {
                                             false(1),
                                             true(2)
                                        }
        MAX-ACCESS                      read-only
        STATUS                          current
	DESCRIPTION
			"Whether NNTP is enabled on this system."
	::= { ncNntpOptions 1 }

	ncNntpIsLicensed                OBJECT-TYPE
	SYNTAX                          INTEGER {
                                             false(1),
                                             true(2)
                                        }
        MAX-ACCESS                      read-only
        STATUS                          current
	DESCRIPTION
			"Whether NNTP is licensed on this system."
	::= { ncNntpOptions 2 }

	-- -- -- -- -- -- -- -- -- -- -- -- -- -- -- -- -- --
	-- the streaming options group
	-- -- -- -- -- -- -- -- -- -- -- -- -- -- -- -- -- --

	ncStreamingOptions	OBJECT IDENTIFIER ::= { ncOptions 6 }

	ncStreamingMmsIsEnabled         OBJECT-TYPE
	SYNTAX                          INTEGER {
                                             false(1),
                                             true(2)
                                        }
        MAX-ACCESS                      read-only
        STATUS                          current
	DESCRIPTION
			"Whether Microsoft Media Services (MMS)
			is enabled on this system."
	::= { ncStreamingOptions 1 }

	ncStreamingMmsIsLicensed        OBJECT-TYPE
	SYNTAX                          INTEGER {
                                             false(1),
                                             true(2)
                                        }
        MAX-ACCESS                      read-only
        STATUS                          current
	DESCRIPTION
			"Whether Microsoft Windows Media Service (MMS)
			is licensed on this system."
	::= { ncStreamingOptions 2 }

	ncStreamingMmsProIsLicensed     OBJECT-TYPE
	SYNTAX                          INTEGER {
                                             false(1),
                                             true(2)
                                        }
        MAX-ACCESS                      read-only
        STATUS                          current
	DESCRIPTION
			"Whether Microsoft Windows Media Service Pro (MMS)
			is licensed on this system."
	::= { ncStreamingOptions 3 }

	ncStreamingRtspIsEnabled        OBJECT-TYPE
	SYNTAX                          INTEGER {
                                             false(1),
                                             true(2)
                                        }
        MAX-ACCESS                      read-only
        STATUS                          current
	DESCRIPTION
			"Whether the Real Time Streaming Protocol (RTSP)
			is enabled on this system."
	::= { ncStreamingOptions 4 }

	ncStreamingQuickTimeIsLicensed  OBJECT-TYPE
	SYNTAX                          INTEGER {
                                             false(1),
                                             true(2)
                                        }
        MAX-ACCESS                      read-only
        STATUS                          current
	DESCRIPTION
			"Whether QuickTime is licensed on this system."
	::= { ncStreamingOptions 5 }

	ncStreamingRealIsLicensed       OBJECT-TYPE
	SYNTAX                          INTEGER {
                                             false(1),
                                             true(2)
                                        }
        MAX-ACCESS                      read-only
        STATUS                          current
	DESCRIPTION
			"Whether Real Media streaming is licensed on
			this system."
	::= { ncStreamingOptions 6 }

	ncStreamingMmsUltraIsLicensed   OBJECT-TYPE
	SYNTAX                          INTEGER {
                                             false(1),
                                             true(2)
                                        }
        MAX-ACCESS                      read-only
        STATUS                          current
	DESCRIPTION
			"Whether Microsoft Windows Media Service Ultra (MMS)
			is licensed on this system."
	::= { ncStreamingOptions 7 }

	ncStreamingRealProIsLicensed    OBJECT-TYPE
	SYNTAX                          INTEGER {
                                             false(1),
                                             true(2)
                                        }
        MAX-ACCESS                      read-only
        STATUS                          current
	DESCRIPTION
			"Whether Real Media Pro streaming is licensed on
			this system."
	::= { ncStreamingOptions 8 }

	ncStreamingRealUltraIsLicensed  OBJECT-TYPE
	SYNTAX                          INTEGER {
                                             false(1),
                                             true(2)
                                        }
        MAX-ACCESS                      read-only
        STATUS                          current
	DESCRIPTION
			"Whether Real Media Ultra streaming is licensed on
			this system."
	::= { ncStreamingOptions 9 }

	-- -- -- -- -- -- -- -- -- -- -- -- -- -- -- -- -- --
	-- the icap options group
	-- -- -- -- -- -- -- -- -- -- -- -- -- -- -- -- -- --

	ncIcapOptions		OBJECT IDENTIFIER ::= { ncOptions 7 }

	ncIcapIsEnabled                 OBJECT-TYPE
	SYNTAX                          INTEGER {
                                             false(1),
                                             true(2)
                                        }
        MAX-ACCESS                      read-only
        STATUS                          current
	DESCRIPTION
			"Whether ICAP v0.95 is enabled on this system."
	::= { ncIcapOptions 1 }

	ncIcapIsLicensed                OBJECT-TYPE
	SYNTAX                          INTEGER {
                                             false(1),
                                             true(2)
                                        }
        MAX-ACCESS                      read-only
        STATUS                          current
	DESCRIPTION
			"Whether ICAP is licensed on this system."
	::= { ncIcapOptions 2 }

	ncIcapv1IsEnabled               OBJECT-TYPE
	SYNTAX                          INTEGER {
                                             false(1),
                                             true(2)
                                        }
        MAX-ACCESS                      read-only
        STATUS                          current
	DESCRIPTION
			"Whether ICAP v1.0 is enabled on this system."
	::= { ncIcapOptions 3 }

	-- -- -- -- -- -- -- -- -- -- -- -- -- -- -- -- -- --
	-- the grm options group
	-- -- -- -- -- -- -- -- -- -- -- -- -- -- -- -- -- --

	ncGrmOptions		OBJECT IDENTIFIER ::= { ncOptions 8 }

	ncGrmServerOptions	OBJECT IDENTIFIER ::= { ncGrmOptions 1 }

	ncGrmAgentOptions	OBJECT IDENTIFIER ::= { ncGrmOptions 2 }

	ncGrmServerIsEnabled            OBJECT-TYPE
	SYNTAX                          INTEGER {
                                             false(1),
                                             true(2)
                                        }
        MAX-ACCESS                      read-only
        STATUS                          current
	DESCRIPTION
			"Whether the Global Request Manager (GRM) Server
			is enabled on this system."
	::= { ncGrmServerOptions 1 }

	ncGrmServerIsLicensed           OBJECT-TYPE
	SYNTAX                          INTEGER {
                                             false(1),
                                             true(2)
                                        }
        MAX-ACCESS                      read-only
        STATUS                          current
	DESCRIPTION
			"Whether the Global Request Manager (GRM) Server
			is licensed on this system."
	::= { ncGrmServerOptions 2 }

	ncGrmAgentIsEnabled             OBJECT-TYPE
	SYNTAX                          INTEGER {
                                             false(1),
                                             true(2)
                                        }
        MAX-ACCESS                      read-only
        STATUS                          current
	DESCRIPTION
			"Whether the Global Request Manager (GRM) Agent
			enabled on this system."
	::= { ncGrmAgentOptions 1 }

	ncGrmAgentIsLicensed            OBJECT-TYPE
	SYNTAX                          INTEGER {
                                             false(1),
                                             true(2)
                                        }
        MAX-ACCESS                      read-only
        STATUS                          current
	DESCRIPTION
			"Whether the Global Request Manager (GRM) Agent
			is licensed on this system."
	::= { ncGrmAgentOptions 2 }

	-- -- -- -- -- -- -- -- -- -- -- -- -- -- -- -- -- --
	-- the content director options group
	-- -- -- -- -- -- -- -- -- -- -- -- -- -- -- -- -- --

	ncCdOptions	OBJECT IDENTIFIER ::= { ncOptions 9 }

	ncCdIsEnabled                   OBJECT-TYPE
	SYNTAX                          INTEGER {
                                             false(1),
                                             true(2)
                                        }
        MAX-ACCESS                      read-only
        STATUS                          current
	DESCRIPTION
			"Whether Content Director is enabled on this system."
	::= { ncCdOptions 1 }

	-- -- -- -- -- -- -- -- -- -- -- -- -- -- -- -- -- --
	-- the https options group
	-- -- -- -- -- -- -- -- -- -- -- -- -- -- -- -- -- --

	ncHttpsProxyOptions		OBJECT IDENTIFIER ::= { ncOptions 10 }

	ncHttpsProxyIsEnabled           OBJECT-TYPE
	SYNTAX                          INTEGER {
                                             false(1),
                                             true(2)
                                        }
        MAX-ACCESS                      read-only
        STATUS                          current
	DESCRIPTION
			"Whether HTTPS is enabled on this system."
	::= { ncHttpsProxyOptions 1 }

	ncHttpsProxyIsLicensed          OBJECT-TYPE
	SYNTAX                          INTEGER {
                                             false(1),
                                             true(2)
                                        }
        MAX-ACCESS                      read-only
        STATUS                          current
	DESCRIPTION
			"Whether HTTPS is licensed on this system."
	::= { ncHttpsProxyOptions 2 }

	-- -- -- -- -- -- -- -- -- -- -- -- -- -- -- -- -- --
	-- the cms options group
	-- -- -- -- -- -- -- -- -- -- -- -- -- -- -- -- -- --
	ncCmsOptions		OBJECT IDENTIFIER ::= { ncOptions 11 }

	ncCmsIsEnabled                  OBJECT-TYPE
	SYNTAX                          INTEGER {
                                             false(1),
                                             true(2)
                                        }
        MAX-ACCESS                      read-only
        STATUS                          current
	DESCRIPTION
			"Whether CMS is enabled on this system."
	::= { ncCmsOptions 1 }

	-- -- -- -- -- -- -- -- -- -- -- -- -- -- -- -- -- --
	-- the netcache info group
	-- -- -- -- -- -- -- -- -- -- -- -- -- -- -- -- -- --

 	ncVersion                       OBJECT-TYPE
	SYNTAX                          DisplayString
        MAX-ACCESS                      read-only
        STATUS                          current
	DESCRIPTION
			"The Netcache version string."
	::= { ncInfo 1 }

 	ncAdminPort                     OBJECT-TYPE
	SYNTAX                          Integer32
        MAX-ACCESS                      read-only
        STATUS                          current
	DESCRIPTION
			"Netcache Admin Port number - this
			 is the first in the list of admin
			 ports configured for the NetCache."
	::= { ncInfo 2 }


	accelmonitor	OBJECT IDENTIFIER ::= { ncInfo 3 }

	-- the acceleration monitor group
	-- Implementation of the Acceleration Monitor (accelmonitor.

	amNumber                        OBJECT-TYPE
	SYNTAX                          Integer32
        MAX-ACCESS                      read-only
        STATUS                          current
	    DESCRIPTION
		"The number of entries in the acceleration monitor table."
	    ::= { accelmonitor 1 }

	amMonitor                       OBJECT-TYPE
	SYNTAX                          INTEGER {
                                             togglea(1),
                                             toggleb(2)
                                        }
        MAX-ACCESS                      read-only
        STATUS                          current
	    DESCRIPTION
		"Variable for user defined SNMP traps to monitor whether			there has been a status change of any of the acceleration
		servers that netcache is probing."
	    ::= { accelmonitor 2 }

	amMonitorString                 OBJECT-TYPE
	SYNTAX                          DisplayString
        MAX-ACCESS                      read-only
        STATUS                          current
	    DESCRIPTION
		"Used in conjunction with amMonitor. This returns a string
		in format of: 'IP:port status' which reports the status
		of all the servers netcache is accelerating as of last
		status change."
	    ::= { accelmonitor 3 }

	-- accelmonitor table

	-- the Acceleration Monitor table contains information of the
	-- the acceleration server, port that we are monitoring and its
	-- status.

	amTable                         OBJECT-TYPE
	SYNTAX                          SEQUENCE OF AmEntry
        MAX-ACCESS                      not-accessible
        STATUS                          current
	    DESCRIPTION
		     "A list of acceleration server and port entries. The
		     number of entries is given by the value of amNumber."
	    ::= { accelmonitor 4 }

	amEntry                         OBJECT-TYPE
	SYNTAX                          AmEntry
        MAX-ACCESS                      not-accessible
        STATUS                          current
	    DESCRIPTION
		    "An acceleration monitor entry contains: the server
		    IP address, server port and the status."
	    INDEX   { amIndex }
	    ::= { amTable 1 }

	AmEntry ::=
	    SEQUENCE {
		amIndex
		    Integer32,
		amAddress
		    IpAddress,
		amPort
		    Integer32,
		amStatus
		    INTEGER
	    }

	amIndex                         OBJECT-TYPE
	SYNTAX                          Integer32 (1..2147483647)
        MAX-ACCESS                      read-only
        STATUS                          current
	    DESCRIPTION
		    " A unique value for each entry in the acceleration monitor
		    table."
	    ::= { amEntry 1 }

	amAddress                       OBJECT-TYPE
	SYNTAX                          IpAddress
        MAX-ACCESS                      read-only
        STATUS                          current
	    DESCRIPTION
		    "The IP address of the acceleration server the NetCache
		    is monitoring."
	    ::= { amEntry 2 }

	amPort                          OBJECT-TYPE
	SYNTAX                          Integer32 (0..65535)
        MAX-ACCESS                      read-only
        STATUS                          current
	    DESCRIPTION
		   "The corresponding port on the server that NetCache is
		   monitoring."
	    ::= { amEntry 3 }

	amStatus                        OBJECT-TYPE
	SYNTAX                          INTEGER {
                                             active(1),
                                             up(2),
					     down(3),
                                             inactive(4)
                                        }
        MAX-ACCESS                      read-only
        STATUS                          current
	    DESCRIPTION
		    "The status of the service running on the server.
		    active -  in queue but no probes done yet.
		    up - the server is reachable and responding to probes.
		    down - the server is unreachable.
		    inactive - monitoring is disabled."
	    ::= { amEntry 4 }

 	ncLocalConfigChanged            OBJECT-TYPE
	SYNTAX                          INTEGER {
                                             false(1),
                                             true(2)
                                        }
        MAX-ACCESS                      read-only
        STATUS                          current
	DESCRIPTION
			"Whether the local configuration file on NetCache
			was changed without using DFM configuration management."
	::= { ncInfo 4 }

 	ncLocalConfigVersion            OBJECT-TYPE
	SYNTAX                          Integer32
        MAX-ACCESS                      read-only
        STATUS                          current
	DESCRIPTION
			"The current cache configuration's version."
	::= { ncInfo 5 }

	grmMonitor	OBJECT IDENTIFIER ::= { ncInfo 6 }

	-- the GRM monitor group
	-- Implementation of the GRM agent monitor

	grmMonitorToggle                OBJECT-TYPE
	SYNTAX                          INTEGER {
                                             togglea(1),
                                             toggleb(2)
                                        }
        MAX-ACCESS                      read-only
        STATUS                          current
       DESCRIPTION
		"Variable for user defined SNMP traps to monitor whether			there has been a status change of any of the GRM
		agents reporting to this GRM server."
	    ::= { grmMonitor 1 }

	grmMonitorString                OBJECT-TYPE
	SYNTAX                          DisplayString
        MAX-ACCESS                      read-only
        STATUS                          current
	    DESCRIPTION
		"Used in conjunction with grmMonitor. This returns a string
		in format of: 'IP status.' which reports the status
		of all the GRM agents reporting to this GRM server as of last
		status change."
	    ::= { grmMonitor 2 }

	takeoverinfo	OBJECT IDENTIFIER ::= { ncInfo 7 }

	-- the takeover information group
	-- information same as status.takeover.addrs and
	-- status.takeover.mode and status.takeover.partner_status

	takeoverAddrs                   OBJECT-TYPE
	SYNTAX                          DisplayString
        MAX-ACCESS                      read-only
        STATUS                          current
	    DESCRIPTION
		"Indicates the list of interfaces and their corresponding IP
		 addresses of the partner NetCache that this appliance has taken 		 over."
	    ::= { takeoverinfo 1 }

	takeoverMode                    OBJECT-TYPE
	SYNTAX                          INTEGER {
                                             normal(1),
                                             takingover(2),
					     takenover(3),
                                             giveback(4)
                                        }
        MAX-ACCESS                      read-only
        STATUS                          current
	    DESCRIPTION
		"Indicates the current takeover mode of this appliance."
	    ::= { takeoverinfo 2 }

	takeoverStatus                  OBJECT-TYPE
	SYNTAX                          INTEGER {
                                             up(1),
                                             unknown(2),
                                             failed(3)
                                        }
        MAX-ACCESS                      read-only
        STATUS                          current
	    DESCRIPTION
		"Indicates the current status of the takeover partner of
		 this appliance. up(1) indicates that the takeover partner is
		 reachable. unknown(2) indicates that an unknown error occurred.
		 failed(3) indicates that the partner has failed, takeoverAddrs
		 indicates the partner's IP address this appliance has taken
		 over."
	    ::= { takeoverinfo 3 }


	-- -- -- -- -- -- -- -- -- -- -- -- -- -- -- -- -- --
	-- the netcache stats group --
	-- -- -- -- -- -- -- -- -- -- -- -- -- -- -- -- -- --

 	ncObjectsStored                 OBJECT-TYPE
	SYNTAX                          Integer32
        MAX-ACCESS                      read-only
        STATUS                          current
	DESCRIPTION
			"The total number of objects stored currently."
	::= { ncStats 1 }

	ncBytesToClients                OBJECT-TYPE
	SYNTAX                          Counter32
        MAX-ACCESS                      read-only
        STATUS                          current
	DESCRIPTION
			"Total bytes sent to clients"
	::= { ncStats 2 }

	ncBytesFromClients              OBJECT-TYPE
	SYNTAX                          Counter32
        MAX-ACCESS                      read-only
        STATUS                          current
	DESCRIPTION
			"Total bytes received from clients"
	::= { ncStats 3 }

	ncBytesToServers                OBJECT-TYPE
	SYNTAX                          Counter32
        MAX-ACCESS                      read-only
        STATUS                          current
	DESCRIPTION
			"Total bytes sent to servers"
	::= { ncStats 4 }

	ncBytesFromServers              OBJECT-TYPE
	SYNTAX                          Counter32
        MAX-ACCESS                      read-only
        STATUS                          current
	DESCRIPTION
			"Total bytes received from servers"
	::= { ncStats 5 }

	ncHttp		OBJECT IDENTIFIER ::= { ncStats 6 }

	-- -- -- -- -- -- -- -- -- -- -- -- -- -- -- -- -- --
	-- the http stats group
	-- -- -- -- -- -- -- -- -- -- -- -- -- -- -- -- -- --

 	ncHttpTotalRequests             OBJECT-TYPE
	SYNTAX                          Counter32
        MAX-ACCESS                      read-only
        STATUS                          current
	DESCRIPTION
			"Total HTTP requests so far"
	::= { ncHttp 1 }

 	ncHttpHitRequests               OBJECT-TYPE
	SYNTAX                          Counter32
        MAX-ACCESS                      read-only
        STATUS                          current
	DESCRIPTION
			"HTTP requests that resulted in hits so far"
	::= { ncHttp 2 }

 	ncHttpMissRequests              OBJECT-TYPE
	SYNTAX                          Counter32
        MAX-ACCESS                      read-only
        STATUS                          current
	DESCRIPTION
			"HTTP requests that resulted in misses so far"
	::= { ncHttp 3 }

 	ncHttpServConns                 OBJECT-TYPE
	SYNTAX                          Integer32
        MAX-ACCESS                      read-only
        STATUS                          current
	DESCRIPTION
			"Number of currently open TCP/IP connections to HTTP servers (active and idle)"
	::= { ncHttp 4 }

 	ncHttpCliConns                  OBJECT-TYPE
	SYNTAX                          Integer32
        MAX-ACCESS                      read-only
        STATUS                          current
	DESCRIPTION
			"Number of currently open TCP/IP connections to HTTP clients (active and idle)"
	::= { ncHttp 5 }

 	ncHttpBWSavings                 OBJECT-TYPE
	SYNTAX                          Integer32
        MAX-ACCESS                      read-only
        STATUS                          current
	DESCRIPTION
			"Bandwidth savings for HTTP requests"
	::= { ncHttp 6 }

 	ncHttpObjHitrate                OBJECT-TYPE
	SYNTAX                          Integer32
        MAX-ACCESS                      read-only
        STATUS                          current
	DESCRIPTION
			"Object Hitrate HTTP requests"
	::= { ncHttp 7 }

 	ncHttpRespTimePerByte           OBJECT-TYPE
	SYNTAX                          Integer32
        MAX-ACCESS                      read-only
        STATUS                          current
	DESCRIPTION
			"Response time in milliseconds per byte for HTTP requests."
	::= { ncHttp 8 }

 	ncHttpAvgRespTime               OBJECT-TYPE
	SYNTAX                          Integer32
        MAX-ACCESS                      read-only
        STATUS                          current
	DESCRIPTION
			"Average response time in milliseconds for all HTTP requests."
	::= { ncHttp 9 }

 	ncHttpAvgHitRespTime            OBJECT-TYPE
	SYNTAX                          Integer32
        MAX-ACCESS                      read-only
        STATUS                          current
	DESCRIPTION
			"Average response time in milliseconds for HTTP hit requests."
	::= { ncHttp 10 }

 	ncHttpAvgMissRespTime           OBJECT-TYPE
	SYNTAX                          Integer32
        MAX-ACCESS                      read-only
        STATUS                          current
	DESCRIPTION
			"Average response time in milliseconds for HTTP miss requests."
	::= { ncHttp 11 }

 	ncHttpInstAvgRespTime           OBJECT-TYPE
	SYNTAX                          Integer32
        MAX-ACCESS                      read-only
        STATUS                          current
	DESCRIPTION
			"Average response time in milliseconds for all HTTP requests during the last 60 seconds."
	::= { ncHttp 12 }


 	ncHttpInstAvgHitRespTime        OBJECT-TYPE
	SYNTAX                          Integer32
        MAX-ACCESS                      read-only
        STATUS                          current
	DESCRIPTION
			"Average response time in milliseconds for HTTP hit requests during the last 60 seconds."
	::= { ncHttp 13 }

 	ncHttpInstAvgMissRespTime       OBJECT-TYPE
	SYNTAX                          Integer32
        MAX-ACCESS                      read-only
        STATUS                          current
	DESCRIPTION
			"Average response time in milliseconds for HTTP miss requests during the last 60 seconds."
	::= { ncHttp 14 }

	ncHttpTotalRespTime             OBJECT-TYPE
	SYNTAX                          Integer32
        MAX-ACCESS                      read-only
        STATUS                          current
	DESCRIPTION
			"Total fetch time in milliseconds for HTTP requests"
	::= { ncHttp 15 }

	ncHttpTotalHitRespTime          OBJECT-TYPE
	SYNTAX                          Integer32
        MAX-ACCESS                      read-only
        STATUS                          current
	DESCRIPTION
			"Total fetch time in milliseconds for HTTP HIT requests"
	::= { ncHttp 16 }

	ncHttpTotalMissRespTime         OBJECT-TYPE
	SYNTAX                          Integer32
        MAX-ACCESS                      read-only
        STATUS                          current
	DESCRIPTION
			"Total fetch time in milliseconds for HTTP MISS requests"
	::= { ncHttp 17 }

	ncHttpBytesToClients            OBJECT-TYPE
	SYNTAX                          Counter32
        MAX-ACCESS                      read-only
        STATUS                          current
	DESCRIPTION
			"Total HTTP bytes sent to clients"
	::= { ncHttp 18 }

	ncHttpBytesFromClients          OBJECT-TYPE
	SYNTAX                          Counter32
        MAX-ACCESS                      read-only
        STATUS                          current
	DESCRIPTION
			"Total HTTP bytes received from clients"
	::= { ncHttp 19 }

	ncHttpBytesToServers            OBJECT-TYPE
	SYNTAX                          Counter32
        MAX-ACCESS                      read-only
        STATUS                          current
	DESCRIPTION
			"Total HTTP bytes sent to servers"
	::= { ncHttp 20 }

	ncHttpBytesFromServers          OBJECT-TYPE
	SYNTAX                          Counter32
        MAX-ACCESS                      read-only
        STATUS                          current
	DESCRIPTION
			"Total HTTP bytes received from servers"
	::= { ncHttp 21 }

	ncHttpHighTotalRespTimes        OBJECT-TYPE
	SYNTAX                          Counter32
        MAX-ACCESS                      read-only
        STATUS                          current
	DESCRIPTION
			"Total fetch time in milliseconds for HTTP requests.
			This object returns the most significant 32 bits
			of the 64 bit unsigned integer."
	::= { ncHttp 22 }

	ncHttpLowTotalRespTimes         OBJECT-TYPE
	SYNTAX                          Counter32
        MAX-ACCESS                      read-only
        STATUS                          current
	DESCRIPTION
			"Total fetch time in milliseconds for HTTP requests.
			This object returns the least significant 32 bits
			of the 64 bit unsigned integer."
	::= { ncHttp 23 }

	ncHttpHighTotalHitRespTimes     OBJECT-TYPE
	SYNTAX                          Counter32
        MAX-ACCESS                      read-only
        STATUS                          current
	DESCRIPTION
			"Total fetch time in milliseconds for HTTP HIT requests.
			This object returns the most significant 32 bits
			of the 64 bit unsigned integer."
	::= { ncHttp 24 }

	ncHttpLowTotalHitRespTimes      OBJECT-TYPE
	SYNTAX                          Counter32
        MAX-ACCESS                      read-only
        STATUS                          current
	DESCRIPTION
			"Total fetch time in milliseconds for HTTP HIT requests.
			This object returns the least significant 32 bits
			of the 64 bit unsigned integer."
	::= { ncHttp 25 }

	ncHttpHighTotalMissRespTimes    OBJECT-TYPE
	SYNTAX                          Counter32
        MAX-ACCESS                      read-only
        STATUS                          current
	DESCRIPTION
			"Total fetch time in milliseconds for HTTP MISS requests.
			This object returns the most significant 32 bits
			of the 64 bit unsigned integer."
	::= { ncHttp 26 }

	ncHttpLowTotalMissRespTimes     OBJECT-TYPE
	SYNTAX                          Counter32
        MAX-ACCESS                      read-only
        STATUS                          current
	DESCRIPTION
			"Total fetch time in milliseconds for HTTP MISS requests.
			This object returns the least significant 32 bits
			of the 64 bit unsigned integer."
	::= { ncHttp 27 }

 	ncHttpReqRate                   OBJECT-TYPE
	SYNTAX                          Integer32
        MAX-ACCESS                      read-only
        STATUS                          current
	DESCRIPTION
			"Request Rate for HTTP requests"
	::= { ncHttp 28 }

 	ncHttpObjHitRateLast1Min        OBJECT-TYPE
	SYNTAX                          Integer32
        MAX-ACCESS                      read-only
        STATUS                          current
	DESCRIPTION
			"HTTP object hit rate in the last 1 minute."
	::= { ncHttp 29 }

 	ncHttpObjHitRateLast5Min        OBJECT-TYPE
	SYNTAX                          Integer32
        MAX-ACCESS                      read-only
        STATUS                          current
	DESCRIPTION
			"HTTP object hit rate in the last 5 minutes."
	::= { ncHttp 30 }

 	ncHttpByteHitRateLast1Min       OBJECT-TYPE
	SYNTAX                          Integer32
        MAX-ACCESS                      read-only
        STATUS                          current
	DESCRIPTION
			"HTTP byte hit rate in the last 1 minute."
	::= { ncHttp 31 }

 	ncHttpByteHitRateLast5Min       OBJECT-TYPE
	SYNTAX                          Integer32
        MAX-ACCESS                      read-only
        STATUS                          current
	DESCRIPTION
			"HTTP byte hit rate in the last 5 minutes."
	::= { ncHttp 32 }

 	ncHttpBWSavingsLast1Min         OBJECT-TYPE
	SYNTAX                          Integer32
        MAX-ACCESS                      read-only
        STATUS                          current
	DESCRIPTION
			"Bandwidth savings for HTTP requests in the last
			 1 minute"
	::= { ncHttp 33 }

	ncHttpBWSavingsLast5Min         OBJECT-TYPE
	SYNTAX                          Integer32
        MAX-ACCESS                      read-only
        STATUS                          current
	DESCRIPTION
			"Bandwidth savings for HTTP requests in the last
			 5 minutes"
	::= { ncHttp 34 }

 	ncHttpActiveServConns           OBJECT-TYPE
	SYNTAX                          Integer32
        MAX-ACCESS                      read-only
        STATUS                          current
	DESCRIPTION
			"Number of currently active TCP/IP connections to HTTP servers"
	::= { ncHttp 35 }

 	ncHttpActiveCliConns            OBJECT-TYPE
	SYNTAX                          Integer32
        MAX-ACCESS                      read-only
        STATUS                          current
	DESCRIPTION
			"Number of currently active TCP/IP connections to HTTP clients"
	::= { ncHttp 36 }

	ncHttpAccelTable                OBJECT-TYPE
	SYNTAX                          SEQUENCE OF NcHttpAccelEntry
        MAX-ACCESS                      not-accessible
        STATUS                          current
	DESCRIPTION
		 	"Number of kilobytes sent to and received from the client side
			per acceleration rule"

 	::= { ncHttp 37 }

	ncHttpAccelEntry                OBJECT-TYPE
	SYNTAX                          NcHttpAccelEntry
        MAX-ACCESS                      not-accessible
        STATUS                          current
 	DESCRIPTION
 			"Each entry contains the number of kilobytes sent and
 			received to/from the clients side per acceleration
			rule"

	INDEX	 { ncHttpAccelIndex }
 	::= { ncHttpAccelTable 1 }

	NcHttpAccelEntry ::=
 	SEQUENCE {
 		ncHttpAccelIndex		Integer32,
 		ncHttpAccelKbytesFromClient 	Counter32,
 		ncHttpAccelKbytesToClient	Counter32,
		ncHttpAccelHits			Counter32
 		}

 	ncHttpAccelIndex                OBJECT-TYPE
	SYNTAX                          Integer32 (1..513)
        MAX-ACCESS                      read-only
        STATUS                          current
 	DESCRIPTION
 			"A unique value for each entry in the http acceleration
			 stats table"
 	::= { ncHttpAccelEntry 1 }

	ncHttpAccelKbytesFromClient     OBJECT-TYPE
	SYNTAX                          Counter32
        MAX-ACCESS                      read-only
        STATUS                          current
 	DESCRIPTION
 			"The total number of kilobytes received from the client
 			for this acceleration rule"
 	::= { ncHttpAccelEntry 2 }

 	ncHttpAccelKbytesToClient       OBJECT-TYPE
	SYNTAX                          Counter32
        MAX-ACCESS                      read-only
        STATUS                          current
 	DESCRIPTION
			"The total number of kilobytes sent to the client for
 			this acceleration rule"
	::= { ncHttpAccelEntry 3 }

	ncHttpAccelHits                 OBJECT-TYPE
	SYNTAX                          Counter32
        MAX-ACCESS                      read-only
        STATUS                          current
	DESCRIPTION
			" The number of times this acceleration rule has been hit"
	::= { ncHttpAccelEntry 4 }

	ncHttpsAccelTable               OBJECT-TYPE
	SYNTAX                          SEQUENCE OF NcHttpsAccelEntry
        MAX-ACCESS                      not-accessible
        STATUS                          current
 	DESCRIPTION
			"Number of kilobytes sent to and received from the client side
 			per acceleration rule"

	::= { ncHttp 38 }

	ncHttpsAccelEntry               OBJECT-TYPE
	SYNTAX                          NcHttpsAccelEntry
        MAX-ACCESS                      not-accessible
        STATUS                          current
	DESCRIPTION
			"Each entry contains the number of kilobytes sent and
			 received to/from the clients side per acceleration
				rule"

	INDEX	 { ncHttpsAccelIndex }
 	::= { ncHttpsAccelTable 1 }

	NcHttpsAccelEntry ::=
	SEQUENCE {
		ncHttpsAccelIndex		Integer32,
		ncHttpsAccelKbytesFromClient	Counter32,
 		ncHttpsAccelKbytesToClient	Counter32,
		ncHttpsAccelHits	Counter32
		}

	ncHttpsAccelIndex               OBJECT-TYPE
	SYNTAX                          Integer32 (1..513)
        MAX-ACCESS                      read-only
        STATUS                          current
 	DESCRIPTION
 			"A unique value for each entry in the http acceleration
			 stats table"
	::= { ncHttpsAccelEntry 1 }

 	ncHttpsAccelKbytesFromClient    OBJECT-TYPE
	SYNTAX                          Counter32
        MAX-ACCESS                      read-only
        STATUS                          current
 	DESCRIPTION
			"The total number of kilobytes received from the client
			 for this acceleration rule"
	::= { ncHttpsAccelEntry 2 }

	ncHttpsAccelKbytesToClient      OBJECT-TYPE
	SYNTAX                          Counter32
        MAX-ACCESS                      read-only
        STATUS                          current
	DESCRIPTION
 			"The total number of kilobytes sent to the client for
			 this acceleration rule"
	::= { ncHttpsAccelEntry 3 }

 	ncHttpsAccelHits                OBJECT-TYPE
	SYNTAX                          Counter32
        MAX-ACCESS                      read-only
        STATUS                          current
 	DESCRIPTION
 			" The number of times this acceleration rule has been hit"
	::= { ncHttpsAccelEntry 4 }


	ncNntp		OBJECT IDENTIFIER ::= { ncStats 7 }

	-- -- -- -- -- -- -- -- -- -- -- -- -- -- -- -- -- --
	-- the nntp stats group
	-- -- -- -- -- -- -- -- -- -- -- -- -- -- -- -- -- --

 	ncNntpTotalRequests             OBJECT-TYPE
	SYNTAX                          Counter32
        MAX-ACCESS                      read-only
        STATUS                          current
	DESCRIPTION
			"NNTP total requests so far"
	::= { ncNntp 1 }
 	ncNntpCacheableRequests         OBJECT-TYPE
	SYNTAX                          Counter32
        MAX-ACCESS                      read-only
        STATUS                          current
	DESCRIPTION
			"NNTP requests that were cacheable"
	::= { ncNntp 2 }

 	ncNntpProxyRequests             OBJECT-TYPE
	SYNTAX                          Counter32
        MAX-ACCESS                      read-only
        STATUS                          current
	DESCRIPTION
			"NNTP requests that were non-cacheable"
	::= { ncNntp 3 }

 	ncNntpServConns                 OBJECT-TYPE
	SYNTAX                          Integer32
        MAX-ACCESS                      read-only
        STATUS                          current
	DESCRIPTION
			"Number of currently open TCP/IP connections to NNTP servers (active and idle)"
	::= { ncNntp 4 }

 	ncNntpCliConns                  OBJECT-TYPE
	SYNTAX                          Integer32
        MAX-ACCESS                      read-only
        STATUS                          current
	DESCRIPTION
			"Number of currently open TCP/IP connections to NNTP clients (active and idle)"
	::= { ncNntp 5 }

 	ncNntpBWSavings                 OBJECT-TYPE
	SYNTAX                          Integer32
        MAX-ACCESS                      read-only
        STATUS                          current
	DESCRIPTION
			"Bandwidth savings for NNTP requests"
	::= { ncNntp 6 }

 	ncNntpRespTimePerByte           OBJECT-TYPE
	SYNTAX                          Integer32
        MAX-ACCESS                      read-only
        STATUS                          current
	DESCRIPTION
			"Response time per byte for NNTP requests"
	::= { ncNntp 7 }

	ncNntpBytesToClients            OBJECT-TYPE
	SYNTAX                          Counter32
        MAX-ACCESS                      read-only
        STATUS                          current
	DESCRIPTION
				"Total NNTP bytes sent to clients"
	::= { ncNntp 8 }

	ncNntpBytesFromClients          OBJECT-TYPE
	SYNTAX                          Counter32
        MAX-ACCESS                      read-only
        STATUS                          current
	DESCRIPTION
				"Total NNTP bytes received from clients"
	::= { ncNntp 9 }

	ncNntpBytesToServers            OBJECT-TYPE
	SYNTAX                          Counter32
        MAX-ACCESS                      read-only
        STATUS                          current
	DESCRIPTION
				"Total NNTP bytes sent to servers"
	::= { ncNntp 10 }

	ncNntpBytesFromServers          OBJECT-TYPE
	SYNTAX                          Counter32
        MAX-ACCESS                      read-only
        STATUS                          current
	DESCRIPTION
				"Total NNTP bytes received from servers"
	::= { ncNntp 11 }

 	ncNntpObjHitrate                OBJECT-TYPE
	SYNTAX                          Integer32
        MAX-ACCESS                      read-only
        STATUS                          current
	DESCRIPTION
			"Object Hitrate of NNTP requests"
	::= { ncNntp 12 }

 	ncNntpActiveServConns           OBJECT-TYPE
	SYNTAX                          Integer32
        MAX-ACCESS                      read-only
        STATUS                          current
	DESCRIPTION
			"Number of currently active TCP/IP connections to NNTP servers"
	::= { ncNntp 13 }

 	ncNntpActiveCliConns            OBJECT-TYPE
	SYNTAX                          Integer32
        MAX-ACCESS                      read-only
        STATUS                          current
	DESCRIPTION
			"Number of currently active TCP/IP connections to NNTP clients"
	::= { ncNntp 14 }

	ncFtp		OBJECT IDENTIFIER ::= { ncStats 8 }

	-- -- -- -- -- -- -- -- -- -- -- -- -- -- -- -- -- --
	-- the ftp stats group
	-- -- -- -- -- -- -- -- -- -- -- -- -- -- -- -- -- --

 	ncFtpTotalRequests              OBJECT-TYPE
	SYNTAX                          Counter32
        MAX-ACCESS                      read-only
        STATUS                          current
	DESCRIPTION
			"FTP total requests so far"
	::= { ncFtp 1 }

 	ncFtpHitRequests                OBJECT-TYPE
	SYNTAX                          Counter32
        MAX-ACCESS                      read-only
        STATUS                          current
	DESCRIPTION
			"FTP requests that resulted in hits so far"
	::= { ncFtp 2 }

 	ncFtpMissRequests               OBJECT-TYPE
	SYNTAX                          Counter32
        MAX-ACCESS                      read-only
        STATUS                          current
	DESCRIPTION
			"FTP requests that resulted in misses so far"
	::= { ncFtp 3 }

 	ncFtpServConns                  OBJECT-TYPE
	SYNTAX                          Integer32
        MAX-ACCESS                      read-only
        STATUS                          current
	DESCRIPTION
			"Number of currently open TCP/IP connections to FTP servers (active and idle)"
	::= { ncFtp 4 }

 	ncFtpCliConns                   OBJECT-TYPE
	SYNTAX                          Integer32
        MAX-ACCESS                      read-only
        STATUS                          current
	DESCRIPTION
			"Number of currently open TCP/IP connections to FTP clients (active and idle)"
	::= { ncFtp 5 }

 	ncFtpBWSavings                  OBJECT-TYPE
	SYNTAX                          Integer32
        MAX-ACCESS                      read-only
        STATUS                          current
	DESCRIPTION
			"Bandwidth savings for FTP requests"
	::= { ncFtp 6 }

 	ncFtpRespTimePerByte            OBJECT-TYPE
	SYNTAX                          Integer32
        MAX-ACCESS                      read-only
        STATUS                          current
	DESCRIPTION
			"Response time per byte for FTP requests"
	::= { ncFtp 7 }

	ncFtpBytesToClients             OBJECT-TYPE
	SYNTAX                          Counter32
        MAX-ACCESS                      read-only
        STATUS                          current
	DESCRIPTION
				"Total FTP bytes sent to clients"
	::= { ncFtp 8 }

	ncFtpBytesFromClients           OBJECT-TYPE
	SYNTAX                          Counter32
        MAX-ACCESS                      read-only
        STATUS                          current
	DESCRIPTION
				"Total FTP bytes received from clients"
	::= { ncFtp 9 }

	ncFtpBytesToServers             OBJECT-TYPE
	SYNTAX                          Counter32
        MAX-ACCESS                      read-only
        STATUS                          current
	DESCRIPTION
				"Total FTP bytes sent to servers"
	::= { ncFtp 10 }

	ncFtpBytesFromServers           OBJECT-TYPE
	SYNTAX                          Counter32
        MAX-ACCESS                      read-only
        STATUS                          current
	DESCRIPTION
				"Total FTP bytes received from servers"
	::= { ncFtp 11 }

 	ncFtpObjHitrate                 OBJECT-TYPE
	SYNTAX                          Integer32
        MAX-ACCESS                      read-only
        STATUS                          current
	DESCRIPTION
			"Object Hitrate of FTP requests"
	::= { ncFtp 12 }

 	ncFtpActiveServConns            OBJECT-TYPE
	SYNTAX                          Integer32
        MAX-ACCESS                      read-only
        STATUS                          current
	DESCRIPTION
			"Number of currently active TCP/IP connections to FTP servers"
	::= { ncFtp 13 }

 	ncFtpActiveCliConns             OBJECT-TYPE
	SYNTAX                          Integer32
        MAX-ACCESS                      read-only
        STATUS                          current
	DESCRIPTION
			"Number of currently active TCP/IP connections to FTP clients"
	::= { ncFtp 14 }

	ncStreaming	OBJECT IDENTIFIER ::= { ncStats 9 }

	-- -- -- -- -- -- -- -- -- -- -- -- -- -- -- -- -- --
	-- the streaming stats group
	-- -- -- -- -- -- -- -- -- -- -- -- -- -- -- -- -- --

 	ncStreamingServConns            OBJECT-TYPE
	SYNTAX                          Integer32
        MAX-ACCESS                      read-only
        STATUS                          current
	DESCRIPTION
			"Number of currently open TCP/IP connections to streaming servers (active and idle)"
	::= { ncStreaming 1 }

 	ncStreamingCliConns             OBJECT-TYPE
	SYNTAX                          Integer32
        MAX-ACCESS                      read-only
        STATUS                          current
	DESCRIPTION
			"Number of currently open TCP/IP connections to streaming clients (active and idle)"
	::= { ncStreaming 2 }

 	ncStreamingBWSavings            OBJECT-TYPE
	SYNTAX                          Integer32
        MAX-ACCESS                      read-only
        STATUS                          current
	DESCRIPTION
			"Bandwidth savings for all streaming requests"
	::= { ncStreaming 3 }

 	ncStreamingRespTimePerByte      OBJECT-TYPE
	SYNTAX                          Integer32
        MAX-ACCESS                      read-only
        STATUS                          current
	DESCRIPTION
			"Response time per byte for all streaming requests"
	::= { ncStreaming 4 }

 	ncStreamingHitRequests          OBJECT-TYPE
	SYNTAX                          Counter32
        MAX-ACCESS                      read-only
        STATUS                          current
	DESCRIPTION
			"STREAMING requests that resulted in hits so far"
	::= { ncStreaming 5 }

 	ncStreamingMissRequests         OBJECT-TYPE
	SYNTAX                          Counter32
        MAX-ACCESS                      read-only
        STATUS                          current
	DESCRIPTION
			"STREAMING requests that resulted in misses so far"
	::= { ncStreaming 6 }

 	ncStreamingTotalRequests        OBJECT-TYPE
	SYNTAX                          Counter32
        MAX-ACCESS                      read-only
        STATUS                          current
	DESCRIPTION
			"STREAMING total requests so far"
	::= { ncStreaming 7 }

	ncStreamingLiveBytesToClients   OBJECT-TYPE
	SYNTAX                          Counter32
        MAX-ACCESS                      read-only
        STATUS                          current
	DESCRIPTION
			"Total Streaming Live bytes sent to clients"
	::= { ncStreaming 8 }

	ncStreamingLiveBytesFromClients OBJECT-TYPE
	SYNTAX                          Counter32
        MAX-ACCESS                      read-only
        STATUS                          current
	DESCRIPTION
			"Total Streaming Live bytes received from clients"
	::= { ncStreaming 9 }

	ncStreamingLiveBytesToServers   OBJECT-TYPE
	SYNTAX                          Counter32
        MAX-ACCESS                      read-only
        STATUS                          current
	DESCRIPTION
			"Total Streaming Live bytes sent to servers"
	::= { ncStreaming 10 }

	ncStreamingLiveBytesFromServers OBJECT-TYPE
	SYNTAX                          Counter32
        MAX-ACCESS                      read-only
        STATUS                          current
	DESCRIPTION
			"Total Streaming Live bytes received from servers"
	::= { ncStreaming 11 }

	ncStreamingProxyBytesToClients  OBJECT-TYPE
	SYNTAX                          Counter32
        MAX-ACCESS                      read-only
        STATUS                          current
	DESCRIPTION
			"Total Streaming Proxy bytes sent to clients"
	::= { ncStreaming 12 }

	ncStreamingProxyBytesFromClients OBJECT-TYPE
	SYNTAX                          Counter32
        MAX-ACCESS                      read-only
        STATUS                          current
	DESCRIPTION
			"Total Streaming Proxy bytes received from clients"
	::= { ncStreaming 13 }

	ncStreamingProxyBytesToServers  OBJECT-TYPE
	SYNTAX                          Counter32
        MAX-ACCESS                      read-only
        STATUS                          current
	DESCRIPTION
			"Total Streaming Proxy bytes sent to servers"
	::= { ncStreaming 14 }

	ncStreamingProxyBytesFromServers OBJECT-TYPE
	SYNTAX                          Counter32
        MAX-ACCESS                      read-only
        STATUS                          current
	DESCRIPTION
			"Total Streaming Proxy bytes received from servers"
	::= { ncStreaming 15 }

	ncStreamingOBTClients           OBJECT-TYPE
	SYNTAX                          Counter32
        MAX-ACCESS                      read-only
        STATUS                          current
	DESCRIPTION
			"Total Streaming Ondemand bytes sent to clients"
	::= { ncStreaming 16 }

	ncStreamingOBFClients           OBJECT-TYPE
	SYNTAX                          Counter32
        MAX-ACCESS                      read-only
        STATUS                          current
	DESCRIPTION
			"Total Streaming Ondemand bytes received from clients"
	::= { ncStreaming 17 }

	ncStreamingOBTServers           OBJECT-TYPE
	SYNTAX                          Counter32
        MAX-ACCESS                      read-only
        STATUS                          current
	DESCRIPTION
			"Total Streaming Ondemand bytes sent to servers"
	::= { ncStreaming 18 }

	ncStreamingOBFServers           OBJECT-TYPE
	SYNTAX                          Counter32
        MAX-ACCESS                      read-only
        STATUS                          current
	DESCRIPTION
			"Total Streaming Ondemand bytes received from servers"
	::= { ncStreaming 19 }

 	ncStreamingObjHitrate           OBJECT-TYPE
	SYNTAX                          Integer32
        MAX-ACCESS                      read-only
        STATUS                          current
	DESCRIPTION
			"Object Hitrate of Streaming requests"
	::= { ncStreaming 20 }

	ncStreamingRealBytesToClients   OBJECT-TYPE
	SYNTAX                          Counter32
        MAX-ACCESS                      read-only
        STATUS                          current
	DESCRIPTION
			"Total Streaming Real bytes sent to clients"
	::= { ncStreaming 21 }

	ncStreamingRealBytesFromClients OBJECT-TYPE
	SYNTAX                          Counter32
        MAX-ACCESS                      read-only
        STATUS                          current
	DESCRIPTION
			"Total Streaming Real bytes received from clients"
	::= { ncStreaming 22 }

	ncStreamingRealBytesToServers   OBJECT-TYPE
	SYNTAX                          Counter32
        MAX-ACCESS                      read-only
        STATUS                          current
	DESCRIPTION
			"Total Streaming Real bytes sent to servers"
	::= { ncStreaming 23 }

	ncStreamingRealBytesFromServers OBJECT-TYPE
	SYNTAX                          Counter32
        MAX-ACCESS                      read-only
        STATUS                          current
	DESCRIPTION
			"Total Streaming Real bytes received from servers"
	::= { ncStreaming 24 }

	ncStreamingMmsBytesToClients    OBJECT-TYPE
	SYNTAX                          Counter32
        MAX-ACCESS                      read-only
        STATUS                          current
	DESCRIPTION
			"Total Streaming Mms bytes sent to clients"
	::= { ncStreaming 25 }

	ncStreamingMmsBytesFromClients  OBJECT-TYPE
	SYNTAX                          Counter32
        MAX-ACCESS                      read-only
        STATUS                          current
	DESCRIPTION
			"Total Streaming Mms bytes received from clients"
	::= { ncStreaming 26 }

	ncStreamingMmsBytesToServers    OBJECT-TYPE
	SYNTAX                          Counter32
        MAX-ACCESS                      read-only
        STATUS                          current
	DESCRIPTION
			"Total Streaming Mms bytes sent to servers"
	::= { ncStreaming 27 }

	ncStreamingMmsBytesFromServers  OBJECT-TYPE
	SYNTAX                          Counter32
        MAX-ACCESS                      read-only
        STATUS                          current
	DESCRIPTION
			"Total Streaming Mms bytes received from servers"
	::= { ncStreaming 28 }

	ncStreamingQTBTClients          OBJECT-TYPE
	SYNTAX                          Counter32
        MAX-ACCESS                      read-only
        STATUS                          current
	DESCRIPTION
			"Total Streaming QuickTime bytes sent to clients"
	::= { ncStreaming 29 }

	ncStreamingQTBFClients          OBJECT-TYPE
	SYNTAX                          Counter32
        MAX-ACCESS                      read-only
        STATUS                          current
	DESCRIPTION
			"Total Streaming QuickTime bytes received from clients"
	::= { ncStreaming 30 }

	ncStreamingQTBTServers          OBJECT-TYPE
	SYNTAX                          Counter32
        MAX-ACCESS                      read-only
        STATUS                          current
	DESCRIPTION
			"Total Streaming QuickTime bytes sent to servers"
	::= { ncStreaming 31 }

	ncStreamingQTBFServers          OBJECT-TYPE
	SYNTAX                          Counter32
        MAX-ACCESS                      read-only
        STATUS                          current
	DESCRIPTION
			"Total Streaming QuickTime bytes received from servers"
	::= { ncStreaming 32 }

 	ncStreamingLiveBWSavings        OBJECT-TYPE
	SYNTAX                          Integer32
        MAX-ACCESS                      read-only
        STATUS                          current
	DESCRIPTION
			"Bandwidth savings for all Live streaming requests"
	::= { ncStreaming 33 }

 	ncStreamingOndemandBWSavings    OBJECT-TYPE
	SYNTAX                          Integer32
        MAX-ACCESS                      read-only
        STATUS                          current
	DESCRIPTION
			"Bandwidth savings for all VOD streaming requests"
	::= { ncStreaming 34 }

 	ncStreamingRealBWSavings        OBJECT-TYPE
	SYNTAX                          Integer32
        MAX-ACCESS                      read-only
        STATUS                          current
	DESCRIPTION
			"Bandwidth savings for all Real streaming requests"
	::= { ncStreaming 35 }

 	ncStreamingMmsBWSavings         OBJECT-TYPE
	SYNTAX                          Integer32
        MAX-ACCESS                      read-only
        STATUS                          current
	DESCRIPTION
			"Bandwidth savings for all MMS streaming requests"
	::= { ncStreaming 36 }

 	ncStreamingQuickTimeBWSavings   OBJECT-TYPE
	SYNTAX                          Integer32
        MAX-ACCESS                      read-only
        STATUS                          current
	DESCRIPTION
			"Bandwidth savings for all QuickTime streaming requests"
	::= { ncStreaming 37 }

 	ncStreamingActiveServConns      OBJECT-TYPE
	SYNTAX                          Integer32
        MAX-ACCESS                      read-only
        STATUS                          current
	DESCRIPTION
			"Number of currently active TCP/IP connections to streaming servers"
	::= { ncStreaming 38 }

 	ncStreamingActiveCliConns       OBJECT-TYPE
	SYNTAX                          Integer32
        MAX-ACCESS                      read-only
        STATUS                          current
	DESCRIPTION
			"Number of currently active TCP/IP connections to streaming clients"
	::= { ncStreaming 39 }

	ncStreamingRtspWMBytesToClients OBJECT-TYPE
	SYNTAX                          Counter32
        MAX-ACCESS                      read-only
        STATUS                          current
	DESCRIPTION
			"Total Streaming Windows Media RTSP bytes sent to clients"
	::= { ncStreaming 40 }

	ncStreamingRtspWMBFClients      OBJECT-TYPE
	SYNTAX                          Counter32
        MAX-ACCESS                      read-only
        STATUS                          current
	DESCRIPTION
			"Total Streaming Windows Media RTSP bytes received from clients"
	::= { ncStreaming 41 }

	ncStreamingRtspWMBytesToServers OBJECT-TYPE
	SYNTAX                          Counter32
        MAX-ACCESS                      read-only
        STATUS                          current
	DESCRIPTION
			"Total Streaming Windows Media RTSP bytes sent to servers"
	::= { ncStreaming 42 }

	ncStreamingRtspWMBFServers      OBJECT-TYPE
	SYNTAX                          Counter32
        MAX-ACCESS                      read-only
        STATUS                          current
	DESCRIPTION
			"Total Streaming Windows Media RTSP bytes received from servers"
	::= { ncStreaming 43 }

	ncStreamingRtspWMBWSavings      OBJECT-TYPE
	SYNTAX                          Integer32
        MAX-ACCESS                      read-only
        STATUS                          current
	DESCRIPTION
			"Bandwidth savings for all Windows Media RTSP streaming requests"
	::= { ncStreaming 44 }

	ncStreamingAccelTable           OBJECT-TYPE
	SYNTAX                          SEQUENCE OF NcStreamingAccelEntry
        MAX-ACCESS                      not-accessible
        STATUS                          current
 	DESCRIPTION
			 "Number of kilobytes sent to and received from the
			 client side per acceleration rule"

 	::= { ncStreaming 45 }

 	ncStreamingAccelEntry           OBJECT-TYPE
	SYNTAX                          NcStreamingAccelEntry
        MAX-ACCESS                      not-accessible
        STATUS                          current
	DESCRIPTION
 			"Each entry contains the number of kilobytes sent and
			 received to/from the clients side per acceleration
			 rule"

 	INDEX	{ ncStreamingAccelIndex }
 	::= { ncStreamingAccelTable 1 }

	NcStreamingAccelEntry ::=
 	SEQUENCE {
 		ncStreamingAccelIndex			Integer32,
 		ncStreamingAccelKbytesFromClient	Counter32,
 		ncStreamingAccelKbytesToClient		Counter32,
 		ncStreamingAccelHits			Counter32
	}

	ncStreamingAccelIndex           OBJECT-TYPE
	SYNTAX                          Integer32 (1..513)
        MAX-ACCESS                      read-only
        STATUS                          current
	DESCRIPTION
			"A unique value for each entry in the streaming
			 acceleration  stats table"
 	::= { ncStreamingAccelEntry 1 }

 	ncStreamingAccelKbytesFromClient OBJECT-TYPE
	SYNTAX                          Counter32
        MAX-ACCESS                      read-only
        STATUS                          current
	DESCRIPTION
			"The total number of kilobytes received from the client
			 for this acceleration rule"
	::= { ncStreamingAccelEntry 2 }

	ncStreamingAccelKbytesToClient  OBJECT-TYPE
	SYNTAX                          Counter32
        MAX-ACCESS                      read-only
        STATUS                          current
	DESCRIPTION
			"The total number of kilobytes sent to the client for
			 this acceleration rule"
	::= { ncStreamingAccelEntry 3 }

	ncStreamingAccelHits            OBJECT-TYPE
	SYNTAX                          Counter32
        MAX-ACCESS                      read-only
        STATUS                          current
 	DESCRIPTION
 			" The number of times this acceleration rule has
				been hit"
 	::= { ncStreamingAccelEntry 4 }

	ncStreamingClientsDelayedSW     OBJECT-TYPE
	SYNTAX                          Counter32
        MAX-ACCESS                      read-only
        STATUS                          current
	DESCRIPTION
			"Number of clients delayed because of a Bandwidth Limit"
	::= { ncStreaming 46 }

	ncTotalBWSavings                OBJECT-TYPE
	SYNTAX                          Integer32
        MAX-ACCESS                      read-only
        STATUS                          current
	DESCRIPTION
			"Total Bandwidth savings for HTTP, FTP, NNTP, and Streaming protocols"
	::= { ncStats 10 }

	ncDns		OBJECT IDENTIFIER ::= { ncStats 11 }

	-- -- -- -- -- -- -- -- -- -- -- -- -- -- -- -- -- --
	-- the netcache dns stats group
	-- -- -- -- -- -- -- -- -- -- -- -- -- -- -- -- -- --

	ncDnsRequestsReceived           OBJECT-TYPE
	SYNTAX                          Counter32
        MAX-ACCESS                      read-only
        STATUS                          current
	DESCRIPTION
			"Total DNS requests received from clients"
	::= { ncDns 1 }

	ncDnsCacheHits                  OBJECT-TYPE
	SYNTAX                          Counter32
        MAX-ACCESS                      read-only
        STATUS                          current
	DESCRIPTION
			"Hits on the DNS cache.  This includes hits
			for DNS lookups generated by NetCache internally"
	::= { ncDns 2 }

	ncDnsCacheMisses                OBJECT-TYPE
	SYNTAX                          Counter32
        MAX-ACCESS                      read-only
        STATUS                          current
	DESCRIPTION
			"Misses on the DNS cache.  This includes misses
			for DNS lookups generated by NetCache internally"
	::= { ncDns 3 }

	ncDnsSuccessfulForwardLookups   OBJECT-TYPE
	SYNTAX                          Counter32
        MAX-ACCESS                      read-only
        STATUS                          current
	DESCRIPTION
			"Forward DNS lookups that are successful"
	::= { ncDns 4 }

	ncDnsFailedForwardLookups       OBJECT-TYPE
	SYNTAX                          Counter32
        MAX-ACCESS                      read-only
        STATUS                          current
	DESCRIPTION
			"Forward DNS lookups that failed"
	::= { ncDns 5 }

	ncDnsPendingForwardLookups      OBJECT-TYPE
	SYNTAX                          Integer32
        MAX-ACCESS                      read-only
        STATUS                          current
	DESCRIPTION
			"Forward DNS lookups that are in progress"
	::= { ncDns 6 }

	ncDnsSuccessfulReverseLookups   OBJECT-TYPE
	SYNTAX                          Counter32
        MAX-ACCESS                      read-only
        STATUS                          current
	DESCRIPTION
			"Reverse DNS lookups that are successful"
	::= { ncDns 7 }

	ncDnsFailedReverseLookups       OBJECT-TYPE
	SYNTAX                          Counter32
        MAX-ACCESS                      read-only
        STATUS                          current
	DESCRIPTION
			"Reverse DNS lookups that failed"
	::= { ncDns 8 }

	ncDnsPendingReverseLookups      OBJECT-TYPE
	SYNTAX                          Integer32
        MAX-ACCESS                      read-only
        STATUS                          current
	DESCRIPTION
			"Reverse DNS lookups that are in progress"
	::= { ncDns 9 }

	ncDnsIres	OBJECT IDENTIFIER ::= { ncDns 10 }

	-- -- -- -- -- -- -- -- -- -- -- -- -- -- -- -- -- --
	-- the netcache dns ires stats group
	-- -- -- -- -- -- -- -- -- -- -- -- -- -- -- -- -- --


	ncDnsIresIsEnabled              OBJECT-TYPE
	SYNTAX                          INTEGER {
                                             false(1),
                                             true(2)
                                        }
        MAX-ACCESS                      read-only
        STATUS                          current
	DESCRIPTION
			"Has Full Service Resolver been enabled"
	::= { ncDnsIres 1 }

	ncDnsIresIsInitialised          OBJECT-TYPE
	SYNTAX                          INTEGER {
                                             false(1),
                                             true(2)
                                        }
        MAX-ACCESS                      read-only
        STATUS                          current
	DESCRIPTION
			"Has Full Service Resolver initialized"
	::= { ncDnsIres 2 }

	ncDnsIresForwardLookups         OBJECT-TYPE
	SYNTAX                          Counter32
        MAX-ACCESS                      read-only
        STATUS                          current
	DESCRIPTION
			"Full Service Resolver's Forward Lookups"
	::= { ncDnsIres 3 }

	ncDnsIresPendingForwardLookups  OBJECT-TYPE
	SYNTAX                          Counter32
        MAX-ACCESS                      read-only
        STATUS                          current
	DESCRIPTION
			"Full Service Resolver's Pending Forward Lookups"
	::= { ncDnsIres 4 }

	ncDnsIresReverseLookups         OBJECT-TYPE
	SYNTAX                          Counter32
        MAX-ACCESS                      read-only
        STATUS                          current
	DESCRIPTION
			"Full Service Resolver's Reverse Lookups"
	::= { ncDnsIres 5 }

	ncDnsIresPendingReverseLookups  OBJECT-TYPE
	SYNTAX                          Counter32
        MAX-ACCESS                      read-only
        STATUS                          current
	DESCRIPTION
			"Full Service Resolver's Pending Reverse Lookups"
	::= { ncDnsIres 6 }


	ncAuth		OBJECT IDENTIFIER ::= { ncStats 12 }

	-- -- -- -- -- -- -- -- -- -- -- -- -- -- -- -- -- --
	-- the netcache authentication stats group
	-- -- -- -- -- -- -- -- -- -- -- -- -- -- -- -- -- --

	ncNtlm		OBJECT IDENTIFIER ::= { ncAuth 1 }

	-- -- -- -- -- -- -- -- -- -- -- -- -- -- -- -- -- --
	-- the netcache ntlm stats group
	-- -- -- -- -- -- -- -- -- -- -- -- -- -- -- -- -- --

 	ncNtlmPossibleProblem           OBJECT-TYPE
	SYNTAX                          INTEGER {
                                             false(1),
                                             true(2)
                                        }
        MAX-ACCESS                      read-only
        STATUS                          current
	DESCRIPTION
			"Whether a possible ntlm problem is detected
			in the appliance's domain environment."
	::= { ncNtlm 1 }


	ncRM		OBJECT IDENTIFIER ::= { ncStats 13 }

	-- -- -- -- -- -- -- -- -- -- -- -- -- -- -- -- -- --
	-- the netcache resource management group
	-- -- -- -- -- -- -- -- -- -- -- -- -- -- -- -- -- --

	ncRMMem		OBJECT IDENTIFIER ::= { ncRM 1 }

	-- -- -- -- -- -- -- -- -- -- -- -- -- -- -- -- -- --
	-- the netcache memory stats group
	-- -- -- -- -- -- -- -- -- -- -- -- -- -- -- -- -- --
	ncRMMemTotal                    OBJECT-TYPE
	SYNTAX                          Integer32
        MAX-ACCESS                      read-only
        STATUS                          current
	DESCRIPTION
	                "Total memory in kilobytes available for
					allocations after boot. It does not imply
					the total system memory."
	::= { ncRMMem 1 }

	ncRMMemFree                     OBJECT-TYPE
	SYNTAX                          Integer32
        MAX-ACCESS                      read-only
        STATUS                          current
	DESCRIPTION
	                "Current free memory in kilobytes available
					for allocations."
	::= { ncRMMem 2 }

	-- -- -- -- -- -- -- -- --
	-- the snapmirror group --
	-- -- -- -- -- -- -- -- --

        snapmirrorOn                    OBJECT-TYPE
	SYNTAX                          INTEGER {
	                                     off(1),
					     on(2)
					}
        MAX-ACCESS                      read-only
        STATUS                          current
	DESCRIPTION
			"Indicates whether snapmirror has been turned on
			or not."
	::= { snapmirror 1 }

	-- the old active snapmirror destination count, new name is
	-- snapmirrorActiveDstNumber.  DEPRECATED
	snapmirrorActiveRestoreCount    OBJECT-TYPE
	SYNTAX                          Integer32
        MAX-ACCESS                      read-only
        STATUS                          current
	DESCRIPTION
			"Number of active SnapMirror restores."

	::= { snapmirror 2 }

	-- the old active snapmirror destination count, new name is
	-- snapmirrorActiveDstNumber.  DEPRECATED
	snapmirrorScheduledRestoreCount OBJECT-TYPE
	SYNTAX                          Integer32
        MAX-ACCESS                      read-only
        STATUS                          current
	DESCRIPTION
			"Number of scheduled SnapMirror restores."

	::= { snapmirror 3 }

	-- the old active snapmirror destination count, new name is
	-- snapmirrorActiveDstNumber.  DEPRECATED
	snapmirrorBackupNumber          OBJECT-TYPE
	SYNTAX                          Integer32
        MAX-ACCESS                      read-only
        STATUS                          current
	DESCRIPTION
			"Number of active SnapMirror backups."

	::= { snapmirror 4 }

	-- the old active snapmirror destination count, new name is
	-- snapmirrorActiveDstNumber.  DEPRECATED
	snapmirrorBackupSuccesses       OBJECT-TYPE
	SYNTAX                          Counter32
        MAX-ACCESS                      read-only
        STATUS                          current
	DESCRIPTION
			"Number of SnapMirror backups which completed.
			Reset on reboot."

	::= { snapmirror 5 }

	-- the old active snapmirror destination count, new name is
	-- snapmirrorActiveDstNumber.  DEPRECATED
	snapmirrorRestoreSuccesses      OBJECT-TYPE
	SYNTAX                          Counter32
        MAX-ACCESS                      read-only
        STATUS                          current
	DESCRIPTION
			"Number of SnapMirror restores which completed.
			Reset on reboot."

	::= { snapmirror 6 }

	-- the old active snapmirror destination count, new name is
	-- snapmirrorActiveDstNumber.  DEPRECATED
	snapmirrorBackupAborts          OBJECT-TYPE
	SYNTAX                          Counter32
        MAX-ACCESS                      read-only
        STATUS                          current
	DESCRIPTION
			"Number of SnapMirror backup transfers which have
			aborted. Reset on reboot."

	::= { snapmirror 7 }

	-- the old active snapmirror destination count, new name is
	-- snapmirrorActiveDstNumber.  DEPRECATED
	snapmirrorRestoreRestartAborts  OBJECT-TYPE
	SYNTAX                          Counter32
        MAX-ACCESS                      read-only
        STATUS                          current
	DESCRIPTION
			"Number of SnapMirror restore temporary aborts.
			Reset on reboot."

	::= { snapmirror 8 }

	-- the old active snapmirror destination count, new name is
	-- snapmirrorActiveDstNumber.  DEPRECATED
	snapmirrorRestoreWaitAborts     OBJECT-TYPE
	SYNTAX                          Counter32
        MAX-ACCESS                      read-only
        STATUS                          current
	DESCRIPTION
			"Number of SnapMirror restore permanent aborts.
			Reset on reboot."

	::= { snapmirror 9 }

	-- the old active snapmirror destination count, new name is
	-- snapmirrorActiveDstNumber.  DEPRECATED
	snapmirrorWrittenBytes          OBJECT-TYPE
	SYNTAX                          Counter32
        MAX-ACCESS                      read-only
        STATUS                          current
	DESCRIPTION
			"Number of Megabytes written by SnapMirror.
			Reset on reboot."

	::= { snapmirror 10 }

	-- the old active snapmirror destination count, new name is
	-- snapmirrorActiveDstNumber.  DEPRECATED
	snapmirrorReadBytes             OBJECT-TYPE
	SYNTAX                          Counter32
        MAX-ACCESS                      read-only
        STATUS                          current
	DESCRIPTION
			"Number of Megabytes read by SnapMirror.
			Reset on reboot."

	::= { snapmirror 11 }

	snapmirrorActiveDstNumber       OBJECT-TYPE
	SYNTAX                          Integer32
        MAX-ACCESS                      read-only
        STATUS                          current
	DESCRIPTION
			"Number of active SnapMirror destination."

	::= { snapmirror 12 }

	snapmirrorActiveSrcNumber       OBJECT-TYPE
	SYNTAX                          Integer32
        MAX-ACCESS                      read-only
        STATUS                          current
	DESCRIPTION
			"Number of active SnapMirror Source."

	::= { snapmirror 13 }

	snapmirrorFilerTotalDstSuccesses OBJECT-TYPE
	SYNTAX                          Counter32
        MAX-ACCESS                      read-only
        STATUS                          current
	DESCRIPTION
			"Total number of successful snapmirror transfers to
			the destination. Persistent across reboot."

	::= { snapmirror 14 }

	snapmirrorFilerTotalSrcSuccesses OBJECT-TYPE
	SYNTAX                          Counter32
        MAX-ACCESS                      read-only
        STATUS                          current
	DESCRIPTION
			"Total number of successful snapmirror transfers
			from the source. Persistent across reboot."

	::= { snapmirror 15 }

	snapmirrorFilerTotalSrcFailures OBJECT-TYPE
	SYNTAX                          Counter32
        MAX-ACCESS                      read-only
        STATUS                          current
	DESCRIPTION
			"Total number of failed SnapMirror transfers on
			the source. Persistent across reboot."

	::= { snapmirror 16 }

	snapmirrorFilerTotalDstFailures OBJECT-TYPE
	SYNTAX                          Counter32
        MAX-ACCESS                      read-only
        STATUS                          current
	DESCRIPTION
			"Total number of failed SnapMirror transfers on
			the destination. Persistent across reboot."

	::= { snapmirror 17 }

	snapmirrorFilerTotalDstDeferments OBJECT-TYPE
	SYNTAX                          Counter32
        MAX-ACCESS                      read-only
        STATUS                          current
	DESCRIPTION
			"Total number of deferred snapmirror transfer on
			the destination. Persistent across reboot."

	::= { snapmirror 18 }

	snapmirrorIsLicensed            OBJECT-TYPE
	SYNTAX                          INTEGER {
                                             false(1),
                                             true(2)
                                        }
        MAX-ACCESS                      read-only
        STATUS                          current
	DESCRIPTION
		"Whether the snapmirror is licensed on the filer."

	::= { snapmirror 19 }

	snapmirrorStatusTable           OBJECT-TYPE
	SYNTAX                          SEQUENCE OF SnapmirrorStatusEntry
        MAX-ACCESS                      not-accessible
        STATUS                          current
	DESCRIPTION
			"provide a list of snapmirror status."

	::= { snapmirror 20 }

	snapmirrorStatusEntry           OBJECT-TYPE
	SYNTAX                          SnapmirrorStatusEntry
        MAX-ACCESS                      not-accessible
        STATUS                          current
	DESCRIPTION
			"Provide a report of current status of snapmirror."

	INDEX	{ snapmirrorIndex }
	::= { snapmirrorStatusTable 1 }

	SnapmirrorStatusEntry ::=
	    SEQUENCE {
	    	snapmirrorIndex
			Integer32,
		snapmirrorSrc
			OCTET STRING,
		snapmirrorDst
			OCTET STRING,
		snapmirrorStatus
			INTEGER,
		snapmirrorState
			INTEGER,
		snapmirrorLag
			TimeTicks,
		snapmirrorTotalSuccesses
			Counter32,
		snapmirrorTotalRestartSuccesses
			Counter32,
		snapmirrorTotalFailures
			Counter32,
		snapmirrorTotalDeferments
			Counter32,
		snapmirrorTotalTransMBs
			Counter32,
		snapmirrorTotalTransTimeSeconds
			Counter32,
		snapmirrorThrottleValue
			Integer32,
		snapmirrorMirrorTimestamp
			DisplayString,
		snapmirrorBaseSnapshot
			DisplayString,
		snapmirrorLastTransType
			DisplayString,
		snapmirrorLastTransMBs
			Counter32,
		snapmirrorLastTransTimeSeconds
			Counter32,
		snapmirrorSchedule
			DisplayString,
		snapmirrorScheduleDesc
			DisplayString,
		snapmirrorArguments
			DisplayString,
		snapmirrorSyncToAsync
		        Counter32
	    }

	snapmirrorIndex                 OBJECT-TYPE
	SYNTAX                          Integer32 (1..2147483647)
        MAX-ACCESS                      read-only
        STATUS                          current
	DESCRIPTION
			"Index into the snapmirror status table."

	::= { snapmirrorStatusEntry 1 }

	snapmirrorSrc                   OBJECT-TYPE
	SYNTAX                          OCTET STRING
        MAX-ACCESS                      read-only
        STATUS                          current
	DESCRIPTION
			"Source of the snapmirror. <filer>:<vol> or
			<filer>:/vol/<qtree_name>"

	::= { snapmirrorStatusEntry 2 }

	snapmirrorDst                   OBJECT-TYPE
	SYNTAX                          OCTET STRING
        MAX-ACCESS                      read-only
        STATUS                          current
	DESCRIPTION
			"Destination of the snapmirror.
			<filer>:<vol> or <filer>:/vol/<qtree_name>"

	::= { snapmirrorStatusEntry 3 }

	snapmirrorStatus                OBJECT-TYPE
	SYNTAX                          INTEGER {
                                             idle(1),
                                             transferring(2),
					     pending(3),
					     aborting(4),
					     migrating(5),
					     quiescing(6),
					     resyncing(7),
					     waiting(8),
					     syncing(9),
                                             inSync(10)
                                        }
        MAX-ACCESS                      read-only
        STATUS                          current
	DESCRIPTION
			"Current transfer status of the snapmirror."

	::= { snapmirrorStatusEntry 4 }

	snapmirrorState                 OBJECT-TYPE
	SYNTAX                          INTEGER {
                                             uninitialized(1),
                                             snapmirrored(2),
					     brokenOff(3),
					     quiesced(4),
					     source(5),
                                             unknown(6)
                                        }
        MAX-ACCESS                      read-only
        STATUS                          current
	DESCRIPTION
			"Current state of the snapmirror."

	::= { snapmirrorStatusEntry 5 }

	snapmirrorLag                   OBJECT-TYPE
	SYNTAX                          TimeTicks
        MAX-ACCESS                      read-only
        STATUS                          current
	DESCRIPTION
			"How far behind from the source the destination is."

	::= { snapmirrorStatusEntry 6 }

	snapmirrorTotalSuccesses        OBJECT-TYPE
	SYNTAX                          Counter32
        MAX-ACCESS                      read-only
        STATUS                          current
	DESCRIPTION
		"Total number of successful transfer since the snapmirror
		is initialized. Persistent across reboot."

	::= { snapmirrorStatusEntry 7 }

	snapmirrorTotalRestartSuccesses OBJECT-TYPE
	SYNTAX                          Counter32
        MAX-ACCESS                      read-only
        STATUS                          current
	DESCRIPTION
		"Total number of successful restarted transfer since
		the snapmirror is initialized. Persistent across reboot."

	::= { snapmirrorStatusEntry 8 }

	snapmirrorTotalFailures         OBJECT-TYPE
	SYNTAX                          Counter32
        MAX-ACCESS                      read-only
        STATUS                          current
	DESCRIPTION
		"Total number of failed or aborted transfer since
		the snapmirror is initialized. Persistent across reboot."

	::= { snapmirrorStatusEntry 9 }

	snapmirrorTotalDeferments       OBJECT-TYPE
	SYNTAX                          Counter32
        MAX-ACCESS                      read-only
        STATUS                          current
	DESCRIPTION
		"Total number of deferment since the snapmirror
		is initialized. Persistent across reboot."

	::= { snapmirrorStatusEntry 10 }

	snapmirrorTotalTransMBs         OBJECT-TYPE
	SYNTAX                          Counter32
        MAX-ACCESS                      read-only
        STATUS                          current
	DESCRIPTION
		"Total transfer size in MB for the snapmirror.
		Reset on reboot."

	::= { snapmirrorStatusEntry 11 }

	snapmirrorTotalTransTimeSeconds OBJECT-TYPE
	SYNTAX                          Counter32
        MAX-ACCESS                      read-only
        STATUS                          current
	DESCRIPTION
		"Total number of seconds spent in successful transfer for the
		snapmirror. Reset on reboot."

	::= { snapmirrorStatusEntry 12 }

	snapmirrorThrottleValue         OBJECT-TYPE
	SYNTAX                          Integer32
        MAX-ACCESS                      read-only
        STATUS                          current
	DESCRIPTION
		"Current throttle value for the snapmirror."

	::= { snapmirrorStatusEntry 13 }

	snapmirrorMirrorTimestamp       OBJECT-TYPE
	SYNTAX                          DisplayString
        MAX-ACCESS                      read-only
        STATUS                          current
	DESCRIPTION
		"Timestamp of the last snapshot successfully transferred from
		 the source to the destination."

	::= { snapmirrorStatusEntry 14 }

	snapmirrorBaseSnapshot          OBJECT-TYPE
	SYNTAX                          DisplayString
        MAX-ACCESS                      read-only
        STATUS                          current
	DESCRIPTION
		"The name of the current base snapshot for the snapmirror."

	::= { snapmirrorStatusEntry 15 }

	snapmirrorLastTransType         OBJECT-TYPE
	SYNTAX                          DisplayString
        MAX-ACCESS                      read-only
        STATUS                          current
	DESCRIPTION
		"The type of the previous successful transfer."

	::= { snapmirrorStatusEntry 16 }

	snapmirrorLastTransMBs          OBJECT-TYPE
	SYNTAX                          Counter32
        MAX-ACCESS                      read-only
        STATUS                          current
	DESCRIPTION
		"Last successful transfer size in MB for the snapmirror."

	::= { snapmirrorStatusEntry 17 }

	snapmirrorLastTransTimeSeconds  OBJECT-TYPE
	SYNTAX                          Counter32
        MAX-ACCESS                      read-only
        STATUS                          current
	DESCRIPTION
		"Duration of last successful transfer in seconds for the
		 snapmirror."

	::= { snapmirrorStatusEntry 18 }

	snapmirrorSchedule              OBJECT-TYPE
	SYNTAX                          DisplayString
        MAX-ACCESS                      read-only
        STATUS                          current
	DESCRIPTION
		"Update schedule for the snapmirror in conf file format."

	::= { snapmirrorStatusEntry 19 }

	snapmirrorScheduleDesc          OBJECT-TYPE
	SYNTAX                          DisplayString
        MAX-ACCESS                      read-only
        STATUS                          current
	DESCRIPTION
		"Description of the update schedule for the snapmirror."

	::= { snapmirrorStatusEntry 20 }

	snapmirrorArguments             OBJECT-TYPE
	SYNTAX                          DisplayString
        MAX-ACCESS                      read-only
        STATUS                          current
	DESCRIPTION
		"Arguments for the snapmirror in conf file format."

	::= { snapmirrorStatusEntry 21 }

        snapmirrorSyncToAsync           OBJECT-TYPE
	SYNTAX                          Counter32
        MAX-ACCESS                      read-only
        STATUS                          current
	DESCRIPTION
	        "The number of times changing from sync mode to async mode
		since the snapmirror is initialized. Persistent across reboot."

	::= { snapmirrorStatusEntry 22 }

	snapmirrorConnTable             OBJECT-TYPE
	SYNTAX                          SEQUENCE OF SnapmirrorConnEntry
        MAX-ACCESS                      not-accessible
        STATUS                          current
	DESCRIPTION
	        "Provide a list of snapmirror connection definitions."

	::= { snapmirror 21 }

	snapmirrorConnEntry             OBJECT-TYPE
	SYNTAX                          SnapmirrorConnEntry
        MAX-ACCESS                      not-accessible
        STATUS                          current
	DESCRIPTION
		"Provide a report of a defined multipath connection."

	INDEX	{ snapmirrorConnIndex }
	::= { snapmirrorConnTable 1 }

        SnapmirrorConnEntry ::=
	    SEQUENCE {
	    	snapmirrorConnIndex
			Integer32,
		snapmirrorConnName
			DisplayString,
		snapmirrorConnType
			INTEGER,
		snapmirrorConnSrc1
			DisplayString,
		snapmirrorConnDst1
		        DisplayString,
		snapmirrorConnSrc2
		        DisplayString,
		snapmirrorConnDst2
		        DisplayString
	    }

	snapmirrorConnIndex             OBJECT-TYPE
	SYNTAX                          Integer32 (1..2147483647)
        MAX-ACCESS                      read-only
        STATUS                          current
	DESCRIPTION
		"Index into the snapmirror multipath connection table."

	::= { snapmirrorConnEntry 1 }

	snapmirrorConnName              OBJECT-TYPE
	SYNTAX                          DisplayString
        MAX-ACCESS                      read-only
        STATUS                          current
	DESCRIPTION
		"The name of the snapmirror multipath connection."

	::= { snapmirrorConnEntry 2 }

	snapmirrorConnType              OBJECT-TYPE
	SYNTAX                          INTEGER {
                                             multi(1),
                                             failover(2)
                                        }
        MAX-ACCESS                      read-only
        STATUS                          current
	DESCRIPTION
		"The type of the snapmirror multipath connection."

	::= { snapmirrorConnEntry 3 }

	snapmirrorConnSrc1              OBJECT-TYPE
	SYNTAX                          DisplayString
        MAX-ACCESS                      read-only
        STATUS                          current
	DESCRIPTION
		"The name of the source for the first path."

        ::= { snapmirrorConnEntry 4 }

	snapmirrorConnDst1              OBJECT-TYPE
	SYNTAX                          DisplayString
        MAX-ACCESS                      read-only
        STATUS                          current
	DESCRIPTION
	        "The name of the destination for the first path."

        ::= { snapmirrorConnEntry 5 }

	snapmirrorConnSrc2              OBJECT-TYPE
	SYNTAX                          DisplayString
        MAX-ACCESS                      read-only
        STATUS                          current
	DESCRIPTION
		"The name of the source for the second path."

	::= { snapmirrorConnEntry 6 }

	snapmirrorConnDst2              OBJECT-TYPE
	SYNTAX                          DisplayString
        MAX-ACCESS                      read-only
        STATUS                          current
	DESCRIPTION
		"The name of the destination for the second path."

        ::= { snapmirrorConnEntry 7 }

	snapmirrorRelStatusTable	OBJECT-TYPE
	SYNTAX				SEQUENCE OF SnapmirrorRelStatusEntry
	MAX-ACCESS			not-accessible
	STATUS				current
	DESCRIPTION
			"Provide a list of snapmirror status."

	::= { sm 1 }

	snapmirrorRelStatusEntry           OBJECT-TYPE
	SYNTAX				   SnapmirrorRelStatusEntry
	MAX-ACCESS			   not-accessible
	STATUS				   current
	DESCRIPTION
			"Provide a report of current status of snapmirror."

	INDEX	{ snapmirrorRelIndex }
	::= { snapmirrorRelStatusTable 1 }

        SnapmirrorRelStatusEntry ::=
	    SEQUENCE {
		snapmirrorRelIndex
			Integer32,
		snapmirrorRelSrcPath
			DisplayString,
		snapmirrorRelDestPath
			DisplayString,
		snapmirrorRelType
			INTEGER,
		snapmirrorRelStatus
			INTEGER,
		snapmirrorRelState
			INTEGER,
		snapmirrorRelLag
			TimeTicks,
		snapmirrorRelThrottleValue
			Unsigned32,
		snapmirrorRelSchedule
			DisplayString,
		snapmirrorRelPolicy
			DisplayString,
		snapmirrorRelTransferSnapshot
			DisplayString,
		snapmirrorRelNewestSnapshot
			DisplayString,
		snapmirrorRelNewestSnapshotTimeStamp
			DateAndTime,
		snapmirrorRelExportedSnapshot
			DisplayString,
		snapmirrorRelExportedSnapshotTimeStamp
			DateAndTime,
		snapmirrorRelHealthy
			INTEGER,
		snapmirrorRelUnHealthyReason
			DisplayString,
		snapmirrorRelLastTransferType
			INTEGER,
		snapmirrorRelLastTransferError
			DisplayString,
		snapmirrorRelLastTransferSize
			Counter64,
		snapmirrorRelLastTransferTimeSeconds
			Unsigned32,
		snapmirrorRelGroupType
			INTEGER,
		snapmirrorRelVserver
			DisplayString,
		snapmirrorRelUpdateSuccCnt
			Counter64,
		snapmirrorRelUpdateFailCnt
			Counter64,
		snapmirrorRelResyncSuccCnt
			Counter64,
		snapmirrorRelResyncFailCnt
			Counter64,
		snapmirrorRelBreakSuccCnt
			Counter64,
		snapmirrorRelBreakFailCnt
			Counter64,
		snapmirrorRelTotalTransBytes
			Counter64,
		snapmirrorRelTotalTransTimeSeconds
			Counter32
	    }

	snapmirrorRelIndex		OBJECT-TYPE
	SYNTAX                          Integer32 (1..2147483647)
	MAX-ACCESS			read-only
	STATUS				current
	DESCRIPTION
		"A number that identifies this snapmirror relationship. The
		cmodeSnapmirrorIndex is not related to any other table defined
		in this MIB."

	::={ snapmirrorRelStatusEntry 1 }

	snapmirrorRelSrcPath		OBJECT-TYPE
	SYNTAX				DisplayString
	MAX-ACCESS			read-only
	STATUS				current
	DESCRIPTION
		"Source path of this relationship."
	::={ snapmirrorRelStatusEntry 2 }

	snapmirrorRelDestPath		OBJECT-TYPE
	SYNTAX				DisplayString
	MAX-ACCESS			read-only
	STATUS				current
	DESCRIPTION
		"Destination path of this relationship."
	::={ snapmirrorRelStatusEntry 3 }

	snapmirrorRelType		OBJECT-TYPE
	SYNTAX				INTEGER {
						dp(0),
						ls(1),
						xdp(2),
						rst(3),
						tdp(4)
					}
	MAX-ACCESS			read-only
	STATUS				current
	DESCRIPTION
		"Relationship type of this relationship."
	::={ snapmirrorRelStatusEntry 4 }

	snapmirrorRelStatus		OBJECT-TYPE
	SYNTAX                          INTEGER {
					    idle(0),
					    transferring(1),
					    restoring(2),
					    checking(3),
					    quiescing(4),
					    quiesced(5),
					    queued(6),
					    preparing(7),
					    waiting(8),
					    finalizing(9),
					    resyncing(10),
					    aborting(11),
					    breaking(12),
					    deleting(13),
					    releasing(14),
					    outOfSync(15),
					    preCutover(16),
					    cutover(17),
					    inSync(18),
					    transitioning(19),
					    fastTransferring(20),
					    inSyncDuplex(21),
					    readyForCutoverPreCommit(22),
					    cutoverPreCommitting(23),
					    cuttingOver(24),
					    waitingForAbort(25)
                                        }
	MAX-ACCESS                      read-only
	STATUS                          current
	DESCRIPTION
			"Current transfer status of this relationship."

	::= { snapmirrorRelStatusEntry 5 }

	snapmirrorRelState		OBJECT-TYPE
	SYNTAX                          INTEGER {
                                             uninitialized(0),
                                             snapmirrored(1),
					     brokenOff(2)
                                        }
	MAX-ACCESS                      read-only
	STATUS                          current
	DESCRIPTION
			"Current state of this relationship."

	::= { snapmirrorRelStatusEntry 6 }

	snapmirrorRelLag		OBJECT-TYPE
	SYNTAX                          TimeTicks
	MAX-ACCESS                      read-only
	STATUS                          current
	DESCRIPTION
			"How far behind from the source the destination is."

	::= { snapmirrorRelStatusEntry 7 }

	snapmirrorRelThrottleValue	OBJECT-TYPE
	SYNTAX                          Unsigned32
	MAX-ACCESS                      read-only
	STATUS                          current
	DESCRIPTION
		"Current throttle value for this relationship."

	::= { snapmirrorRelStatusEntry 8 }

	snapmirrorRelSchedule		OBJECT-TYPE
	SYNTAX				DisplayString
	MAX-ACCESS                      read-only
	STATUS                          current
	DESCRIPTION
		"The schedule associated with this relationship."

	::= { snapmirrorRelStatusEntry 9 }

	snapmirrorRelPolicy		OBJECT-TYPE
	SYNTAX				DisplayString
	MAX-ACCESS                      read-only
	STATUS                          current
	DESCRIPTION
		"The policy associated with this relationship."

	::= { snapmirrorRelStatusEntry 10 }


	snapmirrorRelTransferSnapshot	 OBJECT-TYPE
	SYNTAX                           DisplayString
	MAX-ACCESS                       read-only
	STATUS                           current
	DESCRIPTION
		"The current transfer snapshot for this relationship."

	::= { snapmirrorRelStatusEntry 11 }

	snapmirrorRelNewestSnapshot	 OBJECT-TYPE
	SYNTAX                           DisplayString
	MAX-ACCESS                       read-only
	STATUS                           current
	DESCRIPTION
		"The newest snapshot at the destination of this relationship."

	::= { snapmirrorRelStatusEntry 12 }

	snapmirrorRelNewestSnapshotTimeStamp		 OBJECT-TYPE
	SYNTAX						 DateAndTime
	MAX-ACCESS                                       read-only
	STATUS                                           current
	DESCRIPTION
		"The time stamp of newest snapshot at the destination of this relationship."

	::= { snapmirrorRelStatusEntry 13 }

	snapmirrorRelExportedSnapshot		  OBJECT-TYPE
	SYNTAX					  DisplayString
	MAX-ACCESS                                read-only
	STATUS                                    current
	DESCRIPTION
		"The exported snapshot at the destination of this relationship."

	::= { snapmirrorRelStatusEntry 14 }


	snapmirrorRelExportedSnapshotTimeStamp		   OBJECT-TYPE
	SYNTAX						   DateAndTime
	MAX-ACCESS                                         read-only
	STATUS                                             current
	DESCRIPTION
		"The time stamp of exported snapshot at the destination of this relationship."

	::= { snapmirrorRelStatusEntry 15 }

	snapmirrorRelHealthy		OBJECT-TYPE
	SYNTAX				INTEGER {
					false(0),
					true(1)
		                        }
	MAX-ACCESS                      read-only
	STATUS                          current
	DESCRIPTION
		"Indicates whether this relationship is healthy or not."

	::= { snapmirrorRelStatusEntry 16 }

	snapmirrorRelUnHealthyReason	     OBJECT-TYPE
	SYNTAX				     DisplayString
	MAX-ACCESS                           read-only
	STATUS                               current
	DESCRIPTION
		"Indicates the specific reason due to which this relationship is not healthy."

	::= { snapmirrorRelStatusEntry 17 }

	snapmirrorRelLastTransferType		  OBJECT-TYPE
	SYNTAX					  INTEGER {
						  initialize(0),
						  update(1),
						  resync(2),
						  restore(3),
						  check(4)
						  }
	MAX-ACCESS				  read-only
	STATUS					  current
	DESCRIPTION
		"The type of the last transfer on this relationship."

	::= { snapmirrorRelStatusEntry 18 }

	snapmirrorRelLastTransferError		   OBJECT-TYPE
	SYNTAX					   DisplayString
	MAX-ACCESS				   read-only
	STATUS					   current
	DESCRIPTION
		"The last transfer error for this relationship."

	::= { snapmirrorRelStatusEntry 19 }

	snapmirrorRelLastTransferSize		 OBJECT-TYPE
	SYNTAX					 Counter64
	MAX-ACCESS				 read-only
	STATUS					 current
	DESCRIPTION
		"The size of the last transfer for this relationship."

	::= { snapmirrorRelStatusEntry 20 }

	snapmirrorRelLastTransferTimeSeconds	      OBJECT-TYPE
	SYNTAX					      Unsigned32
	MAX-ACCESS				      read-only
	STATUS					      current
	DESCRIPTION
		"The duration of the last transfer for this relationship."

	::= { snapmirrorRelStatusEntry 21 }

	snapmirrorRelGroupType			  OBJECT-TYPE
	SYNTAX					  INTEGER {
						  flexvol(0),
						  infinitevol-dr(1),
						  vserver-dr(2)
						  }
	MAX-ACCESS				  read-only
	STATUS					  current
	DESCRIPTION
		"Indicate if this relationship is part of an Infinite Volume or Vserver DR relationship."

	::= { snapmirrorRelStatusEntry 22 }

	snapmirrorRelVserver            OBJECT-TYPE
	SYNTAX                          DisplayString
	MAX-ACCESS                      read-only
	STATUS                          current
	DESCRIPTION
			"Destination vserver to which this relationship belongs."
	::= { snapmirrorRelStatusEntry 23 }

	snapmirrorRelUpdateSuccCnt		  OBJECT-TYPE
	SYNTAX					  Counter64
	MAX-ACCESS				  read-only
	STATUS					  current
	DESCRIPTION
		"Total number of successful updates since this relationship was initialized."

	::= { snapmirrorRelStatusEntry 24 }

	snapmirrorRelUpdateFailCnt		  OBJECT-TYPE
	SYNTAX					  Counter64
	MAX-ACCESS				  read-only
	STATUS					  current
	DESCRIPTION
		"Total number of failed updates since this relationship was initialized."

	::= { snapmirrorRelStatusEntry 25 }

	snapmirrorRelResyncSuccCnt		  OBJECT-TYPE
	SYNTAX					  Counter64
	MAX-ACCESS				  read-only
	STATUS					  current
	DESCRIPTION
		"Total number of successful resyncs since this relationship was initialized."

	::= { snapmirrorRelStatusEntry 26 }

	snapmirrorRelResyncFailCnt		  OBJECT-TYPE
	SYNTAX					  Counter64
	MAX-ACCESS				  read-only
	STATUS					  current
	DESCRIPTION
		"Total number of failed resyncs since this relationship was initialized."

	::= { snapmirrorRelStatusEntry 27 }

	snapmirrorRelBreakSuccCnt		  OBJECT-TYPE
	SYNTAX					  Counter64
	MAX-ACCESS				  read-only
	STATUS					  current
	DESCRIPTION
		"Total number of successful breaks since this relationship was initialized."

	::= { snapmirrorRelStatusEntry 28 }

	snapmirrorRelBreakFailCnt		  OBJECT-TYPE
	SYNTAX					  Counter64
	MAX-ACCESS				  read-only
	STATUS					  current
	DESCRIPTION
		"Total number of failed breaks since this relationship was initialized."

	::= { snapmirrorRelStatusEntry 29 }

	snapmirrorRelTotalTransBytes		  OBJECT-TYPE
	SYNTAX					  Counter64
	MAX-ACCESS				  read-only
	STATUS					  current
	DESCRIPTION
		"Total transfer bytes since this relationship was created."

	::= { snapmirrorRelStatusEntry 30 }

	snapmirrorRelTotalTransTimeSeconds	  OBJECT-TYPE
	SYNTAX					  Counter32
	MAX-ACCESS				  read-only
	STATUS					  current
	DESCRIPTION
		"Total transfer time in seconds since this relationship was created."

	::= { snapmirrorRelStatusEntry 31 }

	-- -- -- -- -- -- -- -- --
	-- the snapvault group
	-- -- -- -- -- -- -- -- --

                  -- this group contains statistics for the whole system
                  -- unless otherwise specified.

        svOn                            OBJECT-TYPE
	SYNTAX                          INTEGER {
	                                     off(1),
					     on(2)
					}
        MAX-ACCESS                      read-only
        STATUS                          current
	DESCRIPTION
			"Indicates whether snapvault has been turned on
			or not."
	::= { snapvault 1 }

	svSystemActiveDstNumber         OBJECT-TYPE
	SYNTAX                          Integer32
        MAX-ACCESS                      read-only
        STATUS                          current
	DESCRIPTION
			"Number of active snapvault destinations."

	::= { snapvault 2 }

	svSystemActiveSrcNumber         OBJECT-TYPE
	SYNTAX                          Integer32
        MAX-ACCESS                      read-only
        STATUS                          current
	DESCRIPTION
			"Number of active snapvault sources."

	::= { snapvault 3 }

	svSystemTotalPrimarySuccesses   OBJECT-TYPE
	SYNTAX                          Counter32
        MAX-ACCESS                      read-only
        STATUS                          current
	DESCRIPTION
			"Total number of successful snapvault transfers
			from the snapvault primary. Persistent across reboot."

        ::= { snapvault 4 }

	svSystemTotalSecondarySuccesses OBJECT-TYPE
	SYNTAX                          Counter32
        MAX-ACCESS                      read-only
        STATUS                          current
	DESCRIPTION
			"Total number of successful snapvault transfers to
			the snapvault secondary. Persistent across reboot."

	::= { snapvault 5 }

	svSystemTotalPrimaryFailures    OBJECT-TYPE
	SYNTAX                          Counter32
        MAX-ACCESS                      read-only
        STATUS                          current
	DESCRIPTION
			"Total number of failed snapvault transfers on
			the snapvault primary. Persistent across reboot."

	::= { snapvault 6 }

	svSystemTotalSecondaryFailures  OBJECT-TYPE
	SYNTAX                          Counter32
        MAX-ACCESS                      read-only
        STATUS                          current
	DESCRIPTION
			"Total number of failed snapvault transfers on
			the snapvault secondary. Persistent across reboot."

	::= { snapvault 7 }

	svSystemTotalSecondaryDeferments OBJECT-TYPE
	SYNTAX                          Counter32
        MAX-ACCESS                      read-only
        STATUS                          current
	DESCRIPTION
			"Total number of deferred snapvault transfers on
			the snapvault secondary. Persistent across reboot."

	::= { snapvault 8 }

	svPrimaryIsLicensed             OBJECT-TYPE
	SYNTAX                          INTEGER {
                                             false(1),
                                             true(2)
                                        }
        MAX-ACCESS                      read-only
        STATUS                          current
	DESCRIPTION
		"Whether the snapvault_client(primary) is licensed on the filer."

	::= { snapvault 9 }

	svSecondaryIsLicensed           OBJECT-TYPE
	SYNTAX                          INTEGER {
                                             false(1),
                                             true(2)
                                        }
        MAX-ACCESS                      read-only
        STATUS                          current
	DESCRIPTION
		"Whether the snapvault_server(secondary) is licensed on the filer."

	::= { snapvault 10 }



	snapvaultStatusTable            OBJECT-TYPE
	SYNTAX                          SEQUENCE OF SnapvaultStatusEntry
        MAX-ACCESS                      not-accessible
        STATUS                          current
	DESCRIPTION
			"provide a list of snapvault status."

	::= { snapvault 11 }

	snapvaultStatusEntry            OBJECT-TYPE
	SYNTAX                          SnapvaultStatusEntry
        MAX-ACCESS                      not-accessible
        STATUS                          current
	DESCRIPTION
			"Provide a report of current status of snapvault."

	INDEX	{ svIndex }
	::= { snapvaultStatusTable 1 }

	SnapvaultStatusEntry ::=
	    SEQUENCE {
	    	svIndex
			Integer32,
		svSrc
			OCTET STRING,
		svDst
			OCTET STRING,
		svStatus
			INTEGER,
		svState
			INTEGER,
		svLag
			TimeTicks,
		svTotalSuccesses
			Counter32,
		svTotalRestartSuccesses
			Counter32,
		svTotalFailures
			Counter32,
		svTotalDeferments
			Counter32,
		svTotalTransMBs
			Counter32,
		svTotalTransTimeSeconds
			Counter32,
		svThrottleValue
			Integer32,
		svSrcSnapshotTime
		        Integer32,
		svBaseSnapshot
			DisplayString,
		svLastTransType
			DisplayString,
		svLastTransMBs
			Integer32,
		svLastTransTimeSeconds
			Integer32
	    }

	svIndex                         OBJECT-TYPE
	SYNTAX                          Integer32 (1..2147483647)
        MAX-ACCESS                      read-only
        STATUS                          current
	DESCRIPTION
			"Index into the snapvault status table."

	::= { snapvaultStatusEntry 1 }

	svSrc                           OBJECT-TYPE
	SYNTAX                          OCTET STRING
        MAX-ACCESS                      read-only
        STATUS                          current
	DESCRIPTION
			"Source of the snapvault relationship.
			<filer>:/vol/<qtree_name>"

	::= { snapvaultStatusEntry 2 }

	svDst                           OBJECT-TYPE
	SYNTAX                          OCTET STRING
        MAX-ACCESS                      read-only
        STATUS                          current
	DESCRIPTION
			"Destination of the snapvault relationship.
			<filer>:/vol/<qtree_name>"

	::= { snapvaultStatusEntry 3 }

	svStatus                        OBJECT-TYPE
	SYNTAX                          INTEGER {
                                             idle(1),
                                             transferring(2),
					     pending(3),
					     aborting(4),
					     quiescing(6),
					     resyncing(7),
                                             paused(12)
                                        }
        MAX-ACCESS                      read-only
        STATUS                          current
	DESCRIPTION
			"Current transfer status of the snapvault relationship."

	::= { snapvaultStatusEntry 4 }

	svState                         OBJECT-TYPE
	SYNTAX                          INTEGER {
                                             uninitialized(1),
                                             snapvaulted(2),
					     brokenOff(3),
					     quiesced(4),
					     source(5),
					     unknown(6),
                                             restoring(7)
                                        }
        MAX-ACCESS                      read-only
        STATUS                          current
	DESCRIPTION
			"Current state of the snapvault relationship."

	::= { snapvaultStatusEntry 5 }

	svLag                           OBJECT-TYPE
	SYNTAX                          TimeTicks
        MAX-ACCESS                      read-only
        STATUS                          current
	DESCRIPTION
			"How far behind from the source the destination is."

	::= { snapvaultStatusEntry 6 }

	svTotalSuccesses                OBJECT-TYPE
	SYNTAX                          Counter32
        MAX-ACCESS                      read-only
        STATUS                          current
	DESCRIPTION
		"Total number of successful transfer since the snapvault
		 relationship was established. Persistent across reboot."

	::= { snapvaultStatusEntry 7 }

	svTotalRestartSuccesses         OBJECT-TYPE
	SYNTAX                          Counter32
        MAX-ACCESS                      read-only
        STATUS                          current
	DESCRIPTION
		"Total number of successful restarted transfer since
		 the snapvault relationship was established. Persistent
		 across reboot."

	::= { snapvaultStatusEntry 8 }

	svTotalFailures                 OBJECT-TYPE
	SYNTAX                          Counter32
        MAX-ACCESS                      read-only
        STATUS                          current
	DESCRIPTION
		"Total number of failed or aborted transfer since
		 the snapvault relationship was established. Persistent
		 across reboot."

	::= { snapvaultStatusEntry 9 }

	svTotalDeferments               OBJECT-TYPE
	SYNTAX                          Counter32
        MAX-ACCESS                      read-only
        STATUS                          current
	DESCRIPTION
		"Total number of deferment since the snapvault
		 relationship was established. Persistent across reboot."

	::= { snapvaultStatusEntry 10 }

	svTotalTransMBs                 OBJECT-TYPE
	SYNTAX                          Counter32
        MAX-ACCESS                      read-only
        STATUS                          current
	DESCRIPTION
		"Total transfer size in MB for the snapvault.
		Reset on reboot."

	::= { snapvaultStatusEntry 11 }

	svTotalTransTimeSeconds         OBJECT-TYPE
	SYNTAX                          Counter32
        MAX-ACCESS                      read-only
        STATUS                          current
	DESCRIPTION
		"Total number of seconds spent in successful transfer for the
		 snapvault relationship. Reset on reboot."

	::= { snapvaultStatusEntry 12 }

	svThrottleValue                 OBJECT-TYPE
	SYNTAX                          Integer32
        MAX-ACCESS                      read-only
        STATUS                          current
	DESCRIPTION
		"Current throttle value for the snapvault relationship."

	::= { snapvaultStatusEntry 13 }

	svSrcSnapshotTime               OBJECT-TYPE
	SYNTAX                          Integer32
        MAX-ACCESS                      read-only
        STATUS                          current
	DESCRIPTION
		"Time when the source snapshot was created. The time in
		seconds since January 1, 1970. The source snapshot here
		is the last snapshot successfully transferred from the
		source to the destination."

	::= { snapvaultStatusEntry 14 }

	svBaseSnapshot                  OBJECT-TYPE
	SYNTAX                          DisplayString
        MAX-ACCESS                      read-only
        STATUS                          current
	DESCRIPTION
		"The name of the current base snapshot for the
		 snapvault relationship."

	::= { snapvaultStatusEntry 15 }

	svLastTransType                 OBJECT-TYPE
	SYNTAX                          DisplayString
        MAX-ACCESS                      read-only
        STATUS                          current
	DESCRIPTION
		"The type of the previous successful transfer."

	::= { snapvaultStatusEntry 16 }

	svLastTransMBs                  OBJECT-TYPE
	SYNTAX                          Integer32
        MAX-ACCESS                      read-only
        STATUS                          current
	DESCRIPTION
		"Last successful transfer size in MB for the snapvault
		 relationship."

	::= { snapvaultStatusEntry 17 }

	svLastTransTimeSeconds          OBJECT-TYPE
	SYNTAX                          Integer32
        MAX-ACCESS                      read-only
        STATUS                          current
	DESCRIPTION
		"Duration of last successful transfer in seconds for the
		 snapvault relationship."

	::= { snapvaultStatusEntry 18 }

	snapvaultHostTable              OBJECT-TYPE
	SYNTAX                          SEQUENCE OF SnapvaultHostEntry
        MAX-ACCESS                      not-accessible
        STATUS                          current
	DESCRIPTION
			"Provide a list of remote snapvault hosts."

	::= { snapvault 12 }

	snapvaultHostEntry              OBJECT-TYPE
	SYNTAX                          SnapvaultHostEntry
        MAX-ACCESS                      not-accessible
        STATUS                          current
	DESCRIPTION
			"Provide snapvault statistics for a remote host
			 which has one or more current established
			 relationships with the local snapvault system."

	INDEX	{ svHostIndex }
	::= { snapvaultHostTable 1 }

	SnapvaultHostEntry ::=
	    SEQUENCE {
	    	svHostIndex
			Integer32,
		svHostName
			DisplayString,
		svHostType
			INTEGER,
		svHostTotalSuccesses
			Integer32,
		svHostTotalFailures
			Integer32,
		svHostTotalDeferments
			Integer32
	    }

	svHostIndex                     OBJECT-TYPE
	SYNTAX                          Integer32 (1..2147483647)
        MAX-ACCESS                      read-only
        STATUS                          current
	DESCRIPTION
			"Index into the snapvault remote host table."

	::= { snapvaultHostEntry 1 }

	svHostName                      OBJECT-TYPE
	SYNTAX                          DisplayString
        MAX-ACCESS                      read-only
        STATUS                          current
	DESCRIPTION
		"The name of the remote snapvault host."

	::= { snapvaultHostEntry 2 }

	svHostType                      OBJECT-TYPE
	SYNTAX                          INTEGER {
                                             primary(1),
                                             secondary(2)
                                        }
        MAX-ACCESS                      read-only
        STATUS                          current
	DESCRIPTION
		"The type of the remote snapvault host."

	::= { snapvaultHostEntry 3 }

	svHostTotalSuccesses            OBJECT-TYPE
	SYNTAX                          Integer32
        MAX-ACCESS                      read-only
        STATUS                          current
	DESCRIPTION
	        "Total number of successful snapvault transfers
		for all current established relationships between
		the local snapvault system and the given remote host."

	::= { snapvaultHostEntry 4 }

	svHostTotalFailures             OBJECT-TYPE
	SYNTAX                          Integer32
        MAX-ACCESS                      read-only
        STATUS                          current
	DESCRIPTION
	        "Total number of failed snapvault transfers
		for all current established relationships between
		the local snapvault system and the given remote host."

	::= { snapvaultHostEntry 5 }

	svHostTotalDeferments           OBJECT-TYPE
	SYNTAX                          Integer32
        MAX-ACCESS                      read-only
        STATUS                          current
	DESCRIPTION
		"Total number of deferred snapvault transfers for
		all current established relationships between
		the local snapvault system and the given remote host.
		0 for snapvault client host."

	::= { snapvaultHostEntry 6 }


	snapvaultSchedTable             OBJECT-TYPE
	SYNTAX                          SEQUENCE OF SnapvaultSchedEntry
        MAX-ACCESS                      not-accessible
        STATUS                          current
	DESCRIPTION
			"Provide a list of snapvault schedules."

	::= { snapvault 13 }

	snapvaultSchedEntry             OBJECT-TYPE
	SYNTAX                          SnapvaultSchedEntry
        MAX-ACCESS                      not-accessible
        STATUS                          current
	DESCRIPTION
			"Provide a report of schedules of snapvault."

	INDEX	{ svSchedIndex }
	::= { snapvaultSchedTable 1 }

	SnapvaultSchedEntry ::=
	    SEQUENCE {
	    	svSchedIndex
			Integer32,
		svSchedVolume
			DisplayString,
		svSchedSnapshot
			DisplayString,
		svSchedStatus
			INTEGER,
		svSchedType
			INTEGER,
		svSchedSchedule
			DisplayString
	    }

	svSchedIndex                    OBJECT-TYPE
	SYNTAX                          Integer32 (1..2147483647)
        MAX-ACCESS                      read-only
        STATUS                          current
	DESCRIPTION
			"Index into the snapvault schedule table."

	::= { snapvaultSchedEntry 1 }

	svSchedVolume                   OBJECT-TYPE
	SYNTAX                          DisplayString
        MAX-ACCESS                      read-only
        STATUS                          current
	DESCRIPTION
		"The name of the volume on the snapvault for the
		 snapvault schedule. This does not have a /vol/ prefix."

	::= { snapvaultSchedEntry 2 }

	svSchedSnapshot                 OBJECT-TYPE
	SYNTAX                          DisplayString
        MAX-ACCESS                      read-only
        STATUS                          current
	DESCRIPTION
		"The name of the snapshot for the snapvault schedule."

	::= { snapvaultSchedEntry 3 }

	svSchedStatus                   OBJECT-TYPE
	SYNTAX                          INTEGER {
                                             idle(1),
                                             queued(2),
					     active(3),
                                             aborting(4)
                                        }
        MAX-ACCESS                      read-only
        STATUS                          current
	DESCRIPTION
		"Current status of the snapvault schedule."

	::= { snapvaultSchedEntry 4 }

	svSchedType                     OBJECT-TYPE
	SYNTAX                          INTEGER {
                                             undef(1),
                                             xfer(2),
                                             create(3)
                                        }
        MAX-ACCESS                      read-only
        STATUS                          current
	DESCRIPTION
		"The type of the snapvault schedule."

	::= { snapvaultSchedEntry 5 }


	svSchedSchedule                 OBJECT-TYPE
	SYNTAX                          DisplayString
        MAX-ACCESS                      read-only
        STATUS                          current
	DESCRIPTION
		"The update schedule of the snapvault."

	::= { snapvaultSchedEntry 6 }

	svDrPrimaryIsLicensed           OBJECT-TYPE
	SYNTAX                          INTEGER {
                                             false(1),
                                             true(2)
                                        }
        MAX-ACCESS                      read-only
        STATUS                          current
	DESCRIPTION
		"Whether the snapvault disaster recovery primary is
		licensed on the filer."

	::= { snapvault 14 }

	-- -- -- -- -- -- -- --
	--  the ndmpd group  --
	-- -- -- -- -- -- -- --

        ndmpOn                          OBJECT-TYPE
	SYNTAX                          INTEGER {
	                                     off(1),
					     on(2)
					}
        MAX-ACCESS                      read-only
        STATUS                          obsolete
	DESCRIPTION
		"Indicates whether ndmpd has been turned on or not."
	::= { ndmp 1 }

	ndmpSessionOpened               OBJECT-TYPE
	SYNTAX                          Integer32
        MAX-ACCESS                      read-only
        STATUS                          obsolete
	DESCRIPTION
		"Total number of ndmpd sessions currently opened.
		Sessions may be running backups, restores or neither."
	::= { ndmp 2 }

	ndmpBackupActive                OBJECT-TYPE
	SYNTAX                          Integer32
        MAX-ACCESS                      read-only
        STATUS                          obsolete
	DESCRIPTION
		"Number of ndmpd backups currently active."
	::= { ndmp 3 }

	ndmpRestoreActive               OBJECT-TYPE
	SYNTAX                          Integer32
        MAX-ACCESS                      read-only
        STATUS                          obsolete
	DESCRIPTION
		"Number of ndmpd restores currently active."
	::= { ndmp 4 }

	ndmpTapeActive                  OBJECT-TYPE
	SYNTAX                          Integer32
        MAX-ACCESS                      read-only
        STATUS                          obsolete
	DESCRIPTION
		"Number of tape drives currently active."
	::= { ndmp 5 }

	ndmpBackupSuccesses             OBJECT-TYPE
	SYNTAX                          Counter32
        MAX-ACCESS                      read-only
        STATUS                          obsolete
	DESCRIPTION
		"Number of ndmpd backups that succeeded."
	::= { ndmp 6 }

	ndmpRestoreSuccesses            OBJECT-TYPE
	SYNTAX                          Counter32
        MAX-ACCESS                      read-only
        STATUS                          obsolete
	DESCRIPTION
		"Number of ndmpd restores that succeeded."
	::= { ndmp 7 }

	ndmpBackupFailures              OBJECT-TYPE
	SYNTAX                          Counter32
        MAX-ACCESS                      read-only
        STATUS                          obsolete
	DESCRIPTION
		"Number of ndmpd backups that failed."
	::= { ndmp 8 }

	ndmpRestoreFailures             OBJECT-TYPE
	SYNTAX                          Counter32
        MAX-ACCESS                      read-only
        STATUS                          obsolete
	DESCRIPTION
		"Number of ndmpd restores that failed."
	::= { ndmp 9 }

	ndmpBackupFailureReason         OBJECT-TYPE
	SYNTAX                          DisplayString
        MAX-ACCESS                      read-only
        STATUS                          obsolete
	DESCRIPTION
		"When the ndmpBackupFailures value is non-zero, this string
		describes the reason for the most recent backup failure."
	::= { ndmp 10 }

	ndmpRestoreFailureReason        OBJECT-TYPE
	SYNTAX                          DisplayString
        MAX-ACCESS                      read-only
        STATUS                          obsolete
	DESCRIPTION
		"When the ndmpRestoreFailures value is non-zero, this string
		describes the reason for the most recent restore failure."
	::= { ndmp 11 }

	-- -- -- -- -- -- -- --
	--  the ftpd group  --
	-- -- -- -- -- -- -- --

        ftpdOn                          OBJECT-TYPE
	SYNTAX                          INTEGER {
	                                     off(1),
					     on(2)
					}
        MAX-ACCESS                      read-only
        STATUS                          current
	DESCRIPTION
		"Indicates whether ftpd has been turned on or not."
	::= { ftpd 1 }

 	ftpdCurrentConns                OBJECT-TYPE
	SYNTAX                          Integer32
        MAX-ACCESS                      read-only
        STATUS                          current
	DESCRIPTION
			"Number of currently open TCP/IP connections to ftp daemon (active and idle)"
	::= { ftpd 2 }

 	ftpdMaxConns                    OBJECT-TYPE
	SYNTAX                          Integer32
        MAX-ACCESS                      read-only
        STATUS                          current
	DESCRIPTION
			"Number of maximum simultaneous TCP/IP connections to ftp daemon"
	::= { ftpd 3 }

 	ftpdTotalConns                  OBJECT-TYPE
	SYNTAX                          Integer32
        MAX-ACCESS                      read-only
        STATUS                          current
	DESCRIPTION
			"Number of total TCP/IP connections to ftp daemon"
	::= { ftpd 4 }

	-- -- -- -- -- -- -- --
	--  the fabric group  --
	-- -- -- -- -- -- -- --

	fabricInstances                 OBJECT-TYPE
	SYNTAX                          Integer32
        MAX-ACCESS                      read-only
        STATUS                          current
	DESCRIPTION
			"The number of distinct fabrics present."
	::= { fabric 1 }

	fabricTable                     OBJECT-TYPE
	SYNTAX                          SEQUENCE OF FabricEntry
        MAX-ACCESS                      not-accessible
        STATUS                          current
	DESCRIPTION
			"Provide a list of fabrics."
	::= { fabric 2 }

	fabricEntry                     OBJECT-TYPE
	SYNTAX                          FabricEntry
        MAX-ACCESS                      not-accessible
        STATUS                          current
	DESCRIPTION
			"Provide a report of current configuration and
			status of fabrics."

	INDEX	{ fabricIndex }
	::= { fabricTable 1 }

	FabricEntry ::=
	    SEQUENCE {
		fabricIndex
		    Integer32,
		fabricStatus
		    INTEGER,
		fabricStatusMessage
		    DisplayString,
		fabricName
		    OCTET STRING,
		fabricOwner
		    INTEGER
	    }

	fabricIndex                     OBJECT-TYPE
	SYNTAX                          Integer32 (1..2147483647)
        MAX-ACCESS                      read-only
        STATUS                          current
	DESCRIPTION
			"A number that identifies this fabric entry."
	::= { fabricEntry 1 }

	fabricStatus                    OBJECT-TYPE
	SYNTAX                          INTEGER {
                                             ok(1),
                                             faulty(2),
                                             unknown(3)
                                        }
        MAX-ACCESS                      read-only
        STATUS                          current
	DESCRIPTION
			"This indicates the overall status of the SAN fabric(s)."
	::= { fabricEntry 2 }

	fabricStatusMessage             OBJECT-TYPE
	SYNTAX                          DisplayString
        MAX-ACCESS                      read-only
        STATUS                          current
	DESCRIPTION
			"A string describing the fabric status,
			including a description of the condition (if
			any) that caused the status to be anything
			other than ok(3)."
	::= { fabricEntry 3 }

	fabricName                      OBJECT-TYPE
	SYNTAX                          OCTET STRING (SIZE (8))
        MAX-ACCESS                      read-only
        STATUS                          current
	DESCRIPTION
			"This is the WWN of the fabric."
	::= { fabricEntry 4 }

	fabricOwner                     OBJECT-TYPE
	SYNTAX                          INTEGER {
                                             netapp(1),
                                             other(2),
                                             unknown(3)
                                        }
        MAX-ACCESS                      read-only
        STATUS                          current
	DESCRIPTION
			"This indicates who owns the management of
			the fabric."
	::= { fabricEntry 5 }

	switchTable                     OBJECT-TYPE
	SYNTAX                          SEQUENCE OF SwitchEntry
        MAX-ACCESS                      not-accessible
        STATUS                          current
	DESCRIPTION
			"Provide a list of switches and hubs
			connected to the fabric."
	::= { fabric 3 }

	switchEntry                     OBJECT-TYPE
	SYNTAX                          SwitchEntry
        MAX-ACCESS                      not-accessible
        STATUS                          current
	DESCRIPTION
			"Provide a report of current configuration and
			status of fabric interconnect elements.  This
			include switches and hubs."

	INDEX	{ switchFabricIndex, switchIndex }
	::= { switchTable 1 }

	SwitchEntry ::=
	    SEQUENCE {
		switchIndex
		    Integer32,
		switchName
		    OCTET STRING,
		switchSymbolicName
		    OCTET STRING,
		switchType
		    INTEGER,
		switchDomain
		    Integer32,
		switchManagementId
		    Integer32,
		switchStatus
		    INTEGER,
		switchStatusMessage
		    DisplayString,
		switchLinkSpeed
		    Integer32,
		switchHighPacketsProcessed
		    Counter32,
		switchLowPacketsProcessed
		    Counter32,
		switchHighPacketsRejected
		    Counter32,
		switchLowPacketsRejected
		    Counter32,
		switchFabricIndex
		    Integer32,
		switch64PacketsProcessed
		    Counter64,
		switch64PacketsRejected
		    Counter64
	    }

	switchIndex                     OBJECT-TYPE
	SYNTAX                          Integer32 (1..2147483647)
        MAX-ACCESS                      read-only
        STATUS                          current
	DESCRIPTION
			"A number that identifies this switch entry."
	::= { switchEntry 1 }

	switchName                      OBJECT-TYPE
	SYNTAX                          OCTET STRING (SIZE (8))
        MAX-ACCESS                      read-only
        STATUS                          current
	DESCRIPTION
			"This is the WWN of the switch."
	::= { switchEntry 2 }

	switchSymbolicName              OBJECT-TYPE
	SYNTAX                          OCTET STRING (SIZE (0..255))
        MAX-ACCESS                      read-only
        STATUS                          current
	DESCRIPTION
			"This is the symbolic name of the switch."
	::= { switchEntry 3 }

	switchType                      OBJECT-TYPE
	SYNTAX                          INTEGER {
                                             hub(1),
                                             switch(2),
                                             unknown(3)
                                        }
        MAX-ACCESS                      read-only
        STATUS                          current
	DESCRIPTION
			"The type of the switch."
	::= { switchEntry 4 }

	switchDomain                    OBJECT-TYPE
	SYNTAX                          Integer32
        MAX-ACCESS                      read-only
        STATUS                          current
	DESCRIPTION
			"The domain identifier of the switch."
	::= { switchEntry 5 }

	switchManagementId              OBJECT-TYPE
	SYNTAX                          Integer32
        MAX-ACCESS                      read-only
        STATUS                          current
	DESCRIPTION
			"The in-band management identifier of the switch."
	::= { switchEntry 6 }

	switchStatus                    OBJECT-TYPE
	SYNTAX                          INTEGER {
                                             other(1),
                                             unknown(2),
					     ok(3),
					     nonCritical(4),
					     critical(5),
                                             nonRecoverable(6)
                                        }
        MAX-ACCESS                      read-only
        STATUS                          current
	DESCRIPTION
			"The current status of the switch."
	::= { switchEntry 7 }

	switchStatusMessage             OBJECT-TYPE
	SYNTAX                          DisplayString
        MAX-ACCESS                      read-only
        STATUS                          current
	DESCRIPTION
			"A string describing the switch status,
			including a description of the condition (if
			any) that caused the status to be anything
			other than ok(3)."
	::= { switchEntry 8 }

	switchLinkSpeed                 OBJECT-TYPE
	SYNTAX                          Integer32
        MAX-ACCESS                      read-only
        STATUS                          current
	DESCRIPTION
			"The link speed of the switch.  The value is an integer
			whose units are Gbits (for example, a value of 2 represents
			a link speed of 2 Gbit)."
	::= { switchEntry 9 }

	switchHighPacketsProcessed      OBJECT-TYPE
	SYNTAX                          Counter32
        MAX-ACCESS                      read-only
        STATUS                          deprecated
	DESCRIPTION
			"Number of Packets successfully processed
			since the last reboot/reset of the switch.
			This object returns the most
			significant 32 bits of the 64 bit unsigned integer.
			This object is deprecated - Use switch64PacketsProcessed
			instead."
	::= { switchEntry 10 }

	switchLowPacketsProcessed       OBJECT-TYPE
	SYNTAX                          Counter32
        MAX-ACCESS                      read-only
        STATUS                          deprecated
	DESCRIPTION
			"Number of Packets successfully processed
			since the last reboot/reset of the switch.
			This object returns the least
			significant 32 bits of the 64 bit unsigned integer.
			This object is deprecated - Use switch64PacketsProcessed
			instead."
	::= { switchEntry 11 }

	switchHighPacketsRejected       OBJECT-TYPE
	SYNTAX                          Counter32
        MAX-ACCESS                      read-only
        STATUS                          deprecated
	DESCRIPTION
			"Number of Packets rejected
			since the last reboot/reset of the switch.
			This object returns the most
			significant 32 bits of the 64 bit unsigned integer.
			This object is deprecated - Use switch64PacketsRejected
			instead."
	::= { switchEntry 12 }

	switchLowPacketsRejected        OBJECT-TYPE
	SYNTAX                          Counter32
        MAX-ACCESS                      read-only
        STATUS                          deprecated
	DESCRIPTION
			"Number of Packets rejected
			since the last reboot/reset of the switch.
			This object returns the least
			significant 32 bits of the 64 bit unsigned integer.
			This object is deprecated - Use switch64PacketsRejected
			instead."
	::= { switchEntry 13 }

	switchFabricIndex               OBJECT-TYPE
	SYNTAX                          Integer32 (1..2147483647)
        MAX-ACCESS                      read-only
        STATUS                          current
	DESCRIPTION
			"The index of the fabric on which this switch
			resides.  The value ranges from 1 to the value
			of fabricInstances."
	::= { switchEntry 14 }

	switch64PacketsProcessed        OBJECT-TYPE
	SYNTAX                          Counter64
        MAX-ACCESS                      read-only
        STATUS                          current
	DESCRIPTION
			"Number of Packets successfully processed
			since the last reboot/reset of the switch.
			This object returns all of the 64 bit unsigned
			integer."
	::= { switchEntry 15 }

	switch64PacketsRejected         OBJECT-TYPE
	SYNTAX                          Counter64
        MAX-ACCESS                      read-only
        STATUS                          current
	DESCRIPTION
			"Number of Packets rejected since the last
			reboot/reset of the switch. This object returns
			all of the 64 bit unsigned integer."
	::= { switchEntry 16 }

	portTable                       OBJECT-TYPE
	SYNTAX                          SEQUENCE OF PortEntry
        MAX-ACCESS                      not-accessible
        STATUS                          current
	DESCRIPTION
			"Provide a list of ports
			connected to the fabric."
	::= { fabric 4 }

	portEntry                       OBJECT-TYPE
	SYNTAX                          PortEntry
        MAX-ACCESS                      not-accessible
        STATUS                          current
	DESCRIPTION
			"Provide a report of current configuration and
			status of ports in the fabric."

	INDEX	{ portFabricIndex, portSwitchIndex, portIndex }
	::= { portTable 1 }

	PortEntry ::=
	    SEQUENCE {
		portIndex
		    Integer32,
		portName
		    OCTET STRING,
		portSwitchIndex
		    Integer32,
		portSwitchName
		    OCTET STRING,
		portNumber
		    Integer32,
		portType
		    INTEGER,
		portState
		    INTEGER,
		portFabricIndex
		    Integer32
	    }

	portIndex                       OBJECT-TYPE
	SYNTAX                          Integer32 (1..2147483647)
        MAX-ACCESS                      read-only
        STATUS                          current
	DESCRIPTION
			"A number that identifies this port entry."
	::= { portEntry 1 }

	portName                        OBJECT-TYPE
	SYNTAX                          OCTET STRING (SIZE (8))
        MAX-ACCESS                      read-only
        STATUS                          current
	DESCRIPTION
			"This is the WWN of the port."
	::= { portEntry 2 }

	portSwitchIndex                 OBJECT-TYPE
	SYNTAX                          Integer32 (1..2147483647)
        MAX-ACCESS                      read-only
        STATUS                          current
	DESCRIPTION
			"The index of the switch on which this port
			resides.  The value ranges from 1 to the number of
			of switches."
	::= { portEntry 3 }

	portSwitchName                  OBJECT-TYPE
	SYNTAX                          OCTET STRING (SIZE (8))
        MAX-ACCESS                      read-only
        STATUS                          current
	DESCRIPTION
			"This is the WWN of the switch to which
			the port is attached."
	::= { portEntry 4 }

	portNumber                      OBJECT-TYPE
	SYNTAX                          Integer32
        MAX-ACCESS                      read-only
        STATUS                          current
	DESCRIPTION
			"The port number on the switch."
	::= { portEntry 5 }

	portType                        OBJECT-TYPE
	SYNTAX                          INTEGER {
                                             unidentified(1),
                                             nPort(2),
					     nlPort(3),
					     fPort(4),
					     flPort(5),
					     ePort(6),
                                             bPort(7)
                                        }
        MAX-ACCESS                      read-only
        STATUS                          current
	DESCRIPTION
			"The type of the port."
	::= { portEntry 6 }

	portState                       OBJECT-TYPE
	SYNTAX                          INTEGER {
                                             online(1),
                                             offline(2),
					     testing(3),
					     faulty(4),
                                             unknown(5)
                                        }
        MAX-ACCESS                      read-only
        STATUS                          current
	DESCRIPTION
			"The current state of the port."
	::= { portEntry 7 }

	portFabricIndex                 OBJECT-TYPE
	SYNTAX                          Integer32 (1..2147483647)
        MAX-ACCESS                      read-only
        STATUS                          current
	DESCRIPTION
			"The index of the fabric on which this port
			resides.  The value ranges from 1 to the value
			of fabricInstances."
	::= { portEntry 8 }

	-- -- -- -- -- -- -- -- -- -- -- -- --
	-- The backup(dump/restore) group   --
	-- -- -- -- -- -- -- -- -- -- -- -- --

	dump	OBJECT	IDENTIFIER ::= { backup 1 }

	restore OBJECT	IDENTIFIER ::= { backup 2 }

	-- dump --

	dmpActives                      OBJECT-TYPE
	SYNTAX                          Integer32
        MAX-ACCESS                      read-only
        STATUS                          obsolete
	DESCRIPTION
		"Number of active dump."
	::= { dump 1 }

	dmpAttempts                     OBJECT-TYPE
	SYNTAX                          Counter32
        MAX-ACCESS                      read-only
        STATUS                          obsolete
	DESCRIPTION
		"Number of dump attempted."
	::= { dump 2 }

	dmpSuccesses                    OBJECT-TYPE
	SYNTAX                          Counter32
        MAX-ACCESS                      read-only
        STATUS                          obsolete
	DESCRIPTION
		"Number of dump succeeded."
	::= { dump 3 }

	dmpFailures                     OBJECT-TYPE
	SYNTAX                          Counter32
        MAX-ACCESS                      read-only
        STATUS                          obsolete
	DESCRIPTION
		"Number of dump failed."
	::= { dump 4 }

	dmpTable                        OBJECT-TYPE
	SYNTAX                          SEQUENCE OF DmpEntry
        MAX-ACCESS                      not-accessible
        STATUS                          obsolete
	DESCRIPTION
				"Provides a report of dumps on each
				 dump subtree."
	::= { dump 5 }

        -- dmpTable contained two entries named lastdump and lastsuccess that
        -- were incompatible with many mib compilers. These are replaced
        -- with objects that work better with these compilers.

	dmpEntry                        OBJECT-TYPE
	SYNTAX                          DmpEntry
        MAX-ACCESS                      not-accessible
        STATUS                          obsolete
	DESCRIPTION
				"Shows statistics of dumps on an unique
				 dump subtree."
	INDEX	{ dmpIndex }
	::= { dmpTable 1 }

	DmpEntry ::=
	    SEQUENCE {
	    	dmpIndex
			Integer32,
	    	dmpStPath
			DisplayString,
		dmpStAttempts
			Counter32,
		dmpStSuccesses
			Counter32,
		dmpStFailures
			Counter32,
	    	dmpTime
			Integer32,
		dmpStatus
		        INTEGER,
-- lastdump entries
	    	dmpLevel
			Integer32,
		dmpNumFiles
		        Integer32,
-- lastsuccess entries
		dmpDataAmount
		        Integer32,
		dmpStartTime
		        Integer32,
		dmpDuration
		        TimeTicks
	    }

	dmpIndex                        OBJECT-TYPE
	SYNTAX                          Integer32 (1..2147483647)
        MAX-ACCESS                      read-only
        STATUS                          obsolete
	DESCRIPTION
				"Index into the subtree dump table."
	::= { dmpEntry 1 }

	dmpStPath                       OBJECT-TYPE
	SYNTAX                          DisplayString
        MAX-ACCESS                      read-only
        STATUS                          obsolete
	DESCRIPTION
				"The full path to the dump subtree. In the
				 format of /vol/<volname>/..."
	::= { dmpEntry 2 }

	dmpStAttempts                   OBJECT-TYPE
	SYNTAX                          Counter32
        MAX-ACCESS                      read-only
        STATUS                          obsolete
	DESCRIPTION
				"No. of dump attempted for the subtree."
	::= { dmpEntry 3 }

	dmpStSuccesses                  OBJECT-TYPE
	SYNTAX                          Counter32
        MAX-ACCESS                      read-only
        STATUS                          obsolete
	DESCRIPTION
				"No. of dump succeeded for the subtree."
	::= { dmpEntry 4 }

	dmpStFailures                   OBJECT-TYPE
	SYNTAX                          Counter32
        MAX-ACCESS                      read-only
        STATUS                          obsolete
	DESCRIPTION
				"No. of dump failed for the subtree."
	::= { dmpEntry 5 }

	dmpTime                         OBJECT-TYPE
	SYNTAX                          Integer32
        MAX-ACCESS                      read-only
        STATUS                          obsolete
	DESCRIPTION
				"The start time for the last attempt
				 to dump the subtree, including the
				 currently running one. The time in
				 seconds since January 1, 1970."
	::= { dmpEntry 6 }

        dmpStatus                       OBJECT-TYPE
	SYNTAX                          INTEGER {
	                                     active(1),
					     restartable(2),
					     succeeded(3),
					     failed(4)
					}
        MAX-ACCESS                      read-only
        STATUS                          obsolete
	DESCRIPTION		"The status for the last dump attempt
				 on the subtree."
	::= { dmpEntry 7 }

	dmpLevel                        OBJECT-TYPE
	SYNTAX                          Integer32 (0..9)
        MAX-ACCESS                      read-only
        STATUS                          obsolete
	DESCRIPTION
				"The level of the dump."
	::= { dmpEntry 8 }

	dmpNumFiles                     OBJECT-TYPE
	SYNTAX                          Integer32
        MAX-ACCESS                      read-only
        STATUS                          obsolete
	DESCRIPTION
				"The number of files dumped."
	::= { dmpEntry 9 }

	dmpDataAmount                   OBJECT-TYPE
	SYNTAX                          Integer32
        MAX-ACCESS                      read-only
        STATUS                          obsolete
	DESCRIPTION
				"The amount of data dumped, in Megabytes."
	::= { dmpEntry 10 }

	dmpStartTime                    OBJECT-TYPE
	SYNTAX                          Integer32
        MAX-ACCESS                      read-only
        STATUS                          obsolete
	DESCRIPTION
				"The start time of the dump. The time is
				 in seconds since January 1, 1970."
	::= { dmpEntry 11 }

	dmpDuration                     OBJECT-TYPE
	SYNTAX                          TimeTicks
        MAX-ACCESS                      read-only
        STATUS                          obsolete
	DESCRIPTION
				"The duration of the dump."
	::= { dmpEntry 12 }

	-- restore --

	rstActives                      OBJECT-TYPE
	SYNTAX                          Integer32
        MAX-ACCESS                      read-only
        STATUS                          obsolete
	DESCRIPTION
		"Number of active restore."
	::= { restore 1 }

	rstAttempts                     OBJECT-TYPE
	SYNTAX                          Counter32
        MAX-ACCESS                      read-only
        STATUS                          obsolete
	DESCRIPTION
		"Number of restore attempted."
	::= { restore 2 }

	rstSuccesses                    OBJECT-TYPE
	SYNTAX                          Counter32
        MAX-ACCESS                      read-only
        STATUS                          obsolete
	DESCRIPTION
		"Number of restore succeeded."
	::= { restore 3 }

	rstFailures                     OBJECT-TYPE
	SYNTAX                          Counter32
        MAX-ACCESS                      read-only
        STATUS                          obsolete
	DESCRIPTION
		"Number of restore failed."
	::= { restore 4 }

	-- -- -- -- -- -- -- --
	-- DAFS Option group --
	-- -- -- -- -- -- -- --

	dafsOptions		OBJECT IDENTIFIER ::= {dafs 1}

	dafsIsLicensed                  OBJECT-TYPE
	SYNTAX                          INTEGER {
                                             false(1),
                                             true(2)
                                        }
        MAX-ACCESS                      read-only
        STATUS                          obsolete
	DESCRIPTION
		"Whether the dafs protocol is licensed on the filer.
		Data ONTAP Specific"
	::= { dafsOptions 1 }

	dafsMaxRequestsServer           OBJECT-TYPE
	SYNTAX                          Integer32
        MAX-ACCESS                      read-only
        STATUS                          obsolete
	DESCRIPTION
		"Server wide maximum number of concurrent requests
		Data ONTAP Specific"
	::= { dafsOptions 2 }

	dafsMaxRequests                 OBJECT-TYPE
	SYNTAX                          Integer32
        MAX-ACCESS                      read-only
        STATUS                          obsolete
	DESCRIPTION
		"Server maximum number of concurrent requests per session
		Data ONTAP Specific"
	::= { dafsOptions 3 }

	dafsMaxRequestSize              OBJECT-TYPE
	SYNTAX                          Integer32
        MAX-ACCESS                      read-only
        STATUS                          current
	DESCRIPTION
		"Server maximum size of an inline request"
	::= { dafsOptions 4 }

	dafsMaxResponseSize             OBJECT-TYPE
	SYNTAX                          Integer32
        MAX-ACCESS                      read-only
        STATUS                          current
	DESCRIPTION
		"Server maximum size of an inline response"
	::= { dafsOptions 5 }


	dafsMaxPendingRequestsServer    OBJECT-TYPE
	SYNTAX                          Integer32
        MAX-ACCESS                      read-only
        STATUS                          obsolete
	DESCRIPTION
		"Server wide maximum number of requests that can queue
		waiting for resources Data ONTAP Specific"
	::= { dafsOptions 6 }

	dafsUseChecksums                OBJECT-TYPE
	SYNTAX                          INTEGER	{
				false(1),
				true(2)
			}
        MAX-ACCESS                      read-only
        STATUS                          current
	DESCRIPTION
		"Server uses checksums"
	::= { dafsOptions 7 }

	dafsNicNumRequestDemons         OBJECT-TYPE
	SYNTAX                          Integer32
        MAX-ACCESS                      read-only
        STATUS                          obsolete
	DESCRIPTION
		"Server default number of request demons per Nic.
		Data ONTAP Specific"
	::= { dafsOptions 8 }

	dafsAnonymousAuthentication     OBJECT-TYPE
	SYNTAX                          INTEGER {
                                             false(1),
                                             true(2)
                                        }
        MAX-ACCESS                      read-only
        STATUS                          current
	DESCRIPTION
		"Allow the server to accept connections with
		authentication type NONE."
	::= { dafsOptions 9 }

	dafsServerEnabled               OBJECT-TYPE
	SYNTAX                          INTEGER {
                                             false(1),
                                             true(2)
                                        }
        MAX-ACCESS                      read-only
        STATUS                          current
	DESCRIPTION
		"Current status of the DAFS server. If true, the DAFS
		server is running."
	::= { dafsOptions 10 }

	dafsDefaultUid                  OBJECT-TYPE
	SYNTAX                          Integer32
        MAX-ACCESS                      read-only
        STATUS                          current
	DESCRIPTION
		"Default client User ID if anonymously connected."
	::= { dafsOptions 11 }

	dafsDefaultGid                  OBJECT-TYPE
	SYNTAX                          Integer32
        MAX-ACCESS                      read-only
        STATUS                          current
	DESCRIPTION
		"Default client Group ID if anonymously connected."
	::= { dafsOptions 12 }

	dafsMaxDisconnectedSessions     OBJECT-TYPE
	SYNTAX                          Integer32
        MAX-ACCESS                      read-only
        STATUS                          current
	DESCRIPTION
		"Maximum number of disconnected sessions for which the
		DAFS server will retain response cache data."
	::= { dafsOptions 13 }

        dafsMaxIdleSeconds              OBJECT-TYPE
	SYNTAX                          Integer32
        MAX-ACCESS                      read-only
        STATUS                          current
        DESCRIPTION
                "Maximum number of seconds server will keep a session
                open without hearing from the client."
        ::= { dafsOptions 14 }

	-- the DAFS VI Nic table

	-- The DAFS VI Nic table contains information about this
	-- entity's VI nics attached to DAFS

	dafsNicTable                    OBJECT-TYPE
	SYNTAX                          SEQUENCE OF DafsNicEntry
        MAX-ACCESS                      not-accessible
        STATUS                          current
	DESCRIPTION
                      "A table containing DAFS NIC specific
                      information."
       	::= { dafs 2 }

	dafsNicEntry                    OBJECT-TYPE
	SYNTAX                          DafsNicEntry
        MAX-ACCESS                      not-accessible
        STATUS                          current
	DESCRIPTION
                      "Information about a particular current DAFS
                      nic.  An object of this type is transient,
                      in that it ceases to exist when (or soon after)
                      the nic is detached."
	INDEX   { dafsNicIndex }
              ::= { dafsNicTable 1 }

	DafsNicEntry ::=
	SEQUENCE	{
			dafsNicIndex
				Integer32,
			dafsNicName
				DisplayString,
			dafsNicDevice
				DisplayString,
			dafsNicState
				INTEGER,
			dafsNicListenAddr
				OCTET STRING,
			dafsNicNumRqstDemons
				Integer32,
			dafsNicInBytes
				Counter32,
			dafsNicDirectInBytes
				Counter32,
			dafsNicOutBytes
				Counter32,
			dafsNicDirectOutBytes
				Counter32
			}

	dafsNicIndex                    OBJECT-TYPE
	SYNTAX                          Integer32 (1..2147483647)
        MAX-ACCESS                      read-only
        STATUS                          current
	DESCRIPTION
                      "A unique value for each interface.  Its value
                      ranges between 1 and the value of DafsNicNumber.  The
                      value for each interface must remain constant at
                      least from one re-initialization of the entity's
                      network management system to the next re-
                      initialization."
	::= { dafsNicEntry 1 }

	dafsNicName                     OBJECT-TYPE
	SYNTAX                          DisplayString (SIZE (0..255))
        MAX-ACCESS                      read-only
        STATUS                          current
	DESCRIPTION
                      "A textual string containing the logical name
                      under which the nic has been attached."
	::= { dafsNicEntry 2}

	dafsNicDevice                   OBJECT-TYPE
	SYNTAX                          DisplayString (SIZE (0..255))
        MAX-ACCESS                      read-only
        STATUS                          current
	DESCRIPTION
                      "A textual string containing the physical name
                      of the nic that has been attached."
	::= { dafsNicEntry 3}

	dafsNicState                    OBJECT-TYPE
	SYNTAX                          INTEGER {
                                             up(1), 	-- ready to pass packets
                                             down(2),
                                             testing(3) -- in some test mode
                                        }
        MAX-ACCESS                      read-only
        STATUS                          current
	DESCRIPTION
		"Current state of DAFS nic"
	::= { dafsNicEntry 4 }

	dafsNicListenAddr               OBJECT-TYPE
	SYNTAX                          OCTET STRING
        MAX-ACCESS                      read-only
        STATUS                          current
	DESCRIPTION
                      "Transport specific address structure giving the
		      DAFS listen address for this NIC."
	::= { dafsNicEntry 5}


	dafsNicNumRqstDemons            OBJECT-TYPE
	SYNTAX                          Integer32
        MAX-ACCESS                      read-only
        STATUS                          obsolete
	DESCRIPTION
                      "Number of request demons assigned to this Nic
		      to handle Nic related events. Data ONTAP Specific"
	::= { dafsNicEntry 6}

	dafsNicInBytes                  OBJECT-TYPE
	SYNTAX                          Counter32
        MAX-ACCESS                      read-only
        STATUS                          current
	DESCRIPTION
                      "Total number of bytes, include DMA, received on
		      this interface"
	::= { dafsNicEntry 7}

	dafsNicDirectInBytes            OBJECT-TYPE
	SYNTAX                          Counter32
        MAX-ACCESS                      read-only
        STATUS                          current
	DESCRIPTION
                      "Total number of bytes read directly from the
		      peer memory through this interface"
	::= { dafsNicEntry 8}

	dafsNicOutBytes                 OBJECT-TYPE
	SYNTAX                          Counter32
        MAX-ACCESS                      read-only
        STATUS                          current
	DESCRIPTION
                      "Total number of bytes, include DMA, sent on
		      this interface"
	::= { dafsNicEntry 9}

	dafsNicDirectOutBytes           OBJECT-TYPE
	SYNTAX                          Counter32
        MAX-ACCESS                      read-only
        STATUS                          current
	DESCRIPTION
                      "Total number of bytes written directly to the
		      peer memory through this interface"
	::= { dafsNicEntry 10}

	-- -- -- -- -- -- -- -- -- --
	-- DAFS Server Statistics  --
	-- -- -- -- -- -- -- -- -- --

	curDafs	OBJECT IDENTIFIER ::= {dafs 3}

	dafsPendingRequests             OBJECT-TYPE
	SYNTAX                          Integer32
        MAX-ACCESS                      read-only
        STATUS                          obsolete
	DESCRIPTION
		"Server wide current number of requests that are
		queued waiting for resources Data ONTAP Specific"
	::= { curDafs 1 }

	dafsCurrentRequests             OBJECT-TYPE
	SYNTAX                          Integer32
        MAX-ACCESS                      read-only
        STATUS                          obsolete
	DESCRIPTION
		"Server wide current number of active requests
		Data ONTAP Specific"
	::= { curDafs 2 }

	totDafs	OBJECT IDENTIFIER ::= {dafs 4}

	dafsCalls                       OBJECT-TYPE
	SYNTAX                          Counter32
        MAX-ACCESS                      read-only
        STATUS                          current
	DESCRIPTION
		"Total number of DAFS calls since last reboot"
	::= { totDafs 1 }

	dafsClientAuths                 OBJECT-TYPE
	SYNTAX                          Counter32
        MAX-ACCESS                      read-only
        STATUS                          current
	DESCRIPTION
		"Total number of Client Auth calls since last reboot"
	::= { totDafs 2 }

	dafsClientConnects              OBJECT-TYPE
	SYNTAX                          Counter32
        MAX-ACCESS                      read-only
        STATUS                          current
	DESCRIPTION
		"Total number of Client Connect calls since last reboot"
	::= { totDafs 3 }

	dafsClientConnectAuths          OBJECT-TYPE
	SYNTAX                          Counter32
        MAX-ACCESS                      read-only
        STATUS                          current
	DESCRIPTION
		"Total number of Client Connect Auth calls since last reboot"
	::= { totDafs 4 }

	dafsConnectBinds                OBJECT-TYPE
	SYNTAX                          Counter32
        MAX-ACCESS                      read-only
        STATUS                          current
	DESCRIPTION
		"Total number of Connect Bind calls since last reboot"
	::= { totDafs 5 }

	dafsDisconnects                 OBJECT-TYPE
	SYNTAX                          Counter32
        MAX-ACCESS                      read-only
        STATUS                          current
	DESCRIPTION
		"Total number of Disconnect calls since last reboot"
	::= { totDafs 6 }

	dafsRegisterCreds               OBJECT-TYPE
	SYNTAX                          Counter32
        MAX-ACCESS                      read-only
        STATUS                          current
	DESCRIPTION
		"Total number of Register Credential calls since last reboot"
	::= { totDafs 7 }

	dafsReleaseCreds                OBJECT-TYPE
	SYNTAX                          Counter32
        MAX-ACCESS                      read-only
        STATUS                          current
	DESCRIPTION
		"Total number of Release Credential calls since last reboot"
	::= { totDafs 8 }

	dafsSecinfos                    OBJECT-TYPE
	SYNTAX                          Counter32
        MAX-ACCESS                      read-only
        STATUS                          current
	DESCRIPTION
		"Total number of Secinfo calls since last reboot"
	::= { totDafs 9 }

	dafsServerAuths                 OBJECT-TYPE
	SYNTAX                          Counter32
        MAX-ACCESS                      read-only
        STATUS                          current
	DESCRIPTION
		"Total number of Server Auth calls since last reboot"
	::= { totDafs 10 }

	dafsCheckResponses              OBJECT-TYPE
	SYNTAX                          Counter32
        MAX-ACCESS                      read-only
        STATUS                          current
	DESCRIPTION
		"Total number of Check Response calls since last reboot"
	::= { totDafs 11 }

	dafsFetchResponses              OBJECT-TYPE
	SYNTAX                          Counter32
        MAX-ACCESS                      read-only
        STATUS                          current
	DESCRIPTION
		"Total number of Fetch Response calls since last reboot"
	::= { totDafs 12 }

	dafsDiscardResponses            OBJECT-TYPE
	SYNTAX                          Counter32
        MAX-ACCESS                      read-only
        STATUS                          current
	DESCRIPTION
		"Total number of Discard Responses calls since last reboot"
	::= { totDafs 13 }

	dafsAccesses                    OBJECT-TYPE
	SYNTAX                          Counter32
        MAX-ACCESS                      read-only
        STATUS                          current
	DESCRIPTION
		"Total number of Access calls since last reboot"
	::= { totDafs 14 }

	dafsCacheHints                  OBJECT-TYPE
	SYNTAX                          Counter32
        MAX-ACCESS                      read-only
        STATUS                          current
	DESCRIPTION
		"Total number of Cache Hint calls since last reboot"
	::= { totDafs 15 }

	dafsCloses                      OBJECT-TYPE
	SYNTAX                          Counter32
        MAX-ACCESS                      read-only
        STATUS                          current
	DESCRIPTION
		"Total number of Close calls since last reboot"
	::= { totDafs 16 }

	dafsCommits                     OBJECT-TYPE
	SYNTAX                          Counter32
        MAX-ACCESS                      read-only
        STATUS                          current
	DESCRIPTION
		"Total number of Commit calls since last reboot"
	::= { totDafs 17 }

	dafsCreates                     OBJECT-TYPE
	SYNTAX                          Counter32
        MAX-ACCESS                      read-only
        STATUS                          current
	DESCRIPTION
		"Total number of Create calls since last reboot"
	::= { totDafs 18 }

	dafsDelegPurges                 OBJECT-TYPE
	SYNTAX                          Counter32
        MAX-ACCESS                      read-only
        STATUS                          current
	DESCRIPTION
		"Total number of Delegate Purge calls since last reboot"
	::= { totDafs 19 }

	dafsDelegReturns                OBJECT-TYPE
	SYNTAX                          Counter32
        MAX-ACCESS                      read-only
        STATUS                          current
	DESCRIPTION
		"Total number of Delegate Return calls since last reboot"
	::= { totDafs 20 }

	dafsGetFsattrs                  OBJECT-TYPE
	SYNTAX                          Counter32
        MAX-ACCESS                      read-only
        STATUS                          current
	DESCRIPTION
		"Total number of Get Fsattr  calls since last reboot"
	::= { totDafs 21 }

	dafsGetRootHandles              OBJECT-TYPE
	SYNTAX                          Counter32
        MAX-ACCESS                      read-only
        STATUS                          current
	DESCRIPTION
		"Total number of Get Root Handle calls since last reboot"
	::= { totDafs 22 }

	dafsGetattrInlines              OBJECT-TYPE
	SYNTAX                          Counter32
        MAX-ACCESS                      read-only
        STATUS                          current
	DESCRIPTION
		"Total number of Getattr Inline calls since last reboot"
	::= { totDafs 23 }

	dafsGetattrDirects              OBJECT-TYPE
	SYNTAX                          Counter32
        MAX-ACCESS                      read-only
        STATUS                          current
	DESCRIPTION
		"Total number of Getattr Direct calls since last reboot"
	::= { totDafs 24 }

	dafsLinks                       OBJECT-TYPE
	SYNTAX                          Counter32
        MAX-ACCESS                      read-only
        STATUS                          current
	DESCRIPTION
		"Total number of Link calls since last reboot"
	::= { totDafs 25 }

	dafsLocks                       OBJECT-TYPE
	SYNTAX                          Counter32
        MAX-ACCESS                      read-only
        STATUS                          current
	DESCRIPTION
		"Total number of Lock calls since last reboot"
	::= { totDafs 26 }

	dafsLockts                      OBJECT-TYPE
	SYNTAX                          Counter32
        MAX-ACCESS                      read-only
        STATUS                          current
	DESCRIPTION
		"Total number of LockT calls since last reboot"
	::= { totDafs 27}

	dafsLockus                      OBJECT-TYPE
	SYNTAX                          Counter32
        MAX-ACCESS                      read-only
        STATUS                          current
	DESCRIPTION
		"Total number of LockU calls since last reboot"
	::= { totDafs 28 }

	dafsLookUps                     OBJECT-TYPE
	SYNTAX                          Counter32
        MAX-ACCESS                      read-only
        STATUS                          current
	DESCRIPTION
		"Total number of LookUp calls since last reboot"
	::= { totDafs 29 }

	dafsLookUpps                    OBJECT-TYPE
	SYNTAX                          Counter32
        MAX-ACCESS                      read-only
        STATUS                          current
	DESCRIPTION
		"Total number of LookUpp calls since last reboot"
	::= { totDafs 30 }

	dafsNulls                       OBJECT-TYPE
	SYNTAX                          Counter32
        MAX-ACCESS                      read-only
        STATUS                          current
	DESCRIPTION
		"Total number of Null calls since last reboot"
	::= { totDafs 31 }

	dafsNverifys                    OBJECT-TYPE
	SYNTAX                          Counter32
        MAX-ACCESS                      read-only
        STATUS                          current
	DESCRIPTION
		"Total number of Nverify calls since last reboot"
	::= { totDafs 32 }

	dafsOpens                       OBJECT-TYPE
	SYNTAX                          Counter32
        MAX-ACCESS                      read-only
        STATUS                          current
	DESCRIPTION
		"Total number of Open calls since last reboot"
	::= { totDafs 33 }

	dafsOpenDowngrades              OBJECT-TYPE
	SYNTAX                          Counter32
        MAX-ACCESS                      read-only
        STATUS                          current
	DESCRIPTION
		"Total number of Open Downgrade calls since last reboot"
	::= { totDafs 34 }

	dafsOpenattrs                   OBJECT-TYPE
	SYNTAX                          Counter32
        MAX-ACCESS                      read-only
        STATUS                          current
	DESCRIPTION
		"Total number of Openattr calls since last reboot"
	::= { totDafs 35 }

	dafsReadInlines                 OBJECT-TYPE
	SYNTAX                          Counter32
        MAX-ACCESS                      read-only
        STATUS                          current
	DESCRIPTION
		"Total number of Read Inline calls since last reboot"
	::= { totDafs 36 }

	dafsReadDirects                 OBJECT-TYPE
	SYNTAX                          Counter32
        MAX-ACCESS                      read-only
        STATUS                          current
	DESCRIPTION
		"Total number of Read Direct calls since last reboot"
	::= { totDafs 37 }

	dafsReaddirInlines              OBJECT-TYPE
	SYNTAX                          Counter32
        MAX-ACCESS                      read-only
        STATUS                          current
	DESCRIPTION
		"Total number of Readdir Inline calls since last reboot"
	::= { totDafs 38 }

	dafsReaddirDirects              OBJECT-TYPE
	SYNTAX                          Counter32
        MAX-ACCESS                      read-only
        STATUS                          current
	DESCRIPTION
		"Total number of Readdir Direct calls since last reboot"
	::= { totDafs 39 }

	dafsReadlinkInlines             OBJECT-TYPE
	SYNTAX                          Counter32
        MAX-ACCESS                      read-only
        STATUS                          current
	DESCRIPTION
		"Total number of Readlink Inline calls since last reboot"
	::= { totDafs 40 }

	dafsReadlinkDirects             OBJECT-TYPE
	SYNTAX                          Counter32
        MAX-ACCESS                      read-only
        STATUS                          current
	DESCRIPTION
		"Total number of Readlink Direct calls since last reboot"
	::= { totDafs 41 }

	dafsRemoves                     OBJECT-TYPE
	SYNTAX                          Counter32
        MAX-ACCESS                      read-only
        STATUS                          current
	DESCRIPTION
		"Total number of Remove calls since last reboot"
	::= { totDafs 42 }

	dafsRenames                     OBJECT-TYPE
	SYNTAX                          Counter32
        MAX-ACCESS                      read-only
        STATUS                          current
	DESCRIPTION
		"Total number of Rename calls since last reboot"
	::= { totDafs 43 }

	dafsSetattrInlines              OBJECT-TYPE
	SYNTAX                          Counter32
        MAX-ACCESS                      read-only
        STATUS                          current
	DESCRIPTION
		"Total number of Setattr Inline calls since last reboot"
	::= { totDafs 44 }

	dafsSetattrDirects              OBJECT-TYPE
	SYNTAX                          Counter32
        MAX-ACCESS                      read-only
        STATUS                          current
	DESCRIPTION
		"Total number of Setattr Direct calls since last reboot"
	::= { totDafs 45 }

	dafsVerifys                     OBJECT-TYPE
	SYNTAX                          Counter32
        MAX-ACCESS                      read-only
        STATUS                          current
	DESCRIPTION
		"Total number of Verify calls since last reboot"
	::= { totDafs 46 }

	dafsBatchSubmits                OBJECT-TYPE
	SYNTAX                          Counter32
        MAX-ACCESS                      read-only
        STATUS                          current
	DESCRIPTION
		"Total number of Batch Submit calls since last reboot"
	::= { totDafs 47 }

	dafsWriteInlines                OBJECT-TYPE
	SYNTAX                          Counter32
        MAX-ACCESS                      read-only
        STATUS                          current
	DESCRIPTION
		"Total number of Write Inline calls since last reboot"
	::= { totDafs 48 }

	dafsWriteDirects                OBJECT-TYPE
	SYNTAX                          Counter32
        MAX-ACCESS                      read-only
        STATUS                          current
	DESCRIPTION
		"Total number of Write Direct calls since last reboot"
	::= { totDafs 49 }

	dafsBcGetattrs                  OBJECT-TYPE
	SYNTAX                          Counter32
        MAX-ACCESS                      read-only
        STATUS                          current
	DESCRIPTION
		"Total number of BC Getattr calls since last reboot"
	::= { totDafs 50 }

	dafsBcNulls                     OBJECT-TYPE
	SYNTAX                          Counter32
        MAX-ACCESS                      read-only
        STATUS                          current
	DESCRIPTION
		"Total number of BC Null calls since last reboot"
	::= { totDafs 51 }

	dafsBcRecalls                   OBJECT-TYPE
	SYNTAX                          Counter32
        MAX-ACCESS                      read-only
        STATUS                          current
	DESCRIPTION
		"Total number of BC Recall calls since last reboot"
	::= { totDafs 52 }

	dafsBcBatchCompletions          OBJECT-TYPE
	SYNTAX                          Counter32
        MAX-ACCESS                      read-only
        STATUS                          current
	DESCRIPTION
		"Total number of BC Batch Completion calls since
		last reboot"
	::= { totDafs 53 }

        dafsAppendInlines               OBJECT-TYPE
	SYNTAX                          Counter32
        MAX-ACCESS                      read-only
        STATUS                          current
        DESCRIPTION
                "Total number of Append Inline calls since
                last reboot"
        ::= { totDafs 54 }

        dafsAppendDirects               OBJECT-TYPE
	SYNTAX                          Counter32
        MAX-ACCESS                      read-only
        STATUS                          current
        DESCRIPTION
                "Total number of Append Direct calls since
                last reboot"
        ::= { totDafs 55 }

        dafsGetFencingLists             OBJECT-TYPE
	SYNTAX                          Counter32
        MAX-ACCESS                      read-only
        STATUS                          current
        DESCRIPTION
                "Total number of Get Fencing List calls since
                last reboot"
        ::= { totDafs 56 }

        dafsSetFencingLists             OBJECT-TYPE
	SYNTAX                          Counter32
        MAX-ACCESS                      read-only
        STATUS                          current
        DESCRIPTION
                "Total number of Set Fencing List calls since
                last reboot"
        ::= { totDafs 57 }

        dafsHurryUps                    OBJECT-TYPE
	SYNTAX                          Counter32
        MAX-ACCESS                      read-only
        STATUS                          current
        DESCRIPTION
                "Total number of Hurry Up calls since
                last reboot"
        ::= { totDafs 58 }

	dafsInBytes                     OBJECT-TYPE
	SYNTAX                          Counter32
        MAX-ACCESS                      read-only
        STATUS                          current
	DESCRIPTION
		"Total number of bytes, including DMA, received since the
		last reboot"
	::= { totDafs 59 }

	dafsDirectInBytes               OBJECT-TYPE
	SYNTAX                          Counter32
        MAX-ACCESS                      read-only
        STATUS                          current
	DESCRIPTION
		"Total number of bytes received directly into memory
		since last reboot"
	::= { totDafs 60 }

	dafsOutBytes                    OBJECT-TYPE
	SYNTAX                          Counter32
        MAX-ACCESS                      read-only
        STATUS                          current
	DESCRIPTION
		"Total number of bytes, including DMA, sent since the
		last reboot"
	::= { totDafs 61 }

	dafsDirectOutBytes              OBJECT-TYPE
	SYNTAX                          Counter32
        MAX-ACCESS                      read-only
        STATUS                          current
	DESCRIPTION
		"Total number of bytes sent directly into remote memory since
		the last reboot"
	::= { totDafs 62 }

	dafsSessionTable                OBJECT-TYPE
	SYNTAX                          SEQUENCE OF DafsSessionEntry
        MAX-ACCESS                      not-accessible
        STATUS                          current
	DESCRIPTION
                      "A table containing current DAFS client session
                      information."
       	::= { dafs 5 }

	dafsSessionEntry                OBJECT-TYPE
	SYNTAX                          DafsSessionEntry
        MAX-ACCESS                      not-accessible
        STATUS                          current
	DESCRIPTION
                      "Information about a particular DAFS
                      session.  An object of this type is transient,
                      in that it ceases to exist when (or soon after)
                      the client disconnects."

	INDEX   { dafsSessionIndex }
        ::= { dafsSessionTable 1 }

	DafsSessionEntry ::=
            SEQUENCE {
			dafsSessionIndex
				Integer32,
			dafsSessionId
				OCTET STRING,
			dafsSessionEndian
				INTEGER,
			dafsSessionAllowBackChannel
				INTEGER,
			dafsSessionAllowRdmaReadChannel
				INTEGER,
			dafsSessionUseChecksums
				INTEGER,
			dafsSessionMaxCredentials
				Integer32,
			dafsSessionMaxRequestSize
				Integer32,
			dafsSessionMaxResponseSize
				Integer32,
			dafsSessionMaxRequests
				Integer32,
			dafsSessionInlineWriteHeaderSize
				Integer32,
			dafsSessionClientIdString
				OCTET STRING,
			dafsSessionClientVerifier
				OCTET STRING,
			dafsSessionNumCredentials
				Integer32,
			dafsSessionNumRequests
				Integer32
	    }

	dafsSessionIndex                OBJECT-TYPE
	SYNTAX                          Integer32 (1..2147483647)
        MAX-ACCESS                      read-only
        STATUS                          current
	DESCRIPTION
                      "A unique value for each session."
	::= { dafsSessionEntry 1 }

	dafsSessionId                   OBJECT-TYPE
	SYNTAX                          OCTET STRING
        MAX-ACCESS                      read-only
        STATUS                          current
	DESCRIPTION
		"Session Identifier assigned by the server."
	::= { dafsSessionEntry 2 }

	dafsSessionEndian               OBJECT-TYPE
	SYNTAX                          INTEGER {
                                             bigEndian(1),
                                             littleEndian(2)
                                        }
        MAX-ACCESS                      read-only
        STATUS                          current
	DESCRIPTION
		"Byte order used on this session."
	::= { dafsSessionEntry 3 }

	dafsSessionAllowBackChannel     OBJECT-TYPE
	SYNTAX                          INTEGER {
                                             false(1),
                                             true(2)
                                        }
        MAX-ACCESS                      read-only
        STATUS                          current
	DESCRIPTION
		"Session may use a back control channel."
	::= { dafsSessionEntry 4 }

	dafsSessionAllowRdmaReadChannel OBJECT-TYPE
	SYNTAX                          INTEGER {
                                             false(1),
                                             true(2)
                                        }
        MAX-ACCESS                      read-only
        STATUS                          current
	DESCRIPTION
		"Session may use a RDMA read channel."
	::= { dafsSessionEntry 5 }

	dafsSessionUseChecksums         OBJECT-TYPE
	SYNTAX                          INTEGER {
                                             false(1),
                                             true(2)
                                        }
        MAX-ACCESS                      read-only
        STATUS                          current
	DESCRIPTION
		"Session uses checksums."
	::= { dafsSessionEntry 6 }

	dafsSessionMaxCredentials       OBJECT-TYPE
	SYNTAX                          Integer32
        MAX-ACCESS                      read-only
        STATUS                          current
	DESCRIPTION
		"Maximum number of credentials that can be registered
		on this session."
	::= { dafsSessionEntry 7 }

	dafsSessionMaxRequestSize       OBJECT-TYPE
	SYNTAX                          Integer32
        MAX-ACCESS                      read-only
        STATUS                          current
	DESCRIPTION
		"Maximum size of a DAFS request."
	::= { dafsSessionEntry 8 }

	dafsSessionMaxResponseSize      OBJECT-TYPE
	SYNTAX                          Integer32
        MAX-ACCESS                      read-only
        STATUS                          current
	DESCRIPTION
		"Maximum size of a DAFS response."
	::= { dafsSessionEntry 9 }

	dafsSessionMaxRequests          OBJECT-TYPE
	SYNTAX                          Integer32
        MAX-ACCESS                      read-only
        STATUS                          current
	DESCRIPTION
		"Maximum number of concurrent requests."
	::= { dafsSessionEntry 10 }

	dafsSessionInlineWriteHeaderSize OBJECT-TYPE
	SYNTAX                          Integer32
        MAX-ACCESS                      read-only
        STATUS                          current
	DESCRIPTION
		"Size of DAFS headers plus padding to the start of
		data.  Used to better align inline data."
	::= { dafsSessionEntry 11 }

	dafsSessionClientIdString       OBJECT-TYPE
	SYNTAX                          OCTET STRING (SIZE (32))
        MAX-ACCESS                      read-only
        STATUS                          current
	DESCRIPTION
		"Client ID string supplied by the client.  Intended to
		uniquely identify that client."
	::= { dafsSessionEntry 12 }

	dafsSessionClientVerifier       OBJECT-TYPE
	SYNTAX                          OCTET STRING (SIZE (8))
        MAX-ACCESS                      read-only
        STATUS                          current
	DESCRIPTION
		"Supplied by the client to uniquely identify an
		instance of a client."
	::= { dafsSessionEntry 13 }

	dafsSessionNumCredentials       OBJECT-TYPE
	SYNTAX                          Integer32
        MAX-ACCESS                      read-only
        STATUS                          current
	DESCRIPTION
		"Current number of credentials registered on this
		session"
	::= { dafsSessionEntry 14 }

	dafsSessionNumRequests          OBJECT-TYPE
	SYNTAX                          Integer32
        MAX-ACCESS                      read-only
        STATUS                          current
	DESCRIPTION
		"Current number of active requests on this session"
	::= { dafsSessionEntry 15 }

	-- the DAFS Export table

	-- The DAFS Export table contains information about this
	-- entity's exported filesystems

	dafsExportTable                 OBJECT-TYPE
	SYNTAX                          SEQUENCE OF DafsExportEntry
        MAX-ACCESS                      not-accessible
        STATUS                          current
	DESCRIPTION
                      "A table containing DAFS Export filesystems."
       	::= { dafs 6 }

	dafsExportEntry                 OBJECT-TYPE
	SYNTAX                          DafsExportEntry
        MAX-ACCESS                      not-accessible
        STATUS                          current
	DESCRIPTION
                      "Information about a particular current DAFS
                      export.  An object of this type is transient,
                      in that it ceases to exist when (or soon after)
                      the export is deleted."
	INDEX   { dafsExportIndex }
              ::= { dafsExportTable 1 }

	DafsExportEntry ::=
	SEQUENCE	{
			dafsExportIndex
				Integer32,
			dafsExportName
				DisplayString,
			dafsExportPath
				DisplayString,
			dafsExportEnabled
				INTEGER,
			dafsExportRwMode
				INTEGER,
			dafsExportAccessList
				DisplayString
			}

	dafsExportIndex                 OBJECT-TYPE
	SYNTAX                          Integer32 (1..2147483647)
        MAX-ACCESS                      read-only
        STATUS                          current
	DESCRIPTION
                      "A unique value for each export.  Its value
                      ranges between 1 and the number of exports.  The
                      value for each export must remain constant at
                      least from one re-initialization of the entity's
                      network management system to the next re-
                      initialization."
	::= { dafsExportEntry 1 }

	dafsExportName                  OBJECT-TYPE
	SYNTAX                          DisplayString (SIZE (0..255))
        MAX-ACCESS                      read-only
        STATUS                          current
	DESCRIPTION
                      "A textual string containing information about the
                      export.  This is the logical export name."
	::= { dafsExportEntry 2}

	dafsExportPath                  OBJECT-TYPE
	SYNTAX                          DisplayString (SIZE (0..255))
        MAX-ACCESS                      read-only
        STATUS                          current
	DESCRIPTION
                      "A textual string containing information about the
                      export.  This is the local filesystem path to
		      the export."
	::= { dafsExportEntry 3}

	dafsExportEnabled               OBJECT-TYPE
	SYNTAX                          INTEGER {
                                             false(1),
                                             true(2)
                                        }
        MAX-ACCESS                      read-only
        STATUS                          current
	DESCRIPTION
		"This export is available for access."
	::= { dafsExportEntry 4 }

	dafsExportRwMode                OBJECT-TYPE
	SYNTAX                          INTEGER {
                                             readwrite(1),
                                             readmostly(2),
                                             readonly(3)
                                        }
        MAX-ACCESS                      read-only
        STATUS                          current
	DESCRIPTION
		"Global export mode. This represents the maximum
		access rights."
	::= { dafsExportEntry 5 }

	dafsExportAccessList            OBJECT-TYPE
	SYNTAX                          DisplayString (SIZE (0..255))
        MAX-ACCESS                      read-only
        STATUS                          current
	DESCRIPTION
                      "A textual string containing information about the
                      export.  This is the list of hosts that may
		      access the export. If empty, all hosts may
		      access the export."
	::= { dafsExportEntry 6 }

        --------------------------
        -- VI interface statistics
        --------------------------

	viaNodeConnection OBJECT IDENTIFIER ::= { vi 1 }

	viaNodeSystemName               OBJECT-TYPE
	SYNTAX                          DisplayString(SIZE (0..255))
        MAX-ACCESS                      read-only
        STATUS                          current
	DESCRIPTION
	    "A string by which the node is identified in the cluster."
	::= { viaNodeConnection 1 }

	viaCreated                      OBJECT-TYPE
	SYNTAX                          Integer32
	MAX-ACCESS                      read-only
        STATUS                          current
	DESCRIPTION
	    "The number of VIs created."
	::= { viaNodeConnection 2 }

        viaConnectRequest               OBJECT-TYPE
	SYNTAX                          Counter32
        MAX-ACCESS                      read-only
        STATUS                          current
	DESCRIPTION
	    "The number of times Connect Request call is made."
	::= { viaNodeConnection 3 }

        viaConnectWait                  OBJECT-TYPE
	SYNTAX                          Counter32
        MAX-ACCESS                      read-only
        STATUS                          current
	DESCRIPTION
	    "The number of times Connect wait call is made."
	::= { viaNodeConnection 4 }

        viaDisconnect                   OBJECT-TYPE
	SYNTAX                          Counter32
        MAX-ACCESS                      read-only
        STATUS                          current
	DESCRIPTION
	    "Number of times VI got disconnected without any error."
	::= { viaNodeConnection 5 }

        viaConnectTimeOut               OBJECT-TYPE
	SYNTAX                          Counter32
        MAX-ACCESS                      read-only
        STATUS                          current
	DESCRIPTION
	    "Number of times VI connect request got timed out."
	::= { viaNodeConnection 6 }

        viaConnected                    OBJECT-TYPE
	SYNTAX                          Counter32
        MAX-ACCESS                      read-only
        STATUS                          current
	DESCRIPTION
	    "Number of time VI got connected without any error."
	::= { viaNodeConnection 7 }

        viaCurrConnectPending           OBJECT-TYPE
	SYNTAX                          Gauge32
        MAX-ACCESS                      read-only
        STATUS                          current
	DESCRIPTION
	    "The number of VIs for which connect request is pending."
	::= { viaNodeConnection 8 }

        viaCurrConnectWaitPending       OBJECT-TYPE
	SYNTAX                          Gauge32
        MAX-ACCESS                      read-only
        STATUS                          current
	DESCRIPTION
	    "The number of VIs for which connect wait request is pending."
	::= { viaNodeConnection 9 }

        viaCurrConnected                OBJECT-TYPE
	SYNTAX                          Gauge32
        MAX-ACCESS                      read-only
        STATUS                          current
	DESCRIPTION
	    "The number of VIs for which the current state is CONNECTED."
	::= { viaNodeConnection 10 }

        viaCurrError                    OBJECT-TYPE
	SYNTAX                          Gauge32
        MAX-ACCESS                      read-only
        STATUS                          current
	DESCRIPTION
	    "The number of VIs for which the current state is ERROR"
	::= { viaNodeConnection 11 }

        viaTotalError                   OBJECT-TYPE
	SYNTAX                          Counter32
        MAX-ACCESS                      read-only
        STATUS                          current
	DESCRIPTION
	    "The number of VIs which encountered error state."
	::= { viaNodeConnection 12 }

        viaInMsgs                       OBJECT-TYPE
	SYNTAX                          Counter32
        MAX-ACCESS                      read-only
        STATUS                          current
	DESCRIPTION
	    "The total number of incoming Messages received."
	::= { viaNodeConnection 13 }

        viaInRdma                       OBJECT-TYPE
	SYNTAX                          Counter32
        MAX-ACCESS                      read-only
        STATUS                          current
	DESCRIPTION
	    "The total number of incoming RDMA requests received."
	::= { viaNodeConnection 14 }

        viaInBytes                      OBJECT-TYPE
	SYNTAX                          Counter32
        MAX-ACCESS                      read-only
        STATUS                          current
	DESCRIPTION
	    "The total number of incoming bytes received, including those
	    received in error. This count includes bytes received on
	    currently established connections. This corresponds to the sum
	    of bytes received through received messages, incoming RDMA writes
	    and RDMA reads issued"
	::= { viaNodeConnection 15 }

        viaInRDMAReadBytes              OBJECT-TYPE
	SYNTAX                          Counter32
        MAX-ACCESS                      read-only
        STATUS                          current
	DESCRIPTION
	    "The total number of incoming bytes received through RDMA read,
	    including those received in error. This count includes bytes
	    received on currently established connections."
	::= { viaNodeConnection 16 }

        viaInRDMAWriteBytes             OBJECT-TYPE
	SYNTAX                          Counter32
        MAX-ACCESS                      read-only
        STATUS                          current
	DESCRIPTION
	    "The total number of bytes received through incoming RDMA writes,
	    including those received in error. This count includes bytes
	    received on currently established connections."
	::= { viaNodeConnection 17 }

        viaOutMsgs                      OBJECT-TYPE
	SYNTAX                          Counter32
        MAX-ACCESS                      read-only
        STATUS                          current
	DESCRIPTION
	    "The total number of Messages sent."
	::= { viaNodeConnection 18 }

        viaOutRdma                      OBJECT-TYPE
	SYNTAX                          Counter32
        MAX-ACCESS                      read-only
        STATUS                          current
	DESCRIPTION
	    "The total number of RDMA requests sent."
	::= { viaNodeConnection 19 }

        viaOutBytes                     OBJECT-TYPE
	SYNTAX                          Counter32
        MAX-ACCESS                      read-only
        STATUS                          current
	DESCRIPTION
	    "The total number of bytes sent, including those
	    sent in error. This count includes bytes sent on
	    currently established connections."
	::= { viaNodeConnection 20 }

        viaOutRDMAReadBytes             OBJECT-TYPE
	SYNTAX                          Counter32
        MAX-ACCESS                      read-only
        STATUS                          current
	DESCRIPTION
	    "The total number of bytes sent through an incoming
	    RDMA read request, including those sent in error.
	    This count includes bytes sent on currently established
	    connections."
	::= { viaNodeConnection 21 }

        viaOutRDMAWriteBytes            OBJECT-TYPE
	SYNTAX                          Counter32
        MAX-ACCESS                      read-only
        STATUS                          current
	DESCRIPTION
	    "The total number of bytes sent through a RDMA write
	    operation, including those sent in error. This count
	    includes bytes sent on currently established connections."
	::= { viaNodeConnection 22 }


        viaConnTable                    OBJECT-TYPE
	SYNTAX                          SEQUENCE OF ViaConnEntry
        MAX-ACCESS                      not-accessible
        STATUS                          current
	DESCRIPTION
	    "A table containing via connection specific information."
	::= { viaNodeConnection 23 }

        viaConnEntry                    OBJECT-TYPE
	SYNTAX                          ViaConnEntry
        MAX-ACCESS                      not-accessible
        STATUS                          current
	DESCRIPTION
	    "A conceptual row of the viaConnTable containing information
	    about a particular current via connection. Each row of this
	    table is transient, and it ceases to exist when the
	    connection makes transition to the CLOSED state."
	INDEX    { viaConnVINumber }
	::= { viaConnTable 1 }

        ViaConnEntry  ::= SEQUENCE {
	viaConnState                 INTEGER,
	viaConnVINumber              Integer32,
	viaConnRemoteNetAddress      IpAddress,
	viaConnLocalNetAddress       IpAddress,
	viaConnRemotePortNumber      Integer32,
	viaConnLocalPortNumber       Integer32,
	viaConnLocalDescriminator    OCTET STRING,
	viaConnRemoteDescriminator   OCTET STRING,
	viaConnLocalMaxTransferSize  Integer32,
	viaConnRemoteMaxTransferSize Integer32,
	viaConnLocalEnableRdmaWrite  Integer32,
	viaConnLocalEnableRdmaRead   Integer32,
	viaConnRemoteEnableRdmaWrite Integer32,
	viaConnRemoteEnableRdmaRead  Integer32,
	viaConnSentMessages          Counter32,
	viaConnSentRdmaReadMessages  Counter32,
	viaConnSentRdmaWriteMessages Counter32,
	viaConnRcvdMessages          Counter32,
	viaConnRcvdRdmaReadMessages  Counter32,
	viaConnRcvdRdmaWriteMessages Counter32
	}

        viaConnState                    OBJECT-TYPE
	SYNTAX                          INTEGER {
                                             idle (1),
                                             pendingConnect(2),
					     connected(3),
                                             error(4)
                                        }
        MAX-ACCESS                      read-only
        STATUS                          current
	DESCRIPTION
            "The state of this via connection
             Legal States:
                   Idle            1
                   Pending Connect 2
                   Connected       3
                   Error           4"
	::= { viaConnEntry 1 }

        viaConnVINumber                 OBJECT-TYPE
	SYNTAX                          Integer32 (1..2147483647)
        MAX-ACCESS                      read-only
        STATUS                          current
	DESCRIPTION
	    "A number which uniquely defines a     connection."
	::= { viaConnEntry 2 }

        viaConnRemoteNetAddress         OBJECT-TYPE
	SYNTAX                          IpAddress
        MAX-ACCESS                      read-only
        STATUS                          current
	DESCRIPTION
	    "IP address of the remote system of the connection."
	::= { viaConnEntry 3 }

        viaConnLocalNetAddress          OBJECT-TYPE
	SYNTAX                          IpAddress
        MAX-ACCESS                      read-only
        STATUS                          current
	DESCRIPTION
	    "Local IP address of the connection."
	::= { viaConnEntry 4 }

        viaConnRemotePortNumber         OBJECT-TYPE
	SYNTAX                          Integer32
        MAX-ACCESS                      read-only
        STATUS                          current
	DESCRIPTION
	    "Remote TCP port number of the connection."
	::= { viaConnEntry 5 }

        viaConnLocalPortNumber          OBJECT-TYPE
	SYNTAX                          Integer32
        MAX-ACCESS                      read-only
        STATUS                          current
	DESCRIPTION
	    "Local TCP port number of the connection."
	::= { viaConnEntry 6 }

        viaConnLocalDescriminator       OBJECT-TYPE
	SYNTAX                          OCTET STRING
        MAX-ACCESS                      read-only
        STATUS                          current
	DESCRIPTION
	    "An identifier used by the local process to identify the
	    VI connection."
	::= { viaConnEntry 7 }

        viaConnRemoteDescriminator      OBJECT-TYPE
	SYNTAX                          OCTET STRING
        MAX-ACCESS                      read-only
        STATUS                          current
	DESCRIPTION
	    "An identifier used by the remote process to identify the
	    VI connection."
	::= { viaConnEntry 8 }

        viaConnLocalMaxTransferSize     OBJECT-TYPE
	SYNTAX                          Integer32
        MAX-ACCESS                      read-only
        STATUS                          current
	DESCRIPTION
	    "The local limit on the maximum packet size that can be
	    transferred through the connection."
	::= { viaConnEntry 9 }

        viaConnRemoteMaxTransferSize    OBJECT-TYPE
	SYNTAX                          Integer32
        MAX-ACCESS                      read-only
        STATUS                          current
	DESCRIPTION
	    "The remote limit on the maximum packet size that can be
	    transferred through the connection."
	::= { viaConnEntry 10 }

        viaConnLocalEnableRdmaWrite     OBJECT-TYPE
	SYNTAX                          Integer32
        MAX-ACCESS                      read-only
        STATUS                          current
	DESCRIPTION
            "The value is 1 if remote DMA write is enabled
            in the local system otherwise, it is 0."
	::= { viaConnEntry 11 }

        viaConnLocalEnableRdmaRead      OBJECT-TYPE
	SYNTAX                          Integer32
        MAX-ACCESS                      read-only
        STATUS                          current
	DESCRIPTION
            "The value is 1 if remote DMA read is enabled
            in the local system otherwise, it is 0."
	::= { viaConnEntry 12 }

        viaConnRemoteEnableRdmaWrite    OBJECT-TYPE
	SYNTAX                          Integer32
        MAX-ACCESS                      read-only
        STATUS                          current
	DESCRIPTION
            "The value is 1 if remote DMA write is enabled
            in the remote system otherwise, it is 0."
	::= { viaConnEntry 13 }

        viaConnRemoteEnableRdmaRead     OBJECT-TYPE
	SYNTAX                          Integer32
        MAX-ACCESS                      read-only
        STATUS                          current
	DESCRIPTION
            "The value is 1 if remote DMA read is enabled
            in the remote system otherwise, it is 0."
	::= { viaConnEntry 14 }

        viaConnSentMessages             OBJECT-TYPE
	SYNTAX                          Counter32
        MAX-ACCESS                      read-only
        STATUS                          current
	DESCRIPTION
            "Total number of messages sent through the connection."
	::= { viaConnEntry 15 }

        viaConnSentRdmaReadMessages     OBJECT-TYPE
	SYNTAX                          Counter32
        MAX-ACCESS                      read-only
        STATUS                          current
	DESCRIPTION
            "Total number of rdma read messages sent through the
            connection."
	::= { viaConnEntry 16 }

        viaConnSentRdmaWriteMessages    OBJECT-TYPE
	SYNTAX                          Counter32
        MAX-ACCESS                      read-only
        STATUS                          current
	DESCRIPTION
            "Total number of rdma write messages sent through the
            connection."
	::= { viaConnEntry 17 }

        viaConnRcvdMessages             OBJECT-TYPE
	SYNTAX                          Counter32
        MAX-ACCESS                      read-only
        STATUS                          current
	DESCRIPTION
            "Total number of messages received through the connection."
	::= { viaConnEntry 18 }

        viaConnRcvdRdmaReadMessages     OBJECT-TYPE
	SYNTAX                          Counter32
        MAX-ACCESS                      read-only
        STATUS                          current
	DESCRIPTION
            "Total number of rdma read messages received through the
            connection."
	::= { viaConnEntry 19 }

        viaConnRcvdRdmaWriteMessages    OBJECT-TYPE
	SYNTAX                          Counter32
        MAX-ACCESS                      read-only
        STATUS                          current
	DESCRIPTION
            "Total number of rdma write messages received through the
            connection."
	::= { viaConnEntry 20 }

        viaErrors OBJECT IDENTIFIER ::= { vi 2 }

	viaErrPostDesc                  OBJECT-TYPE
	SYNTAX                          Counter32
	MAX-ACCESS                      read-only
	STATUS                          current
	DESCRIPTION
	    "The total number of descriptors completed in error
            by NIC."
	::= { viaErrors 1 }

        viaErrConnLost                  OBJECT-TYPE
	SYNTAX                          Counter32
        MAX-ACCESS                      read-only
        STATUS                          current
	DESCRIPTION
            "The total number of Lost Connection errors. "
	::= { viaErrors 2 }

        viaErrRecvQEmpty                OBJECT-TYPE
	SYNTAX                          Counter32
        MAX-ACCESS                      read-only
        STATUS                          current
	DESCRIPTION
            "The total number of errors due to an empty receive Queue. "
	::= { viaErrors 3 }

        viaErrRdmawProt                 OBJECT-TYPE
	SYNTAX                          Counter32
        MAX-ACCESS                      read-only
        STATUS                          current
	DESCRIPTION
            "The total number of remote DMA write protection errors. "
	::= { viaErrors 4 }

        viaErrRdmarProt                 OBJECT-TYPE
	SYNTAX                          Counter32
        MAX-ACCESS                      read-only
        STATUS                          current
	DESCRIPTION
            "The total number of remote DMA read protection errors. "
	::= { viaErrors 5 }

        viaErrCompProt                  OBJECT-TYPE
	SYNTAX                          Counter32
        MAX-ACCESS                      read-only
        STATUS                          current
	DESCRIPTION
            "The total number of protection errors. "
	::= { viaErrors 6 }

        viaErrorThreshold               OBJECT-TYPE
	SYNTAX                          Integer32
        MAX-ACCESS                      read-only
        STATUS                          current
	DESCRIPTION
	    "Setting this threshold will cause a trap to be enabled
	    such that if the total error exceeds error threshold set
	    a viaNodeErrorsTrap trap will be generated."
	::= { viaErrors 7 }

        viaNicAttributes OBJECT IDENTIFIER ::= { vi 3 }

	viaNicTable                     OBJECT-TYPE
	SYNTAX                          SEQUENCE OF ViaNicEntry
	MAX-ACCESS                      not-accessible
	STATUS                          current
	DESCRIPTION
            "A table containing via NIC-specific information."
	::= { viaNicAttributes 1}

        viaNicEntry                     OBJECT-TYPE
	SYNTAX                          ViaNicEntry
        MAX-ACCESS                      not-accessible
        STATUS                          current
	DESCRIPTION
            "A conceptual row of the viaNicTable containing information
            about a particular present VINic."

	INDEX    {    viaNicIndex }
	::= { viaNicTable 1 }

        ViaNicEntry ::= SEQUENCE {
            viaNicIndex               Integer32,
            viaName                   DisplayString,
            viaHardwareVersion        DisplayString,
            viaProviderVersion        DisplayString,
            viaNicAddress             PhysAddress,
            viaThreadSafe             Integer32,
            viaMaxDiscriminatorLength Integer32,
            viaMaxRegisterBytes       Integer32,
            viaMaxRegisterRegions     Integer32,
            viaMaxRegisterBlockBytes  Integer32,
            viaMaxVI                  Integer32,
            viaMaxDescriptorsPerQueue Integer32,
            viaMaxSegmentsPerDesc     Integer32,
            viaMaxCQ                  Integer32,
            viaMaxCQEntries           Integer32,
            viaMaxTransferSize        Integer32,
            viaNativeMTU              Integer32,
            viaMaxPTags               Integer32,
            viaCurrRegisterBytes      Integer32,
            viaCurrRegisterRegions    Integer32,
            viaCurrVI                 Integer32,
            viaCurrCQ                 Integer32,
            viaCurrPTags              Integer32,
            viaConnectionListenPort   Integer32
	}

        viaNicIndex                     OBJECT-TYPE
	SYNTAX                          Integer32 (1..2147483647)
        MAX-ACCESS                      read-only
        STATUS                          current
	DESCRIPTION
	    "The index of the NIC in the NIC table."
	::= { viaNicEntry 1 }

        viaName                         OBJECT-TYPE
	SYNTAX                          DisplayString (SIZE (0..255))
        MAX-ACCESS                      read-only
        STATUS                          current
	DESCRIPTION
	    "The symbolic name of the NIC device."
	::= { viaNicEntry 2 }

        viaHardwareVersion              OBJECT-TYPE
	SYNTAX                          DisplayString (SIZE (0..255))
        MAX-ACCESS                      read-only
        STATUS                          current
	DESCRIPTION
	    "The version of the VINIC described by this MIB."
	::= { viaNicEntry 3 }

        viaProviderVersion              OBJECT-TYPE
	SYNTAX                          DisplayString (SIZE (0..255))
        MAX-ACCESS                      read-only
        STATUS                          current
	DESCRIPTION
	    "The version of the VI provider."
	::= { viaNicEntry 4 }

        viaNicAddress                   OBJECT-TYPE
	SYNTAX                          PhysAddress
        MAX-ACCESS                      read-only
        STATUS                          current
	DESCRIPTION
	    "The Network address of this NIC."
	::= { viaNicEntry 5 }

        viaThreadSafe                   OBJECT-TYPE
	SYNTAX                          Integer32
        MAX-ACCESS                      read-only
        STATUS                          current
	DESCRIPTION
	    "1 if synchronization model is thread safe else 0."
	::= { viaNicEntry 6 }

        viaMaxDiscriminatorLength       OBJECT-TYPE
	SYNTAX                          Integer32
        MAX-ACCESS                      read-only
        STATUS                          current
	DESCRIPTION
	    "The maximum number of bytes that the VI provider allows
	    for a connection discriminator."
	::= { viaNicEntry 7 }

        viaMaxRegisterBytes             OBJECT-TYPE
	SYNTAX                          Integer32
        MAX-ACCESS                      read-only
        STATUS                          current
	DESCRIPTION
	    "Maximum number of bytes that can be registered."
	::= { viaNicEntry 8 }

        viaMaxRegisterRegions           OBJECT-TYPE
	SYNTAX                          Integer32
        MAX-ACCESS                      read-only
        STATUS                          current
	DESCRIPTION
	    "Maximum number of memory regions that can be registered."
	::= { viaNicEntry 9 }

        viaMaxRegisterBlockBytes        OBJECT-TYPE
	SYNTAX                          Integer32
        MAX-ACCESS                      read-only
        STATUS                          current
	DESCRIPTION
	    "Largest contiguous block of memory that can be registered."
	::= { viaNicEntry 10 }

        viaMaxVI                        OBJECT-TYPE
	SYNTAX                          Integer32
        MAX-ACCESS                      read-only
        STATUS                          current
	DESCRIPTION
	    "The limit on the total number of VI instances this entity can
	    support."
	::= { viaNicEntry 11 }

        viaMaxDescriptorsPerQueue       OBJECT-TYPE
	SYNTAX                          Integer32
        MAX-ACCESS                      read-only
        STATUS                          current
	DESCRIPTION
	    "Maximum Descriptors per VI Work Queue that this VI provider
	    can support."
	::= { viaNicEntry 12 }

        viaMaxSegmentsPerDesc           OBJECT-TYPE
	SYNTAX                          Integer32
        MAX-ACCESS                      read-only
        STATUS                          current
	DESCRIPTION
	    "Maximum number of segments per descriptor that this VI provider
	    can support."
	::= { viaNicEntry 13 }

        viaMaxCQ                        OBJECT-TYPE
	SYNTAX                          Integer32
	MAX-ACCESS                      read-only
        STATUS                          current
	DESCRIPTION
	    "Maximum number of completion queues this VI provider can support."
	::= { viaNicEntry 14 }

        viaMaxCQEntries                 OBJECT-TYPE
	SYNTAX                          Integer32
        MAX-ACCESS                      read-only
        STATUS                          current
	DESCRIPTION
	    "Maximum number of Completion queue entries per completion queue
	    that this VI provider can support."
	::= { viaNicEntry 15 }

        viaMaxTransferSize              OBJECT-TYPE
	SYNTAX                          Integer32
        MAX-ACCESS                      read-only
        STATUS                          current
	DESCRIPTION
	    "The maximum transfer size supported by the VI Nic. The maximum
	    transfer size is the amount of data that can be described by a
	    single VI descriptor."
	::= { viaNicEntry 16 }

        viaNativeMTU                    OBJECT-TYPE
	SYNTAX                          Integer32
        MAX-ACCESS                      read-only
        STATUS                          current
	DESCRIPTION
	    "The native MTU size of the underlying network. For frame-based
	    networks, this could reflect its native frame size. For cell-based
	    networks, it could reflect the MTU of the appropriate abstraction
	    layer that it supports."
	::= { viaNicEntry 17 }

        viaMaxPTags                     OBJECT-TYPE
	SYNTAX                          Integer32
        MAX-ACCESS                      read-only
        STATUS                          current
	DESCRIPTION
	    "The maximum number of protection tags that are supported by this
	    VI provider."
	::= { viaNicEntry 18 }

       viaCurrRegisterBytes             OBJECT-TYPE
       SYNTAX                           Integer32
       MAX-ACCESS                       read-only
       STATUS                           current
       DESCRIPTION
	    "Number of bytes registered by the VI user for this
	    NIC."
	::= { viaNicEntry 19 }

       viaCurrRegisterRegions           OBJECT-TYPE
       SYNTAX                           Integer32
        MAX-ACCESS                      read-only
        STATUS                          current
	DESCRIPTION
	    "Number of memory regions that is registered by VI user
	    for this NIC."
	::= { viaNicEntry 20 }

       viaCurrVI                        OBJECT-TYPE
       SYNTAX                           Integer32
       MAX-ACCESS                       read-only
       STATUS                           current
       DESCRIPTION
	    "The current number of VI instances for this NIC."
	::= { viaNicEntry 21 }

       viaCurrCQ                        OBJECT-TYPE
       SYNTAX                           Integer32
       MAX-ACCESS                       read-only
       STATUS                           current
       DESCRIPTION
	   "Current number of completion queues this VI provider
	   has."
       ::= { viaNicEntry 22 }

       viaCurrPTags                     OBJECT-TYPE
       SYNTAX                           Integer32
       MAX-ACCESS                       read-only
       STATUS                           current
       DESCRIPTION
	    "Current Number of protection tags this VI provider has."
	::= { viaNicEntry 23 }

        viaConnectionListenPort         OBJECT-TYPE
	SYNTAX                          Integer32
        MAX-ACCESS                      read-only
        STATUS                          current
	DESCRIPTION
	    "Port number on which VI server is listening for VI connection
	    request."
	::= { viaNicEntry 24 }


        -- -- -- -- -- -- -- --
	-- VFILER group --
	-- -- -- -- -- -- -- --
	vfilerIsLicensed                OBJECT-TYPE
	SYNTAX                          INTEGER {
                                             false(1),
                                             true(2)
                                        }
        MAX-ACCESS                      read-only
        STATUS                          current
        DESCRIPTION
                        "Whether vfiler  is licensed on the
			filer."
        ::= { vfiler 1 }

	vfFilers                        OBJECT-TYPE
	SYNTAX                          Counter32
        MAX-ACCESS                      read-only
        STATUS                          current
        DESCRIPTION
                      "Number of vfilers in the physical Filer."
        ::= { vfiler 2 }

        vfTable                         OBJECT-TYPE
	SYNTAX                          SEQUENCE OF VfEntry
        MAX-ACCESS                      not-accessible
        STATUS                          current
	DESCRIPTION
		     "Provide a report of per-vfiler general information "
	::= { vfiler 3 }

	vfEntry                         OBJECT-TYPE
	SYNTAX                          VfEntry
        MAX-ACCESS                      not-accessible
        STATUS                          current
        DESCRIPTION
                     "Provide a report of per-vfiler information"
 	INDEX   { vfIndex}
        ::= { vfTable 1 }

        VfEntry ::=
       	     SEQUENCE {
	       	 vfIndex
		 	Integer32,
		 vfName
		 	DisplayString,
                 vfUuid
                        OCTET STRING,
                 vfIpAddresses
                        Integer32,
                 vfStoragePaths
                        Integer32,
		 vfIpSpace
		 	DisplayString,
		 vfAllowedProtocols
		 	Integer32,
		 vfDisallowedProtocols
		 	Integer32,
		 vfState
		 	INTEGER
      	     }

	vfIndex                         OBJECT-TYPE
	SYNTAX                          Integer32 (1..2147483647)
        MAX-ACCESS                      read-only
        STATUS                          current
        DESCRIPTION
                     "A number that identifies this entry for the referenced vfiler."
        ::= { vfEntry 1 }


	vfName                          OBJECT-TYPE
	SYNTAX                          DisplayString
        MAX-ACCESS                      read-only
        STATUS                          current
        DESCRIPTION
                      " A textual string that contains the name of the referenced vfiler."
        ::= { vfEntry 2 }

        vfUuid                          OBJECT-TYPE
	SYNTAX                          OCTET STRING (SIZE (0..36))
        MAX-ACCESS                      read-only
        STATUS                          current

        DESCRIPTION
                      "The UUID of the referenced vfiler."
        ::= { vfEntry 3 }

	vfIpAddresses                   OBJECT-TYPE
	SYNTAX                          Integer32
        MAX-ACCESS                      read-only
        STATUS                          current
	DESCRIPTION
	               "The total number of IP addresses for the referenced vfiler."
        ::= { vfEntry 4 }


        vfStoragePaths                  OBJECT-TYPE
	SYNTAX                          Integer32
        MAX-ACCESS                      read-only
        STATUS                          current
        DESCRIPTION
                       "The total number of storage paths for the referenced vfiler."
        ::= { vfEntry 5 }

        vfIpSpace                       OBJECT-TYPE
	SYNTAX                          DisplayString
        MAX-ACCESS                      read-only
        STATUS                          current
        DESCRIPTION
                      " A textual string that contains the name of the ipspace that the referenced vfiler belongs to."
        ::= { vfEntry 6 }

        vfAllowedProtocols              OBJECT-TYPE
	SYNTAX                          Integer32
        MAX-ACCESS                      read-only
        STATUS                          current
        DESCRIPTION
                       "Total number of protocols allowed for the referenced vfiler."
        ::= { vfEntry 7 }

        vfDisallowedProtocols           OBJECT-TYPE
	SYNTAX                          Integer32
        MAX-ACCESS                      read-only
        STATUS                          current
        DESCRIPTION
                       "Total number of protocols disallowed for the referenced vfiler."
        ::= { vfEntry 8 }

        vfState                         OBJECT-TYPE
	SYNTAX                          INTEGER {
                                             stopped (1),
                                             running (2)
                                        }
        MAX-ACCESS                      read-only
        STATUS                          current
        DESCRIPTION
                       "Status of the vfiler: Running or stopped."
        ::= { vfEntry 9 }

	vfIpTable                       OBJECT-TYPE
	SYNTAX                          SEQUENCE OF VfIpEntry
        MAX-ACCESS                      not-accessible
        STATUS                          current
	DESCRIPTION
			"Provide a report of per-vfiler IP addresses information "
        ::= { vfiler 4 }

        vfIpEntry                       OBJECT-TYPE
	SYNTAX                          VfIpEntry
        MAX-ACCESS                      not-accessible
        STATUS                          current
	DESCRIPTION
	                "Provide a report of per-vfiler IP addresses information"
        INDEX   { vfFiIndex, vfIpIndex }
        ::= { vfIpTable 1 }

        VfIpEntry ::=
 	    SEQUENCE {
        	vfFiIndex
		          Integer32,
                vfIpIndex
			  Integer32,
	   	vfIpAddr
	                  IpAddress
            }

        vfFiIndex                       OBJECT-TYPE
	SYNTAX                          Integer32 (1..2147483647)
        MAX-ACCESS                      read-only
        STATUS                          current
        DESCRIPTION
                     "A number that identifies the referenced vfiler."
        ::= { vfIpEntry 1 }

        vfIpIndex                       OBJECT-TYPE
	SYNTAX                          Integer32 (1..2147483647)
        MAX-ACCESS                      read-only
        STATUS                          current
        DESCRIPTION
                     "A number that identifies which IP address in the referenced vfiler."
        ::= { vfIpEntry 2 }

        vfIpAddr                        OBJECT-TYPE
	SYNTAX                          IpAddress
        MAX-ACCESS                      read-only
        STATUS                          current
        DESCRIPTION
                      "A IP address for the referenced vfiler."
        ::= { vfIpEntry 3 }

        vfSpTable                       OBJECT-TYPE
	SYNTAX                          SEQUENCE OF VfSpEntry
        MAX-ACCESS                      not-accessible
        STATUS                          current
        DESCRIPTION
                       "Provide a report of per-vfiler storage path information "
        ::= { vfiler 5 }

        vfSpEntry                       OBJECT-TYPE
	SYNTAX                          VfSpEntry
        MAX-ACCESS                      not-accessible
        STATUS                          current
        DESCRIPTION
                       "Provide a report of per-vfiler storage path information"
        INDEX   { vfFsIndex, vfSpIndex }
        ::= { vfSpTable 1 }

        VfSpEntry ::=
            SEQUENCE {
                vfFsIndex
                          Integer32,
                vfSpIndex
                          Integer32,
                vfSpName
	                  OCTET STRING
	    }

        vfFsIndex                       OBJECT-TYPE
	SYNTAX                          Integer32 (1..2147483647)
        MAX-ACCESS                      read-only
        STATUS                          current
        DESCRIPTION
                     "A number that identifies the referenced vfiler."
        ::= { vfSpEntry 1 }

        vfSpIndex                       OBJECT-TYPE
	SYNTAX                          Integer32 (1..2147483647)
        MAX-ACCESS                      read-only
        STATUS                          current
        DESCRIPTION
                     "A number that identifies which storage path in the referenced vfiler."
        ::= { vfSpEntry 2 }

        vfSpName                        OBJECT-TYPE
	SYNTAX                          OCTET STRING (SIZE (0..1024))
        MAX-ACCESS                      read-only
        STATUS                          current
        DESCRIPTION
                      "The storage path name  for the referenced vfiler."
        ::= { vfSpEntry 3 }


        vfProTable                      OBJECT-TYPE
	SYNTAX                          SEQUENCE OF VfProEntry
        MAX-ACCESS                      not-accessible
        STATUS                          current
        DESCRIPTION
                       "Provide a report of per-vfiler protocol information "
        ::= { vfiler 6 }

        vfProEntry                      OBJECT-TYPE
	SYNTAX                          VfProEntry
        MAX-ACCESS                      not-accessible
        STATUS                          current
        DESCRIPTION
                       "Provide a report of per-vfiler protocol information"
        INDEX   { vfFpIndex, vfProIndex }
        ::= { vfProTable 1 }

        VfProEntry ::=
            SEQUENCE {
       	        vfFpIndex
	                   Integer32,
                vfProIndex
                           Integer32,
                vfProName
                           OCTET STRING,
		vfProStatus
			   INTEGER
	    }

        vfFpIndex                       OBJECT-TYPE
	SYNTAX                          Integer32 (1..2147483647)
        MAX-ACCESS                      read-only
        STATUS                          current
        DESCRIPTION
                     "A number that identifies the referenced vfiler."
        ::= { vfProEntry 1 }

        vfProIndex                      OBJECT-TYPE
	SYNTAX                          Integer32 (1..2147483647)
        MAX-ACCESS                      read-only
        STATUS                          current
        DESCRIPTION
                     "A number that identifies a protocol in the referenced vfiler."
        ::= { vfProEntry 2 }

        vfProName                       OBJECT-TYPE
	SYNTAX                          OCTET STRING (SIZE (0..1024))
        MAX-ACCESS                      read-only
        STATUS                          current
        DESCRIPTION
                      "A textual string that contains the protocol name  for the referenced vfiler."
        ::= { vfProEntry 3 }

        vfProStatus                     OBJECT-TYPE
	SYNTAX                          INTEGER {
                                             false(1),
                                             true(2)
                                        }
        MAX-ACCESS                      read-only
        STATUS                          current
        DESCRIPTION
			"Whether the referenced vfiler protocol  is allowed or disallowed."
        ::= { vfProEntry 4 }

        -- -- -- -- -- -- -- --
	-- Block access protocols group --
	-- -- -- -- -- -- -- --
	fcpIsLicensed                   OBJECT-TYPE
	SYNTAX                          INTEGER {
                                             false(1),
                                             true(2)
                                        }
        MAX-ACCESS                      read-only
        STATUS                          current
        DESCRIPTION
                        "Whether FCP access protocols are licensed on the
			filer."
        ::= { blocks 1 }

	iscsiIsLicensed                 OBJECT-TYPE
	SYNTAX                          INTEGER {
                                             false(1),
                                             true(2)
                                        }
        MAX-ACCESS                      read-only
        STATUS                          current
        DESCRIPTION
                        "Whether iSCSI access protocols are licensed on the
			filer."
        ::= { blocks 2 }

	fcpLowReadBytes                 OBJECT-TYPE
	SYNTAX                          Counter32
        MAX-ACCESS                      read-only
        STATUS                          deprecated
        DESCRIPTION
			"The total number of bytes read via FCP
			since the last boot.  This object returns the
			least significant 32 bits of the 64 bit unsigned
			integer. This object is deprecated - Use
			fcp64ReadBytes  instead."
	::= { blocks 3 }

	fcpHighReadBytes                OBJECT-TYPE
	SYNTAX                          Counter32
        MAX-ACCESS                      read-only
        STATUS                          deprecated
        DESCRIPTION
			"The total number of bytes read via FCP
			since the last boot.  This object returns the
			most significant 32 bits of the 64 bit unsigned
			integer. This object is deprecated - Use
			fcp64ReadBytes  instead."
	::= { blocks 4 }


	fcpLowWriteBytes                OBJECT-TYPE
	SYNTAX                          Counter32
        MAX-ACCESS                      read-only
        STATUS                          deprecated
        DESCRIPTION
			"The total number of bytes written via FCP
			since the last boot.  This object returns the
			least significant 32 bits of the 64 bit unsigned
			integer. This object is deprecated - Use
			fcp64WriteBytes  instead."
	::= { blocks 5 }


	fcpHighWriteBytes               OBJECT-TYPE
	SYNTAX                          Counter32
        MAX-ACCESS                      read-only
        STATUS                          deprecated
        DESCRIPTION
			"The total number of bytes written via FCP
			since the last boot.  This object returns the
			most significant 32 bits of the 64 bit unsigned
			integer. This object is deprecated - Use
			fcp64WriteBytes  instead."
	::= { blocks 6 }


	iscsiLowReadBytes               OBJECT-TYPE
	SYNTAX                          Counter32
        MAX-ACCESS                      read-only
        STATUS                          deprecated
        DESCRIPTION
			"The total number of bytes read via iSCSI
			since the last boot.  This object returns the
			least significant 32 bits of the 64 bit unsigned
			integer. This object is deprecated - Use
			iscsi64ReadBytes  instead."
	::= { blocks 7 }


	iscsiHighReadBytes              OBJECT-TYPE
	SYNTAX                          Counter32
        MAX-ACCESS                      read-only
        STATUS                          deprecated
        DESCRIPTION
			"The total number of bytes read via iSCSI
			since the last boot.  This object returns the
			most significant 32 bits of the 64 bit unsigned
			integer. This object is deprecated - Use
			iscsi64ReadBytes  instead."
	::= { blocks 8 }


	iscsiLowWriteBytes              OBJECT-TYPE
	SYNTAX                          Counter32
        MAX-ACCESS                      read-only
        STATUS                          deprecated
        DESCRIPTION
			"The total number of bytes written via iSCSI
			since the last boot.  This object returns the
			least significant 32 bits of the 64 bit unsigned
			integer. This object is deprecated - Use
			iscsi64WriteBytes  instead."
	::= { blocks 9 }


	iscsiHighWriteBytes             OBJECT-TYPE
	SYNTAX                          Counter32
        MAX-ACCESS                      read-only
        STATUS                          deprecated
        DESCRIPTION
			"The total number of bytes written via iSCSI
			since the last boot.  This object returns the
			most significant 32 bits of the 64 bit unsigned
			integer. This object is deprecated - Use
			iscsi64WriteBytes  instead."
	::= { blocks 10 }


	iscsiHighOps                    OBJECT-TYPE
	SYNTAX                          Counter32
        MAX-ACCESS                      read-only
        STATUS                          deprecated
	DESCRIPTION
			"The total number of iSCSI ops handled since the
			last boot.  This object returns the most significant
			32 bits of the 64 bit unsigned integer.
			This object is deprecated - Use iscsi64Ops instead."
	::= {blocks 11}

	iscsiLowOps                     OBJECT-TYPE
	SYNTAX                          Counter32
        MAX-ACCESS                      read-only
        STATUS                          deprecated
	DESCRIPTION
			"The total number of iSCSI ops handled since the
			last boot.  This object returns the least significant
			32 bits of the 64 bit unsigned integer.
			This object is deprecated - Use iscsi64Ops instead."
	::= {blocks 12}

	fcpHighOps                      OBJECT-TYPE
	SYNTAX                          Counter32
        MAX-ACCESS                      read-only
        STATUS                          deprecated
	DESCRIPTION
			"The total number of FCP ops handled since the
			last boot.  This object returns the most significant
			32 bits of the 64 bit unsigned integer.
			This object is deprecated - Use fcp64Ops instead."
	::= {blocks 13}

	fcpLowOps                       OBJECT-TYPE
	SYNTAX                          Counter32
        MAX-ACCESS                      read-only
        STATUS                          deprecated
	DESCRIPTION
			"The total number of FCP ops handled since the
			last boot.  This object returns the least significant
			32 bits of the 64 bit unsigned integer.
			This object is deprecated - Use fcp64Ops instead."
	::= {blocks 14}

	lun		OBJECT IDENTIFIER ::= {blocks 15 }

	lunCount                        OBJECT-TYPE
	SYNTAX                          Integer32
        MAX-ACCESS                      read-only
        STATUS                          current
        DESCRIPTION
                      "Number of LUNs in the Filer in 7-mode. Unsupported in Clustered Data ONTAP."
        ::= { lun 1 }

	lunTable                        OBJECT-TYPE
	SYNTAX                          SEQUENCE OF LunEntry
        MAX-ACCESS                      not-accessible
        STATUS                          obsolete
	DESCRIPTION
			"Provide a report of per-LUN general information."
	::= {lun 2}

	lunEntry                        OBJECT-TYPE
	SYNTAX                          LunEntry
        MAX-ACCESS                      not-accessible
        STATUS                          current
	DESCRIPTION
			"Provide a report of per-LUN information"
	INDEX	{ lunIndex}
	::= { lunTable 1 }

	LunEntry ::=
	    SEQUENCE {
		lunIndex Integer32,
		lunName DisplayString,
		lunComment DisplayString,
		lunSizeLow Integer32,
		lunSizeHigh Integer32,
		lunMapped INTEGER,
		lunSerialNumber DisplayString,
		lunQtreeName FileOrDirectoryString,
		lunHighOps Counter32,
		lunLowOps Counter32,
		lunHighReadBytes Counter32,
		lunLowReadBytes Counter32,
		lunHighWriteBytes Counter32,
		lunLowWriteBytes Counter32,
		lunHighErrors Counter32,
		lunLowErrors Counter32,
		lunOnline INTEGER,
		lunSnapStatus	INTEGER,
		lunShareStatus INTEGER,
		lunSpaceReserved INTEGER,
		lunStatsResetTime Integer32,
		lunHighReadOps Counter32,
		lunLowReadOps Counter32,
		lunHighWriteOps Counter32,
		lunLowWriteOps Counter32,
		lunHighOtherOps Counter32,
		lunLowOtherOps Counter32,
		lunSize64 Counter64,
		lun64Ops Counter64,
		lun64ReadBytes Counter64,
		lun64WriteBytes Counter64,
		lun64Errors Counter64,
		lun64ReadOps Counter64,
		lun64WriteOps Counter64,
		lun64OtherOps Counter64,
		lunAlignment DisplayString,
		lunVserver  DisplayString
		}

	lunIndex                        OBJECT-TYPE
	SYNTAX                          Integer32 (1..2147483647)
        MAX-ACCESS                      read-only
        STATUS                          current
        DESCRIPTION
                     "A number that identifies the referenced LUN."
        ::= { lunEntry 1 }

	lunName                         OBJECT-TYPE
	SYNTAX                          DisplayString
        MAX-ACCESS                      read-only
        STATUS                          current
        DESCRIPTION
                      "The name of the LUN.  This is also the path to the LUN
		      on the filer."
        ::= { lunEntry 2 }

	lunComment                      OBJECT-TYPE
	SYNTAX                          DisplayString
        MAX-ACCESS                      read-only
        STATUS                          current
        DESCRIPTION
                      "The comment, if any, for this LUN."
        ::= { lunEntry 3 }

	lunSizeLow                      OBJECT-TYPE
	SYNTAX                          Integer32
        MAX-ACCESS                      read-only
        STATUS                          deprecated
        DESCRIPTION
                     "Size of the LUN in bytes.  This object returns the
		     least significant 32 bits of the 64 bit unsigned integer.
		     This object is deprecated - Use lunSize64 instead."
        ::= { lunEntry 4 }

	lunSizeHigh                     OBJECT-TYPE
	SYNTAX                          Integer32
        MAX-ACCESS                      read-only
        STATUS                          deprecated
        DESCRIPTION
                     "Size of the LUN in bytes.  This object returns the
		     most significant 32 bits of the 64 bit unsigned integer.
		     This object is deprecated - Use lunSize64 instead."
        ::= { lunEntry 5 }

	lunMapped                       OBJECT-TYPE
	SYNTAX                          INTEGER {
                                             false(1),
                                             true(2)
                                        }

        MAX-ACCESS                      read-only
        STATUS                          current
        DESCRIPTION
                     "This LUN has been mapped to at least one initiator group."
        ::= { lunEntry 6 }

	lunSerialNumber                 OBJECT-TYPE
	SYNTAX                          DisplayString
        MAX-ACCESS                      read-only
        STATUS                          current
	DESCRIPTION
		    "The 12 character SCSI serial number of the LUN."
	::= { lunEntry 7 }


	lunQtreeName                    OBJECT-TYPE
	SYNTAX                          FileOrDirectoryString
        MAX-ACCESS                      read-only
        STATUS                          current
	DESCRIPTION
		    "A string that indicates which qtree this LUN belongs to."
	::= { lunEntry 8 }

	lunHighOps                      OBJECT-TYPE
	SYNTAX                          Counter32
        MAX-ACCESS                      read-only
        STATUS                          deprecated
        DESCRIPTION
			"The total number of Target side SCSI ops for
			this LUN since the stats were last reset.  This object
			returns the most significant 32 bits of the 64 bit
			unsigned integer. This object is deprecated - Use
			lun64Ops instead."
	::= { lunEntry 9}

	lunLowOps                       OBJECT-TYPE
	SYNTAX                          Counter32
        MAX-ACCESS                      read-only
        STATUS                          deprecated
        DESCRIPTION
			"The total number of Target side SCSI ops for
			this LUN since the stats were last reset.  This object
			returns the least significant 32 bits of the 64 bit
			unsigned integer. This object is deprecated - Use
			lun64Ops instead."
	::= { lunEntry 10 }

	lunHighReadBytes                OBJECT-TYPE
	SYNTAX                          Counter32
        MAX-ACCESS                      read-only
        STATUS                          deprecated
        DESCRIPTION
			"The total number of bytes read from this LUN
			since the stats were last reset.  This object returns
			the most significant 32 bits of the 64 bit unsigned
			integer. This object is deprecated - Use
			lun64ReadBytes instead."
	::= { lunEntry 11 }

	lunLowReadBytes                 OBJECT-TYPE
	SYNTAX                          Counter32
        MAX-ACCESS                      read-only
        STATUS                          deprecated
        DESCRIPTION
			"The total number of bytes read from this LUN
			since the stats were last reset.  This object returns
			the least significant 32 bits of the 64 bit unsigned
			integer. This object is deprecated - Use
			lun64ReadBytes instead."
	::= { lunEntry 12 }


	lunHighWriteBytes               OBJECT-TYPE
	SYNTAX                          Counter32
        MAX-ACCESS                      read-only
        STATUS                          deprecated
        DESCRIPTION
			"The total number of bytes written to this LUN
			since the stats were last reset.  This object returns
			the most significant 32 bits of the 64 bit unsigned
			integer. This object is deprecated - Use
			lun64WriteBytes instead."
	::= { lunEntry 13 }

	lunLowWriteBytes                OBJECT-TYPE
	SYNTAX                          Counter32
        MAX-ACCESS                      read-only
        STATUS                          deprecated
        DESCRIPTION
			"The total number of bytes written to this LUN
			since the stats were last reset.  This object returns
			the least significant 32 bits of the 64 bit unsigned
			integer. This object is deprecated - Use
			lun64WriteBytes instead."
	::= { lunEntry 14 }

	lunHighErrors                   OBJECT-TYPE
	SYNTAX                          Counter32
        MAX-ACCESS                      read-only
        STATUS                          deprecated
        DESCRIPTION
			"The total number of errors seen on this LUN
			since the stats were last reset.  This object
			returns the most significant 32 bits of the 64 bit
			unsigned integer. This object is deprecated - Use
			lun64Errors instead."
	::= { lunEntry 15 }

	lunLowErrors                    OBJECT-TYPE
	SYNTAX                          Counter32
        MAX-ACCESS                      read-only
        STATUS                          deprecated
        DESCRIPTION
			"The total number of errors seen on this LUN
			since the stats were last reset.  This object
			returns the least significant 32 bits of the 64 bit
			unsigned integer. This object is deprecated - Use
			lun64Errors instead."
	::= { lunEntry 16 }

	lunOnline                       OBJECT-TYPE
	SYNTAX                          INTEGER {
                                             false(1),
                                             true(2)
                                        }
        MAX-ACCESS                      read-only
        STATUS                          current
	DESCRIPTION
			"Whether the LUN is online."
	::= { lunEntry 17 }

	lunSnapStatus                   OBJECT-TYPE
	SYNTAX                          INTEGER {
                                             false(1),
                                             true(2)
                                        }
        MAX-ACCESS                      read-only
        STATUS                          current
	DESCRIPTION
			"Whether a snapshot of this LUN can be taken.
			 Not supported in c-mode."
	::= { lunEntry 18 }


	lunShareStatus                  OBJECT-TYPE
	SYNTAX                          INTEGER {
                                             none(1),
                                             read(2),
					     write(3),
                                             all(4)
                                        }
        MAX-ACCESS                      read-only
        STATUS                          current
	DESCRIPTION
			"The sharing status for the LUN.
			 Not supported in c-mode."
	::= { lunEntry 19 }


	lunSpaceReserved                OBJECT-TYPE
	SYNTAX                          INTEGER {
                                             false(1),
                                             true(2)
                                        }
        MAX-ACCESS                      read-only
        STATUS                          current
	DESCRIPTION
			"Whether the LUN has space reservation enabled."
	::= { lunEntry 20 }

	lunStatsResetTime               OBJECT-TYPE
	SYNTAX                          Integer32
        MAX-ACCESS                      read-only
        STATUS                          current
	DESCRIPTION
			"Number of seconds since this LUN's stats were
			last reset."
	::= { lunEntry 21 }


	lunHighReadOps                  OBJECT-TYPE
	SYNTAX                          Counter32
        MAX-ACCESS                      read-only
        STATUS                          deprecated
        DESCRIPTION
			"The total number of Target side SCSI read ops for
			this LUN since the stats were last reset.  This object
			returns the least significant 32 bits of the 64 bit
			unsigned integer. This object is deprecated - Use
			lun64ReadOps instead."
	::= { lunEntry 22}

	lunLowReadOps                   OBJECT-TYPE
	SYNTAX                          Counter32
        MAX-ACCESS                      read-only
        STATUS                          deprecated
        DESCRIPTION
			"The total number of Target side SCSI read ops for
			this LUN since the stats were last reset.  This object
			returns the most significant 32 bits of the 64 bit
			unsigned integer. This object is deprecated - Use
			lun64ReadOps instead."
	::= { lunEntry 23 }


	lunHighWriteOps                 OBJECT-TYPE
	SYNTAX                          Counter32
        MAX-ACCESS                      read-only
        STATUS                          deprecated
        DESCRIPTION
			"The total number of Target side SCSI write ops for
			this LUN since the stats were last reset.  This object
			returns the least significant 32 bits of the 64 bit
			unsigned integer. This object is deprecated - Use
			lun64WriteOps instead."
	::= { lunEntry 24}

	lunLowWriteOps                  OBJECT-TYPE
	SYNTAX                          Counter32
        MAX-ACCESS                      read-only
        STATUS                          deprecated
        DESCRIPTION
			"The total number of Target side SCSI write ops for
			this LUN since the stats were last reset.  This object
			returns the most significant 32 bits of the 64 bit
			unsigned integer. This object is deprecated - Use
			lun64WriteOps instead."
	::= { lunEntry 25 }


	lunHighOtherOps                 OBJECT-TYPE
	SYNTAX                          Counter32
        MAX-ACCESS                      read-only
        STATUS                          deprecated
        DESCRIPTION
			"The total number of Target side SCSI ops that are not
			read or write for this LUN since the stats were last
			reset.  This object returns the least significant 32
			bits of the 64 bit unsigned integer. This object is
			deprecated - Use lun64OtherOps instead."
	::= { lunEntry 26}

	lunLowOtherOps                  OBJECT-TYPE
	SYNTAX                          Counter32
        MAX-ACCESS                      read-only
        STATUS                          deprecated
        DESCRIPTION
			"The total number of Target side SCSI ops that are not
			read or write for this LUN since the stats were last
			reset. This object returns the most significant 32
			bits of the 64 bit unsigned integer. This object is
			deprecated - Use lun64OtherOps instead."
	::= { lunEntry 27 }

	lunSize64                       OBJECT-TYPE
	SYNTAX                          Counter64
        MAX-ACCESS                      read-only
        STATUS                          current
        DESCRIPTION
                     "Size of the LUN in bytes.  This object returns all
		     of the 64 bit unsigned integer."
        ::= { lunEntry 28 }

	lun64Ops                        OBJECT-TYPE
	SYNTAX                          Counter64
        MAX-ACCESS                      read-only
        STATUS                          current
        DESCRIPTION
			"The total number of Target side SCSI ops for
			this LUN since the stats were last reset.  This object
			all of the 64 bit unsigned integer."
	::= { lunEntry 29}

	lun64ReadBytes                  OBJECT-TYPE
	SYNTAX                          Counter64
        MAX-ACCESS                      read-only
        STATUS                          current
        DESCRIPTION
			"The total number of bytes read from this LUN
			since the stats were last reset.  This object returns
			all of the 64 bit unsigned integer."
	::= { lunEntry 30 }

	lun64WriteBytes                 OBJECT-TYPE
	SYNTAX                          Counter64
        MAX-ACCESS                      read-only
        STATUS                          current
        DESCRIPTION
			"The total number of bytes written to this LUN
			since the stats were last reset.  This object returns
			all of the 64 bit unsigned integer."
	::= { lunEntry 31 }

	lun64Errors                     OBJECT-TYPE
	SYNTAX                          Counter64
        MAX-ACCESS                      read-only
        STATUS                          current
        DESCRIPTION
			"The total number of errors seen on this LUN
			since the stats were last reset.  This object
			returns all the 64 bit unsigned integer."
	::= { lunEntry 32 }

	lun64ReadOps                    OBJECT-TYPE
	SYNTAX                          Counter64
        MAX-ACCESS                      read-only
        STATUS                          current
        DESCRIPTION
			"The total number of Target side SCSI read ops for
			this LUN since the stats were last reset.  This object
			returns all of the 64 bit unsigned integer."
	::= { lunEntry 33}

	lun64WriteOps                   OBJECT-TYPE
	SYNTAX                          Counter64
        MAX-ACCESS                      read-only
        STATUS                          current
        DESCRIPTION
			"The total number of Target side SCSI write ops for
			this LUN since the stats were last reset.  This object
			returns all of the 64 bit unsigned integer."
	::= { lunEntry 34}

	lun64OtherOps                   OBJECT-TYPE
	SYNTAX                          Counter64
        MAX-ACCESS                      read-only
        STATUS                          current
        DESCRIPTION
			"The total number of Target side SCSI ops that are not
			read or write for this LUN since the stats were last
			reset.  This object returns all of the 64 bit
			unsigned integer."
	::= { lunEntry 35}

	lunAlignment			OBJECT-TYPE
	SYNTAX				DisplayString
	MAX-ACCESS			read-only
	STATUS				current
	DESCRIPTION
			"The alignment of the LUN. Possible values are:
			  'aligned': 		 LUN is aligned.
			  'misaligned':		 LUN is misaligned.
			  'possibly_misaligned': LUN is possibly misaligned.
			  'indeterminate':       Not enough information is
						 available to determine LUN
						 alignment."
	::= { lunEntry 36 }

        lunVserver                      OBJECT-TYPE
	SYNTAX                          DisplayString
        MAX-ACCESS                      read-only
	STATUS                          current
	DESCRIPTION
	                "Name of the vserver to which the LUN belongs.
			This field is returned only from the c-mode cluster
			and vserver management interfaces."
        ::= { lunEntry 37}



	lunMapTable                     OBJECT-TYPE
	SYNTAX                          SEQUENCE OF LunMapEntry
        MAX-ACCESS                      not-accessible
        STATUS                          obsolete
	DESCRIPTION
			"Provide a table listing the initiator group to
			Logical Unit Number mapping for each LUN."
	::= { lun 3 }

	lunMapEntry                     OBJECT-TYPE
	SYNTAX                          LunMapEntry
        MAX-ACCESS                      not-accessible
        STATUS                          current
	DESCRIPTION
			"Provide a per LUN and Initiator group mapping of
			SCSI logical unit numbers."
	INDEX	{ lunMapLUNIndex, lunMapInitiatorGroupIndex }
	::= { lunMapTable 1 }

	LunMapEntry ::=
	    SEQUENCE {
		lunMapLUNIndex		Integer32,
		lunMapInitiatorGroupIndex	Integer32,
		lunMapLUNName			DisplayString,
		lunMapInitiatorGroupName	DisplayString,
		lunMapLogicalUnitNumber		Integer32,
		lunMapVserver                   DisplayString

	    }

	lunMapLUNIndex                  OBJECT-TYPE
	SYNTAX                          Integer32 (1..2147483647)
        MAX-ACCESS                      read-only
        STATUS                          current
        DESCRIPTION
                     "A number that identifies the LUN in the table."
        ::= { lunMapEntry 1 }

	lunMapInitiatorGroupIndex       OBJECT-TYPE
	SYNTAX                          Integer32 (1..2147483647)
        MAX-ACCESS                      read-only
        STATUS                          current
        DESCRIPTION
                     "A number that identifies an initiator group in
		     the table."
        ::= { lunMapEntry 2 }

	lunMapLUNName                   OBJECT-TYPE
	SYNTAX                          DisplayString
        MAX-ACCESS                      read-only
        STATUS                          current
	DESCRIPTION
		    "The name of the LUN."
	::= { lunMapEntry 3 }

	lunMapInitiatorGroupName        OBJECT-TYPE
	SYNTAX                          DisplayString
        MAX-ACCESS                      read-only
        STATUS                          current
	DESCRIPTION
		    "The name of the initiator group that this LUN is
		    mapped to."
	::= { lunMapEntry 4 }

	lunMapLogicalUnitNumber         OBJECT-TYPE
	SYNTAX                          Integer32
        MAX-ACCESS                      read-only
        STATUS                          current
        DESCRIPTION
                     "SCSI Logical Unit Number that this LUN is mapped to
		     for this initiator group."
        ::= { lunMapEntry 5 }

        lunMapVserver                   OBJECT-TYPE
        SYNTAX                          DisplayString
        MAX-ACCESS                      read-only
        STATUS                          current
        DESCRIPTION
                     "Name of the vserver containing the LUN and initiator group.
		      This field is returned only from the c-mode management and
		      cluster interfaces."
	::= { lunMapEntry 6}


	initiator 	OBJECT IDENTIFIER ::= {blocks 16}

	initiatorGroupTable             OBJECT-TYPE
	SYNTAX                          SEQUENCE OF InitiatorGroupEntry
        MAX-ACCESS                      not-accessible
        STATUS                          obsolete
	DESCRIPTION
			"Provide a report of per-initiator group general
			information "
	::= {initiator 1}

	initiatorGroupEntry             OBJECT-TYPE
	SYNTAX                          InitiatorGroupEntry
        MAX-ACCESS                      not-accessible
        STATUS                          current
	DESCRIPTION
			"Provide a report of per-initiator group information"
	INDEX	{ initiatorGroupIndex }
	::= { initiatorGroupTable 1 }

	InitiatorGroupEntry ::=
	    SEQUENCE {
		initiatorGroupIndex Integer32,
		initiatorGroupName  DisplayString,
		initiatorGroupType  INTEGER,
		initiatorGroupOS    INTEGER,
		initiatorGroupThrottleReserve Integer32,
		initiatorGroupThrottleBorrow  INTEGER,
		initiatorGroupUsePartner  INTEGER,
		initiatorGroupUseALUA	INTEGER,
		initiatorGroupVserver         DisplayString
		}

	initiatorGroupIndex             OBJECT-TYPE
	SYNTAX                          Integer32 (1..2147483647)
        MAX-ACCESS                      read-only
        STATUS                          current
        DESCRIPTION
                     "A number that identifies a specific initiator group."
        ::= { initiatorGroupEntry 1 }

	initiatorGroupName              OBJECT-TYPE
	SYNTAX                          DisplayString
        MAX-ACCESS                      read-only
        STATUS                          current
	DESCRIPTION
		    "The name of the initiator group"
	::= { initiatorGroupEntry 2 }

	initiatorGroupType              OBJECT-TYPE
	SYNTAX                          INTEGER {
                                             fcp(1),
                                             iSCSI(2),
					     mixed(3)
                                        }
        MAX-ACCESS                      read-only
        STATUS                          current
	DESCRIPTION
		    "Type of this initiator group, either iSCSI or FCP"
	::= { initiatorGroupEntry 3 }

	initiatorGroupOS                OBJECT-TYPE
	SYNTAX                          INTEGER {
                                             default(1),
                                             solaris(2),
					     windows(3),
					     hpux(4),
					     aix(5),
					     linux(6),
					     defaultPartner(7),
					     netware(8),
					     vmware(9),
					     openvms(10),
					     xen(11),
					     hyperv(12),
                                             invalid(256)
                                        }
        MAX-ACCESS                      read-only
        STATUS                          current
	DESCRIPTION
		    "Operating system the clients in this initiator
		    group run.  This governs  the finer details of
		    SCSI protocol interaction with these initiators"
	::= { initiatorGroupEntry 4 }

	initiatorGroupThrottleReserve   OBJECT-TYPE
	SYNTAX                          Integer32 (0..99)
        MAX-ACCESS                      read-only
        STATUS                          current
	DESCRIPTION
		    "Percentage of filer scsi command blocks reserved for
		    this initiator group"
	::= { initiatorGroupEntry 5 }

	initiatorGroupThrottleBorrow    OBJECT-TYPE
	SYNTAX                          INTEGER {
                                             false(1),
                                             true(2)
                                        }
        MAX-ACCESS                      read-only
        STATUS                          current
	DESCRIPTION
		    "True if this initiator group is allowed to
		    exceed its throttle settings if more resources
		    are needed and otherwise available.  If
		    initiatorGroupThrottleReserve is 0, this value
		    is meaningless"
	::= { initiatorGroupEntry 6 }

        initiatorGroupUsePartner        OBJECT-TYPE
	SYNTAX                          INTEGER {
                                             false(1),
                                             true(2)
                                        }
        MAX-ACCESS                      read-only
        STATUS                          current
	DESCRIPTION
		    "The takeover mode for the initiator group.  This is
		    only applicable to FCP initiator groups on clustered
		    filers"
	::= { initiatorGroupEntry 7 }

	initiatorGroupUseALUA           OBJECT-TYPE
	SYNTAX                          INTEGER {
                                             false(1),
                                             true(2)
                                        }
        MAX-ACCESS                      read-only
        STATUS                          current
	DESCRIPTION
		    "If true this initiator group supports Asymmetric Logical
		    Unit Access."
	::= { initiatorGroupEntry 8 }

   initiatorGroupVserver           OBJECT-TYPE
   SYNTAX                          DisplayString
       MAX-ACCESS                      read-only
       STATUS                          current
       DESCRIPTION
       "Name of the vserver containing the initiator group.
       This field is available only from the c-mode cluster
       and vserver management interfaces."
   ::= { initiatorGroupEntry 9}



	initiatorGroupMemberTable       OBJECT-TYPE
	SYNTAX                          SEQUENCE OF InitiatorGroupMemberEntry
        MAX-ACCESS                      not-accessible
        STATUS                          obsolete
	DESCRIPTION
			"Table of individual Initiator names in each Initiator
			group"
	::= {initiator 2}

	initiatorGroupMemberEntry       OBJECT-TYPE
	SYNTAX                          InitiatorGroupMemberEntry
        MAX-ACCESS                      not-accessible
        STATUS                          current
	DESCRIPTION
			"Provide a report of per-initiator group information"
	INDEX	{ initiatorGroupMemberIndex, initiatorGroupMemberNameIndex}
	::= { initiatorGroupMemberTable 1 }

	InitiatorGroupMemberEntry ::=
	    SEQUENCE {
		initiatorGroupMemberIndex
			Integer32,
		initiatorGroupMemberNameIndex
			Integer32,
		initiatorName
			DisplayString
		}

	initiatorGroupMemberIndex       OBJECT-TYPE
	SYNTAX                          Integer32 (1..2147483647)
        MAX-ACCESS                      read-only
        STATUS                          current
        DESCRIPTION
                     "A number that identifies a specific initiator group."
        ::= { initiatorGroupMemberEntry 1 }

	initiatorGroupMemberNameIndex   OBJECT-TYPE
	SYNTAX                          Integer32 (1..2147483647)
        MAX-ACCESS                      read-only
        STATUS                          current
        DESCRIPTION
                      "A number the identifies the initiator in the group."
        ::= { initiatorGroupMemberEntry 2 }

	initiatorName                   OBJECT-TYPE
	SYNTAX                          DisplayString
        MAX-ACCESS                      read-only
        STATUS                          current
        DESCRIPTION
		    "A textual name for this initiator."
	::= { initiatorGroupMemberEntry 3 }

	initiatorListTable              OBJECT-TYPE
	SYNTAX                          SEQUENCE OF InitiatorListEntry
        MAX-ACCESS                      not-accessible
        STATUS                          current
	DESCRIPTION
		    "Table of initiators that are connected to the filer."
	::= { initiator 3 }

	initiatorListEntry              OBJECT-TYPE
	SYNTAX                          InitiatorListEntry
        MAX-ACCESS                      not-accessible
        STATUS                          current
	DESCRIPTION
		    "Provide a report of per-connected-initiator information."
	INDEX { initiatorListEntryIndex}
	::= { initiatorListTable 1 }

	InitiatorListEntry ::=
	    SEQUENCE {
		initiatorListEntryIndex	        Integer32,
		targetAdapterName		DisplayString,
		connectedInitiatorNodeName	DisplayString,
		connectedInitiatorPortName	DisplayString,
		connectedInitiatorType		INTEGER,
		connectedInitiatorIsid		DisplayString,
		connectedInitiatorPortalGroup	Integer32,
		connectedInitiatorVserver       DisplayString

	    }

	initiatorListEntryIndex         OBJECT-TYPE
	SYNTAX                          Integer32 (1..2147483647)
        MAX-ACCESS                      read-only
        STATUS                          current
        DESCRIPTION
                     "A number that identifies the initiator connected to
		     the target adapter."
        ::= { initiatorListEntry 1 }

	targetAdapterName               OBJECT-TYPE
	SYNTAX                          DisplayString
        MAX-ACCESS                      read-only
        STATUS                          current
        DESCRIPTION
                     "The name of the target adapter in the filer.
                     In c-mode, this field returns the target LIF name."
        ::= { initiatorListEntry 2 }

	connectedInitiatorNodeName      OBJECT-TYPE
	SYNTAX                          DisplayString
        MAX-ACCESS                      read-only
        STATUS                          current
        DESCRIPTION
                     "A textual name for this initiator node."
        ::= { initiatorListEntry 3 }

	connectedInitiatorPortName      OBJECT-TYPE
	SYNTAX                          DisplayString
        MAX-ACCESS                      read-only
        STATUS                          current
        DESCRIPTION
                     "The FibreChannel device's portname. This is FCP only."
        ::= { initiatorListEntry 4 }

	connectedInitiatorType          OBJECT-TYPE
	SYNTAX                          INTEGER {
                                             fcp(1),
                                             iSCSI(2)
                                        }
        MAX-ACCESS                      read-only
        STATUS                          current
	DESCRIPTION
		    "Type of this init group, either iSCSI or FCP"
	::= { initiatorListEntry 5 }

	connectedInitiatorIsid          OBJECT-TYPE
	SYNTAX                          DisplayString
        MAX-ACCESS                      read-only
        STATUS                          current
	DESCRIPTION
		    "The iSCSI isid (initiator session id) for this initiator.
		    This is iSCSI only."
	::= { initiatorListEntry 6 }

	connectedInitiatorPortalGroup   OBJECT-TYPE
	SYNTAX                          Integer32
        MAX-ACCESS                      read-only
        STATUS                          current
	DESCRIPTION
		    "The iSCSI portal group ID for this initiator.
		    This is iSCSI only."
	::= { initiatorListEntry 7 }

        connectedInitiatorVserver       OBJECT-TYPE
        SYNTAX                          DisplayString
        MAX-ACCESS                      read-only
        STATUS                          current
        DESCRIPTION
	            "Name of the vserver hosting the LIF on which the
                    initiator connection is made.
                    This field is returned only from the c-mode cluster
                    and vserver management interfaces."
         ::= { initiatorListEntry 8 }

	fcpTarget	OBJECT IDENTIFIER ::= {blocks 17}

	fcpTargetTable                  OBJECT-TYPE
	SYNTAX                          SEQUENCE OF FcpTargetEntry
        MAX-ACCESS                      not-accessible
        STATUS                          current
	DESCRIPTION
			"Provide a report of fcp target adapter general
			information. This table is not available from the c-mode
			management interfaces"
	::= {fcpTarget 1}

	fcpTargetEntry             OBJECT-TYPE
	SYNTAX                          FcpTargetEntry
        MAX-ACCESS                      not-accessible
        STATUS                          current
	DESCRIPTION
			"Provide a report of per fcp target device information"
	INDEX	{ fcpTargetTableIndex }
	::= { fcpTargetTable 1 }

	FcpTargetEntry ::=
	    SEQUENCE {
		fcpTargetTableIndex    Integer32,
		fcpTargetName   DisplayString,
		fcpTargetNN	DisplayString,
		fcpTargetPN	DisplayString,
		fcpTargetSpeed	Integer32,
		fcpTargetStatus	INTEGER,
		fcpTargetStandby INTEGER,
		fcpTargetTopology INTEGER,
		fcpTargetType	INTEGER
		}

	fcpTargetTableIndex             OBJECT-TYPE
	SYNTAX                          Integer32 (1..2147483647)
        MAX-ACCESS                      read-only
        STATUS                          current
        DESCRIPTION
                     "A number that identifies a specific fcp target device."
        ::= { fcpTargetEntry 1 }

	fcpTargetName                   OBJECT-TYPE
	SYNTAX                          DisplayString
        MAX-ACCESS                      read-only
        STATUS                          current
	DESCRIPTION
		    "The name of the fcp target device"
	::= { fcpTargetEntry 2 }

	fcpTargetNN                     OBJECT-TYPE
	SYNTAX                          DisplayString
        MAX-ACCESS                      read-only
        STATUS                          current
	DESCRIPTION
		    "The FC WWNN of the fcp target device"
	::= { fcpTargetEntry 3 }

	fcpTargetPN                     OBJECT-TYPE
	SYNTAX                          DisplayString
        MAX-ACCESS                      read-only
        STATUS                          current
	DESCRIPTION
		    "The FC WWPN of the fcp target device"
	::= { fcpTargetEntry 4 }

	fcpTargetSpeed                  OBJECT-TYPE
	SYNTAX                          Integer32
        MAX-ACCESS                      read-only
        STATUS                          current
	DESCRIPTION
		    "speed in gigabits per second. 0 is unknown."
	::= { fcpTargetEntry 5 }

	fcpTargetStatus                 OBJECT-TYPE
	SYNTAX                          INTEGER {
                                             startup(1),
                                             uninitialized(2),
					     initializingFW(3),
					     linkNotConnected(4),
					     waitingForLinkUp(5),
					     online(6),
					     linkDisconnected(7),
					     resetting(8),
					     offline(9),
					     offlinedByUserSystem(10),
                                             unknown(11)
                                        }
        MAX-ACCESS                      read-only
        STATUS                          current
	DESCRIPTION
		    "Status of the fcp target adapter"
	::= { fcpTargetEntry 6 }

	fcpTargetStandby                OBJECT-TYPE
	SYNTAX                          INTEGER {
                                             false(1),
                                             true(2)
                                        }
        MAX-ACCESS                      read-only
        STATUS                          current
	DESCRIPTION
			"Whether this target adapter is in standby mode."
	::= { fcpTargetEntry 7 }

	fcpTargetTopology               OBJECT-TYPE
	SYNTAX                          INTEGER {
                                             unknown(1),
                                             fabric(2),
					     pointToPoint(3),
                                             loop(4)
                                        }
        MAX-ACCESS                      read-only
        STATUS                          current
	DESCRIPTION
			"fibre channel topology for this adapter. "
	::= { fcpTargetEntry 8 }

        fcpTargetType                   OBJECT-TYPE
	SYNTAX                          INTEGER {
                                             physical(1),
                                             local(2),
					     standby(3),
					     partner(4),
                                             unknown(5)
                                        }
        MAX-ACCESS                      read-only
        STATUS                          current
        DESCRIPTION
			"Responsibility/Type for this adapter."
	::= { fcpTargetEntry 9 }

        fcpCfMode                       OBJECT-TYPE
	SYNTAX                          INTEGER {
                                             mixed(1),
                                             standby(2),
					     partner(3),
					     partnerProxy(4),
					     partnerStandby(5),
					     localPrimary(6),
					     dualFabric(7),
					     ssi(8),
                                             unknown(256)
                                        }
        MAX-ACCESS                      read-only
        STATUS                          current
        DESCRIPTION
			"Failover setting for the FCP target cluster.
			This field is not available from the c-mode management interfaces"
	::= { blocks 18 }

	-- -- -- -- -- -- -- -- -- -- -- -- -- -- -- -- -- --
	-- -- -- -- -- -- -- -- -- -- -- -- -- -- -- -- -- --
	-- Port sets
	-- -- -- -- -- -- -- -- -- -- -- -- -- -- -- -- -- --
	-- -- -- -- -- -- -- -- -- -- -- -- -- -- -- -- -- --

	pset 		OBJECT IDENTIFIER ::= {blocks 19}

	psetTable                       OBJECT-TYPE
	SYNTAX                          SEQUENCE OF PsetEntry
        MAX-ACCESS                      not-accessible
        STATUS                          obsolete
	DESCRIPTION
			"Provide a report of portset general
			information "
	::= {pset 1}

	psetEntry                       OBJECT-TYPE
	SYNTAX                          PsetEntry
        MAX-ACCESS                      not-accessible
        STATUS                          current
	DESCRIPTION
			"Provide a report of portset information"
	INDEX	{ psetIndex }
	::= { psetTable 1 }

	PsetEntry ::=
	    SEQUENCE {
		psetIndex Integer32,
		psetName  DisplayString,
		psetType  INTEGER,
		psetVserver  DisplayString
		}

	psetIndex                       OBJECT-TYPE
	SYNTAX                          Integer32 (1..2147483647)
        MAX-ACCESS                      read-only
        STATUS                          current
        DESCRIPTION
                     "A number that identifies a specific port set."
        ::= { psetEntry 1 }

	psetName                        OBJECT-TYPE
	SYNTAX                          DisplayString
        MAX-ACCESS                      read-only
        STATUS                          current
	DESCRIPTION
		    "The name of the port set"
	::= { psetEntry 2 }

	psetType                        OBJECT-TYPE
	SYNTAX                          INTEGER {
                                             fcp(1),
                                             iSCSI(2),
					     mixed(3)
                                        }
        MAX-ACCESS                      read-only
        STATUS                          current
	DESCRIPTION
		    "Type of this port set, either iSCSI, fcp or mixed. "
	::= { psetEntry 3 }

       psetVserver                         OBJECT-TYPE
       SYNTAX                              DisplayString
       MAX-ACCESS                      read-only
       STATUS                          current
       DESCRIPTION
	            "Name of the vserver to which the port set belongs.
                     This field is returned only from the c-mode cluster
                     and vserver management interfaces."
       ::= { psetEntry 4 }



	psetMemberTable                 OBJECT-TYPE
	SYNTAX                          SEQUENCE OF PsetMemberEntry
        MAX-ACCESS                      not-accessible
        STATUS                          obsolete
	DESCRIPTION
			"Table of individual Port names in each Port
			set"
	::= {pset 2}

	psetMemberEntry                 OBJECT-TYPE
	SYNTAX                          PsetMemberEntry
        MAX-ACCESS                      not-accessible
        STATUS                          current
	DESCRIPTION
			"Provide a report of portset port information"
	INDEX	{ psetMemberIndex, psetMemberNameIndex}
	::= { psetMemberTable 1 }

	PsetMemberEntry ::=
	    SEQUENCE {
		psetMemberIndex
			Integer32,
		psetMemberNameIndex
			Integer32,
		psetPortName
			DisplayString,
		psetPortVserver
			DisplayString
		}

	psetMemberIndex                 OBJECT-TYPE
	SYNTAX                          Integer32 (1..2147483647)
        MAX-ACCESS                      read-only
        STATUS                          current
        DESCRIPTION
                     "A number that identifies a specific port set."
        ::= { psetMemberEntry 1 }

	psetMemberNameIndex             OBJECT-TYPE
	SYNTAX                          Integer32 (1..2147483647)
        MAX-ACCESS                      read-only
        STATUS                          current
        DESCRIPTION
                      "A number the identifies the port in the set."
        ::= { psetMemberEntry 2 }

	psetPortName                    OBJECT-TYPE
	SYNTAX                          DisplayString
        MAX-ACCESS                      read-only
        STATUS                          current
        DESCRIPTION
		    "A textual name for this port."
	::= { psetMemberEntry 3 }
	psetPortVserver                 OBJECT-TYPE
	SYNTAX                          DisplayString
        MAX-ACCESS                      read-only
        STATUS                          current
        DESCRIPTION
		"Name of the vserver to which the port set and LIFs in the
		     port set belong. This field is available from c-mode management
		     interfaces only."
   ::= { psetMemberEntry 4}

        -- The rest of the blocks group.

	fcp64ReadBytes                  OBJECT-TYPE
	SYNTAX                          Counter64
        MAX-ACCESS                      read-only
        STATUS                          current
        DESCRIPTION
			"The total number of bytes read via FCP
			since the last boot.  This object returns all
			of the 64 bit unsigned integer.
			This field is not available from the c-mode management interfaces"
	::= { blocks 20 }

	fcp64WriteBytes                 OBJECT-TYPE
	SYNTAX                          Counter64
        MAX-ACCESS                      read-only
        STATUS                          current
        DESCRIPTION
			"The total number of bytes written via FCP
			since the last boot.  This object returns all
			of the 64 bit unsigned integer.
			This field is not available from the c-mode management interfaces"
	::= { blocks 21 }

	iscsi64ReadBytes                OBJECT-TYPE
	SYNTAX                          Counter64
        MAX-ACCESS                      read-only
        STATUS                          current
        DESCRIPTION
			"The total number of bytes read via iSCSI
			since the last boot.  This object returns all
			of the 64 bit unsigned integer.
			This field is not available from the c-mode management interfaces"
	::= { blocks 22 }

	iscsi64WriteBytes               OBJECT-TYPE
	SYNTAX                          Counter64
        MAX-ACCESS                      read-only
        STATUS                          current
        DESCRIPTION
			"The total number of bytes written via iSCSI
			since the last boot.  This object returns all
			of the 64 bit unsigned integer.
			This field is not available from the c-mode management interfaces"
	::= { blocks 23 }

	iscsi64Ops                      OBJECT-TYPE
	SYNTAX                          Counter64
        MAX-ACCESS                      read-only
        STATUS                          current
	DESCRIPTION
			"The total number of iSCSI ops handled since the
			last boot.  This object returns all of the 64 bit
			unsigned integer.
			This field is not available from the c-mode management interfaces"
	::= { blocks 24 }

	fcp64Ops                        OBJECT-TYPE
	SYNTAX                          Counter64
        MAX-ACCESS                      read-only
        STATUS                          current
	DESCRIPTION
			"The total number of FCP ops handled since the
			last boot.  This object returns all of the 64 bit
			unsigned integer.
			This field is not available from the c-mode management interfaces"
	::= { blocks 25 }


   -- -- -- -- -- -- -- -- -- -- -- -- -- -- -- -- -- --
   -- -- -- -- -- -- -- -- -- -- -- -- -- -- -- -- -- --
   -- FCP Target Ports
   -- -- -- -- -- -- -- -- -- -- -- -- -- -- -- -- -- --
   -- -- -- -- -- -- -- -- -- -- -- -- -- -- -- -- -- --
   fcpTargetPort    OBJECT IDENTIFIER ::= {blocks 26}

   fcpTargetPortTable              OBJECT-TYPE
   SYNTAX                          SEQUENCE OF FcpTargetPortEntry
       MAX-ACCESS                      not-accessible
       STATUS                          obsolete
   DESCRIPTION
       "Provide a report of fcp target port general
       information. This table is available from Clustered
       Data ONTAP management interfaces only."
   ::= {fcpTargetPort 1}

   fcpTargetPortEntry         OBJECT-TYPE
   SYNTAX                          FcpTargetPortEntry
       MAX-ACCESS                      not-accessible
       STATUS                          current
   DESCRIPTION
       "Provide a report of per fcp target port device information."

   INDEX    { fcpTargetPortNodeName, IMPLIED fcpTargetPortName }
   ::= { fcpTargetPortTable 1 }

   FcpTargetPortEntry ::=
       SEQUENCE {
       fcpTargetPortNodeName      DisplayString,
       fcpTargetPortName          DisplayString,
       fcpTargetPortSpeed         Integer32,
       fcpTargetPortStandby       INTEGER,
       fcpTargetPortTopology      INTEGER
       }

   fcpTargetPortNodeName               OBJECT-TYPE
   SYNTAX                              DisplayString
       MAX-ACCESS                      read-only
       STATUS                          current
   DESCRIPTION
       "Name of the node hosting the FCP target port."
   ::= { fcpTargetPortEntry 1 }

   fcpTargetPortName               OBJECT-TYPE
   SYNTAX                          DisplayString
       MAX-ACCESS                      read-only
       STATUS                          current
   DESCRIPTION
       "FCP target port name."
   ::= { fcpTargetPortEntry 2 }

   fcpTargetPortSpeed              OBJECT-TYPE
   SYNTAX                          Integer32
       MAX-ACCESS                      read-only
       STATUS                          current
   DESCRIPTION
       "Speed in gigabits per second. 0 indicates speed is set to auto."
   ::= { fcpTargetPortEntry 3 }

   fcpTargetPortStandby                OBJECT-TYPE
   SYNTAX                          INTEGER {
                                       false(1),
                                       true(2)
                                    }
       MAX-ACCESS                      read-only
       STATUS                          current
   DESCRIPTION
       "Whether this target adapter is in standby mode."
   ::= { fcpTargetPortEntry 4 }

   fcpTargetPortTopology               OBJECT-TYPE
       SYNTAX                      INTEGER {
                                        unknown(1),
                                        fabric(2),
				        pointToPoint(3),
                                        loop(4),
                                        auto(5)
                                    }
       MAX-ACCESS                      read-only
       STATUS                          current
   DESCRIPTION
       "Fibre channel topology for this adapter."
   ::= { fcpTargetPortEntry 5 }


   -- -- -- -- -- -- -- -- -- -- -- -- -- -- -- -- -- --
   -- -- -- -- -- -- -- -- -- -- -- -- -- -- -- -- -- --
   -- FCP Target LIFs
   -- -- -- -- -- -- -- -- -- -- -- -- -- -- -- -- -- --
   -- -- -- -- -- -- -- -- -- -- -- -- -- -- -- -- -- --
   fcpTargetLif    OBJECT IDENTIFIER ::= {blocks 27}

   fcpTargetLifTable               OBJECT-TYPE
   SYNTAX                          SEQUENCE OF FcpTargetLifEntry
       MAX-ACCESS                      not-accessible
       STATUS                          obsolete
   DESCRIPTION
       "Provide a report of FCP target LIFs general
       information. This table is available from Clustered
       Data ONTAP management interfaces only."
   ::= {fcpTargetLif 1}

   fcpTargetLifEntry          OBJECT-TYPE
   SYNTAX                          FcpTargetLifEntry
       MAX-ACCESS                      not-accessible
       STATUS                          current
   DESCRIPTION
       "Provide a report of per fcp target LIF information."
   INDEX    {fcpTargetLifVserver, fcpTargetLifName }
   ::= { fcpTargetLifTable 1 }

   FcpTargetLifEntry ::=
       SEQUENCE {
       fcpTargetLifVserver       DisplayString,
       fcpTargetLifName          DisplayString,
       fcpTargetLifHomeNode      DisplayString,
       fcpTargetLifHomePort      DisplayString,
       fcpTargetLifNN            DisplayString,
       fcpTargetLifPN            DisplayString,
       fcpTargetLifStatusAdmin   INTEGER,
       fcpTargetLifStatusOper    INTEGER
       }

   fcpTargetLifVserver             OBJECT-TYPE
   SYNTAX                          DisplayString
       MAX-ACCESS                      read-only
       STATUS                          current
       DESCRIPTION
       "Vserver containing the FCP target LIF."
   ::= { fcpTargetLifEntry 1 }
   fcpTargetLifName                OBJECT-TYPE
   SYNTAX                          DisplayString
       MAX-ACCESS                      read-only
       STATUS                          current
   DESCRIPTION
       "The name of the FCP target device."
   ::= { fcpTargetLifEntry 2 }

   fcpTargetLifHomeNode             OBJECT-TYPE
   SYNTAX                           DisplayString
       MAX-ACCESS                       read-only
       STATUS                           current
   DESCRIPTION
       "The home node of the FCP target LIF."
   ::= { fcpTargetLifEntry 3 }

   fcpTargetLifHomePort              OBJECT-TYPE
   SYNTAX                            DisplayString
       MAX-ACCESS                        read-only
       STATUS                            current
   DESCRIPTION
       "The home port of the FCP target LIF."
   ::= { fcpTargetLifEntry 4 }

   fcpTargetLifNN                  OBJECT-TYPE
   SYNTAX                          DisplayString
       MAX-ACCESS                      read-only
       STATUS                          current
   DESCRIPTION
       "The FC WWNN of the FCP target hosting the LIF."
   ::= { fcpTargetLifEntry 5 }

   fcpTargetLifPN                  OBJECT-TYPE
   SYNTAX                          DisplayString
       MAX-ACCESS                      read-only
       STATUS                          current
   DESCRIPTION
       "The FC WWPN of the FCP target LIF."
   ::= { fcpTargetLifEntry 6 }

   fcpTargetLifStatusAdmin         OBJECT-TYPE
   SYNTAX                          INTEGER {
                                       up(0),
                                       down(1)
                                    }
       MAX-ACCESS                      read-only
       STATUS                          current
   DESCRIPTION
       "Status of the FCP target LIF assigned by an administrator."
   ::= { fcpTargetLifEntry 7 }

   fcpTargetLifStatusOper          OBJECT-TYPE
   SYNTAX                          INTEGER {
                                       up(0),
                                       down(1)
                                    }
       MAX-ACCESS                      read-only
       STATUS                          current
   DESCRIPTION
       "Operational status of the FCP target LIF."
   ::= { fcpTargetLifEntry 8 }


	-- -- -- -- -- -- -- -- -- -- -- -- -- -- -- -- -- --
	-- -- -- -- -- -- -- -- -- -- -- -- -- -- -- -- -- --
	-- NFS caching group
	-- -- -- -- -- -- -- -- -- -- -- -- -- -- -- -- -- --
	-- -- -- -- -- -- -- -- -- -- -- -- -- -- -- -- -- --


	-- -- -- -- -- -- -- -- -- -- -- -- -- -- -- -- -- --
	-- NFS caching options
	-- -- -- -- -- -- -- -- -- -- -- -- -- -- -- -- -- --
	nfsCacheOptions		OBJECT IDENTIFIER ::= { nfscache 1 }

	nfsCacheIsEnabled               OBJECT-TYPE
	SYNTAX                          INTEGER {
                                             false(1),
                                             true(2)
                                        }
        MAX-ACCESS                      read-only
        STATUS                          current
	DESCRIPTION
				"Whether NFS caching is enabled on this system."
	::= { nfsCacheOptions 1 }

	nfsCacheIsLicensed              OBJECT-TYPE
	SYNTAX                          INTEGER {
                                             false(1),
                                             true(2)
                                        }
        MAX-ACCESS                      read-only
        STATUS                          current
	DESCRIPTION
				"Whether NFS caching is licensed on this system."
	::= { nfsCacheOptions 2 }

	-- -- -- -- -- -- -- -- -- -- -- -- -- -- -- -- -- --
	-- NFS caching stats
	-- -- -- -- -- -- -- -- -- -- -- -- -- -- -- -- -- --

	nfsCacheStats		OBJECT IDENTIFIER ::= { nfscache 2 }

	nfsCacheBytesFromClients        OBJECT-TYPE
	SYNTAX                          Counter32
        MAX-ACCESS                      read-only
        STATUS                          deprecated
	DESCRIPTION
			"Total NFS bytes received from clients"
	::= { nfsCacheStats 1 }

	nfsCacheBytesToClients          OBJECT-TYPE
	SYNTAX                          Counter32
        MAX-ACCESS                      read-only
        STATUS                          deprecated
	DESCRIPTION
			"Total NFS bytes sent to clients"
	::= { nfsCacheStats 2 }

	nfsCacheBytesFromServers        OBJECT-TYPE
	SYNTAX                          Counter32
        MAX-ACCESS                      read-only
        STATUS                          deprecated
	DESCRIPTION
			"Total NFS bytes received from servers"
	::= { nfsCacheStats 3 }

	nfsCacheBytesToServers          OBJECT-TYPE
	SYNTAX                          Counter32
        MAX-ACCESS                      read-only
        STATUS                          deprecated
	DESCRIPTION
			"Total NFS bytes sent to servers"
	::= { nfsCacheStats 4 }

	nfsCacheTotalRequests           OBJECT-TYPE
	SYNTAX                          Counter32
        MAX-ACCESS                      read-only
        STATUS                          deprecated
	DESCRIPTION
			"Total NFS requests received"
	::= { nfsCacheStats 5 }

	nfsCacheHitRequests             OBJECT-TYPE
	SYNTAX                          Counter32
        MAX-ACCESS                      read-only
        STATUS                          deprecated
	DESCRIPTION
			"Total NFS requests resulting in cache hits"
	::= { nfsCacheStats 6 }

	nfsCacheMissRequests            OBJECT-TYPE
	SYNTAX                          Counter32
        MAX-ACCESS                      read-only
        STATUS                          deprecated
	DESCRIPTION
			"Total NFS requests resulting in cache misses"
	::= { nfsCacheStats 7 }

	nfsCacheMissCacheableRequests   OBJECT-TYPE
	SYNTAX                          Counter32
        MAX-ACCESS                      read-only
        STATUS                          current
	DESCRIPTION
			"Total NFS requests that were cacheable misses"
	::= { nfsCacheStats 8 }

	nfsCacheMissUnCacheableRequests OBJECT-TYPE
	SYNTAX                          Counter32
        MAX-ACCESS                      read-only
        STATUS                          current
	DESCRIPTION
			"Total NFS requests that were uncacheable misses"
	::= { nfsCacheStats 9 }

	nfsCacheEjectRequests           OBJECT-TYPE
	SYNTAX                          Counter32
        MAX-ACCESS                      read-only
        STATUS                          current
	DESCRIPTION
			"Total NFS requests resulting in object eject due to expiration"
	::= { nfsCacheStats 10 }

	nfsCacheVerifyRequests          OBJECT-TYPE
	SYNTAX                          Counter32
        MAX-ACCESS                      read-only
        STATUS                          current
	DESCRIPTION
			"Total NFS requests resulting in object verification"
	::= { nfsCacheStats 11 }

	nfsCacheRpcRecords              OBJECT-TYPE
	SYNTAX                          Counter32
        MAX-ACCESS                      read-only
        STATUS                          current
	DESCRIPTION
			"Total RPC records received"
	::= { nfsCacheStats 12 }

	nfsCacheBWSavings               OBJECT-TYPE
	SYNTAX                          Integer32
        MAX-ACCESS                      read-only
        STATUS                          current
	DESCRIPTION
			"Bandwidth savings for NFS requests"
	::= { nfsCacheStats 13 }

	nfsCacheHighBytesFromClients    OBJECT-TYPE
	SYNTAX                          Counter32
        MAX-ACCESS                      read-only
        STATUS                          deprecated
	DESCRIPTION
			"Total NFS bytes received from clients.  This object
			 returns the most significant 32 bits of the 64 bit
			 unsigned integer. This object is deprecated - Use
			 nfsCache64BytesFromClients instead."
	::= { nfsCacheStats 14 }

	nfsCacheLowBytesFromClients     OBJECT-TYPE
	SYNTAX                          Counter32
        MAX-ACCESS                      read-only
        STATUS                          deprecated
	DESCRIPTION
			"Total NFS bytes received from clients.  This object
			 returns the least significant 32 bits of the 64 bit
			 unsigned integer. This object is deprecated - Use
			 nfsCache64BytesFromClients instead."
	::= { nfsCacheStats 15 }

	nfsCacheHighBytesToClients      OBJECT-TYPE
	SYNTAX                          Counter32
        MAX-ACCESS                      read-only
        STATUS                          deprecated
	DESCRIPTION
			"Total NFS bytes sent to clients.  This object returns
			 the most significant 32 bits of the 64 bit unsigned
			 integer. This object is deprecated - Use
			 nfsCache64BytesToClients instead."
	::= { nfsCacheStats 16 }

	nfsCacheLowBytesToClients       OBJECT-TYPE
	SYNTAX                          Counter32
        MAX-ACCESS                      read-only
        STATUS                          deprecated
	DESCRIPTION
			"Total NFS bytes sent to clients.  This object returns
			 the least significant 32 bits of the 64 bit unsigned
			 integer. This object is deprecated - Use
			 nfsCache64BytesToClients instead."
	::= { nfsCacheStats 17 }

	nfsCacheHighBytesFromServers    OBJECT-TYPE
	SYNTAX                          Counter32
        MAX-ACCESS                      read-only
        STATUS                          deprecated
	DESCRIPTION
			"Total NFS bytes received from servers.  This object
			 returns the most significant 32 bits of the 64 bit
			 unsigned integer. This object is deprecated - Use
			 nfsCache64BytesFromServers instead."
	::= { nfsCacheStats 18 }

	nfsCacheLowBytesFromServers     OBJECT-TYPE
	SYNTAX                          Counter32
        MAX-ACCESS                      read-only
        STATUS                          deprecated
	DESCRIPTION
			"Total NFS bytes received from servers.  This object
			 returns the least significant 32 bits of the 64 bit
			 unsigned integer. This object is deprecated - Use
			 nfsCache64BytesFromServers instead."
	::= { nfsCacheStats 19 }

	nfsCacheHighBytesToServers      OBJECT-TYPE
	SYNTAX                          Counter32
        MAX-ACCESS                      read-only
        STATUS                          deprecated
	DESCRIPTION
			"Total NFS bytes sent to servers.  This object
			 returns the most significant 32 bits of the 64 bit
			 unsigned integer. This object is deprecated - Use
			 nfsCache64BytesToServers instead."
	::= { nfsCacheStats 20 }

	nfsCacheLowBytesToServers       OBJECT-TYPE
	SYNTAX                          Counter32
        MAX-ACCESS                      read-only
        STATUS                          deprecated
	DESCRIPTION
			"Total NFS bytes sent to servers.  This object
			 returns the least significant 32 bits of the 64 bit
			 unsigned integer. This object is deprecated - Use
			 nfsCache64BytesToServers instead."
	::= { nfsCacheStats 21 }

	nfsCacheHighTotalRequests       OBJECT-TYPE
	SYNTAX                          Counter32
        MAX-ACCESS                      read-only
        STATUS                          deprecated
	DESCRIPTION
			"Total NFS requests received.  This object returns
			 the most significant 32 bits of the 64 bit unsigned
			 integer. This object is deprecated - Use
			 nfsCache64TotalRequests instead."
	::= { nfsCacheStats 22 }

	nfsCacheLowTotalRequests        OBJECT-TYPE
	SYNTAX                          Counter32
        MAX-ACCESS                      read-only
        STATUS                          deprecated
	DESCRIPTION
			"Total NFS requests received.  This object returns
			 the least significant 32 bits of the 64 bit unsigned
			 integer. This object is deprecated - Use
			 nfsCache64TotalRequests instead."
	::= { nfsCacheStats 23 }

	nfsCacheHighHitRequests         OBJECT-TYPE
	SYNTAX                          Counter32
        MAX-ACCESS                      read-only
        STATUS                          deprecated
	DESCRIPTION
			"Total NFS requests resulting in cache hits.  This
			 object returns the most significant 32 bits of the
			 64 bit unsigned integer. This object is deprecated -
			 Use nfsCache64HitRequests instead."
	::= { nfsCacheStats 24 }

	nfsCacheLowHitRequests          OBJECT-TYPE
	SYNTAX                          Counter32
        MAX-ACCESS                      read-only
        STATUS                          deprecated
	DESCRIPTION
			"Total NFS requests resulting in cache hits.  This
			 object returns the least significant 32 bits of the
			 64 bit unsigned integer. This object is deprecated -
			 Use nfsCache64HitRequests instead."
	::= { nfsCacheStats 25 }

	nfsCacheHighMissRequests        OBJECT-TYPE
	SYNTAX                          Counter32
        MAX-ACCESS                      read-only
        STATUS                          deprecated
	DESCRIPTION
			"Total NFS requests resulting in cache misses.  This
			 object returns the most significant 32 bits of the
			 64 bit unsigned integer. This object is deprecated -
			 Use nfsCache64MissRequests instead."
	::= { nfsCacheStats 26 }

	nfsCacheLowMissRequests         OBJECT-TYPE
	SYNTAX                          Counter32
        MAX-ACCESS                      read-only
        STATUS                          deprecated
	DESCRIPTION
			"Total NFS requests resulting in cache misses.  This
			 object returns the least significant 32 bits of the
			 64 bit unsigned integer. This object is deprecated -
			 Use nfsCache64MissRequests instead."
	::= { nfsCacheStats 27 }

	nfsCache64BytesFromClients      OBJECT-TYPE
	SYNTAX                          Counter64
        MAX-ACCESS                      read-only
        STATUS                          current
	DESCRIPTION
			"Total NFS bytes received from clients.  This object
			 returns all of the 64 bit unsigned integer."
	::= { nfsCacheStats 28 }

	nfsCache64BytesToClients        OBJECT-TYPE
	SYNTAX                          Counter64
        MAX-ACCESS                      read-only
        STATUS                          current
	DESCRIPTION
			"Total NFS bytes sent to clients.  This object returns
			 all of the 64 bit unsigned integer."
	::= { nfsCacheStats 29 }

	nfsCache64BytesFromServers      OBJECT-TYPE
	SYNTAX                          Counter64
        MAX-ACCESS                      read-only
        STATUS                          current
	DESCRIPTION
			"Total NFS bytes received from servers.  This object
			 returns all of the 64 bit unsigned integer."
	::= { nfsCacheStats 30 }

	nfsCache64BytesToServers        OBJECT-TYPE
	SYNTAX                          Counter64
        MAX-ACCESS                      read-only
        STATUS                          current
	DESCRIPTION
			"Total NFS bytes sent to servers.  This object
			 returns all of the 64 bit unsigned integer."
	::= { nfsCacheStats 31 }

	nfsCache64TotalRequests         OBJECT-TYPE
	SYNTAX                          Counter64
        MAX-ACCESS                      read-only
        STATUS                          current
	DESCRIPTION
			"Total NFS requests received.  This object returns
			 all of the 64 bit unsigned integer."
	::= { nfsCacheStats 32 }

	nfsCache64HitRequests           OBJECT-TYPE
	SYNTAX                          Counter64
        MAX-ACCESS                      read-only
        STATUS                          current
	DESCRIPTION
			"Total NFS requests resulting in cache hits.  This
			 object returns all of the  64 bit unsigned integer."
	::= { nfsCacheStats 33 }

	nfsCache64MissRequests          OBJECT-TYPE
	SYNTAX                          Counter64
        MAX-ACCESS                      read-only
        STATUS                          current
	DESCRIPTION
			"Total NFS requests resulting in cache misses.  This
			 object returns all of the 64 bit unsigned integer."
	::= { nfsCacheStats 34 }

	-- -- -- -- -- -- -- --
	-- the storage group --
	-- -- -- -- -- -- -- --

	enclosure	OBJECT IDENTIFIER ::=	{ storage 1 }

        -- -- -- -- -- -- --
        -- The enclosure group for storage

	enclNumber                      OBJECT-TYPE
	SYNTAX                          Integer32
        MAX-ACCESS                      read-only
        STATUS                          current
	DESCRIPTION
	    "The number of storage enclosures in the storage subsystem."
	::= { enclosure 1 }

	enclTable                       OBJECT-TYPE
	SYNTAX                          SEQUENCE OF EnclEntry
        MAX-ACCESS                      not-accessible
        STATUS                          current
	DESCRIPTION
	    "Display disk enclosure environmental information for disk
	     shelves that support SCSI Enclosure Services."
	::= { enclosure 2 }

	enclEntry                       OBJECT-TYPE
	SYNTAX                          EnclEntry
        MAX-ACCESS                      not-accessible
        STATUS                          current
	DESCRIPTION
	    "Display disk enclosure (shelf) environmental
	     information for the referenced disk enclosure."
	INDEX	{ enclIndex }
	::= { enclTable 1 }

	EnclEntry ::=
	    SEQUENCE {
	        enclIndex
		    Integer32,
		enclContactState
		    INTEGER,
		enclChannelShelfAddr
		    DisplayString,
		enclProductLogicalID
		    DisplayString,
		enclProductID
		    DisplayString,
		enclProductVendor
		    DisplayString,
		enclProductModel
		    DisplayString,
		enclProductRevision
		    DisplayString,
		enclProductSerialNo
		    DisplayString,
		enclNumberDiskBays
		    Integer32,
		enclDisksPresent
		    DisplayString,
		enclPowerSuppliesMaximum
		    Integer32,
		enclPowerSuppliesPresent
		    DisplayString,
		enclPowerSuppliesSerialNos
		    DisplayString,
		enclPowerSuppliesFailed
		    DisplayString,
		enclFansMaximum
		    Integer32,
		enclFansPresent
		    DisplayString,
		enclFansFailed
		    DisplayString,
		enclTempSensorsMaximum
		    Integer32,
		enclTempSensorsPresent
		    DisplayString,
		enclTempSensorsOverTempFail
		    DisplayString,
		enclTempSensorsOverTempWarn
		    DisplayString,
		enclTempSensorsUnderTempFail
		    DisplayString,
		enclTempSensorsUnderTempWarn
		    DisplayString,
		enclTempSensorsCurrentTemp
		    DisplayString,
		enclTempSensorsOverTempFailThr
		    DisplayString,
		enclTempSensorsOverTempWarnThr
		    DisplayString,
		enclTempSensorsUnderTempFailThr
		    DisplayString,
		enclTempSensorsUnderTempWarnThr
		    DisplayString,
		enclElectronicsMaximum
		    Integer32,
		enclElectronicsPresent
		    DisplayString,
		enclElectronicsSerialNos
		    DisplayString,
	        enclElectronicsFailed
		    DisplayString,
		enclVoltSensorsMaximum
		    Integer32,
		enclVoltSensorsPresent
		    DisplayString,
		enclVoltSensorsOverVoltFail
		    DisplayString,
		enclVoltSensorsOverVoltWarn
		    DisplayString,
		enclVoltSensorsUnderVoltFail
		    DisplayString,
		enclVoltSensorsUnderVoltWarn
		    DisplayString,
		enclVoltSensorsOverVoltFailThr
		    DisplayString,
		enclVoltSensorsOverVoltWarnThr
		    DisplayString,
		enclVoltSensorsUnderVoltFailThr
		    DisplayString,
		enclVoltSensorsUnderVoltWarnThr
		    DisplayString,
		enclVoltSensorsCurrentVolt
		    DisplayString,
		enclCurSensorsMaximum
		    Integer32,
		enclCurSensorsPresent
		    DisplayString,
		enclCurSensorsOverCurFail
		    DisplayString,
		enclCurSensorsOverCurWarn
		    DisplayString,
		enclCurSensorsOverCurFailThr
		    DisplayString,
		enclCurSensorsOverCurWarnThr
		    DisplayString,
		enclCurSensorsCurrentCur
		    DisplayString,
		enclSASConnectMaximum
		    Integer32,
		enclSASConnectPresent
		    DisplayString,
		enclSASConnectVendor
		    DisplayString,
		enclSASConnectType
		    DisplayString,
		enclSASConnectCableLen
		    DisplayString,
		enclSASConnectCableTech
		    DisplayString,
		enclSASConnectCableEnd
		    DisplayString,
		enclSASConnectSerialNos
		    DisplayString,
		enclSASConnectPartNos
		    DisplayString,
		enclPowerSuppliesPartNos
		    DisplayString,
		enclFansSpeed
		    DisplayString,
		enclElectronicsPartNos
		    DisplayString,
		enclElectronicsCPLDVers
		    DisplayString,
		enclNodeName
		    DisplayString
	    }

	enclIndex                       OBJECT-TYPE
	SYNTAX                          Integer32 (0..255)
        MAX-ACCESS                      read-only
        STATUS                          current
	DESCRIPTION
			"A number that identifies this enclosure among the
			 possible monitored enclosures.  This number normally
			 uniquely identifies one shelf within one boot,
			 but may it change between boots.  The number may
			 also change within a boot if shelves are removed
			 and added."
	::= { enclEntry 1 }

	enclContactState                OBJECT-TYPE
	SYNTAX                          INTEGER {
                                             initializing(1),
                                             transitioning(2),
					     active(3),
					     inactive(4),
					     reconfiguring(5),
                                             nonexistent(6)
                                        }
        MAX-ACCESS                      read-only
        STATUS                          current
	DESCRIPTION
	    "The state of the communication between the filer or storage
	    engine and the enclosure monitoring device in the enclosure."
	::= { enclEntry 2 }

	enclChannelShelfAddr            OBJECT-TYPE
	SYNTAX                          DisplayString
        MAX-ACCESS                      read-only
        STATUS                          current
	DESCRIPTION
	    "The adapter number or switch name and the port number
	    (together, called the channel), and shelf ID of this
	    enclosure.  Examples are 8a.1 and switch:5.1."
	::= { enclEntry 3 }

	enclProductLogicalID            OBJECT-TYPE
	SYNTAX                          DisplayString
        MAX-ACCESS                      read-only
        STATUS                          current
	DESCRIPTION
	    "The logical identifier of this enclosure.  This a form of the
	    World-Wide Name (WWN)."
	::= { enclEntry 4 }

	enclProductID                   OBJECT-TYPE
	SYNTAX                          DisplayString
        MAX-ACCESS                      read-only
        STATUS                          current
	DESCRIPTION
	    "The product ID of the shelf hardware module that provides
	    the enclosure monitoring function.  Example is LRC."
	::= { enclEntry 5 }

	enclProductVendor               OBJECT-TYPE
	SYNTAX                          DisplayString
        MAX-ACCESS                      read-only
        STATUS                          current
	DESCRIPTION
	    "The name of the vendor of this enclosure.  Example is Xyratex."
	::= { enclEntry 6 }

	enclProductModel                OBJECT-TYPE
	SYNTAX                          DisplayString
        MAX-ACCESS                      read-only
        STATUS                          current
	DESCRIPTION
	    "The model name of this enclosure.  Example is DiskShelf14."
	::= { enclEntry 7 }

	enclProductRevision             OBJECT-TYPE
	SYNTAX                          DisplayString
        MAX-ACCESS                      read-only
        STATUS                          current
	DESCRIPTION
	    "The revision number of this enclosure."
	::= { enclEntry 8 }

	enclProductSerialNo             OBJECT-TYPE
	SYNTAX                          DisplayString
        MAX-ACCESS                      read-only
        STATUS                          current
	DESCRIPTION
	    "The serial number of this enclosure."
	::= { enclEntry 9 }

	enclNumberDiskBays              OBJECT-TYPE
	SYNTAX                          Integer32
        MAX-ACCESS                      read-only
        STATUS                          current
	DESCRIPTION
	    "The number of disk bays in this enclosure."
	::= { enclEntry 10 }

	enclDisksPresent                OBJECT-TYPE
	SYNTAX                          DisplayString
        MAX-ACCESS                      read-only
        STATUS                          current
	DESCRIPTION
	    "The list of disks present by bay number in this enclosure."
	::= { enclEntry 11 }

	enclPowerSuppliesMaximum        OBJECT-TYPE
	SYNTAX                          Integer32
        MAX-ACCESS                      read-only
        STATUS                          current
	DESCRIPTION
	    "The maximum number of power supplies in this enclosure."
	::= { enclEntry 12 }

	enclPowerSuppliesPresent        OBJECT-TYPE
	SYNTAX                          DisplayString
        MAX-ACCESS                      read-only
        STATUS                          current
	DESCRIPTION
	    "The list of power supplies present in the enclosure.
	     Numbering is from left to right (top supply, then bottom,
	     on each side, if applicable) in their intended location
	     in the shelf, while facing the supplies."
	::= { enclEntry 13 }

	enclPowerSuppliesSerialNos      OBJECT-TYPE
	SYNTAX                          DisplayString
        MAX-ACCESS                      read-only
        STATUS                          current
	DESCRIPTION
	    "The list of serial numbers of power supplies present
	     in the enclosure.  Not all shelves are able to report the
	     power supply serial number.  Communication errors may
	     make the serial number unavailable. The order follows that
	     of enclPowerSuppliesPresent"
	::= { enclEntry 14 }

	enclPowerSuppliesFailed         OBJECT-TYPE
	SYNTAX                          DisplayString
        MAX-ACCESS                      read-only
        STATUS                          current
	DESCRIPTION
	    "The list of failed power supplies in this enclosure, numbered as
	     in enclPowerSuppliesPresent."
	::= { enclEntry 15 }

	enclFansMaximum                 OBJECT-TYPE
	SYNTAX                          Integer32
        MAX-ACCESS                      read-only
        STATUS                          current
	DESCRIPTION
	    "The maximum number of fans or fan modules monitored by this
	     enclosure.  R100/R150 shelf power supply fans are not included
	     in this number."
	::= { enclEntry 16 }

	enclFansPresent                 OBJECT-TYPE
	SYNTAX                          DisplayString
        MAX-ACCESS                      read-only
        STATUS                          current
	DESCRIPTION
	    "The list of fans or fan modules present and for which
	     status is known in this enclosure.  Numbering begins with
	     fans on the front of the enclosure, if applicable. Fans
	     are numbered left-to-right (upper fans, then lower, if
	     applicable) as facing the fans or the modules that
	     contain them, such as power supply modules.  R100/R150
	     shelf power supply fans are not included in this list."
	::= { enclEntry 17 }

	enclFansFailed                  OBJECT-TYPE
	SYNTAX                          DisplayString
        MAX-ACCESS                      read-only
        STATUS                          current
	DESCRIPTION
	    "The list of failed fans or fan modules in this enclosure.  Fans
	     are numbered as described in enclFansPresent."
	::= { enclEntry 18 }

	enclTempSensorsMaximum          OBJECT-TYPE
	SYNTAX                          Integer32
        MAX-ACCESS                      read-only
        STATUS                          current
	DESCRIPTION
	    "The maximum number of temperature sensors monitored
	     by this enclosure."
	::= { enclEntry 19 }

	enclTempSensorsPresent          OBJECT-TYPE
	SYNTAX                          DisplayString
        MAX-ACCESS                      read-only
        STATUS                          current
	DESCRIPTION
	    "The list of temperature sensors present and for which
	     status is known in this enclosure.  Temperature sensors are
	     numbered top-to-bottom and left-to-right, beginning with
	     the front of the enclosure, then the rear, as the modules
	     containing them are faced."
	::= { enclEntry 20 }

	enclTempSensorsOverTempFail     OBJECT-TYPE
	SYNTAX                          DisplayString
        MAX-ACCESS                      read-only
        STATUS                          current
	DESCRIPTION
	    "The list of temperature sensors reporting
	     overtemperature failure in this enclosure.  Sensors are
	     numbered as in TempSensorsPresent."
	::= { enclEntry 21 }

	enclTempSensorsOverTempWarn     OBJECT-TYPE
	SYNTAX                          DisplayString
        MAX-ACCESS                      read-only
        STATUS                          current
	DESCRIPTION
	    "The list of temperature sensors reporting overtemperature
	     warning in this enclosure.  Sensors are numbered as in
	     TempSensorsPresent."
	::= { enclEntry 22 }

	enclTempSensorsUnderTempFail    OBJECT-TYPE
	SYNTAX                          DisplayString
        MAX-ACCESS                      read-only
        STATUS                          current
	DESCRIPTION
	    "The list of temperature sensors reporting undertemperature
	     failure in this enclosure.  Sensors are numbered as in
	     TempSensorsPresent."
	::= { enclEntry 23 }

	enclTempSensorsUnderTempWarn    OBJECT-TYPE
	SYNTAX                          DisplayString
        MAX-ACCESS                      read-only
        STATUS                          current
	DESCRIPTION
	    "The list of temperature sensors reporting undertemperature
	     warning in this enclosure.  Sensors are numbered as in
	     TempSensorsPresent."
	::= { enclEntry 24 }

	enclTempSensorsCurrentTemp      OBJECT-TYPE
	SYNTAX                          DisplayString
        MAX-ACCESS                      read-only
        STATUS                          current
	DESCRIPTION
	    "The list of temperatures reported by all temperature sensors in
	     the enclosure, including the ambient temperature.  Sensors are
	     numbered as in TempSensorsPresent."
	::= { enclEntry 25 }

	enclTempSensorsOverTempFailThr  OBJECT-TYPE
	SYNTAX                          DisplayString
        MAX-ACCESS                      read-only
        STATUS                          current
	DESCRIPTION
	    "The list of overtemperature failure thresholds for all
	     temperature sensors in the enclosure.  Sensors are
	     numbered as in TempSensorsPresent."
	::= { enclEntry 26 }

	enclTempSensorsOverTempWarnThr  OBJECT-TYPE
	SYNTAX                          DisplayString
        MAX-ACCESS                      read-only
        STATUS                          current
	DESCRIPTION
	    "The list of overtemperature warning thresholds for all
	     temperature sensors in the enclosure.  Sensors are
	     numbered as in TempSensorsPresent."
	::= { enclEntry 27 }

	enclTempSensorsUnderTempFailThr OBJECT-TYPE
	SYNTAX                          DisplayString
        MAX-ACCESS                      read-only
        STATUS                          current
	DESCRIPTION
	    "The list of undertemperature failure thresholds for all
	     temperature sensors in the enclosure.  Sensors are numbered as
	     in TempSensorsPresent."
	::= { enclEntry 28 }

	enclTempSensorsUnderTempWarnThr OBJECT-TYPE
	SYNTAX                          DisplayString
        MAX-ACCESS                      read-only
        STATUS                          current
	DESCRIPTION
	    "The list of undertemperature warning thresholds for all
	     temperature sensors in the enclosure.   Sensors are numbered as
	     in TempSensorsPresent."
	::= { enclEntry 29 }

	enclElectronicsMaximum          OBJECT-TYPE
	SYNTAX                          Integer32
        MAX-ACCESS                      read-only
        STATUS                          current
	DESCRIPTION
	    "The number of enclosure services electronics modules that it is
	     possible for this enclosure to detect and/or monitor."
	::= { enclEntry 30 }

	enclElectronicsPresent          OBJECT-TYPE
	SYNTAX                          DisplayString
        MAX-ACCESS                      read-only
        STATUS                          current
	DESCRIPTION
	    "The list those enclosure services electronics modules present in
	     this enclosure.  Numbering is from left-to-right or top-to-bottom
	     in their intended location in the shelf, while facing the
	     electronics modules.  It is normal for the R200 FC-AT module to be
	     reported as the second module."
	::= { enclEntry 31 }

	enclElectronicsSerialNos        OBJECT-TYPE
	SYNTAX                          DisplayString
        MAX-ACCESS                      read-only
        STATUS                          current
	DESCRIPTION
	    "The list of serial numbers of the enclosure services electronics
	     modules present in this enclosure.  The order follows that of
	     enclElectronicsPresent."
	::= { enclEntry 32 }

	enclElectronicsFailed           OBJECT-TYPE
	SYNTAX                          DisplayString
        MAX-ACCESS                      read-only
        STATUS                          current
	DESCRIPTION
	    "The list of failed electronics elements.  Valid only if
	     enclElectronicsPresent shows that some are present."
	::= { enclEntry 33 }

	enclVoltSensorsMaximum          OBJECT-TYPE
	SYNTAX                          Integer32
        MAX-ACCESS                      read-only
        STATUS                          current
	DESCRIPTION
	    "The number of voltage sensors monitored by
	     this enclosure."
	::= { enclEntry 34 }

	enclVoltSensorsPresent          OBJECT-TYPE
	SYNTAX                          DisplayString
        MAX-ACCESS                      read-only
        STATUS                          current
	DESCRIPTION
	    "The list of voltage sensors present and for which
	     status is known in this enclosure.  Voltage sensors are
	     numbered top-to-bottom and left-to-right, as the modules
	     containing them are faced."
	::= { enclEntry 35 }

	enclVoltSensorsOverVoltFail     OBJECT-TYPE
	SYNTAX                          DisplayString
        MAX-ACCESS                      read-only
        STATUS                          current
	DESCRIPTION
	    "The list of voltage sensors reporting
	     overvoltage failure in this enclosure.  Sensors are
	     numbered as in VoltSensorsPresent."
	::= { enclEntry 36 }

	enclVoltSensorsOverVoltWarn     OBJECT-TYPE
	SYNTAX                          DisplayString
        MAX-ACCESS                      read-only
        STATUS                          current
	DESCRIPTION
	    "The list of voltage sensors reporting overvoltage
	     warning in this enclosure.  Sensors are numbered as in
	     VoltSensorsPresent."
	::= { enclEntry 37 }

	enclVoltSensorsUnderVoltFail    OBJECT-TYPE
	SYNTAX                          DisplayString
        MAX-ACCESS                      read-only
        STATUS                          current
	DESCRIPTION
	    "The list of voltage sensors reporting undervoltage
	     failure in this enclosure.  Sensors are numbered as in
	     VoltSensorsPresent."
	::= { enclEntry 38 }

	enclVoltSensorsUnderVoltWarn    OBJECT-TYPE
	SYNTAX                          DisplayString
        MAX-ACCESS                      read-only
        STATUS                          current
	DESCRIPTION
	    "The list of voltage sensors reporting undervoltage
	     warning in this enclosure.  Sensors are numbered as in
	     VoltSensorsPresent."
	::= { enclEntry 39 }

	enclVoltSensorsCurrentVolt      OBJECT-TYPE
	SYNTAX                          DisplayString
        MAX-ACCESS                      read-only
        STATUS                          current
	DESCRIPTION
	    "The list of voltages reported by all voltage sensors in
	     the enclosure, Sensors are
	     numbered as in VoltSensorsPresent."
	::= { enclEntry 40 }

	enclVoltSensorsOverVoltFailThr  OBJECT-TYPE
	SYNTAX                          DisplayString
        MAX-ACCESS                      read-only
        STATUS                          current
	DESCRIPTION
	    "The list of overvoltage failure thresholds for all
	     voltage sensors in the enclosure.  Sensors are
	     numbered as in VoltSensorsPresent."
	::= { enclEntry 41 }

	enclVoltSensorsOverVoltWarnThr  OBJECT-TYPE
	SYNTAX                          DisplayString
        MAX-ACCESS                      read-only
        STATUS                          current
	DESCRIPTION
	    "The list of overvoltage warning thresholds for all
	     voltage sensors in the enclosure.  Sensors are
	     numbered as in VoltSensorsPresent."
	::= { enclEntry 42 }

	enclVoltSensorsUnderVoltFailThr OBJECT-TYPE
	SYNTAX                          DisplayString
        MAX-ACCESS                      read-only
        STATUS                          current
	DESCRIPTION
	    "The list of undervoltage failure thresholds for all
	     voltage sensors in the enclosure.  Sensors are numbered
	     as in VoltSensorsPresent."
	::= { enclEntry 43 }

	enclVoltSensorsUnderVoltWarnThr OBJECT-TYPE
	SYNTAX                          DisplayString
        MAX-ACCESS                      read-only
        STATUS                          current
	DESCRIPTION
	    "The list of undervoltage warning thresholds for all
	     voltage sensors in the enclosure.  Sensors are numbered as
	     in VoltSensorsPresent."
	::= { enclEntry 44 }

	enclCurSensorsMaximum           OBJECT-TYPE
	SYNTAX                          Integer32
        MAX-ACCESS                      read-only
        STATUS                          current
	DESCRIPTION
	    "The number of current sensors monitored by
	     this enclosure."
	::= { enclEntry 45 }

	enclCurSensorsPresent           OBJECT-TYPE
	SYNTAX                          DisplayString
        MAX-ACCESS                      read-only
        STATUS                          current
	DESCRIPTION
	    "The list of current sensors present and for which
	     status is known in this enclosure.  Current sensors are
	     numbered top-to-bottom and left-to-right, beginning with
	     the front of the enclosure, then the rear, as the modules
	     containing them are faced."
	::= { enclEntry 46 }

	enclCurSensorsOverCurFail       OBJECT-TYPE
	SYNTAX                          DisplayString
        MAX-ACCESS                      read-only
        STATUS                          current
	DESCRIPTION
	    "The list of current sensors reporting
	     overcurrent failure in this enclosure.  Sensors are
	     numbered as in CurSensorsPresent."
	::= { enclEntry 47 }

	enclCurSensorsOverCurWarn       OBJECT-TYPE
	SYNTAX                          DisplayString
        MAX-ACCESS                      read-only
        STATUS                          current
	DESCRIPTION
	    "The list of current sensors reporting overcurrent
	     warning in this enclosure.  Sensors are numbered as in
	     CurSensorsPresent."
	::= { enclEntry 48 }

	enclCurSensorsCurrentCur        OBJECT-TYPE
	SYNTAX                          DisplayString
        MAX-ACCESS                      read-only
        STATUS                          current
	DESCRIPTION
	    "The list of currents reported by all current sensors in
	     the enclosure, Sensors are
	     numbered as in CurSensorsPresent."
	::= { enclEntry 49 }

	enclCurSensorsOverCurFailThr    OBJECT-TYPE
	SYNTAX                          DisplayString
        MAX-ACCESS                      read-only
        STATUS                          current
	DESCRIPTION
	    "The list of overcurrent failure thresholds for all
	     current sensors in the enclosure.  Sensors are
	     numbered as in CurSensorsPresent."
	::= { enclEntry 50 }

	enclCurSensorsOverCurWarnThr    OBJECT-TYPE
	SYNTAX                          DisplayString
        MAX-ACCESS                      read-only
        STATUS                          current
	DESCRIPTION
	    "The list of overcurrent warning thresholds for all
	     current sensors in the enclosure.  Sensors are
	     numbered as in CurSensorsPresent."
	::= { enclEntry 51 }

	enclSASConnectMaximum		OBJECT-TYPE
	SYNTAX            		Integer32
        MAX-ACCESS                      read-only
        STATUS                          current
	DESCRIPTION
	    "The number of possible SAS connectors monitored
	     by this enclosure."
	::= { enclEntry 52 }

	enclSASConnectPresent		OBJECT-TYPE
	SYNTAX            		DisplayString
        MAX-ACCESS                      read-only
        STATUS                          current
	DESCRIPTION
	    "The list of SAS connector numbers in this
	     enclosure that have cables attached.  Connectors
	     are numbered beginning at one on module one,
	     counting connectors innermost-to-outermost on the
	     module, then module two innermost-to-outermost.
	     Modules are numbered as in enclElectronicsPresent."
	::= { enclEntry 53 }

	enclSASConnectVendor		OBJECT-TYPE
	SYNTAX       			DisplayString
        MAX-ACCESS                      read-only
        STATUS                          current
	DESCRIPTION
	    "The list of vendors of cables attached to the
	     SES connectors of the enclosure. If no cable,
	     is attached, the entry is shown as <N/A>."
	::= { enclEntry 54 }

	enclSASConnectType		OBJECT-TYPE
	SYNTAX        			DisplayString
        MAX-ACCESS                      read-only
        STATUS                          current
	DESCRIPTION
	    "The list of connector types of connectors attached
	     to the enclosure. If no cable is attached,
	     the entry is shown as <N/A>."
	::= { enclEntry 55 }

        enclSASConnectCableLen		OBJECT-TYPE
	SYNTAX         			DisplayString
        MAX-ACCESS                      read-only
        STATUS                          current
	DESCRIPTION
	    "The list of lengths (in meters) of cables attached
	     to the enclosure.  If no cable is attached,
	     the entry is shown as <N/A>."
	::= { enclEntry 56 }

	enclSASConnectCableTech    	OBJECT-TYPE
	SYNTAX				DisplayString
        MAX-ACCESS                      read-only
        STATUS                          current
	DESCRIPTION
	    "The list of cable technologies of connectors attached
	     to the enclosure.  If no cable is attached, the
	     entry is shown as <N/A>."
	::= { enclEntry 57 }

	enclSASConnectCableEnd		OBJECT-TYPE
	SYNTAX				DisplayString
        MAX-ACCESS                      read-only
        STATUS                          current
	DESCRIPTION
	    "The list of identifiers of which end of the cable is
	     attached to the enclosure.  If no cable is attached,
	     the entry is shown as <N/A>."
	::= { enclEntry 58 }

	enclSASConnectSerialNos         OBJECT-TYPE
	SYNTAX                          DisplayString
        MAX-ACCESS                      read-only
        STATUS                          current
	DESCRIPTION
	    "The list of serial numbers of the SAS cables attached
	     to this enclosure.  If no cable is attached, the
	     entry is shown as <N/A>."
	::= { enclEntry 59 }

 	enclSASConnectPartNos           OBJECT-TYPE
	SYNTAX                          DisplayString
        MAX-ACCESS                      read-only
        STATUS                          current
	DESCRIPTION
	    "The list of part numbers of the SAS cables attached
	     to this enclosure.  If no cable is attached, the
	     entry is shown as <N/A>."
	::= { enclEntry 60 }

	enclPowerSuppliesPartNos        OBJECT-TYPE
	SYNTAX                          DisplayString
        MAX-ACCESS                      read-only
        STATUS                          current
	DESCRIPTION
	    "The list of part numbers of power supplies present
	     in the enclosure.  Not all shelves are able to report the
	     power supply part number.  Communication errors may
	     make the part number unavailable. The order follows that of
	     enclPowerSuppliesPresent."
	::= { enclEntry 61 }

	enclFansSpeed                   OBJECT-TYPE
	SYNTAX                          DisplayString
        MAX-ACCESS                      read-only
        STATUS                          current
	DESCRIPTION
	    "The list of fan speeds in revolutions per minute (RPM) for fans
	     or fan modules present and for which speed status
	     is known in this enclosure. Not all enclosure types report
	     fan speeds. Fans are numbered as described in enclFansPresent."
	::= { enclEntry 62 }

	enclElectronicsPartNos          OBJECT-TYPE
	SYNTAX                          DisplayString
        MAX-ACCESS                      read-only
        STATUS                          current
	DESCRIPTION
	    "The list of part numbers of the enclosure services electronics
	     modules present in this enclosure.  The order follows that of
	     enclElectronicsPresent."
	::= { enclEntry 63 }

	enclElectronicsCPLDVers         OBJECT-TYPE
	SYNTAX                          DisplayString
        MAX-ACCESS                      read-only
        STATUS                          current
	DESCRIPTION
	    "The list of CPLDs ('complex programmable logic devices') of the
	     enclosure services electronics modules present in this enclosure.
	     Not all module types contain this part.
             The order follows that of enclElectronicsPresent."
	::= { enclEntry 64 }

	enclNodeName                    OBJECT-TYPE
	SYNTAX                          DisplayString
        MAX-ACCESS                      read-only
        STATUS                          current
	DESCRIPTION
	    "Node to which this enclosure belongs."
	::= { enclEntry 65 }



	-- the High Availability Group for Storage

	haTable                 OBJECT-TYPE
	SYNTAX                  SEQUENCE OF HaEntry
	MAX-ACCESS              not-accessible
	STATUS                  current
	DESCRIPTION
				"High Availability configuration information
				table. This table fields are returned only from the
				cluster interfaces"
	::= { storage 2 }

	haEntry			OBJECT-TYPE
	SYNTAX			HaEntry
	MAX-ACCESS		not-accessible
	STATUS			current
	DESCRIPTION
				"High Availability Entry"
	INDEX {IMPLIED haNodeName }
	::= { haTable 1 }

	HaEntry ::=
		SEQUENCE {
		haNodeName
			DisplayString,
		haNodeSysid
			Unsigned32,
		haSettings
			INTEGER,
		haState
			INTEGER,
		haCannotTakeoverCause
			INTEGER,
		haPartnerStatus
			INTEGER,
		haPartnerLastStatusUpdate
			TimeTicks,
		haPartnerName
			DisplayString,
		haPartnerSysid
			Unsigned32,
		haInterconnectStatus
			INTEGER
		}

--	haEntry OBJECT IDENTIFIER ::= { storage 2 }

	haNodeName                      OBJECT-TYPE
	SYNTAX                          DisplayString
	MAX-ACCESS                      read-only
	STATUS                          current
	DESCRIPTION
		"Name of the node."
	::= { haEntry 1 }

	haNodeSysid                     OBJECT-TYPE
	SYNTAX                          Unsigned32
	MAX-ACCESS                      read-only
	STATUS                          current
	DESCRIPTION
		"System ID of the node."
	::= { haEntry 2 }

	haSettings                      OBJECT-TYPE
	SYNTAX                          INTEGER {
						notConfigured(1),
						enabled(2),
						disabled(3),
						takeoverByPartnerDisabled(4),
						thisNodeDead(5)
					}
	MAX-ACCESS                      read-only
	STATUS                          current
	DESCRIPTION
		"High Availability configuration settings. The value
		notConfigured(1) indicates that the HA is not licensed.
		The thisNodeDead(5) setting indicates that this node has
		been takenover."
	::={ haEntry 3 }

	haState                         OBJECT-TYPE
	SYNTAX                          INTEGER {
						dead(1),
						canTakeover(2),
						cannotTakeover(3),
						takeover(4),
						partialGiveback(5)
					}
	MAX-ACCESS                      read-only
	STATUS                          current
	DESCRIPTION
		"High Availability State."
	::= { haEntry 4 }

	haCannotTakeoverCause           OBJECT-TYPE
	SYNTAX                          INTEGER {
						ok(1),
						unknownReason(2),
						disabledByOperator(3),
						interconnectOffline(4),
						disabledByPartner(5),
						takeoverFailed(6),
						mailboxIsInDegradedState(7),
						partnermailboxIsInUninitialisedState(8),
						mailboxVersionMismatch(9),
						nvramSizeMismatch(10),
						kernelVersionMismatch(11),
						partnerIsInBootingStage(12),
						diskshelfIsTooHot(13),
						partnerIsPerformingRevert(14),
						nodeIsPerformingRevert(15),
						sametimePartnerIsAlsoTryingToTakeUsOver(16),
						alreadyInTakenoverMode(17),
						nvramLogUnsynchronized(18),
						stateofBackupMailboxIsDoubtful(19)
					}
	MAX-ACCESS                      read-only
	STATUS                          current
	DESCRIPTION
		"The reason node cannot takeover its HA partner"
	::= { haEntry 5 }

	haPartnerStatus                 OBJECT-TYPE
	SYNTAX                          INTEGER {
						maybeDown(1),
						ok(2),
						dead(3)
					}
	MAX-ACCESS                      read-only
	STATUS                          current
	DESCRIPTION
		"This is the status last returned by its HA partner."
	::= { haEntry 6 }

	haPartnerLastStatusUpdate       OBJECT-TYPE
	SYNTAX                          TimeTicks
	MAX-ACCESS                      read-only
	STATUS                          current
	DESCRIPTION
		"If non-zero, the absolute time of the last update
		from the partner."
	::= { haEntry 7 }

	haPartnerName                   OBJECT-TYPE
	SYNTAX                          DisplayString
	MAX-ACCESS                      read-only
	STATUS                          current
	DESCRIPTION
		"Hostname of partner."
	::= { haEntry 8 }

	haPartnerSysid                  OBJECT-TYPE
	SYNTAX                          Unsigned32
	MAX-ACCESS                      read-only
	STATUS                          current
	DESCRIPTION
		"System ID of partner."
	::= { haEntry 9 }

	haInterconnectStatus            OBJECT-TYPE
	SYNTAX                          INTEGER {
						notPresent(1),
						down(2),
						partialFailure(3),
						up(4)
					}
	MAX-ACCESS                      read-only
	STATUS                          current
	DESCRIPTION
		"The current status of the interconnect. The partialFailure(3)
		status indicates that one of the links in the interconnect
		hardware is down."
	::= { haEntry 10 }



	-- -- -- -- -- -- -- --
	-- the network group
	-- -- -- -- -- -- -- --

	netInterfaces OBJECT IDENTIFIER ::= { network 1 }

	-- The net Interfaces table contains information on the entity's
	-- interfaces.


	netifNumber                     OBJECT-TYPE
	SYNTAX                          Integer32
        MAX-ACCESS                      read-only
        STATUS                          current
	DESCRIPTION
                      "The number of network interfaces (regardless of
                      their current state) present on this system."
	::= { netInterfaces 1 }

	netifTable                      OBJECT-TYPE
	SYNTAX                          SEQUENCE OF NetIfEntry
        MAX-ACCESS                      not-accessible
        STATUS                          current
	DESCRIPTION
	        "A list of interface entries.  The number of
                 entries is given by the value of netifNumber."
	::= { netInterfaces 2 }

        netifEntry                      OBJECT-TYPE
	SYNTAX                          NetIfEntry
        MAX-ACCESS                      not-accessible
        STATUS                          current
	DESCRIPTION
                      "An interface entry containing objects at the
                      subnetwork layer and below for a particular
                      interface."
	INDEX   { netifIndex }
	::= { netifTable 1 }

	NetIfEntry ::=
	    SEQUENCE {
		netifIndex
		    Integer32,
		netifDescr
                      DisplayString,
		ifHighInOctets
                      Counter32,
		ifLowInOctets
                      Counter32,
	    	ifHighInUcastPkts
                      Counter32,
		ifLowInUcastPkts
                      Counter32,
		ifHighInNUcastPkts
                      Counter32,
		ifLowInNUcastPkts
                      Counter32,
		ifHighInDiscards
                      Counter32,
		ifLowInDiscards
                      Counter32,
		ifHighInErrors
                      Counter32,
		ifLowInErrors
                      Counter32,
		ifHighInUnknownProtos
                      Counter32,
		ifLowInUnknownProtos
                      Counter32,
		ifHighOutOctets
                      Counter32,
		ifLowOutOctets
                      Counter32,
		ifHighOutUcastPkts
                      Counter32,
		ifLowOutUcastPkts
                      Counter32,
		ifHighOutNUcastPkts
                      Counter32,
		ifLowOutNUcastPkts
                      Counter32,
		ifHighOutDiscards
                      Counter32,
		ifLowOutDiscards
                      Counter32,
		ifHighOutErrors
                      Counter32,
		ifLowOutErrors
                      Counter32,
		if64InOctets
                      Counter64,
	    	if64InUcastPkts
                      Counter64,
		if64InNUcastPkts
                      Counter64,
		if64InDiscards
                      Counter64,
		if64InErrors
                      Counter64,
		if64InUnknownProtos
                      Counter64,
		if64OutOctets
                      Counter64,
		if64OutUcastPkts
                      Counter64,
		if64OutNUcastPkts
                      Counter64,
		if64OutDiscards
                      Counter64,
		if64OutErrors
                      Counter64
	}
        netifIndex                      OBJECT-TYPE
	SYNTAX                          Integer32 (1..2147483647)
        MAX-ACCESS                      read-only
        STATUS                          current
	DESCRIPTION
                      "A unique value for each interface. For
		      clustered Data ONTAP, the high-order 16-bits
		      denote the node identifier and the low-order
		      16-bits denote the interface index within
		      the node. For Data ONTAP operating in 7-mode,
		      it ranges between 1 and the ifNumber value.
		      The value for each interface must remain
		      constant at least from one re-initialization
		      of the entity's network management system to
		      the next re-initialization."
        ::= { netifEntry 1 }

	netifDescr                      OBJECT-TYPE
	SYNTAX                          DisplayString (SIZE (0..255))
        MAX-ACCESS                      read-only
        STATUS                          current
	DESCRIPTION
		      "A textual string that contains interface information.
		      For clustered Data ONTAP, the string is in the
		      the following format:
		      <node name>:<interface name>
		      For Data ONTAP operating in 7-Mode, the string
		      contains only the interface name.

		      For a management port (for example, e0M or e0P), the
		      interface name is preceded by the text MGMT_PORT_ONLY
		      and a blank space after the text, in both clustered
		      Data ONTAP and Data ONTAP operating in 7-Mode.

		      Example:
		      The strings are in the following formats:
		      <node name>:MGMT_PORT_ONLY <interface name>, for clustered Data ONTAP.
		      MGMT_PORT_ONLY <interface name>, for Data ONTAP operating in 7-mode."
	::= { netifEntry 2 }

        ifHighInOctets                  OBJECT-TYPE
	SYNTAX                          Counter32
        MAX-ACCESS                      read-only
        STATUS                          deprecated
	DESCRIPTION
                     "The total number of octets received on the
                      interface, including framing characters.
		      This object returns the most significant 32 bits of
		      the 64 bit unsigned integer. This object is deprecated -
			 		Use if64InOctets instead."
	::= { netifEntry 3 }

        ifLowInOctets                   OBJECT-TYPE
	SYNTAX                          Counter32
        MAX-ACCESS                      read-only
        STATUS                          deprecated
	DESCRIPTION
                     "The total number of octets received on the
                      interface, including framing characters.
		      This object returns the least significant 32 bits of
		      the 64 bit unsigned integer. This object is deprecated -
			 		Use if64InOctets instead."
	::= { netifEntry 4 }

	ifHighInUcastPkts               OBJECT-TYPE
	SYNTAX                          Counter32
        MAX-ACCESS                      read-only
        STATUS                          deprecated
	DESCRIPTION
                      "The number of subnetwork-unicast packets
                      delivered to a higher-layer protocol.
		      This object returns the most significant 32 bits of
		      the 64 bit unsigned integer. This object is deprecated -
			 		Use if64InUcastPkts instead."
	::= { netifEntry 5 }

	ifLowInUcastPkts                OBJECT-TYPE
	SYNTAX                          Counter32
        MAX-ACCESS                      read-only
        STATUS                          deprecated
	DESCRIPTION
                      "The number of subnetwork-unicast packets
                      delivered to a higher-layer protocol.
		      This object returns the least significant 32 bits of
		      the 64 bit unsigned integer. This object is deprecated -
			 		Use if64InUcastPkts instead."
	::= { netifEntry 6 }


	ifHighInNUcastPkts              OBJECT-TYPE
	SYNTAX                          Counter32
        MAX-ACCESS                      read-only
        STATUS                          deprecated
	DESCRIPTION
                      "The number of non-unicast (i.e., subnetwork-
                      broadcast or subnetwork-multicast) packets
                      delivered to a higher-layer protocol.
		      This object returns the most significant 32 bits of
		      the 64 bit unsigned integer. This object is deprecated -
			 		Use if64InNUcastPkts instead."
	::= { netifEntry 7 }

	ifLowInNUcastPkts               OBJECT-TYPE
	SYNTAX                          Counter32
        MAX-ACCESS                      read-only
        STATUS                          deprecated
	DESCRIPTION
                      "The number of non-unicast (i.e., subnetwork-
                      broadcast or subnetwork-multicast) packets
                      delivered to a higher-layer protocol.
		      This object returns the least significant 32 bits of
		      the 64 bit unsigned integer. This object is deprecated -
			 		Use if64InNUcastPkts instead."
	::= { netifEntry 8 }

	ifHighInDiscards                OBJECT-TYPE
	SYNTAX                          Counter32
        MAX-ACCESS                      read-only
        STATUS                          deprecated
	DESCRIPTION
                      "The number of inbound packets which were chosen
                      to be discarded even though no errors had been
                      detected to prevent their being deliverable to a
                      higher-layer protocol.  One possible reason for
                      discarding such a packet could be to free up
                      buffer space. This object returns the most
		      significant 32 bits of the 64 bit unsigned integer. This object
		      is deprecated - Use if64InDiscards instead."
	::= { netifEntry 9 }

	ifLowInDiscards                 OBJECT-TYPE
	SYNTAX                          Counter32
        MAX-ACCESS                      read-only
        STATUS                          deprecated
	DESCRIPTION
                      "The number of inbound packets which were chosen
                      to be discarded even though no errors had been
                      detected to prevent their being deliverable to a
                      higher-layer protocol.  One possible reason for
                      discarding such a packet could be to free up
                      buffer space. This object returns the least
		      significant 32 bits of the 64 bit unsigned integer. This object
		      is deprecated - Use if64InDiscards instead."
	::= { netifEntry 10 }

	ifHighInErrors                  OBJECT-TYPE
	SYNTAX                          Counter32
        MAX-ACCESS                      read-only
        STATUS                          deprecated
	DESCRIPTION
                      "The number of inbound packets that contained
                      errors preventing them from being deliverable to a
                      higher-layer protocol. This object returns the
		      most significant 32 bits of the 64 bit unsigned integer.
		      This object is deprecated - Use if64InErrors instead."
	::= { netifEntry 11 }

	ifLowInErrors                   OBJECT-TYPE
	SYNTAX                          Counter32
        MAX-ACCESS                      read-only
        STATUS                          deprecated
	DESCRIPTION
                      "The number of inbound packets that contained
                      errors preventing them from being deliverable to a
                      higher-layer protocol. This object returns the
		      least significant 32 bits of the 64 bit unsigned integer.
		      This object is deprecated - Use if64InErrors instead."
	::= { netifEntry 12 }

	ifHighInUnknownProtos           OBJECT-TYPE
	SYNTAX                          Counter32
        MAX-ACCESS                      read-only
        STATUS                          deprecated
	DESCRIPTION
                      "The number of packets received via the interface
                      which were discarded because of an unknown or
                      unsupported protocol. This object returns the
		      most significant 32 bits of the 64 bit unsigned integer.
		      This object is deprecated - Use if64InUnknownProtos instead."
	::= { netifEntry 13 }

	ifLowInUnknownProtos            OBJECT-TYPE
	SYNTAX                          Counter32
        MAX-ACCESS                      read-only
        STATUS                          deprecated
	DESCRIPTION
                      "The number of packets received via the interface
                      which were discarded because of an unknown or
                      unsupported protocol. This object returns the
		      least significant 32 bits of the 64 bit unsigned integer.
		      This object is deprecated - Use if64InUnknownProtos instead."
	::= { netifEntry 14 }

	ifHighOutOctets                 OBJECT-TYPE
	SYNTAX                          Counter32
        MAX-ACCESS                      read-only
        STATUS                          deprecated
	DESCRIPTION
                      "The total number of octets transmitted out of the
                      interface, including framing characters.
                      This object returns the most significant 32 bits of the
		      64 bit unsigned integer. This object is deprecated - Use
		      if64OutOctets instead."
	::= { netifEntry 15 }

	ifLowOutOctets                  OBJECT-TYPE
	SYNTAX                          Counter32
        MAX-ACCESS                      read-only
        STATUS                          deprecated
	DESCRIPTION
                      "The total number of octets transmitted out of the
                      interface, including framing characters.
                      This object returns the least significant 32 bits of
		      the 64 bit unsigned integer. This object is deprecated - Use
		      if64OutOctets instead."
	::= { netifEntry 16 }

	ifHighOutUcastPkts              OBJECT-TYPE
	SYNTAX                          Counter32
        MAX-ACCESS                      read-only
        STATUS                          deprecated
	DESCRIPTION
                      "The total number of packets that higher-level
                      protocols requested be transmitted to a
                      subnetwork-unicast address, including those that
                      were discarded or not sent. This object returns
		      the most significant 32 bits of the 64 bit unsigned
		      integer. This object is deprecated - Use if64OutUcastPkts
		      instead."
	::= { netifEntry 17 }

	ifLowOutUcastPkts               OBJECT-TYPE
	SYNTAX                          Counter32
        MAX-ACCESS                      read-only
        STATUS                          deprecated
	DESCRIPTION
                      "The total number of packets that higher-level
                      protocols requested be transmitted to a
                      subnetwork-unicast address, including those that
                      were discarded or not sent. This object returns
		      the least significant 32 bits of the 64 bit unsigned
		      integer. This object is deprecated - Use if64OutUcastPkts
		      instead."
	::= { netifEntry 18 }

	ifHighOutNUcastPkts             OBJECT-TYPE
	SYNTAX                          Counter32
        MAX-ACCESS                      read-only
        STATUS                          deprecated
	DESCRIPTION
                      "The total number of packets that higher-level
                      protocols requested be transmitted to a non-
                      unicast (i.e., a subnetwork-broadcast or
                      subnetwork-multicast) address, including those
                      that were discarded or not sent. This object returns
		      the most significant 32 bits of the 64 bit unsigned integer.
		      This object is deprecated - Use if64OutNUcastPkts instead."
	::= { netifEntry 19 }

	ifLowOutNUcastPkts              OBJECT-TYPE
	SYNTAX                          Counter32
        MAX-ACCESS                      read-only
        STATUS                          deprecated
	DESCRIPTION
                      "The total number of packets that higher-level
                      protocols requested be transmitted to a non-
                      unicast (i.e., a subnetwork-broadcast or
                      subnetwork-multicast) address, including those
                      that were discarded or not sent. This object returns
		      the least significant 32 bits of the 64 bit unsigned integer.
		      This object is deprecated - Use if64OutNUcastPkts instead."
	::= { netifEntry 20 }

	ifHighOutDiscards               OBJECT-TYPE
	SYNTAX                          Counter32
        MAX-ACCESS                      read-only
        STATUS                          deprecated
	DESCRIPTION
                      "The number of outbound packets which were chosen
                      to be discarded even though no errors had been
                      detected to prevent their being transmitted.  One
                      possible reason for discarding such a packet could
                      be to free up buffer space. This object returns
		      the most significant 32 bits of the 64 bit unsigned integer.
		      This object is deprecated - Use if64OutDiscards instead."
	::= { netifEntry 21 }

	ifLowOutDiscards                OBJECT-TYPE
	SYNTAX                          Counter32
        MAX-ACCESS                      read-only
        STATUS                          deprecated
	DESCRIPTION
                      "The number of outbound packets which were chosen
                      to be discarded even though no errors had been
                      detected to prevent their being transmitted.  One
                      possible reason for discarding such a packet could
                      be to free up buffer space. This object returns
		      the least significant 32 bits of the 64 bit unsigned integer.
		      This object is deprecated - Use if64OutDiscards instead."
	::= { netifEntry 22 }

	ifHighOutErrors                 OBJECT-TYPE
	SYNTAX                          Counter32
        MAX-ACCESS                      read-only
        STATUS                          deprecated
	DESCRIPTION
                      "The number of outbound packets that could not be
                      transmitted because of errors. This object returns
		      the most significant 32 bits of the 64 bit unsigned integer.
		      This object is deprecated - Use if64OutErrors instead."
	::= { netifEntry 23 }

	ifLowOutErrors                  OBJECT-TYPE
	SYNTAX                          Counter32
        MAX-ACCESS                      read-only
        STATUS                          deprecated
	DESCRIPTION
                      "The number of outbound packets that could not be
                      transmitted because of errors. This object returns
		      the least significant 32 bits of the 64 bit unsigned integer.
		      This object is deprecated - Use if64OutErrors instead."
	::= { netifEntry 24 }

        if64InOctets                    OBJECT-TYPE
	SYNTAX                          Counter64
        MAX-ACCESS                      read-only
        STATUS                          current
	DESCRIPTION
                     "The total number of octets received on the
                      interface, including framing characters.
		      This object returns all of the 64 bit unsigned integer."
	::= { netifEntry 25 }

	if64InUcastPkts                 OBJECT-TYPE
	SYNTAX                          Counter64
        MAX-ACCESS                      read-only
        STATUS                          current
	DESCRIPTION
                      "The number of subnetwork-unicast packets
                      delivered to a higher-layer protocol.
		      This object returns all of the 64 bit unsigned integer."
	::= { netifEntry 26 }

	if64InNUcastPkts                OBJECT-TYPE
	SYNTAX                          Counter64
        MAX-ACCESS                      read-only
        STATUS                          current
	DESCRIPTION
                      "The number of non-unicast (i.e., subnetwork-
                      broadcast or subnetwork-multicast) packets
                      delivered to a higher-layer protocol.
		      This object returns all of the 64 bit unsigned integer."
	::= { netifEntry 27 }

	if64InDiscards                  OBJECT-TYPE
	SYNTAX                          Counter64
        MAX-ACCESS                      read-only
        STATUS                          current
	DESCRIPTION
                      "The number of inbound packets which were chosen
                      to be discarded even though no errors had been
                      detected to prevent their being deliverable to a
                      higher-layer protocol.  One possible reason for
                      discarding such a packet could be to free up
                      buffer space. This object returns all of the 64 bit
		      unsigned integer."
	::= { netifEntry 28 }

	if64InErrors                    OBJECT-TYPE
	SYNTAX                          Counter64
        MAX-ACCESS                      read-only
        STATUS                          current
	DESCRIPTION
                      "The number of inbound packets that contained
                      errors preventing them from being deliverable to a
                      higher-layer protocol. This object returns all
		      of the 64 bit unsigned integer."
	::= { netifEntry 29 }

	if64InUnknownProtos             OBJECT-TYPE
	SYNTAX                          Counter64
        MAX-ACCESS                      read-only
        STATUS                          current
	DESCRIPTION
                      "The number of packets received via the interface
                      which were discarded because of an unknown or
                      unsupported protocol. This object returns all
		      of the 64 bit unsigned integer."
	::= { netifEntry 30 }

	if64OutOctets                   OBJECT-TYPE
	SYNTAX                          Counter64
        MAX-ACCESS                      read-only
        STATUS                          current
	DESCRIPTION
                      "The total number of octets transmitted out of the
                      interface, including framing characters.
                      This object returns all of the 64 bit unsigned integer."
	::= { netifEntry 31 }

	if64OutUcastPkts                OBJECT-TYPE
	SYNTAX                          Counter64
        MAX-ACCESS                      read-only
        STATUS                          current
	DESCRIPTION
                      "The total number of packets that higher-level
                      protocols requested be transmitted to a
                      subnetwork-unicast address, including those that
                      were discarded or not sent. This object returns
		      all of the 64 bit unsigned  integer."
	::= { netifEntry 32 }

	if64OutNUcastPkts               OBJECT-TYPE
	SYNTAX                          Counter64
        MAX-ACCESS                      read-only
        STATUS                          current
	DESCRIPTION
                      "The total number of packets that higher-level
                      protocols requested be transmitted to a non-
                      unicast (i.e., a subnetwork-broadcast or
                      subnetwork-multicast) address, including those
                      that were discarded or not sent. This object returns
		      all of the 64 bit unsigned integer."
	::= { netifEntry 33 }

	if64OutDiscards                 OBJECT-TYPE
	SYNTAX                          Counter64
        MAX-ACCESS                      read-only
        STATUS                          current
	DESCRIPTION
                      "The number of outbound packets which were chosen
                      to be discarded even though no errors had been
                      detected to prevent their being transmitted.  One
                      possible reason for discarding such a packet could
                      be to free up buffer space. This object returns
		      all of the 64 bit unsigned integer."
	::= { netifEntry 34 }

	if64OutErrors                   OBJECT-TYPE
	SYNTAX                          Counter64
        MAX-ACCESS                      read-only
        STATUS                          current
	DESCRIPTION
                      "The number of outbound packets that could not be
                      transmitted because of errors. This object returns
		      all of the 64 bit unsigned integer."
	::= { netifEntry 35 }


	-- netportTable

	netportTable			OBJECT-TYPE
	SYNTAX				SEQUENCE OF NetportEntry
	MAX-ACCESS			not-accessible
	STATUS				current
	DESCRIPTION
		 "A list of network ports (both physical and logical)
		  on all nodes in the cluster."
	::= { network 2 }

	netportEntry			OBJECT-TYPE
	SYNTAX				NetportEntry
	MAX-ACCESS			not-accessible
	STATUS				current
	DESCRIPTION
		"Network port entry."
	INDEX { netportNode, netportPort }
	::= { netportTable 1 }

	NetportEntry ::= SEQUENCE {
         netportNode                      DisplayString,
         netportPort                      DisplayString,
         netportRole                      INTEGER,
         netportLinkState                 INTEGER,
         netportMtu                       INTEGER,
         netportAutonegAdmin              Boolean,
         netportAutonegOper               Boolean,
         netportDuplexAdmin               INTEGER,
         netportDuplexOper                INTEGER,
         netportSpeedAdmin                INTEGER,
         netportSpeedOper                 INTEGER,
         netportSpeed                     INTEGER,
         netportMac                       DisplayString,
         netportUpAdmin                   Boolean,
         netportType                      INTEGER,
         netportIfgNode                   DisplayString,
         netportIfgPort                   DisplayString,
         netportIfgDistrFunc              INTEGER,
         netportIfgMode                   INTEGER,
         netportVlanNode                  DisplayString,
         netportVlanPort                  DisplayString,
         netportVlanTag                   INTEGER,
         netportFlowcontrolAdmin          INTEGER,
         netportFlowcontrolOper           INTEGER,
         netportAutorevertDelay           INTEGER,
         netportRemoteDeviceId	          DisplayString,
	 netportIPspace                   DisplayString,
	 netportBroadcastDomain           DisplayString,
	 netportMtuAdmin		  INTEGER,
         netportHealthStatus              INTEGER,
         netportIgnoreHealthStatus        Boolean,
         netportDegradedReason            DisplayString
	}

	netportNode				OBJECT-TYPE
	SYNTAX					DisplayString
	MAX-ACCESS				read-only
	STATUS					current
	DESCRIPTION
		"Node where the port belongs to."
	::= { netportEntry 1 }

	netportPort				OBJECT-TYPE
	SYNTAX					DisplayString
	MAX-ACCESS				read-only
	STATUS					current
	DESCRIPTION
		"Port identity."
	::= { netportEntry 2 }

	netportRole				OBJECT-TYPE
	SYNTAX					INTEGER {
							undef(0),
							cluster(1),
							data(2),
							node-mgmt(3),
							intercluster(4),
							cluster-mgmt(5)
							}
	MAX-ACCESS				read-only
	STATUS					current
	DESCRIPTION
		"Role of the port. A port must have one of the following roles:
		 cluster(1), data(2), mgmt(3), intercluster(4), cluster-mgmt(5) or  undef(0).
		 The cluster port is used to communicate to other node(s) in
		 the cluster. The data port services clients' requests. It is where
		 all the file requests come in. The management port is used
		 by administrator to manage resources within a node.
		 The intercluster port is used to communicate to other cluster.
		 The cluster-mgmt port is used to manage resources within the cluster.
		 The undef role is for the port that has not yet been assigned a role."
	::= { netportEntry 3 }

	netportLinkState			OBJECT-TYPE
	SYNTAX					INTEGER {
							undef(0),
							off(1),
							up(2),
							down(3)
							}
	MAX-ACCESS				read-only
	STATUS					current
	DESCRIPTION
		"The link-state of the port.
		 Normally it is either UP(2) or DOWN(3)."
	::= { netportEntry 4 }

	netportMtu				OBJECT-TYPE
	SYNTAX					INTEGER
	MAX-ACCESS				read-only
	STATUS					current
	DESCRIPTION
		"The Maximum Transmission Unit (MTU) refers to the size (in bytes)
		 of the largest packet that is supported by the port."
	::= { netportEntry 5 }

	netportAutonegAdmin			OBJECT-TYPE
	SYNTAX					Boolean
	MAX-ACCESS				read-only
	STATUS					current
	DESCRIPTION
		"Indicates whether the port's auto-negotiation property
		 is enabled by an administrator."
	::= { netportEntry 6 }


	netportAutonegOper			OBJECT-TYPE
	SYNTAX					Boolean
	MAX-ACCESS				read-only
	STATUS					current
	DESCRIPTION
		"Indicates whether the auto-negotiation is enabled on the port."
	::= { netportEntry 7 }

	netportDuplexAdmin			OBJECT-TYPE
	SYNTAX					INTEGER {
							undef(0),
							auto(1),
							half(2),
							full(3)
							}
	MAX-ACCESS				read-only
	STATUS					current
	DESCRIPTION
		"The duplex mode of the port set by the administrator.
		 It can be either undef(0), auto(1), half-duplex(2), or full-duplex(3)."
	::= { netportEntry 8 }

	netportDuplexOper			OBJECT-TYPE
	SYNTAX					INTEGER {
							undef(0),
							auto(1),
							half(2),
							full(3)
							}
	MAX-ACCESS				read-only
	STATUS					current
	DESCRIPTION
		"The duplex mode appears on the port.
		 It can be either undef(0), auto(1), half-duplex(2), or full-duplex(3)."
	::= { netportEntry 9 }

	netportSpeedAdmin			OBJECT-TYPE
	SYNTAX					INTEGER{
							undef(0),
							auto(1),
							ten-Mb(2),
							hundred-Mb(3),
							one-Gb(4),
							ten-Gb(5),
							fourty-Gb(6),
							hundred-Gb(7),
							twenty-five-Gb(8)
							}
	MAX-ACCESS				read-only
	STATUS					current
	DESCRIPTION
		"The speed of the port set by an administrator.
		 It can be either undef(0), auto(1), ten Mb/s(2), hundred Mb/s(3), one Gb/s(4), or ten Gb/s(5)."
	::= { netportEntry 10 }

	netportSpeedOper			OBJECT-TYPE
	SYNTAX					INTEGER{
							undef(0),
							auto(1),
							ten-Mb(2),
							hundred-Mb(3),
							one-Gb(4),
							ten-Gb(5),
							fourty-Gb(6),
							hundred-Gb(7),
							twenty-five-Gb(8)
							}
	MAX-ACCESS				read-only
	STATUS					current
	DESCRIPTION
		"The speed appears on the port.
		 It can be either undef(0), auto(1), ten Mb/s(2), hundred Mb/s(3), one Gb/s(4), or ten Gb/s(5)."
	::= { netportEntry 11 }

	netportSpeed				OBJECT-TYPE
	SYNTAX					INTEGER
	MAX-ACCESS				read-only
	STATUS					current
	DESCRIPTION
		"The speed that appears in the port scaled to megabits/sec."
	::= { netportEntry 12 }

	netportMac				OBJECT-TYPE
	SYNTAX					DisplayString
	MAX-ACCESS				read-only
	STATUS					current
	DESCRIPTION
		"The port's MAC address"
	::= { netportEntry 13 }

	netportUpAdmin				OBJECT-TYPE
	SYNTAX					Boolean
	MAX-ACCESS				read-only
	STATUS					current
	DESCRIPTION
		"Indicates whether the port status is set 'UP' by an administrator."
	::= { netportEntry 14 }

	netportType				OBJECT-TYPE
	SYNTAX					INTEGER {
							physical(0),
							if-group(1),
							vlan(2),
							undef(3)
							}
	MAX-ACCESS				read-only
	STATUS					current
	DESCRIPTION
		"The type of the port which can be either physical(0), if-group(1), vlan(2) or undef(3)."
	::= { netportEntry 15 }

	netportIfgNode				OBJECT-TYPE
	SYNTAX					DisplayString
	MAX-ACCESS				read-only
	STATUS					current
	DESCRIPTION
		"This field shows the if-group node name if the port type is if-group,
		 It show an empty string, otherwise."
	::= { netportEntry 16 }

	netportIfgPort				OBJECT-TYPE
	SYNTAX					DisplayString
	MAX-ACCESS				read-only
	STATUS					current
	DESCRIPTION
		"This field shows the if-group port if the port type is if-group,
		 It show an empty string, otherwise."
	::= { netportEntry 17 }

	netportIfgDistrFunc			OBJECT-TYPE
	SYNTAX					INTEGER {
							mac(0),
							ip(1),
							sequential(2),
							none(-1)
							}
	MAX-ACCESS				read-only
	STATUS					current
	DESCRIPTION
		"If the port type is if-group, this field shows the distribution
		 function of the port. This function is used to pick the forwarding
		 port for a packet. It can be either mac(0), ip(1), or sequential(2).
		 The mac function selects the port based on the hash of the MAC
		 address of the destination. Instead of MAC address, the ip function
		 uses the destination's IP address. The sequential function uses
		 the round-robin port selection."
	::= { netportEntry 18 }


	netportIfgMode				OBJECT-TYPE
	SYNTAX					INTEGER {
							multimode(0),
							multimode-lacp(1),
							singlemode(2),
							none(-1)
							}
	MAX-ACCESS				read-only
	STATUS					current
	DESCRIPTION
		"If the port type is if-group, this field shows the if-group's
		 policy. It can be either multimode(0), multimode-lacp(1), or
		 single-mode(2). Otherwise, it shows an empty string. The multimode
		 policy uses the static link-aggregation, while the multimode-lacp
		 uses the link-aggregation with lacp (Link Aggregate Control Protocol).
		 The single mode does not use link-aggregation."
	::= { netportEntry 19 }

	netportVlanNode				OBJECT-TYPE
	SYNTAX					DisplayString
	MAX-ACCESS				read-only
	STATUS					current
	DESCRIPTION
		"If the port type is vlan, this field shows its vlan node.
		 Otherwise, it shows an empty string."
	::= { netportEntry 20 }

	netportVlanPort				OBJECT-TYPE
	SYNTAX					DisplayString
	MAX-ACCESS				read-only
	STATUS					current
	DESCRIPTION
		"If the port type is vlan, this field shows its vlan port.
		 Otherwise, it shows an empty string."
	::= { netportEntry 21 }

	netportVlanTag				OBJECT-TYPE
	SYNTAX					INTEGER
	MAX-ACCESS				read-only
	STATUS					current
	DESCRIPTION
		"If the port type is vlan, this field shows its vlan tag.
		 Otherwise, it shows an empty string."
	::= { netportEntry 22 }

	netportFlowcontrolAdmin			OBJECT-TYPE
	SYNTAX					INTEGER{
							undef(0),
							none(1),
							receive(2),
							send(3),
							full(4)
							}
	MAX-ACCESS				read-only
	STATUS					current
	DESCRIPTION
		"The flowcontrol of the port set by an administrator.
		 It can be either undef(0), none(1), receive(2), send(3), or full(4)."
	::= { netportEntry 23 }

	netportFlowcontrolOper			OBJECT-TYPE
	SYNTAX					INTEGER{
							undef(0),
							none(1),
							receive(2),
							send(3),
							full(4)
							}
	MAX-ACCESS				read-only
	STATUS					current
	DESCRIPTION
		"The flowcontrol that appears on the port.
		 It can be either undef(0), none(1), receive(2), send(3), or full(4)."
	::= { netportEntry 24 }

	netportAutorevertDelay			OBJECT-TYPE
	SYNTAX					INTEGER
	MAX-ACCESS				read-only
	STATUS					current
	DESCRIPTION
		"If the port is designated as a cluster port, this field shows
		the delay in seconds before auto reverting a LIF to this port.
		otherwise, it shows an empty string."
	::= { netportEntry 25 }

	netportRemoteDeviceId			OBJECT-TYPE
	SYNTAX					DisplayString
	MAX-ACCESS				read-only
	STATUS					current
	DESCRIPTION
		"Remote device ID discovered by L2 protocol."
	::= { netportEntry 26 }

	netportIPspace				OBJECT-TYPE
	SYNTAX					DisplayString
	MAX-ACCESS				read-only
	STATUS					current
	DESCRIPTION
		"IPspace where the port is assigned."
	::= { netportEntry 27 }

	netportBroadcastDomain			OBJECT-TYPE
	SYNTAX					DisplayString
	MAX-ACCESS				read-only
	STATUS					current
	DESCRIPTION
		"Broadcast Domain of the port is assigned."
	::= { netportEntry 28 }

	netportMtuAdmin				OBJECT-TYPE
	SYNTAX					INTEGER
	MAX-ACCESS				read-only
	STATUS					current
	DESCRIPTION
		"The Maximum Transmission Unit (MTU) set by the Administrator
		 (in bytes) of the largest packet that is supported by the
		 port."
        ::= { netportEntry 29 }


	netportHealthStatus			OBJECT-TYPE
	SYNTAX					INTEGER {
                                                        healthy(0),
                                                        degraded(1)
                                                }
	MAX-ACCESS				read-only
	STATUS					current
	DESCRIPTION
		"The health status of the port."
        ::= { netportEntry 30 }

	netportIgnoreHealthStatus	 OBJECT-TYPE
	SYNTAX			        Boolean
	MAX-ACCESS				read-only
	STATUS					current
	DESCRIPTION
		"The health overrided status of the port."
        ::= { netportEntry 31 }

	netportDegradedReason			OBJECT-TYPE
	SYNTAX					DisplayString
	MAX-ACCESS				read-only
	STATUS					current
	DESCRIPTION
		"The list of reasons why the port is marked as degraded"
        ::= { netportEntry 32 }

	-- netportIfGrpTable

	netportIfGrpTable			OBJECT-TYPE
	SYNTAX					SEQUENCE OF NetportIfGrpEntry
	MAX-ACCESS				not-accessible
	STATUS					current
	DESCRIPTION
		"A table of if-groups, where each entry represents an interface
		 of the group."
	::= { network 3 }

	netportIfGrpEntry			OBJECT-TYPE
	SYNTAX					NetportIfGrpEntry
	MAX-ACCESS				not-accessible
	STATUS					current
	DESCRIPTION
		"If-group entry."
	INDEX { netportIfGrpNode, netportIfGrpName }
	::= { netportIfGrpTable 1 }

	NetportIfGrpEntry ::=
			SEQUENCE {
		netportIfGrpNode		DisplayString,
		netportIfGrpName		DisplayString,
		netportIfGrpDistrFunc		INTEGER,
		netportIfGrpMode		INTEGER,
		netportIfGrpMac			DisplayString,
		netportIfGrpActivePorts		INTEGER,
		netportIfGrpPorts		DisplayString,
		netportIfGrpUpPorts		DisplayString,
		netportIfGrpDownPorts		DisplayString
			}

	netportIfGrpNode			OBJECT-TYPE
	SYNTAX					DisplayString
	MAX-ACCESS				read-only
	STATUS					current
	DESCRIPTION
		"The node that the If-group belongs to."
	::= { netportIfGrpEntry 1 }

	netportIfGrpName			OBJECT-TYPE
	SYNTAX					DisplayString
	MAX-ACCESS				read-only
	STATUS					current
	DESCRIPTION
		"The name of the if-group."
	::= { netportIfGrpEntry 2 }

	netportIfGrpDistrFunc			 OBJECT-TYPE
	SYNTAX					 INTEGER {
							  mac(0),
							  ip(1),
							  sequential(2)
							 }
	MAX-ACCESS				 read-only
	STATUS					 current
	DESCRIPTION
		"The distribute function of the if-group.
		 This function is used to pick the forwarding port for a packet.
		 It can be either mac(0), ip(1), or sequential(2). The mac function selects
		 the port based on the hash of the MAC address of the destination.
		 Instead of MAC address, the ip function uses IP address.
		 The sequential function uses the round-robin port selection."
	::= { netportIfGrpEntry 3 }


	netportIfGrpMode			 OBJECT-TYPE
	SYNTAX					 INTEGER {
							  multimode(0),
							  multimode-lacp(1),
							  singlemode(2)
							 }
	MAX-ACCESS				 read-only
	STATUS					 current
	DESCRIPTION
		"The policy of the if-group. It can be either multimode(0),
		 multimode-lacp(1), or single-mode(2). The multimode policy uses the
		 static link-aggregation, while the multimode-lacp uses the
		 link-aggregation with lacp (Link Aggregate Control Protocol).
		 The single mode does not use link-aggregation."
	::= { netportIfGrpEntry 4 }

	netportIfGrpMac				 OBJECT-TYPE
	SYNTAX					 DisplayString
	MAX-ACCESS				 read-only
	STATUS					 current
	DESCRIPTION
		"The MAC address of the if-group."
	::= { netportIfGrpEntry 5 }

	netportIfGrpActivePorts			 OBJECT-TYPE
	SYNTAX					 INTEGER {
							  full(0),
							  partial(1),
							  none(2)
							 }
	MAX-ACCESS				  read-only
	STATUS					  current
	DESCRIPTION
		"The participation of the network ports in the if-group.
		 It can be full, partial, and none."
	::= { netportIfGrpEntry 6 }

	netportIfGrpPorts			 OBJECT-TYPE
	SYNTAX					 DisplayString
	MAX-ACCESS				 read-only
	STATUS					 current
	DESCRIPTION
		"A list of network ports that participate in the if-group."
	::= { netportIfGrpEntry 7 }

	netportIfGrpUpPorts			 OBJECT-TYPE
	SYNTAX					 DisplayString
	MAX-ACCESS				 read-only
	STATUS					 current
	DESCRIPTION
		"A list of network ports that are 'UP' in the if-group."
	::= { netportIfGrpEntry 8 }

	netportIfGrpDownPorts			 OBJECT-TYPE
	SYNTAX					 DisplayString
	MAX-ACCESS				 read-only
	STATUS					 current
	DESCRIPTION
		"A list of network ports that are 'DOWN' in the if-group."
	::= { netportIfGrpEntry 9 }

	-- logicalInterfaceTable

	logicalInterfaceTable			 OBJECT-TYPE
	SYNTAX					 SEQUENCE OF LogicalInterfaceEntry
	MAX-ACCESS				 not-accessible
	STATUS					 current
	DESCRIPTION
		"A list of logical interface entries."
	::= { network 4 }

	logicalInterfaceEntry			 OBJECT-TYPE
	SYNTAX					 LogicalInterfaceEntry
	MAX-ACCESS				 not-accessible
	STATUS					 current
	DESCRIPTION
		"Logical interface entry."
	INDEX { logicalInterfaceServer, logicalInterfaceVif }
	::= { logicalInterfaceTable 1 }


	LogicalInterfaceEntry ::=
			  SEQUENCE {
		logicalInterfaceServer		 DisplayString,
		logicalInterfaceVif		 DisplayString,
		logicalInterfaceRole		 INTEGER,
		logicalInterfaceHomeNode	 DisplayString,
		logicalInterfaceHomePort	 DisplayString,
		logicalInterfaceCurrNode	 DisplayString,
		logicalInterfaceCurrPort	 DisplayString,
		logicalInterfaceStatusOper	 INTEGER,
		logicalInterfaceNumericId	 INTEGER,
		logicalInterfaceIsHome		 Boolean,
		logicalInterfaceAddress		 IpAddress,
		logicalInterfaceNetmask		 IpAddress,
		logicalInterfaceNetmaskLength	 INTEGER,
		logicalInterfaceRoutingGroup	 DisplayString,
		logicalInterfaceStatusAdmin	 INTEGER,
		logicalInterfaceFailoverPolicy	 INTEGER,
		logicalInterfaceFirewallPolicy	 DisplayString,
		logicalInterfaceAutoRevert	 Boolean,
		logicalInterfaceSticky		 Boolean,
		logicalInterfaceUseFailoverGroup INTEGER,
		logicalInterfaceDnsZone		 DisplayString,
		logicalInterfaceAllowLbMigrate	 Boolean,
		logicalInterfaceLbWeight	 INTEGER,
		logicalInterfaceFailoverGroup	 DisplayString,
		logicalInterfaceStatusVserver	 INTEGER,
		logicalInterfaceDataProtocol	 DisplayString,
		logicalInterfaceFcpWwpn          DisplayString,
		logicalInterfaceComment		 DisplayString,
		logicalInterfaceListenForDnsQuery Boolean,
		logicalInterfaceAddressString    DisplayString
			  }

	logicalInterfaceServer			 OBJECT-TYPE
	SYNTAX					 DisplayString
	MAX-ACCESS				 read-only
	STATUS					 current
	DESCRIPTION
		"The node where the logical interface belongs to."
	::= { logicalInterfaceEntry 1 }

	logicalInterfaceVif			 OBJECT-TYPE
	SYNTAX					 DisplayString
	MAX-ACCESS				 read-only
	STATUS					 current
	DESCRIPTION
		"The name of the logical interface."
	::= { logicalInterfaceEntry 2 }

	logicalInterfaceRole			 OBJECT-TYPE
	SYNTAX					 INTEGER {
							  undef(0),
							  cluster(1),
							  data(2),
							  node-mgmt(3),
							  intercluster(4),
							  cluster-mgmt(5)
							 }
	MAX-ACCESS				 read-only
	STATUS					 current
	DESCRIPTION
		"The role of logical interface. An interface can have one of the following roles:
		 undef(0), cluster(1), data(2), mgmt(3), intercluster(4), and cluster-mgmt(5).
		 The cluster interface is used to communicate
		 to other node(s) in the cluster. The data interface services
		 external clients where all the file requests come in.
		 The management interface is used by administrator to manage resources
		 within a node. The intercluster interface is used to communicate to other cluster.
		 The cluster-mgmt port is used to manage resources within the cluster.
		 The undef role is for the interface that has not yet been assigned a role."
	::= { logicalInterfaceEntry 3 }

	logicalInterfaceHomeNode		 OBJECT-TYPE
	SYNTAX					 DisplayString
	MAX-ACCESS				 read-only
	STATUS					 current
	DESCRIPTION
		"The home node of the interface where the interface is initially setup."
	::= { logicalInterfaceEntry 4 }

	logicalInterfaceHomePort		 OBJECT-TYPE
	SYNTAX					 DisplayString
	MAX-ACCESS				 read-only
	STATUS					 current
	DESCRIPTION
		"The home port of the interface where the interface is initially setup."
	::= { logicalInterfaceEntry 5 }

	logicalInterfaceCurrNode		 OBJECT-TYPE
	SYNTAX					 DisplayString
	MAX-ACCESS				 read-only
	STATUS					 current
	DESCRIPTION
		"The node where the interface is currently on."
	::= { logicalInterfaceEntry 6 }

	logicalInterfaceCurrPort		 OBJECT-TYPE
	SYNTAX					 DisplayString
	MAX-ACCESS				 read-only
	STATUS					 current
	DESCRIPTION
		"The port where the interface is currently attached to."
	::= { logicalInterfaceEntry 7 }

	logicalInterfaceStatusOper		 OBJECT-TYPE
	SYNTAX					 INTEGER {
							  up(0),
							  down(1)
							 }
	MAX-ACCESS				 read-only
	STATUS					 current
	DESCRIPTION
		"The operational status, which can be UP(0) or DOWN(1)."
	::= { logicalInterfaceEntry 8 }

	logicalInterfaceNumericId		 OBJECT-TYPE
	SYNTAX					 INTEGER
	MAX-ACCESS				 read-only
	STATUS					 current
	DESCRIPTION
		"The interface ID."
	::= { logicalInterfaceEntry 9 }

	logicalInterfaceIsHome			 OBJECT-TYPE
	SYNTAX					 Boolean
	MAX-ACCESS				 read-only
	STATUS					 current
	DESCRIPTION
		"Indicates whether the interface is at the home node."
	::= { logicalInterfaceEntry 10 }

	logicalInterfaceAddress			 OBJECT-TYPE
	SYNTAX					 IpAddress
	MAX-ACCESS				 read-only
	STATUS					 current
	DESCRIPTION
		"The IP address assigned to the interface. This field only
		displays ipv4 addresses correctly. Ipv6 addresses will display as
		0.0.0.0. Refer to the logicalInterfaceAddressString field for
		the address of an ipv6 interface."
	::= { logicalInterfaceEntry 11 }

	logicalInterfaceNetmask			 OBJECT-TYPE
	SYNTAX					 IpAddress
	MAX-ACCESS				 read-only
	STATUS					 current
	DESCRIPTION
		"The netmask assigned to the interface. This field only
		displays ipv4 netmasks correctly. Ipv6 netmasks will display as
		0.0.0.0. Refer to the logicalInterfaceAddressString field for
		the netmask length of an ipv6 interface."
	::= { logicalInterfaceEntry 12 }

	logicalInterfaceNetmaskLength		 OBJECT-TYPE
	SYNTAX					 INTEGER
	MAX-ACCESS				 read-only
	STATUS					 current
	DESCRIPTION
		"The number of set bits of the netmask."
	::= { logicalInterfaceEntry 13 }

	logicalInterfaceRoutingGroup		 OBJECT-TYPE
	SYNTAX					 DisplayString
	MAX-ACCESS				 read-only
	STATUS					 current
	DESCRIPTION
		"The interface's routing group name"
	::= { logicalInterfaceEntry 14 }

	logicalInterfaceStatusAdmin		 OBJECT-TYPE
	SYNTAX					 INTEGER {
							  up(0),
							  down(1)
							 }
	MAX-ACCESS				 read-only
	STATUS					 current
	DESCRIPTION
		"The status of the interface assigned by an administrator.
		 It can be either UP(0) or DOWN(1)."
	::= { logicalInterfaceEntry 15 }

	logicalInterfaceFailoverPolicy		 OBJECT-TYPE
	SYNTAX					 INTEGER {
							  next-avail(0),
							  priority(1),
							  disabled(2),
							  system-defined(3),
							  local-only(4),
							  sfo-partner-only(5),
							  ipspace-wide(6),
							  broadcast-domain-wide(7)
							 }
	MAX-ACCESS				 read-only
	STATUS					 current
	DESCRIPTION
		"The interface's failover policy.
		 It can be next-available(0), where the interface will failover to any
		 next available interface, priority(1), where the interface will failover to
		 the interface that has the highest priority, or disabled(2)."
	::= { logicalInterfaceEntry 16 }

	logicalInterfaceFirewallPolicy		 OBJECT-TYPE
	SYNTAX					 DisplayString
	MAX-ACCESS				 read-only
	STATUS					 current
	DESCRIPTION
		"The firewall policy of the interface."
	::= { logicalInterfaceEntry 17 }


	logicalInterfaceAutoRevert		 OBJECT-TYPE
	SYNTAX					 Boolean
	MAX-ACCESS				 read-only
	STATUS					 current
	DESCRIPTION
		"Indicates whether the auto-revert property of the interface is set.
		 If the value is 'true', the interface will automatically revert back to the home port
		 whenever the interface is not on the home port and the home port becomes operational."
	::= { logicalInterfaceEntry 18 }

	logicalInterfaceSticky			 OBJECT-TYPE
	SYNTAX					 Boolean
	MAX-ACCESS				 read-only
	STATUS					 current
	DESCRIPTION
		"Indicates whether the sticky bit is set. It is the readonly field that is set by
		 the system. When it is set, the interface's auto-revert is disabled.
		 It is set when the interface is migrated manually, so that it will not
		 auto-revert to the home port."

	::= { logicalInterfaceEntry 19 }

	logicalInterfaceUseFailoverGroup	 OBJECT-TYPE
	SYNTAX					 INTEGER {
							  system-defined(0),
							  disabled(1),
							  enabled(2),
							  unused(3)
							 }
	MAX-ACCESS				 read-only
	STATUS					 current
	DESCRIPTION
		"The field identifies whether the interface's failover is system-defined(0),
		 set to 'enabled'(1) or 'disable'(2)."
	::= { logicalInterfaceEntry 20 }

	logicalInterfaceDnsZone			 OBJECT-TYPE
	SYNTAX					 DisplayString
	MAX-ACCESS				 read-only
	STATUS					 current
	DESCRIPTION
		"The interface's DNS Zone"
	::= { logicalInterfaceEntry 21 }

	logicalInterfaceAllowLbMigrate		 OBJECT-TYPE
	SYNTAX					 Boolean
	MAX-ACCESS				 read-only
	STATUS					 current
	DESCRIPTION
		"Indicates whether the load balancing migration
		 is enabled for the interface."
	::= { logicalInterfaceEntry 22 }

	logicalInterfaceLbWeight		 OBJECT-TYPE
	SYNTAX					 INTEGER{
							 min-weight(0),
							 max-weight(100),
							 load(101)
							}
	MAX-ACCESS				 read-only
	STATUS					 current
	DESCRIPTION
		"The load balancing weight of the interface.
		 It can be either minimum (0), maximum(100), or load(101)."
	::= { logicalInterfaceEntry 23 }

	logicalInterfaceFailoverGroup		 OBJECT-TYPE
	SYNTAX					 DisplayString
	MAX-ACCESS				 read-only
	STATUS					 current
	DESCRIPTION
		"The interface failover group's name."
	::= { logicalInterfaceEntry 24 }

	logicalInterfaceStatusVserver		 OBJECT-TYPE
	SYNTAX					 INTEGER {
							  up(0),
							  down(1)
							 }
	MAX-ACCESS				 read-only
	STATUS					 current
	DESCRIPTION
		"The status of the interface with respect to its Vserver.
		 It can be either UP(0) or DOWN(1)."
	::= { logicalInterfaceEntry 25 }

	logicalInterfaceDataProtocol		 OBJECT-TYPE
	SYNTAX					 DisplayString
	MAX-ACCESS				 read-only
	STATUS					 current
	DESCRIPTION
		"A list of data protocols."
	::= { logicalInterfaceEntry 26 }

	logicalInterfaceFcpWwpn			OBJECT-TYPE
	SYNTAX					DisplayString
	MAX-ACCESS				read-only
	STATUS					current
	DESCRIPTION
		"The WWPN of a FCP data LIF."
	::= { logicalInterfaceEntry 27 }

	logicalInterfaceComment			OBJECT-TYPE
	SYNTAX					DisplayString
	MAX-ACCESS				read-only
	STATUS					current
	DESCRIPTION
		"A comment to further identify a LIF."
	::= { logicalInterfaceEntry 28 }

	logicalInterfaceListenForDnsQuery	 OBJECT-TYPE
	SYNTAX					 Boolean
	MAX-ACCESS				 read-only
	STATUS					 current
	DESCRIPTION
		"Indicates whether the LIF has to listen for DNS
		 queries for load-balancing."
	::= { logicalInterfaceEntry 29 }

	logicalInterfaceAddressString	         OBJECT-TYPE
	SYNTAX					 DisplayString
	MAX-ACCESS				 read-only
	STATUS					 current
	DESCRIPTION
		"The IP address assigned to the interface. This field displays
		properly for both ipv4 addresses as well as ipv6 addresses.
		Format: <ip address>/<netmask length>"
	::= { logicalInterfaceEntry 30 }

	-- netOpts

	netOpts OBJECT IDENTIFIER ::= { network 5 }

	netOptsv6Table OBJECT IDENTIFIER ::= { netOpts 1 }

	netOptsv6Enabled 	        OBJECT-TYPE
	SYNTAX                          Boolean
	MAX-ACCESS                      read-only
	STATUS                          current
	DESCRIPTION
		"Indicates whether the cluster supports IPv6."
	::= { netOptsv6Table 1 }

	netOptsv6RAProcEnabled          OBJECT-TYPE
	SYNTAX                          Boolean
	MAX-ACCESS                      read-only
	STATUS                          current
	DESCRIPTION
		"Indicates whether the cluster supports IPv6 Router
		Advertisement Processing."
	::= { netOptsv6Table 2 }

        netOptsSwitchlessCluster OBJECT IDENTIFIER ::= { netOpts 2 }

        netOptsSwitchlessClusterEnabled OBJECT-TYPE
        SYNTAX                          Boolean
        MAX-ACCESS                      read-only
        STATUS                          current
        DESCRIPTION
                "Indicates whether the cluster network is switchless."
        ::= { netOptsSwitchlessCluster 1 }

	-- ipspaceTable

	ipspaceTable	     			OBJECT-TYPE
	SYNTAX					SEQUENCE OF IPspaceEntry
	MAX-ACCESS				not-accessible
	STATUS					current
	DESCRIPTION
		"A table of IPspaces, where each entry represents an IPspace."
	::= { network 6 }

	ipspaceEntry				OBJECT-TYPE
	SYNTAX					IPspaceEntry
	MAX-ACCESS				not-accessible
	STATUS					current
	DESCRIPTION
		"IPspace entry."
	INDEX { IMPLIED ipspaceName }
	::= { ipspaceTable 1 }

	IPspaceEntry ::=
	SEQUENCE {
		ipspaceName		        DisplayString,
		ipspaceID		        Unsigned32,
		ipspacePorts                    DisplayString,
		ipspaceBroadcastDomains         DisplayString,
		ipspaceVservers                 DisplayString
		}

	ipspaceName 			        OBJECT-TYPE
	SYNTAX					DisplayString
	MAX-ACCESS				read-only
	STATUS					current
	DESCRIPTION
		"The IPspace name."
	::= { ipspaceEntry 1 }

	ipspaceID			        OBJECT-TYPE
	SYNTAX					Unsigned32
	MAX-ACCESS				read-only
	STATUS					current
	DESCRIPTION
		"The Identifier of the IPspace."
	::= { ipspaceEntry 2 }

	ipspacePorts 			        OBJECT-TYPE
	SYNTAX					DisplayString
	MAX-ACCESS				read-only
	STATUS					current
	DESCRIPTION
		"The network ports assigned to the IPspace of the form {node1:port1},{node2:port2}."
	::= { ipspaceEntry 3 }

	ipspaceBroadcastDomains			OBJECT-TYPE
	SYNTAX					DisplayString
	MAX-ACCESS				read-only
	STATUS					current
	DESCRIPTION
		"The broadcast domains for the IPspace."
	::= { ipspaceEntry 4 }

	ipspaceVservers				OBJECT-TYPE
	SYNTAX					DisplayString
	MAX-ACCESS				read-only
	STATUS					current
	DESCRIPTION
		"The vservers assigned to the IPspace of the form {vs1,vs2}."
	::= { ipspaceEntry 5 }

	-- vsRouteTable

	vsRouteTable	     			OBJECT-TYPE
	SYNTAX					SEQUENCE OF VsRouteEntry
	MAX-ACCESS				not-accessible
	STATUS					current
	DESCRIPTION
		"A table of vserver routes, where each entry represents a vserver route."
	::= { network 7 }

	vsRouteEntry				OBJECT-TYPE
	SYNTAX					VsRouteEntry
	MAX-ACCESS				not-accessible
	STATUS					current
	DESCRIPTION
		"Vsroutes entry."
	INDEX { vsRouteVserverID, IMPLIED vsRouteUuid }
	::= { vsRouteTable 1 }

	VsRouteEntry ::=
	SEQUENCE {
		vsRouteVserverID		Unsigned32,
		vsRouteUuid                     DisplayString,
		vsRouteDestination	        DisplayString,
		vsRouteGateway                  DisplayString,
		vsRouteMetric                   INTEGER,
		vsRouteAddressFamily            DisplayString
		}

	vsRouteVserverID			OBJECT-TYPE
	SYNTAX					Unsigned32 (0..4294967295)
	MAX-ACCESS				read-only
	STATUS					current
	DESCRIPTION
		"The vserver of the vserver route."
	::= { vsRouteEntry 1 }

        vsRouteUuid		                OBJECT-TYPE
	SYNTAX					DisplayString
	MAX-ACCESS				read-only
	STATUS					current
	DESCRIPTION
		"The Uuid of the vserver route."
	::= { vsRouteEntry 2 }

	vsRouteDestination		        OBJECT-TYPE
	SYNTAX					DisplayString
	MAX-ACCESS				read-only
	STATUS					current
	DESCRIPTION
		"The destination of the vserver route."
	::= { vsRouteEntry 3 }

	vsRouteGateway			        OBJECT-TYPE
	SYNTAX					DisplayString
	MAX-ACCESS				read-only
	STATUS					current
	DESCRIPTION
		"The gateway of the vserver route."
	::= { vsRouteEntry 4 }


	vsRouteMetric			        OBJECT-TYPE
	SYNTAX					INTEGER
	MAX-ACCESS				read-only
	STATUS					current
	DESCRIPTION
		"The metric of the vserver route."
	::= { vsRouteEntry 5 }

	vsRouteAddressFamily		        OBJECT-TYPE
	SYNTAX					DisplayString
	MAX-ACCESS				read-only
	STATUS					current
	DESCRIPTION
		"The address family of the vserver route."
	::= { vsRouteEntry 6 }

        -- vsFailoverGroupTable

	vsFailoverGroupTable	     		OBJECT-TYPE
	SYNTAX					SEQUENCE OF VsFailoverGroupEntry
	MAX-ACCESS				not-accessible
	STATUS					current
	DESCRIPTION
		"A table of logical interface failover groups, where each entry
		represents a logical interface failover group."
	::= { network 8 }

	vsFailoverGroupEntry			OBJECT-TYPE
	SYNTAX					VsFailoverGroupEntry
	MAX-ACCESS				not-accessible
	STATUS					current
	DESCRIPTION
		"VsFailoverGroup entry."
	INDEX { vsFailoverGroupVserverID, IMPLIED vsFailoverGroupName }
	::= { vsFailoverGroupTable 1 }

	VsFailoverGroupEntry ::=
	SEQUENCE {
		vsFailoverGroupVserverID        Unsigned32,
		vsFailoverGroupName	        DisplayString,
		vsFailoverGroupTargets          DisplayString
		}

	vsFailoverGroupVserverID		OBJECT-TYPE
	SYNTAX					Unsigned32 (0..4294967295)
	MAX-ACCESS				read-only
	STATUS					current
	DESCRIPTION
		"The vserver of the failover group."
	::= { vsFailoverGroupEntry 1 }

	vsFailoverGroupName      		OBJECT-TYPE
	SYNTAX					DisplayString
	MAX-ACCESS				read-only
	STATUS					current
	DESCRIPTION
		"The name of the failover group."
	::= { vsFailoverGroupEntry 2 }

	vsFailoverGroupTargets			OBJECT-TYPE
	SYNTAX					DisplayString
	MAX-ACCESS				read-only
	STATUS					current
	DESCRIPTION
		"The failover targets of the failover group."
	::= { vsFailoverGroupEntry 3 }

        -- vsFirewallPolicyTable

	vsFirewallPolicyTable	     		OBJECT-TYPE
	SYNTAX					SEQUENCE OF VsFirewallPolicyEntry
	MAX-ACCESS				not-accessible
	STATUS					current
	DESCRIPTION
		"A table of firewall policies, where each entry represents a
		firewall policy."
	::= { network 9 }

	vsFirewallPolicyEntry			OBJECT-TYPE
	SYNTAX					VsFirewallPolicyEntry
	MAX-ACCESS				not-accessible
	STATUS					current
	DESCRIPTION
		"Vsfailovergroups entry."
	INDEX { vsFirewallPolicyVserverID, IMPLIED vsFirewallPolicyUuid }
	::= { vsFirewallPolicyTable 1 }

	VsFirewallPolicyEntry ::=
	SEQUENCE {
                vsFirewallPolicyVserverID	Unsigned32,
                vsFirewallPolicyUuid            DisplayString,
                vsFirewallPolicyName	        DisplayString,
                vsFirewallPolicyService         DisplayString,
                vsFirewallPolicyAllowList       DisplayString
                }

	vsFirewallPolicyVserverID		OBJECT-TYPE
	SYNTAX					Unsigned32 (0..4294967295)
	MAX-ACCESS				read-only
	STATUS					current
	DESCRIPTION
		"The vserver on which this firewall policy is defined."
	::= { vsFirewallPolicyEntry 1 }

	vsFirewallPolicyUuid                    OBJECT-TYPE
	SYNTAX					DisplayString
	MAX-ACCESS				read-only
	STATUS					current
	DESCRIPTION
		"The unique identifier for this firewall policy."
	::= { vsFirewallPolicyEntry 2 }

	vsFirewallPolicyName		        OBJECT-TYPE
	SYNTAX					DisplayString
	MAX-ACCESS				read-only
	STATUS					current
	DESCRIPTION
		"The name of this firewall policy."
	::= { vsFirewallPolicyEntry 3 }

	vsFirewallPolicyService		        OBJECT-TYPE
	SYNTAX					DisplayString
	MAX-ACCESS				read-only
	STATUS					current
	DESCRIPTION
		"The service that this firewall policy is restricting access to."
	::= { vsFirewallPolicyEntry 4 }

	vsFirewallPolicyAllowList		OBJECT-TYPE
	SYNTAX					DisplayString
	MAX-ACCESS				read-only
	STATUS					current
	DESCRIPTION
		"The list of source IPs that are allowed to access the
		underlying service of this firewall policy."
	::= { vsFirewallPolicyEntry 5 }

        -- broadcastDomainTable

        broadcastDomainTable                    OBJECT-TYPE
        SYNTAX                                  SEQUENCE OF BroadcastDomainEntry
        MAX-ACCESS                              not-accessible
        STATUS                                  current
        DESCRIPTION
                "A table of broadcast domains, where each entry represents a broadcast domain."
        ::= { network 10 }

        broadcastDomainEntry                    OBJECT-TYPE
        SYNTAX                                  BroadcastDomainEntry
        MAX-ACCESS                              not-accessible
        STATUS                                  current
        DESCRIPTION
                "Broadcast domain entry."
        INDEX { broadcastDomainIpspaceName, broadcastDomainName }
        ::= { broadcastDomainTable 1 }

        BroadcastDomainEntry ::=
        SEQUENCE {
                broadcastDomainIpspaceName      DisplayString,
                broadcastDomainName             DisplayString,
                broadcastDomainMTU              INTEGER,
                broadcastDomainPorts            DisplayString,
                broadcastDomainFailoverGroups   DisplayString,
                broadcastDomainSubnets          DisplayString
                }

        broadcastDomainIpspaceName              OBJECT-TYPE
        SYNTAX                                  DisplayString
        MAX-ACCESS                              read-only
        STATUS                                  current
        DESCRIPTION
                "The IPspace name."
        ::= { broadcastDomainEntry 1 }

        broadcastDomainName                     OBJECT-TYPE
        SYNTAX                                  DisplayString
        MAX-ACCESS                              read-only
        STATUS                                  current
        DESCRIPTION
                "The broadcast domain name."
        ::= { broadcastDomainEntry 2 }

        broadcastDomainMTU                      OBJECT-TYPE
        SYNTAX                                  INTEGER
        MAX-ACCESS                              read-only
        STATUS                                  current
        DESCRIPTION
                "MTU of the broadcast domain."
        ::= { broadcastDomainEntry 3 }

        broadcastDomainPorts                    OBJECT-TYPE
        SYNTAX                                  DisplayString
        MAX-ACCESS                              read-only
        STATUS                                  current
        DESCRIPTION
                "The network ports assigned to the broadcast domain of the form {node1:port1},{node2:port2}."
        ::= { broadcastDomainEntry 4 }

        broadcastDomainFailoverGroups           OBJECT-TYPE
        SYNTAX                                  DisplayString
        MAX-ACCESS                              read-only
        STATUS                                  current
        DESCRIPTION
                "The failover groups for the broadcast domain of the form {fg1,fg2}."
        ::= { broadcastDomainEntry 5 }

        broadcastDomainSubnets                  OBJECT-TYPE
        SYNTAX                                  DisplayString
        MAX-ACCESS                              read-only
        STATUS                                  current
        DESCRIPTION
                "The subnets associated with this broadcast domain."
        ::= { broadcastDomainEntry 6 }

        -- subnetTable

        subnetTable                             OBJECT-TYPE
        SYNTAX                                  SEQUENCE OF SubnetEntry
        MAX-ACCESS                              not-accessible
        STATUS                                  current
        DESCRIPTION
                "A table of Subnets, where each entry represents a Subnet."
        ::= { network 11 }

        subnetEntry                             OBJECT-TYPE
        SYNTAX                                  SubnetEntry
        MAX-ACCESS                              not-accessible
        STATUS                                  current
        DESCRIPTION
                "Subnet entry."
        INDEX { subnetIpspaceName, subnetName }
        ::= { subnetTable 1 }

        SubnetEntry ::=
        SEQUENCE {
                subnetIpspaceName               DisplayString,
                subnetBroadcastDomainName       DisplayString,
                subnetName                      DisplayString,
                subnetMask                      DisplayString,
                subnetGateway                   DisplayString,
                subnetIpRanges                  DisplayString,
                subnetTotalCount                INTEGER,
                subnetUsedCount                 INTEGER,
                subnetAvailableCount            INTEGER
                }

        subnetIpspaceName                       OBJECT-TYPE
        SYNTAX                                  DisplayString
        MAX-ACCESS                              read-only
        STATUS                                  current
        DESCRIPTION
                "The IPspace name."
        ::= { subnetEntry 1 }

        subnetBroadcastDomainName               OBJECT-TYPE
        SYNTAX                                  DisplayString
        MAX-ACCESS                              read-only
        STATUS                                  current
        DESCRIPTION
                "The broadcast domain name."
        ::= { subnetEntry 2 }

        subnetName                              OBJECT-TYPE
        SYNTAX                                  DisplayString
        MAX-ACCESS                              read-only
        STATUS                                  current
        DESCRIPTION
                "The Subnet name."
        ::= { subnetEntry 3 }

        subnetMask                              OBJECT-TYPE
        SYNTAX                                  DisplayString
        MAX-ACCESS                              read-only
        STATUS                                  current
        DESCRIPTION
             "Subnet IP and Mask."
        ::= { subnetEntry 4 }

        subnetGateway                           OBJECT-TYPE
        SYNTAX                                  DisplayString
        MAX-ACCESS                              read-only
        STATUS                                  current
        DESCRIPTION
                "Subnet Gateway IP."
        ::= { subnetEntry 5 }

        subnetIpRanges                          OBJECT-TYPE
        SYNTAX                                  DisplayString
        MAX-ACCESS                              read-only
        STATUS                                  current
        DESCRIPTION
                "Subnet IP Ranges."
        ::= { subnetEntry 6 }

        subnetTotalCount                        OBJECT-TYPE
        SYNTAX                                  INTEGER
        MAX-ACCESS                              read-only
        STATUS                                  current
        DESCRIPTION
                "Total address count for all ranges."
        ::= { subnetEntry 7 }

        subnetUsedCount                         OBJECT-TYPE
        SYNTAX                                  INTEGER
        MAX-ACCESS                              read-only
        STATUS                                  current
        DESCRIPTION
                "Used address count for all ranges."
        ::= { subnetEntry 8 }

        subnetAvailableCount                     OBJECT-TYPE
        SYNTAX                                  INTEGER
        MAX-ACCESS                              read-only
        STATUS                                  current
        DESCRIPTION
                "Available address count for all ranges."
        ::= { subnetEntry 9 }

	-- -- -- -- -- -- -- --
	-- the sis group
	-- -- -- -- -- -- -- --

	sisIsLicensed                   OBJECT-TYPE
	SYNTAX                          INTEGER {
                                             false(1),
                                             true(2)
                                        }
        MAX-ACCESS                      read-only
        STATUS                          current
	DESCRIPTION
			"Indicates whether Advanced SIS is licensed on the
			filer."
	::= { sis 1 }

	sisTable                        OBJECT-TYPE
	SYNTAX                          SEQUENCE OF SisEntry
        MAX-ACCESS                      not-accessible
        STATUS                          current
	DESCRIPTION
			"Provide a list of the SIS volumes on the
			 system."

	::= { sis 2 }

	sisEntry                        OBJECT-TYPE
	SYNTAX                          SisEntry
        MAX-ACCESS                      not-accessible
        STATUS                          current
	DESCRIPTION
			"Provide details about a particular SIS volume.
			 For entries returned only from the cluster
			 interfaces, the value of sisRowAvailable needs to be
			 1, for the contents of the row to be valid."

	INDEX	{ sisIndex }
	::= { sisTable 1 }

	SisEntry ::=
	    SEQUENCE {
	    	sisIndex
		    Integer32,
		sisPath
		    DisplayString,
		sisState
		    INTEGER,
		sisStatus
		    INTEGER,
		sisProgress
		    DisplayString,
		sisType
		    INTEGER,
		sisSchedule
		    DisplayString,
		sisLastOpBeginTime
		    DisplayString,
		sisLastOpEndTime
		    DisplayString,
		sisHighLastOpSize
		    Integer32,
		sisLowLastOpSize
		    Integer32,
		sisLastOpError
		    DisplayString,
		sis64LastOpSize
		    Counter64,
		sisIsCompressionEnabled
		    Boolean,
		sisIsInlineEnabled
		    Boolean,
		sisVserver
		    DisplayString,
		sisPolicy
		    DisplayString,
		sisRowAvailable
		    Boolean,
		sisMinBlocksShared
		    Integer32,
		sisBlocksSkippedSharing
		    Counter32,
		sisChangelogUsedPercent
		    Integer32,
		sisLastSuccessfulOpBeginTime
		    DisplayString,
		sisLastSuccessfulOpEndTime
		    DisplayString,
		sisLastOpState
		    DisplayString,
		sisLogicalSize
		    Counter64,
		sisLogicalLimit
		    Counter64,
		sisQueuedJob
		    DisplayString,
		sisStaleFpPercentage
		    Integer32,
		sisIsIddEnabled
		    Boolean,
		sisQuickCheckFsize
		    Counter64,
		sisIsConstituent
		    Boolean,
		sisIsInlineDedupeEnabled
		    Boolean,
		sisIsDataCompactionEnabled
		    Boolean,
		sisIsCrossVolumeInlineDedupeEnabled
		    Boolean,
		sisIsCrossVolumeBackgroundDedupeEnabled
		    Boolean,
		sisApplicationIOSize
		    INTEGER,
		sisCompressionType
		    INTEGER,
		sisHasExtendedCompressedData
		    Boolean
	    }

	sisIndex                        OBJECT-TYPE
	SYNTAX                          Integer32 (1..2147483647)
        MAX-ACCESS                      read-only
        STATUS                          current
	DESCRIPTION
				"A number that identifies this entry for the
				 SIS volume."
	::= { sisEntry 1 }

	sisPath                         OBJECT-TYPE
	SYNTAX                          DisplayString
        MAX-ACCESS                      read-only
        STATUS                          current
	DESCRIPTION
				"The path to the SIS volume."
	::= { sisEntry 2 }

	sisState                        OBJECT-TYPE
	SYNTAX                          INTEGER {
                                             disabled(1),
                                             enabled(2)
                                        }
        MAX-ACCESS                      read-only
        STATUS                          current
	DESCRIPTION
				"Indicates whether SIS is enabled on the
				 volume or not."
	::= { sisEntry 3 }

	sisStatus                       OBJECT-TYPE
	SYNTAX                          INTEGER {
											idle(1),
											active(2),
											undoing(3),
											pending(4),
											initializing(5),
											downgrading(6),
											disabled(7)
                                        }
        MAX-ACCESS                      read-only
        STATUS                          current
	DESCRIPTION
				"Current status of the SIS volume."
	::= { sisEntry 4 }

	sisProgress                     OBJECT-TYPE
	SYNTAX                          DisplayString
        MAX-ACCESS                      read-only
        STATUS                          current
	DESCRIPTION
				"The progress of the current SIS operation."
	::= { sisEntry 5 }

	sisType                         OBJECT-TYPE
	SYNTAX                          INTEGER {
                                             regular(1),
                                             snapvault(2)
                                        }
        MAX-ACCESS                      read-only
        STATUS                          current
	DESCRIPTION
				"Indicates whether it is a regular or
				 snapvaulted SIS volume."
	::= { sisEntry 6 }

	sisSchedule                     OBJECT-TYPE
	SYNTAX                          DisplayString
        MAX-ACCESS                      read-only
        STATUS                          current
	DESCRIPTION
				"The schedule for the SIS operations."
	::= { sisEntry 7 }

	sisLastOpBeginTime              OBJECT-TYPE
	SYNTAX                          DisplayString
        MAX-ACCESS                      read-only
        STATUS                          current
	DESCRIPTION
				"The starting time of the last completed SIS
				 operation."
	::= { sisEntry 8 }

	sisLastOpEndTime                OBJECT-TYPE
	SYNTAX                          DisplayString
        MAX-ACCESS                      read-only
        STATUS                          current
	DESCRIPTION
				"The ending time of the last completed SIS
				 operation."
	::= { sisEntry 9 }

	sisHighLastOpSize               OBJECT-TYPE
	SYNTAX                          Integer32
        MAX-ACCESS                      read-only
        STATUS                          deprecated
	DESCRIPTION
				"The total amount of data in KBytes that the
				 last completed SIS operation had processed.
				 This object returns the most significant 32
				 bits of the 64 bit unsigned integer. This object
				 is deprecated - Use sis64LastOpSize instead."
	::= { sisEntry 10 }

	sisLowLastOpSize                OBJECT-TYPE
	SYNTAX                          Integer32
        MAX-ACCESS                      read-only
        STATUS                          deprecated
	DESCRIPTION
				"The total amount of data in KBytes that the
				 last completed SIS operation had processed.
				 This object returns the least significant 32
				 bits of the 64 bit unsigned integer. This object
				 is deprecated - Use sis64LastOpSize instead."
	::= { sisEntry 11 }

	sisLastOpError                  OBJECT-TYPE
	SYNTAX                          DisplayString
        MAX-ACCESS                      read-only
        STATUS                          current
	DESCRIPTION
				"The error that the last SIS operation
				 encountered if it failed."
	::= { sisEntry 12 }

	sis64LastOpSize                 OBJECT-TYPE
	SYNTAX                          Counter64
        MAX-ACCESS                      read-only
        STATUS                          current
	DESCRIPTION
				"The total amount of data in KBytes that the
				 last completed SIS operation had processed.
				 This object returns all of the 64 bit
				 unsigned integer."
	::= { sisEntry 13 }

	sisIsCompressionEnabled		OBJECT-TYPE
	SYNTAX                          Boolean
        MAX-ACCESS                      read-only
        STATUS                          current
	DESCRIPTION
				"Indicates whether background compression is enabled on
				the volume or not."
	::= { sisEntry 14 }

	sisIsInlineEnabled		OBJECT-TYPE
	SYNTAX                          Boolean
        MAX-ACCESS                      read-only
        STATUS                          current
	DESCRIPTION
				"Indicates whether inline compression is enabled on
                the volume or not"
	::= { sisEntry 15 }

	sisVserver		        OBJECT-TYPE
	SYNTAX                          DisplayString
        MAX-ACCESS                      read-only
        STATUS                          current
	DESCRIPTION
				"Vserver owning the Storage efficiency volume.
				This entry is only available from the cluster interface."
	::= { sisEntry 16 }

	sisPolicy		        OBJECT-TYPE
	SYNTAX                          DisplayString
        MAX-ACCESS                      read-only
        STATUS                          current
	DESCRIPTION
				"Storage efficiency policy name set on the volume.
				This entry is only available from the cluster interface."
	::= { sisEntry 17 }

        sisRowAvailable                 OBJECT-TYPE
        SYNTAX                          Boolean
        MAX-ACCESS                      read-only
        STATUS                          current
        DESCRIPTION
                "Indicates if other fields in this entry are available.
		This field is returned only from the cluster interfaces.
		If something goes wrong while fetching the values for
		fields in this table, the values returned may not be valid.
		The volume returned may not be a SIS volume.
                For fields that could not be fetched, default
                values are set. For integers it is -1, for
                counters 0, and for string it is null."

	::= { sisEntry 18 }

	sisMinBlocksShared              OBJECT-TYPE
	SYNTAX                          Integer32 (1..64)
        MAX-ACCESS                      read-only
        STATUS                          current
	DESCRIPTION
 			  "The minimum number of contiguous blocks in a file
                           that will be considered for block sharing.
                           If the number of contiguous duplicate blocks is
                           less than this number, then they won't be considered
			   for sharing."
	::= { sisEntry 19 }

	sisBlocksSkippedSharing         OBJECT-TYPE
	SYNTAX                          Counter32
        MAX-ACCESS                      read-only
        STATUS                          current
	DESCRIPTION
			 "Number of blocks not considered for sharing because
                         contiguous duplicate blocks were less than the value
			 set for sisMinBlocksShared."
	::= { sisEntry 20 }

	sisChangelogUsedPercent         OBJECT-TYPE
	SYNTAX                          Integer32
        MAX-ACCESS                      read-only
        STATUS                          current
	DESCRIPTION
			 "Percentage of changelog used."
	::= { sisEntry 21 }

	sisLastSuccessfulOpBeginTime          OBJECT-TYPE
	SYNTAX                          DisplayString
        MAX-ACCESS                      read-only
        STATUS                          current
	DESCRIPTION
				"The starting time of the last successful SIS
				 operation."
	::= { sisEntry 22 }

	sisLastSuccessfulOpEndTime            OBJECT-TYPE
	SYNTAX                          DisplayString
        MAX-ACCESS                      read-only
        STATUS                          current
	DESCRIPTION
				"The ending time of the last successful SIS
				 operation."
	::= { sisEntry 23 }

	sisLastOpState                  OBJECT-TYPE
	SYNTAX                          DisplayString
        MAX-ACCESS                      read-only
        STATUS                          current
	DESCRIPTION
				"The state of the last SIS operation."
	::= { sisEntry 24 }


        sisLogicalSize                  OBJECT-TYPE
        SYNTAX                          Counter64
        MAX-ACCESS                      read-only
        STATUS                          current
        DESCRIPTION
                "The size of logical data in the volume in bytes.
		This may be calculated approximately using these fields in dfTable MIB
		[df64DedupeSaved +  df64CompressSaved + df64SisSharedKBytes * 1024]."

	::= { sisEntry 25 }

        sisLogicalLimit                 OBJECT-TYPE
        SYNTAX                          Counter64
        MAX-ACCESS                      read-only
        STATUS                          current
        DESCRIPTION
                "Indicates  SIS logical limit for the volume.
		 It is equal to WAFL maximum nominal size of 64bit
		 volume."

	::= { sisEntry 26 }

        sisQueuedJob 	                OBJECT-TYPE
        SYNTAX                          DisplayString
        MAX-ACCESS                      read-only
        STATUS                          current
        DESCRIPTION
                "Indicates type of sis operation that is queued for the
		 volume. Possible values: 'scan', 'start', 'check', 'downgrade'."

	::= { sisEntry 27 }

        sisStaleFpPercentage            OBJECT-TYPE
        SYNTAX                         	Integer32
        MAX-ACCESS                      read-only
        STATUS                          current
        DESCRIPTION
                "Indicates percentage of fingerprints that are stale in
		the fingerprint database. It can be more than 100%, if blocks are
		overwritten or deleted."

	::= { sisEntry 28 }

	sisIsIddEnabled	              	OBJECT-TYPE
	SYNTAX				Boolean
	MAX-ACCESS			read-only
	STATUS				current
	DESCRIPTION
		"Indicates Incompressible data detection is enabled on
		compressed volume."

	::= { sisEntry 29 }

	sisQuickCheckFsize		OBJECT-TYPE
	SYNTAX				Counter64
	MAX-ACCESS                      read-only
	STATUS                          current
	DESCRIPTION
		"Compression quick check file size. If Incompressible data
		detection is enabled and if the file size is >=
		quick-check-fsize, inline compression will do a 4k
		quick check before doing full CG compression."

	::= { sisEntry 30 }

	sisIsConstituent               OBJECT-TYPE
	SYNTAX                         Boolean
	MAX-ACCESS                     read-only
	STATUS	                       current
	DESCRIPTION
		"Indicates whether the volume is a constituent or not."

	::= { sisEntry 31 }

	sisIsInlineDedupeEnabled        OBJECT-TYPE
	SYNTAX                          Boolean
	MAX-ACCESS                      read-only
	STATUS                          current
	DESCRIPTION
		"Indicates whether inline dedupe is enabled on
		the volume or not"

	::= { sisEntry 32 }

	sisIsCrossVolumeInlineDedupeEnabled    OBJECT-TYPE
	SYNTAX                                 Boolean
	MAX-ACCESS                             read-only
	STATUS                                 current
	DESCRIPTION
		"Indicates whether cross volume inline deduplication is enabled
		 on the volume or not"

	::= { sisEntry 33 }

        sisIsCrossVolumeBackgroundDedupeEnabled    OBJECT-TYPE
        SYNTAX                                     Boolean
        MAX-ACCESS                                 read-only
        STATUS                                     current
        DESCRIPTION
                "Indicates whether cross volume background deduplication is enabled
                 on the volume or not"

        ::= { sisEntry 34 }

	sisIsDataCompactionEnabled      OBJECT-TYPE
	SYNTAX                          Boolean
	MAX-ACCESS                      read-only
	STATUS                          current
	DESCRIPTION
		"Indicates whether data compaction is enabled on
		the volume or not"

	::= { sisEntry 35 }

	sisApplicationIOSize            OBJECT-TYPE
	SYNTAX                          INTEGER {
						  default(0),
						  size8k(1),
						  size16k(2),
					          size32k(3)
                                        }
        MAX-ACCESS                      read-only
        STATUS                          current
	DESCRIPTION
				"Indicates the Application IO Size used for compression."
	::= { sisEntry 36 }

	sisCompressionType            OBJECT-TYPE
	SYNTAX                          INTEGER {
						  default(0),
						  secondary(1),
						  adaptive(2)
                                        }
        MAX-ACCESS                      read-only
        STATUS                          current
	DESCRIPTION
				"Indicates the Compression Type used by the volume."
	::= { sisEntry 37 }
	sisHasExtendedCompressedData    OBJECT-TYPE
	SYNTAX                                 Boolean
	MAX-ACCESS                             read-only
	STATUS                                 current
	DESCRIPTION
		"Indicates whether the volume has data compressed in extended compression
		 format or not"

	::= { sisEntry 38 }

	-- -- -- -- -- -- -- -- --
	-- the compression group
	-- -- -- -- -- -- -- -- --

	compressIsLicensed              OBJECT-TYPE
	SYNTAX                          INTEGER {
                                             false(1),
                                             true(2)
                                        }
        MAX-ACCESS                      read-only
        STATUS                          deprecated
	DESCRIPTION
				"Indicates whether compression is licensed on
				the filer."
	::= { compress 1 }

	compressTable                   OBJECT-TYPE
	SYNTAX                          SEQUENCE OF CompressEntry
        MAX-ACCESS                      not-accessible
        STATUS                          deprecated
	DESCRIPTION
				"Provide a report of the total space used as
				 well as the space saved by compression on
				 volumes."
	::= { compress 2 }


	-- display the active file system compression statistics

	compressEntry                 	OBJECT-TYPE
	SYNTAX                          CompressEntry
        MAX-ACCESS                      not-accessible
        STATUS                          deprecated
	DESCRIPTION
				"Provide a report of the total space used as
				 well as the space saved by compression on
				 the referenced file system."
	INDEX      { compressIndex }
	::= { compressTable 1 }

	CompressEntry ::=
	    SEQUENCE {
		compressIndex
		    Integer32,
		compressFileSys
		    DisplayString,
 		compressHighUsedKBytes
		    Counter32,
                compressLowUsedKBytes
	            Counter32,
		compress64UsedKBytes
		    Counter64,
                compressHighSavedKBytes
		    Counter32,
		compressLowSavedKBytes
		    Counter32,
		compress64SavedKBytes
		    Counter64,
		compressPercentSaved
		    INTEGER
	    }

	compressIndex                   OBJECT-TYPE
	SYNTAX                          Integer32 (1..2147483647)
        MAX-ACCESS                      read-only
        STATUS                          deprecated
	DESCRIPTION
				"A number that identifies this entry for the
			 	referenced file system."
	::= { compressEntry 1 }

	compressFileSys                 OBJECT-TYPE
	SYNTAX                          DisplayString
        MAX-ACCESS                      read-only
        STATUS                          deprecated
	DESCRIPTION
				"The name for the referenced file system."
	::= { compressEntry 2 }

	compressHighUsedKBytes	        OBJECT-TYPE
	SYNTAX                          Counter32
        MAX-ACCESS                      read-only
        STATUS                          deprecated
	DESCRIPTION
				"The total disk space in KBytes that is in use
				 on the referenced file system.  This object
				 returns the most significant 32 bits of the 64
				 bit unsigned integer. This object is
				 deprecated - Use compress64UsedKBytes instead."
	::= { compressEntry 3 }

	compressLowUsedKBytes	        OBJECT-TYPE
	SYNTAX                          Counter32
        MAX-ACCESS                      read-only
        STATUS                          deprecated
	DESCRIPTION
				"The total disk space in KBytes that is in use
				 on the referenced file system.  This object
				 returns the least significant 32 bits of the
				 64 bit unsigned integer. This object is
				 deprecated - Use compress64UsedKBytes instead."
	::= { compressEntry 4 }

	compress64UsedKBytes	        OBJECT-TYPE
	SYNTAX                          Counter64
        MAX-ACCESS                      read-only
        STATUS                          deprecated
	DESCRIPTION
				"The total disk space in KBytes that is in use
				 on the referenced file system. This object
				 returns all of the 64 bit unsigned integer."
	::= { compressEntry 5 }

	compressHighSavedKBytes	        OBJECT-TYPE
	SYNTAX                          Counter32
        MAX-ACCESS                      read-only
        STATUS                          deprecated
	DESCRIPTION
				"The disk space in KBytes of disk space that
				 is saved by compression on the referenced
				 file system. This object returns the most
				 significant 32 bits of the 64 bit unsigned
				 integer. This object is deprecated - Use
				 compress64SavedKBytes instead."
	::= { compressEntry 6 }

	compressLowSavedKBytes	        OBJECT-TYPE
	SYNTAX                          Counter32
        MAX-ACCESS                      read-only
        STATUS                          deprecated
	DESCRIPTION
				"The disk space in KBytes of disk space that
				 is saved by compression on the referenced
				 filesystem. This object returns the least
				 significant 32 bits of the 64 bit unsigned
				 integer. This object is deprecated - Use
				 compress64SavedKBytes instead."
	::= { compressEntry 7 }

	compress64SavedKBytes		OBJECT-TYPE
	SYNTAX				Counter64
	MAX-ACCESS			read-only
	STATUS				deprecated
	DESCRIPTION
				"The disk space in KBytes of disk space that
				 is saved by compression on the referenced
				 filesystem. This object returns all of the
				 64 bit unsigned integer."
	::= { compressEntry 8 }

	compressPercentSaved		OBJECT-TYPE
	SYNTAX				INTEGER
	MAX-ACCESS			read-only
	STATUS				deprecated
	DESCRIPTION
				"The percentage of disk space saved by
				 compression on the referenced filesystem."
	::= { compressEntry 9 }

	-- -- -- -- -- -- -- -- --
	-- the extcache group
	-- -- -- -- -- -- -- -- --

	extcacheType	                OBJECT-TYPE
	SYNTAX                          DisplayString
        MAX-ACCESS                      read-only
        STATUS                          current
	DESCRIPTION
				"Indicates the type of external cache being used.
				Examples are none, PCS, IOMEM."
	::= { extcache 1 }

	extcacheSubType	                OBJECT-TYPE
	SYNTAX                          DisplayString
        MAX-ACCESS                      read-only
        STATUS                          current
	DESCRIPTION
				"Indicates the sub-type of external cache being used.
				Examples are none, PAM1, PAM2."
	::= { extcache 2 }

	extcache64Uptime                OBJECT-TYPE
	SYNTAX                          Counter64
        MAX-ACCESS                      read-only
        STATUS                          current
	DESCRIPTION
				"Indicates the uptime of the external cache."
	::= { extcache 3 }

	extcache64Size	                OBJECT-TYPE
	SYNTAX                          Counter64
        MAX-ACCESS                      read-only
        STATUS                          current
	DESCRIPTION
				"Indicates size of the external cache in bytes."
	::= { extcache 4 }

	extcache64Usedsize 	        OBJECT-TYPE
	SYNTAX                          Counter64
        MAX-ACCESS                      read-only
        STATUS                          current
	DESCRIPTION
				"Indicates number of bytes used in the external cache."
	::= { extcache 5 }

	extcache64TotalBuffers		OBJECT-TYPE
	SYNTAX				Counter64
	MAX-ACCESS			read-only
	STATUS				current
	DESCRIPTION
				"Indicates total number of 4k blocks in the external cache."
	::= { extcache 6 }

	extcacheOptions 	        OBJECT-TYPE
	SYNTAX                          DisplayString
        MAX-ACCESS                      read-only
        STATUS                          current
	DESCRIPTION
				"Indicates external cache options that are
				currently turned on. "
	::= { extcache 7 }

	extcache64Hits 	                OBJECT-TYPE
	SYNTAX                          Counter64
        MAX-ACCESS                      read-only
        STATUS                          current
	DESCRIPTION
				"Indicates number of wafl buffers read from
				the external cache"
	::= { extcache 8 }

	extcache64Misses   	        OBJECT-TYPE
	SYNTAX                          Counter64
        MAX-ACCESS                      read-only
        STATUS                          current
	DESCRIPTION
				"Indicates the number of external cache misses"
	::= { extcache 9 }

	extcache64Inserts 	        OBJECT-TYPE
	SYNTAX                          Counter64
        MAX-ACCESS                      read-only
        STATUS                          current
	DESCRIPTION
				"Indicates number of wafl buffers inserted
				into the external cache"
	::= { extcache 10 }

	extcache64Evicts  	        OBJECT-TYPE
	SYNTAX                          Counter64
        MAX-ACCESS                      read-only
        STATUS                          current
	DESCRIPTION
				"Indicates the number of buffers evicted
				from the external cache"
	::= { extcache 11 }

	extcache64Invalidates	        OBJECT-TYPE
	SYNTAX                          Counter64
        MAX-ACCESS                      read-only
        STATUS                          current
	DESCRIPTION
				"Indicates the number of buffers invalidated
			       	in the external cache"
	::= { extcache 12 }

	extcache64BlocksRef0	        OBJECT-TYPE
	SYNTAX                          Counter64
        MAX-ACCESS                      read-only
        STATUS                          current
	DESCRIPTION
				"Indicates the number of non-referenced buffers
			       	currently in the external cache"
	::= { extcache 13 }

	extcache64HitNormalL0	        OBJECT-TYPE
	SYNTAX                          Counter64
        MAX-ACCESS                      read-only
        STATUS                          current
	DESCRIPTION
				"Indicates the number of L0 buffers read from
				the external cache"
	::= { extcache 14 }

	extcache64MetaData	        OBJECT-TYPE
	SYNTAX                          Counter64
        MAX-ACCESS                      read-only
        STATUS                          current
	DESCRIPTION
				"Indicates the number of metadata buffers
				read from the external cache"
	::= { extcache 15 }

	extcache64ReadLatency	        OBJECT-TYPE
	SYNTAX                          Counter64
        MAX-ACCESS                      read-only
        STATUS                          current
	DESCRIPTION
				"Indicates the average latency of read IOs
				in the external cache in milliseconds"
	::= { extcache 16 }

	extcache64WriteLatency		OBJECT-TYPE
	SYNTAX                          Counter64
        MAX-ACCESS                      read-only
        STATUS                          current
	DESCRIPTION
				"Indicates the average latency of write IOs
			       	in the external cache in milliseconds"
	::= { extcache 17 }

	extcache64RCLength	        OBJECT-TYPE
	SYNTAX                          Counter64
        MAX-ACCESS                      read-only
        STATUS                          current
	DESCRIPTION
				"Indicates the average read chain length
				in the external cache"
	::= { extcache 18 }

	extcache64WCLength	        OBJECT-TYPE
	SYNTAX                          Counter64
        MAX-ACCESS                      read-only
        STATUS                          current
	DESCRIPTION
				"Indicates the average write chain length
			       	in the external cache"
	::= { extcache 19 }

	extcacheIsFlexShareOn           OBJECT-TYPE
	SYNTAX                          INTEGER {
                                             false(1),
                                             true(2)
                                        }
        MAX-ACCESS                      read-only
        STATUS                          current
	DESCRIPTION
				"Indicates whether FlexShare is on"
	::= { extcache 20 }

	-- qosWorkload


        qosWorkloadTable       OBJECT-TYPE
        SYNTAX                  SEQUENCE OF QosWorkloadEntry
        MAX-ACCESS              not-accessible
        STATUS                  current
        DESCRIPTION             "QoS Workload Table."
        ::= { qos 1 }

        qosWorkloadEntry       OBJECT-TYPE
        SYNTAX                  QosWorkloadEntry
        MAX-ACCESS              not-accessible
        STATUS                  current
        DESCRIPTION             "Entry for a QoS Workload."
        INDEX { IMPLIED qosWorkloadName}
        ::= { qosWorkloadTable 1 }

        QosWorkloadEntry ::=
        SEQUENCE {
            qosWorkloadUuid              DisplayString,
            qosWorkloadName              DisplayString,
            qosWorkloadClass             INTEGER,
            qosWorkloadId                Counter32,
            qosWorkloadPolicyGroup       DisplayString,
            qosWorkloadVserver           DisplayString,
            qosWorkloadVolume            DisplayString,
            qosWorkloadLun               DisplayString,
            qosWorkloadFile              DisplayString,
            qosWorkloadQtree             FileOrDirectoryString,
            qosWorkloadReadAhead         DisplayString,
            qosWorkloadCache          	 DisplayString,
            qosWorkloadMinThroughput     DisplayString,
            qosWorkloadMaxThroughput     DisplayString
        }

        qosWorkloadUuid                  OBJECT-TYPE
        SYNTAX                           DisplayString
        MAX-ACCESS                       read-only
        STATUS                           current
        DESCRIPTION
                      "Workload Uuid"
        ::= { qosWorkloadEntry  1 }


        qosWorkloadName                  OBJECT-TYPE
        SYNTAX                           DisplayString
        MAX-ACCESS                       read-only
        STATUS                           current
        DESCRIPTION
                      "Workload Name"
        ::= { qosWorkloadEntry  2 }


        qosWorkloadClass                 OBJECT-TYPE
        SYNTAX                           INTEGER {
                                                 preset(1),
                                                 user-defined(2),
                                                 system-defined(3),
                                                 autovolume(4)
                                         }
        MAX-ACCESS                       read-only
        STATUS                           current
        DESCRIPTION
                      "Workload Class"
        ::= { qosWorkloadEntry  3 }


        qosWorkloadId                   OBJECT-TYPE
        SYNTAX                           Counter32
        MAX-ACCESS                       read-only
        STATUS                           current
        DESCRIPTION
                      "Workload ID"
        ::= { qosWorkloadEntry  4 }


        qosWorkloadPolicyGroup           OBJECT-TYPE
        SYNTAX                           DisplayString
        MAX-ACCESS                       read-only
        STATUS                           current
        DESCRIPTION
                      "Policy Group Uuid"
        ::= { qosWorkloadEntry  5 }


        qosWorkloadVserver               OBJECT-TYPE
        SYNTAX                           DisplayString
        MAX-ACCESS                       read-only
        STATUS                           current
        DESCRIPTION
                      "Vserver ID"
        ::= { qosWorkloadEntry  6 }


        qosWorkloadVolume                OBJECT-TYPE
        SYNTAX                           DisplayString
        MAX-ACCESS                       read-only
        STATUS                           current
        DESCRIPTION
                      "Volume Name"
        ::= { qosWorkloadEntry  7 }


        qosWorkloadLun                   OBJECT-TYPE
        SYNTAX                           DisplayString
        MAX-ACCESS                       read-only
        STATUS                           current
        DESCRIPTION
                      "LUN Name"
        ::= { qosWorkloadEntry  8 }


        qosWorkloadFile                  OBJECT-TYPE
        SYNTAX                           DisplayString
        MAX-ACCESS                       read-only
        STATUS                           current
        DESCRIPTION
                      "Filename"
        ::= { qosWorkloadEntry  9 }


        qosWorkloadQtree                 OBJECT-TYPE
        SYNTAX                           FileOrDirectoryString
        MAX-ACCESS                       read-only
        STATUS                           current
        DESCRIPTION
                      "Qtree"
        ::= { qosWorkloadEntry  10 }


        qosWorkloadReadAhead             OBJECT-TYPE
        SYNTAX                           DisplayString
        MAX-ACCESS                       read-only
        STATUS                           current
        DESCRIPTION
                      "Readahead Tunables"
        ::= { qosWorkloadEntry  11 }


	qosWorkloadCache		 OBJECT-TYPE
        SYNTAX                           DisplayString
        MAX-ACCESS                       read-only
        STATUS                           current
        DESCRIPTION
                      "Ext Cache Tunables"
        ::= { qosWorkloadEntry  12 }


	qosWorkloadMinThroughput	 OBJECT-TYPE
        SYNTAX                           DisplayString
        MAX-ACCESS                       read-only
        STATUS                           current
        DESCRIPTION
                      "Minimum Throughput"
        ::= { qosWorkloadEntry  13 }

	qosWorkloadMaxThroughput	 OBJECT-TYPE
        SYNTAX                           DisplayString
        MAX-ACCESS                       read-only
        STATUS                           current
        DESCRIPTION
                      "Maximum Throughput"
        ::= { qosWorkloadEntry  14 }

-- qos Policy Group
        qosPolicyGroupTable     OBJECT-TYPE
        SYNTAX                  SEQUENCE OF QosPolicyGroupEntry
        MAX-ACCESS              not-accessible
        STATUS                  current
        DESCRIPTION             "QoS Policy Group Table."
        ::= { qos 2 }

        qosPolicyGroupEntry       OBJECT-TYPE
        SYNTAX                  QosPolicyGroupEntry
        MAX-ACCESS              not-accessible
        STATUS                  current
        DESCRIPTION             "Entry for a QoS Policy Group."
        INDEX { IMPLIED qosPolicyGroupName }
        ::= { qosPolicyGroupTable 1 }

        QosPolicyGroupEntry ::=
        SEQUENCE {
            qosPolicyGroupUuid                  DisplayString,
            qosPolicyGroupName                  DisplayString,
            qosPolicyGroupPgid                  Counter32,
            qosPolicyGroupClass                 INTEGER,
            qosPolicyGroupMaxThroughput         DisplayString,
            qosPolicyGroupVserver               DisplayString,
	    qosPolicyGroupMinThroughput         DisplayString,
            qosPolicyGroupShared                Boolean,
            qosPolicyGroupAutoGenerated         Boolean
        }

        qosPolicyGroupUuid               OBJECT-TYPE
        SYNTAX                           DisplayString
        MAX-ACCESS                       read-only
        STATUS                           current
        DESCRIPTION
                      "Policy Group Uuid"
        ::= { qosPolicyGroupEntry  1 }


        qosPolicyGroupName               OBJECT-TYPE
        SYNTAX                           DisplayString
        MAX-ACCESS                       read-only
        STATUS                           current
        DESCRIPTION
                      "Policy Group Name"
        ::= { qosPolicyGroupEntry  2 }


        qosPolicyGroupPgid               OBJECT-TYPE
        SYNTAX                           Counter32
        MAX-ACCESS                       read-only
        STATUS                           current
        DESCRIPTION
                      "Policy Group ID"
        ::= { qosPolicyGroupEntry  3 }


        qosPolicyGroupClass              OBJECT-TYPE
        SYNTAX                           INTEGER {
                                                 preset(1),
                                                 user-defined(2),
                                                 system-defined(3)
                                         }
        MAX-ACCESS                       read-only
        STATUS                           current
        DESCRIPTION
                      "Policy Group Class"
        ::= { qosPolicyGroupEntry  4 }


        qosPolicyGroupMaxThroughput      OBJECT-TYPE
        SYNTAX                           DisplayString
        MAX-ACCESS                       read-only
        STATUS                           current
        DESCRIPTION
                      "Maximum Throughput"
        ::= { qosPolicyGroupEntry  5 }


        qosPolicyGroupVserver            OBJECT-TYPE
        SYNTAX                           DisplayString
        MAX-ACCESS                       read-only
        STATUS                           current
        DESCRIPTION
                      "Vserver that the QoS Policy Group belongs to"
        ::= { qosPolicyGroupEntry  6 }

        qosPolicyGroupMinThroughput      OBJECT-TYPE
        SYNTAX                           DisplayString
        MAX-ACCESS                       read-only
        STATUS                           current
        DESCRIPTION
                      "Minimum Throughput"
        ::= { qosPolicyGroupEntry  7 }

        qosPolicyGroupShared             OBJECT-TYPE
        SYNTAX                           Boolean
        MAX-ACCESS                       read-only
        STATUS                           current
        DESCRIPTION
                      "Whether or not the policy group is shared"
        ::= { qosPolicyGroupEntry  8 }

        qosPolicyGroupAutoGenerated      OBJECT-TYPE
        SYNTAX                           Boolean
        MAX-ACCESS                       read-only
        STATUS                           current
        DESCRIPTION
                      "Whether or not the policy group is auto-generated by ONTAP"
        ::= { qosPolicyGroupEntry  9 }

    --qos  Read Ahead
    qosReadaheadSettingsTable OBJECT-TYPE
    SYNTAX                  SEQUENCE OF QosReadaheadSettingsEntry
    MAX-ACCESS              not-accessible
    STATUS                  current
    DESCRIPTION
        "Table of QoS Read-Ahead Settings."
    ::= { qos 3 }

	qosReadaheadSettingsEntry OBJECT-TYPE
    SYNTAX                  QosReadaheadSettingsEntry
    MAX-ACCESS              not-accessible
    STATUS                  current
    DESCRIPTION
        "Entry for a Read-Ahead Setting."
	INDEX { IMPLIED qosReadaheadSettingName }
    ::= { qosReadaheadSettingsTable 1 }

    QosReadaheadSettingsEntry ::=
	SEQUENCE {
		qosReadaheadSettingName DisplayString,
			qosReadaheadClass		INTEGER,
			qosReadaheadDefault		Boolean,
			qosReadaheadMinBlocks	Integer32,
			qosReadaheadMaxBlocks	Integer32,
			qosReadaheadAlignBlocks	Integer32,
			qosReadaheadMaxGap		Integer32,
			qosReadaheadMaxRange	Integer32,
			qosReadaheadMinRange	Integer32,
			qosReadaheadMaxDeadline	Integer32,
			qosReadaheadInterarrivalWeight	Integer32,
			qosReadaheadDiskResponseWeight	Integer32,
			qosReadaheadMinDiskResponseTime	Integer32,
			qosReadaheadMaxDiskResponseTime	Integer32,
			qosReadaheadDiskResponseFactor	Integer32,
			qosReadaheadOvershoot	Integer32,
			qosReadaheadUseTiming	Boolean,
			qosReadaheadUseAsync	Boolean,
			qosReadaheadMetadata	Boolean,
			qosReadaheadForceDump	Boolean,
			qosReadaheadForceFull	Boolean,
			qosReadaheadForceNone	Boolean,
			qosReadaheadUseFeedback	Boolean,
			qosReadaheadSmallFileBlocks	Integer32,
			qosReadaheadMetadataBlocks	Integer32,
			qosReadaheadEarlyCount		Integer32,
			qosReadaheadJitter			Integer32,
			qosReadaheadMinRetireTime	Integer32,
			qosReadaheadMaxRetireTime	Integer32,
			qosReadaheadUseHistogram	Boolean,
			qosReadaheadMinFileHistogram	Integer32
	}

    qosReadaheadSettingName	OBJECT-TYPE
    SYNTAX					DisplayString
    MAX-ACCESS              read-only
    STATUS                  current
    DESCRIPTION
        "Readahead Setting Name."
    ::= { qosReadaheadSettingsEntry 1 }

	qosReadaheadClass		OBJECT-TYPE
	SYNTAX      			INTEGER {
	            			        preset(1),
	            			        user-defined(2),
	            			        system-defined(3)
	            			}
    MAX-ACCESS              read-only
    STATUS                  current
    DESCRIPTION
        "Readahead Setting Class."
    ::= { qosReadaheadSettingsEntry 2 }

    qosReadaheadDefault       OBJECT-TYPE
    SYNTAX                 	Boolean
    MAX-ACCESS              read-only
    STATUS                  current
    DESCRIPTION
        "Indicates if this is the default Read-Ahead Setting."
    ::= { qosReadaheadSettingsEntry 3 }


    qosReadaheadMinBlocks       OBJECT-TYPE
    SYNTAX                  Integer32 (64..1024)
    MAX-ACCESS              read-only
    STATUS                  current
    DESCRIPTION
        "Minimum Blocks to Speculate."
    ::= { qosReadaheadSettingsEntry 4 }

    qosReadaheadMaxBlocks       OBJECT-TYPE
    SYNTAX                  Integer32 (64..1024)
    MAX-ACCESS              read-only
    STATUS                  current
    DESCRIPTION
        "Maximum Blocks to Speculate."
    ::= { qosReadaheadSettingsEntry 5 }

    qosReadaheadAlignBlocks       OBJECT-TYPE
    SYNTAX                  Integer32 (8..256)
    MAX-ACCESS              read-only
    STATUS                  current
    DESCRIPTION
        "Block Alignment."
    ::= { qosReadaheadSettingsEntry 6 }

    qosReadaheadMaxGap       OBJECT-TYPE
    SYNTAX                  Integer32 (512..4096)
    MAX-ACCESS              read-only
    STATUS                  current
    DESCRIPTION
        "Maximum Speculative Blocks Outstanding."
    ::= { qosReadaheadSettingsEntry 7 }

    qosReadaheadMaxRange       OBJECT-TYPE
    SYNTAX                  Integer32 (1024..40960)
    MAX-ACCESS              read-only
    STATUS                  current
    DESCRIPTION
        "Maximum Range Used When Aging Streams (Blocks."
    ::= { qosReadaheadSettingsEntry 8 }

    qosReadaheadMinRange       OBJECT-TYPE
    SYNTAX                  Integer32 (1024..40960)
    MAX-ACCESS              read-only
    STATUS                  current
    DESCRIPTION
        "Minimum Range Used When Aging Streams (Blocks)."
    ::= { qosReadaheadSettingsEntry 9 }

    qosReadaheadMaxDeadline       OBJECT-TYPE
    SYNTAX                  Integer32 (100000..5000000)
    MAX-ACCESS              read-only
    STATUS                  current
    DESCRIPTION
        "Maximum Deadline Offset (ms)."
    ::= { qosReadaheadSettingsEntry 10 }

    qosReadaheadInterarrivalWeight       OBJECT-TYPE
    SYNTAX                  Integer32 (0..100)
    MAX-ACCESS              read-only
    STATUS                  current
    DESCRIPTION
        "Weight for Interarrival Time Aging (%)."
    ::= { qosReadaheadSettingsEntry 11 }

    qosReadaheadDiskResponseWeight       OBJECT-TYPE
    SYNTAX                  Integer32 (0..100)
    MAX-ACCESS              read-only
    STATUS                  current
    DESCRIPTION
        "Weight for Disk Response Time Aging (%)."
    ::= { qosReadaheadSettingsEntry 12 }

    qosReadaheadMinDiskResponseTime       OBJECT-TYPE
    SYNTAX                  Integer32 (100..50000)
    MAX-ACCESS              read-only
    STATUS                  current
    DESCRIPTION
        "Minimum Disk Response Time (ms)."
    ::= { qosReadaheadSettingsEntry 13 }

    qosReadaheadMaxDiskResponseTime       OBJECT-TYPE
    SYNTAX                  Integer32 (100..50000)
    MAX-ACCESS              read-only
    STATUS                  current
    DESCRIPTION
        "Maximum Disk Response Time (ms).."
    ::= { qosReadaheadSettingsEntry 14 }

    qosReadaheadDiskResponseFactor	OBJECT-TYPE
    SYNTAX                  Integer32 (1..10)
    MAX-ACCESS              read-only
    STATUS                  current
    DESCRIPTION
        "Disk Response Time Factor."
    ::= { qosReadaheadSettingsEntry 15 }

    qosReadaheadOvershoot			OBJECT-TYPE
    SYNTAX                  Integer32 (0..500)
    MAX-ACCESS              read-only
    STATUS                  current
    DESCRIPTION
        "Allowable Overshoot (%)."
    ::= { qosReadaheadSettingsEntry 16 }

    qosReadaheadUseTiming            OBJECT-TYPE
    SYNTAX                 	Boolean
    MAX-ACCESS              read-only
    STATUS                  current
    DESCRIPTION
        "Use Timing Algorithms."
    ::= { qosReadaheadSettingsEntry 17 }

    qosReadaheadUseAsync            OBJECT-TYPE
    SYNTAX                 	Boolean
    MAX-ACCESS              read-only
    STATUS                  current
    DESCRIPTION
        "Use Asynchronous Speculation."
    ::= { qosReadaheadSettingsEntry 18 }

    qosReadaheadMetadata            OBJECT-TYPE
    SYNTAX                  Boolean
    MAX-ACCESS              read-only
    STATUS                  current
    DESCRIPTION
        "Do Metadata Speculation."
    ::= { qosReadaheadSettingsEntry 19 }


    qosReadaheadForceDump            OBJECT-TYPE
    SYNTAX                 	Boolean
    MAX-ACCESS              read-only
    STATUS                  current
    DESCRIPTION
        "Force DUMP-Style Readahead."
    ::= { qosReadaheadSettingsEntry 20 }


    qosReadaheadForceFull            OBJECT-TYPE
    SYNTAX                 	Boolean
    MAX-ACCESS              read-only
    STATUS                  current
    DESCRIPTION
        "Force Full-File Readahead."
    ::= { qosReadaheadSettingsEntry 21 }


    qosReadaheadForceNone            OBJECT-TYPE
    SYNTAX                 	Boolean
    MAX-ACCESS              read-only
    STATUS                  current
    DESCRIPTION
        "Disable Readahead."
    ::= { qosReadaheadSettingsEntry 22 }


    qosReadaheadUseFeedback            OBJECT-TYPE
    SYNTAX                 	Boolean
    MAX-ACCESS              read-only
    STATUS                  current
    DESCRIPTION
        "Provide Cache-Miss Feedback."
    ::= { qosReadaheadSettingsEntry 23 }


    qosReadaheadSmallFileBlocks            OBJECT-TYPE
    SYNTAX                  Integer32 (0..128)
    MAX-ACCESS              read-only
    STATUS                  current
    DESCRIPTION
        "Maximum Blocks for Small-File Handling."
    ::= { qosReadaheadSettingsEntry 24 }


    qosReadaheadMetadataBlocks            OBJECT-TYPE
    SYNTAX                  Integer32 (0..2048)
    MAX-ACCESS              read-only
    STATUS                  current
    DESCRIPTION
        "Minimum Blocks for Which Metadata is Predicted."
    ::= { qosReadaheadSettingsEntry 25 }


    qosReadaheadEarlyCount            OBJECT-TYPE
    SYNTAX                  Integer32 (0..1024)
    MAX-ACCESS              read-only
    STATUS                  current
    DESCRIPTION
        "Number of IO Operations Cautiously Predicted."
    ::= { qosReadaheadSettingsEntry 26 }


	qosReadaheadJitter		OBJECT-TYPE
	SYNTAX					Integer32 (0..100)
	MAX-ACCESS              read-only
	STATUS                  current
	DESCRIPTION
		"Threshold for Detecting Jitter (%)."
	::= { qosReadaheadSettingsEntry 27 }

	qosReadaheadMinRetireTime		OBJECT-TYPE
	SYNTAX					Integer32 (10000..10000000)
	MAX-ACCESS		read-only
	STATUS			current
	DESCRIPTION
		"Minimum Time Before a Stream is Retired (us)"
	::= { qosReadaheadSettingsEntry 28 }

	qosReadaheadMaxRetireTime		OBJECT-TYPE
	SYNTAX					Integer32 (10000..10000000)
	MAX-ACCESS		read-only
	STATUS			current
	DESCRIPTION
		"Maximum Time Before a Stream is Retired (us)"
	::= { qosReadaheadSettingsEntry 29 }


	qosReadaheadUseHistogram		OBJECT-TYPE
	SYNTAX					Boolean
	MAX-ACCESS              read-only
	STATUS                  current
	DESCRIPTION
		"Use Histogram-based predictions."
	::= { qosReadaheadSettingsEntry 30 }

	qosReadaheadMinFileHistogram		OBJECT-TYPE
	SYNTAX					Integer32 (8192..33554432)
	MAX-ACCESS				read-only
	STATUS					current
	DESCRIPTION
		"Minimum filesize for Histogram-based predictions (blocks)"
	::= { qosReadaheadSettingsEntry 31 }


-- qos Adaptive Policy Group
        qosAdaptivePolicyGroupTable         OBJECT-TYPE
        SYNTAX                              SEQUENCE OF QosAdaptivePolicyGroupEntry
        MAX-ACCESS                          not-accessible
        STATUS                              current
        DESCRIPTION                         "QoS Adaptive Policy Group Table."
        ::= { qos 4 }

        qosAdaptivePolicyGroupEntry          OBJECT-TYPE
        SYNTAX                              QosAdaptivePolicyGroupEntry
        MAX-ACCESS                          not-accessible
        STATUS                              current
        DESCRIPTION                         "Entry for a QoS Adaptive Policy Group."
        INDEX { IMPLIED qosAdaptivePolicyGroupName }
        ::= { qosAdaptivePolicyGroupTable 1 }

        QosAdaptivePolicyGroupEntry ::=
        SEQUENCE {
            qosAdaptivePolicyGroupUuid                  DisplayString,
            qosAdaptivePolicyGroupName                  DisplayString,
            qosAdaptivePolicyGroupPgid                  Counter32,
            qosAdaptivePolicyGroupVserver               DisplayString,
            qosAdaptivePolicyGroupPeakIops              DisplayString,
            qosAdaptivePolicyGroupExpectedIops          DisplayString,
            qosAdaptivePolicyGroupAbsoluteMinIops       DisplayString,
            qosAdaptivePolicyGroupPeakIopsAllocation    INTEGER,
	    qosAdaptivePolicyGroupExpectedIopsAllocation INTEGER,
            qosAdaptivePolicyGroupBlockSize             INTEGER
        }

        qosAdaptivePolicyGroupUuid       OBJECT-TYPE
        SYNTAX                           DisplayString
        MAX-ACCESS                       read-only
        STATUS                           current
        DESCRIPTION
                      "Adaptive Policy Group Uuid"
        ::= { qosAdaptivePolicyGroupEntry  1 }


        qosAdaptivePolicyGroupName       OBJECT-TYPE
        SYNTAX                           DisplayString
        MAX-ACCESS                       read-only
        STATUS                           current
        DESCRIPTION
                      "Adaptive Policy Group Name"
        ::= { qosAdaptivePolicyGroupEntry  2 }


        qosAdaptivePolicyGroupPgid       OBJECT-TYPE
        SYNTAX                           Counter32
        MAX-ACCESS                       read-only
        STATUS                           current
        DESCRIPTION
                      "Adaptive Policy Group ID"
        ::= { qosAdaptivePolicyGroupEntry  3 }


        qosAdaptivePolicyGroupVserver    OBJECT-TYPE
        SYNTAX                           DisplayString
        MAX-ACCESS                       read-only
        STATUS                           current
        DESCRIPTION
                      "Vserver that the QoS Adaptive Policy Group belongs to"
        ::= { qosAdaptivePolicyGroupEntry  4 }

        qosAdaptivePolicyGroupPeakIops   OBJECT-TYPE
        SYNTAX                           DisplayString
        MAX-ACCESS                       read-only
        STATUS                           current
        DESCRIPTION
                      "Peak IOPS"
        ::= { qosAdaptivePolicyGroupEntry  5 }

        qosAdaptivePolicyGroupExpectedIops OBJECT-TYPE
        SYNTAX                           DisplayString
        MAX-ACCESS                       read-only
        STATUS                           current
        DESCRIPTION
                      "Expected IOPS"
        ::= { qosAdaptivePolicyGroupEntry  6 }

        qosAdaptivePolicyGroupAbsoluteMinIops OBJECT-TYPE
        SYNTAX                           DisplayString
        MAX-ACCESS                       read-only
        STATUS                           current
        DESCRIPTION
                      "Minimum IOPS"
        ::= { qosAdaptivePolicyGroupEntry  7 }

        qosAdaptivePolicyGroupPeakIopsAllocation OBJECT-TYPE
        SYNTAX                            INTEGER {
                                            allocated-space(0),
                                            used-space(1)
                                          }
        MAX-ACCESS                       read-only
        STATUS                           current
        DESCRIPTION
                      "Peak IOPS Allocation"
        ::= { qosAdaptivePolicyGroupEntry  8 }

        qosAdaptivePolicyGroupExpectedIopsAllocation  OBJECT-TYPE
        SYNTAX                            INTEGER {
                                            used-space(0),
                                            allocated-space(1)
                                          }
        MAX-ACCESS                       read-only
        STATUS                           current
        DESCRIPTION
                      "Expected IOPS Allocation"
        ::= { qosAdaptivePolicyGroupEntry  9 }

        qosAdaptivePolicyGroupBlockSize             OBJECT-TYPE
        SYNTAX                          INTEGER {
                                           any(0),
                                           size4K(1),
                                           size8K(2),
                                           size16K(3),
                                           size32K(4),
                                           size64K(5),
                                           size128K(6)
                                        }
        MAX-ACCESS                       read-only
        STATUS                           current
        DESCRIPTION
                      "Block Size"
        ::= { qosAdaptivePolicyGroupEntry  10 }


	-- -- -- -- -- -- -- -- -- -- -- -- -- -- -- -- -- --
	-- -- -- -- -- -- -- -- -- -- -- -- -- -- -- -- -- --
	-- NetApp trap definitions
	-- See RFC 1215 for instructions on building traps
	--
	-- All EnterpriseSpecific Traps of NetApp
	-- contain the OIDs 'productTrapData and productSerialNum'
	--
	-- The last digit of a trap contains information about the
	-- priority of the trap:
	--
	-- 1 emergency
	-- 2 alert
	-- 3 critical
	-- 4 error
	-- 5 warning
	-- 6 notification
	-- 7 information
	-- 8 debug
	--
	-- -- -- -- -- -- -- -- -- -- -- -- -- -- -- -- -- --
	-- -- -- -- -- -- -- -- -- -- -- -- -- -- -- -- -- --

	-- -- -- -- -- -- -- -- -- -- -- -- -- -- -- -- -- --
	--
	--  A generic, unprioritized, user-defined trap.  These
	--  are generated in releases prior to 5.4.
	--
	-- -- -- -- -- -- -- -- -- -- -- -- -- -- -- -- -- --

	userDefined                     NOTIFICATION-TYPE
	OBJECTS                         {productTrapData, productSerialNum}
	STATUS                          current
	DESCRIPTION
            "A polling-style trap built using the 'snmp traps'
	     command on the filer."

	::= { netapp 0 2 }

	-- -- -- -- -- -- -- -- -- -- -- -- -- -- -- -- -- --
        -- -- -- -- -- -- -- -- -- -- -- -- -- -- -- -- -- --
        -- Disk Health Monitor Notices for Disk Fault
        -- -- -- -- -- -- -- -- -- -- -- -- -- -- -- -- -- --
        -- -- -- -- -- -- -- -- -- -- -- -- -- -- -- -- -- --

        dhmNoticeDegradedIO             NOTIFICATION-TYPE
	OBJECTS                         {productTrapData, productSerialNum}
	STATUS                          current
        DESCRIPTION
                "Disk Health Monitor -
                Reported a Disk Degraded-I/O  Event"

        ::= { netapp 0 6 }

        dhmNoticePFAEvent               NOTIFICATION-TYPE
	OBJECTS                         {productTrapData, productSerialNum}
	STATUS                          current
        DESCRIPTION
                "Disk Health Monitor -
                Reported a Disk Predictive-Failure Event"

        ::= { netapp 0 7 }

	-- -- -- -- -- -- -- -- -- -- -- -- -- -- -- -- -- --
	--
	--  This section contains generic user-defined traps.
	--  All user-defined traps with the same priority
	--  use the trap for that priority level.
	--
	--  For example, all "critical" user-defined traps are
	--  sent with ID 13.  The string data sent with the
	--  trap identifies the specific critical event.
	--
	-- -- -- -- -- -- -- -- -- -- -- -- -- -- -- -- -- --

        emergencyTrap                   NOTIFICATION-TYPE
	OBJECTS                         {productTrapData, productSerialNum}
	STATUS                          current
        DESCRIPTION
            "A user-defined trap indicating an extremely urgent
             situation, usually indicating that the system has
             failed and is shutting down."

        ::= { netapp 0 11 }

        alertTrap                       NOTIFICATION-TYPE
	OBJECTS                         {productTrapData, productSerialNum}
	STATUS                          current
        DESCRIPTION
            "A user-defined trap indicating a condition that
             should be corrected immediately, such as a failed disk."

        ::= { netapp 0 12 }

        criticalTrap                    NOTIFICATION-TYPE
	OBJECTS                         {productTrapData, productSerialNum}
	STATUS                          current
        DESCRIPTION
            "A user-defined trap indicating a critical condition,
             such as a hard device error."

        ::= { netapp 0 13 }

        errorTrap                       NOTIFICATION-TYPE
	OBJECTS                         {productTrapData, productSerialNum}
	STATUS                          current
        DESCRIPTION
            "A user-defined trap indicating an error condition,
             such as a mistake in a configuration file."

        ::= { netapp 0 14 }

        warningTrap                     NOTIFICATION-TYPE
	OBJECTS                         {productTrapData, productSerialNum}
	STATUS                          current
        DESCRIPTION
            "A user-defined trap indicating a condition which
            is not an error, but which may require special handling."

        ::= { netapp 0 15 }

        notificationTrap                NOTIFICATION-TYPE
	OBJECTS                         {productTrapData, productSerialNum}
	STATUS                          current
        DESCRIPTION
            "A user-defined trap meant to provide notification,
             such as an hourly uptime message."

        ::= { netapp 0 16 }

        informationalTrap               NOTIFICATION-TYPE
	OBJECTS                         {productTrapData, productSerialNum}
	STATUS                          current
        DESCRIPTION
            "A user-defined trap used for informational purposes."

        ::= { netapp 0 17 }

        dbgTrap                         NOTIFICATION-TYPE
	OBJECTS                         {productTrapData, productSerialNum}
	STATUS                          current
        DESCRIPTION
            "A user-defined trap used for debugging purposes.
	     This trap was previously mis-documented as being trap
	     number 17, with the name debugTrap.  It has always,
	     actually, been trap 18.  The name change is to avoid
	     issues with environments that already have a record
	     for debugTrap."

        ::= { netapp 0 18 }

	-- -- -- -- -- -- -- -- -- -- -- -- -- -- -- -- -- --
	--
	--  Specific traps.
	--
	-- -- -- -- -- -- -- -- -- -- -- -- -- -- -- -- -- --


	diskFailedShutdown              NOTIFICATION-TYPE
	OBJECTS                         {productTrapData, productSerialNum}
	STATUS                          current
	DESCRIPTION
		"System is shutting down because the system has been
		running in degraded mode for 24 hours.
		The trap includes a string describing the failed disk."

	::= { netapp 0 21 }

	diskFailed                      NOTIFICATION-TYPE
	OBJECTS                         {productTrapData, productSerialNum}
	STATUS                          current
	DESCRIPTION
		"One or more disks failed.
		The trap includes a string describing the failed disk(s)."

	::= { netapp 0 22 }

	diskRepaired                    NOTIFICATION-TYPE
	OBJECTS                         {productTrapData, productSerialNum}
	STATUS                          current
	DESCRIPTION
		"The failed disks have been repaired.
		This trap is a placeholder -
		it is not currently sent by Data ONTAP."

	::= { netapp 0 26 }

	-- -- -- -- -- -- -- -- -- -- -- -- -- -- -- -- -- --
	--
	--  The fan and power supply traps are not supported
	--  on all platforms.
	--
	-- -- -- -- -- -- -- -- -- -- -- -- -- -- -- -- -- --

	fanFailureShutdown              NOTIFICATION-TYPE
	OBJECTS                         {productTrapData, productSerialNum}
	STATUS                          current
	DESCRIPTION
		"Critical chassis or cpu fans have failed and the system
		is shutting down."

	::= { netapp 0 31 }

	fanFailed                       NOTIFICATION-TYPE
	OBJECTS                         {productTrapData, productSerialNum}
	STATUS                          current
	DESCRIPTION
		"One or more chassis fans failed.
		The trap includes a string describing the failed fan(s)."

	::= { netapp 0 33 }

	fanWarning                      NOTIFICATION-TYPE
	OBJECTS                         {productTrapData, productSerialNum}
	STATUS                          current
	DESCRIPTION
		"One or more chassis or cpu fans are in warning state.
		The trap includes a string describing the fan(s) in
		the warning state."

	::= { netapp 0 35 }

	fanRepaired                     NOTIFICATION-TYPE
	OBJECTS                         {productTrapData, productSerialNum}
	STATUS                          current
	DESCRIPTION
		"All fans are repaired."

	::= { netapp 0 36 }

	powerSupplyFailureShutdown      NOTIFICATION-TYPE
	OBJECTS                         {productTrapData, productSerialNum}
	STATUS                          current
	DESCRIPTION
		"Critical power supplies or power rails failed and
		the system is shutting down."

	::= { netapp 0 41 }

	powerSupplyFailed               NOTIFICATION-TYPE
	OBJECTS                         {productTrapData, productSerialNum}
	STATUS                          current
	DESCRIPTION
		"One or more redundant power supplies failed.
		Include in the trap a string describing
		the failed power supply(ies)."

	::= { netapp 0 43 }

	powerSupplyWarning              NOTIFICATION-TYPE
	OBJECTS                         {productTrapData, productSerialNum}
	STATUS                          current
	DESCRIPTION
		"One or more power supplies or power rails in
		warning state.  Include in the trap a string describing
		the power supply(ies) or the power rail(s) in the
		warning state."

	::= { netapp 0 45 }

	powerSupplyRepaired             NOTIFICATION-TYPE
	OBJECTS                         {productTrapData, productSerialNum}
	STATUS                          current
	DESCRIPTION
		"Previously-failed power supplies or power rails have been
		repaired."

	::= { netapp 0 46 }

	cpuTooBusy                      NOTIFICATION-TYPE
	OBJECTS                         {productTrapData, productSerialNum}
	STATUS                          current
	DESCRIPTION
		"CPU utilization exceeds 90%.
		This trap is not enabled by default.
		To enable this trap set the registry
		entry options.monitor.cpu.enable to on.
		Note that as the threshold for this trap is
		checked once a minute it is possible to receive
		multiple instances of this trap in a short time."


	::= { netapp 0 55 }

	cpuOk                          NOTIFICATION-TYPE
	OBJECTS                         {productTrapData, productSerialNum}
	STATUS                          current
	DESCRIPTION
		"CPU utilization has dropped back below 90%."

	::= { netapp 0 56 }

	nvramBatteryDischarged          NOTIFICATION-TYPE
	OBJECTS                         {productTrapData, productSerialNum}
	STATUS                          current
	DESCRIPTION
		"The NVRAM battery is fully discharged."

	::= { netapp 0 62 }

	nvramBatteryLow                 NOTIFICATION-TYPE
	OBJECTS                         {productTrapData, productSerialNum}
	STATUS                          current
	DESCRIPTION
		"The charge in the NVRAM battery is low."

	::= { netapp 0 63 }

	clusterNodeFailed               NOTIFICATION-TYPE
	OBJECTS                         {productTrapData, productSerialNum}
	STATUS                          current
	DESCRIPTION
		"A node in a Cluster FailOver configuration failed.
		Its partner will assume service for the failed node."

	::= { netapp 0 72 }

	clusterNodeTakenOver            NOTIFICATION-TYPE
	OBJECTS                         {productTrapData, productSerialNum}
	STATUS                          current
	DESCRIPTION
		"The partner has taken over for a failed cluster node."

	::= { netapp 0 75 }

	clusterNodeRepaired             NOTIFICATION-TYPE
	OBJECTS                         {productTrapData, productSerialNum}
	STATUS                          current
	DESCRIPTION
		"A cluster node has resumed operation."

	::= { netapp 0 76 }

	clusterNodeRepairing            NOTIFICATION-TYPE
	OBJECTS                         {productTrapData, productSerialNum}
        STATUS                          current
	DESCRIPTION
		"A cluster node has rebooted, and a giveback has started."

	::= { netapp 0 77 }


	volumeFull                      NOTIFICATION-TYPE
	OBJECTS                         {productTrapData, productSerialNum}
	STATUS                          current
	DESCRIPTION
		"At least one volume is more than 98% full.
		The string sent with the trap gives the
		name of the volume or volumes which exceed
		the volumeFull or volumeNearlyFull thresholds"

	::= { netapp 0 82 }

	volumeNearlyFull                NOTIFICATION-TYPE
	OBJECTS                         {productTrapData, productSerialNum}
	STATUS                          current
	DESCRIPTION
		"At least one volume is more than 95% full.
		The string sent with the trap gives the
		name of the volume or volumes which exceed
		the volumeFull or volumeNearlyFull thresholds"

	::= { netapp 0 85 }

	volumeRepaired                  NOTIFICATION-TYPE
	OBJECTS                         {productTrapData, productSerialNum}
	STATUS                          current
	DESCRIPTION
		"All volumes are now under 95% full."

	::= { netapp 0 86 }

	volumesStillFull                NOTIFICATION-TYPE
	OBJECTS                         {productTrapData, productSerialNum}
	STATUS                          current
	DESCRIPTION
		"At least one volume that was full or nearly full is now OK,
		but more volumes still exceed the volumeNearlyFull or
		volumeFull thresholds. This trap is generally sent within
		a short time of when a volume becomes OK, though if two
		volumes become OK within this timeframe, only one trap is
		sent. The string sent with the trap gives the name of the
		volume or volumes which still exceed the volumeFull or
		volumeNearlyFull thresholds. It does not send the name of
		any volume that is OK."

	::= { netapp 0 87 }

	overTempShutdown                NOTIFICATION-TYPE
	OBJECTS                         {productTrapData, productSerialNum}
	STATUS                          current
	DESCRIPTION
		"System temperature is too high to continue
		operating.  The system is shutting down."

	::= { netapp 0 91 }

	overTemp                        NOTIFICATION-TYPE
	OBJECTS                         {productTrapData, productSerialNum}
	STATUS                          current
	DESCRIPTION
		"System temperature is too high and in the
		warning level."

	::= { netapp 0 95 }

	overTempRepaired                NOTIFICATION-TYPE
	OBJECTS                         {productTrapData, productSerialNum}
	STATUS                          current
	DESCRIPTION
		"System temperature has returned to an
		acceptable value."

	::= { netapp 0 96 }

	shelfFault                      NOTIFICATION-TYPE
	OBJECTS                         {productTrapData, productSerialNum}
	STATUS                          current
	DESCRIPTION
		"A disk storage shelf reported a fault, probably due
		to a problem with drive placement, fans, power,
		or temperature."

	::= { netapp 0 103 }

	shelfWarning                    NOTIFICATION-TYPE
	OBJECTS                         {productTrapData, productSerialNum}
	STATUS                          current
	DESCRIPTION
		"A disk storage shelf reported a warning, probably due
		to a problem with drive placement, fans, power,
		or temperature."

	::= { netapp 0 105 }

	shelfRepaired                   NOTIFICATION-TYPE
	OBJECTS                         {productTrapData, productSerialNum}
	STATUS                          current
	DESCRIPTION
		"A previously-reported shelf fault is now corrected."

	::= { netapp 0 106 }

	-- -- -- -- -- -- -- -- -- -- -- -- -- -- -- -- -- --
	--
	--  This section contains "general health" traps,
	--  based on changes to the miscGlobalStatus
	--  variable.
	--
	-- -- -- -- -- -- -- -- -- -- -- -- -- -- -- -- -- --

	globalStatusNonRecoverable      NOTIFICATION-TYPE
	OBJECTS                         {productTrapData, productSerialNum}
	STATUS                          current
	DESCRIPTION
		"The appliance's overall status changed to
		'nonRecoverable', indicating a problem so severe
		that the appliance is shutting down."

	::= { netapp 0 111 }

	globalStatusCritical            NOTIFICATION-TYPE
	OBJECTS                         {productTrapData, productSerialNum}
	STATUS                          current
	DESCRIPTION
		"The appliance's overall status changed to 'critical',
		indicating a problem that needs immediate attention."

	::= { netapp 0 113 }

	globalStatusNonCritical         NOTIFICATION-TYPE
	OBJECTS                         {productTrapData, productSerialNum}
	STATUS                          current
	DESCRIPTION
		"The appliance's overall status changed to 'nonCritical',
		indicating a problem that needs attention."

	::= { netapp 0 115 }

	globalStatusOk                  NOTIFICATION-TYPE
	OBJECTS                         {productTrapData, productSerialNum}
	STATUS                          current
	DESCRIPTION
		"The appliance's overall status returned to normal."

	::= { netapp 0 116 }

	-- -- -- -- -- -- -- -- -- -- -- -- -- -- -- -- -- --
	--
	--  This section contains traps related to soft quotas.
	--
	-- -- -- -- -- -- -- -- -- -- -- -- -- -- -- -- -- --

        softQuotaExceeded               NOTIFICATION-TYPE
	OBJECTS                         {productTrapData, productSerialNum}
	STATUS                          current
        DESCRIPTION
            "A user has exceeded their soft quota limit."

        ::= { netapp 0 126 }

        softQuotaNormal                 NOTIFICATION-TYPE
	OBJECTS                         {productTrapData, productSerialNum}
	STATUS                          current
        DESCRIPTION
            "A user is safely back under their soft quota limit."

        ::= { netapp 0 127 }

	-- -- -- -- -- -- -- -- -- -- -- -- -- -- -- -- -- --
	--
	--  This section contains traps related to auto support
	--
	-- -- -- -- -- -- -- -- -- -- -- -- -- -- -- -- -- --

	autosupportSendError            NOTIFICATION-TYPE
	OBJECTS                         {productTrapData, productSerialNum}
	STATUS                          current
	DESCRIPTION
		"Unable to send auto support.
		The trap includes a string describing the reason for the failure."

	::= { netapp 0 134 }

	autosupportConfigurationError   NOTIFICATION-TYPE
	OBJECTS                         {productTrapData, productSerialNum}
	STATUS                          deprecated
	DESCRIPTION
		"Auto support may be configured incorrectly.
		The trap includes a string describing the mis-configuration."

	::= { netapp 0 135 }

	autosupportSent                 NOTIFICATION-TYPE
	OBJECTS                         {productTrapData, productSerialNum}
	STATUS                          current
	DESCRIPTION
		"Auto support was sent successfully."

	::= { netapp 0 136 }

	-- -- -- -- -- -- -- -- -- -- -- -- -- -- -- -- -- --
	--
	--  This section contains traps related to UPS
	--
	-- -- -- -- -- -- -- -- -- -- -- -- -- -- -- -- -- --

	upsLinePowerOff                 NOTIFICATION-TYPE
	OBJECTS                         {productTrapData, productSerialNum}
	STATUS                          deprecated
	DESCRIPTION
		"UPS: Input line power has failed and UPS is now on battery."

	::= { netapp 0 142 }

	upsBatteryCritical              NOTIFICATION-TYPE
	OBJECTS                         {productTrapData, productSerialNum}
	STATUS                          deprecated
	DESCRIPTION
		"UPS: Battery is nearly exhausted, starting graceful shutdown."

	::= { netapp 0 143 }


	upsShuttingDown                 NOTIFICATION-TYPE
	OBJECTS                         {productTrapData, productSerialNum}
	STATUS                          deprecated
	DESCRIPTION
		"UPS: Shutting down now: Time left on battery is exhausted."

	::= { netapp 0 144 }
	upsBatteryWarning               NOTIFICATION-TYPE
	OBJECTS                         {productTrapData, productSerialNum}
	STATUS                          deprecated
	DESCRIPTION
		"UPS: Warning: Time left on battery is getting critical."

	::= { netapp 0 145 }

	upsLinePowerRestored            NOTIFICATION-TYPE
	OBJECTS                         {productTrapData, productSerialNum}
	STATUS                          current
	DESCRIPTION
		"UPS:  Input line power has been restored and UPS is now off battery."

	::= { netapp 0 146 }

	-- -- -- -- -- -- -- -- -- -- -- -- -- -- -- -- -- -- -- -- -- --
	--
	--  This section contains traps related to Client Side Applications.
	--
	-- -- -- -- -- -- -- -- -- -- -- -- -- -- -- -- -- -- -- -- -- --

	appEmergency                    NOTIFICATION-TYPE
	OBJECTS                         {productTrapData, productSerialNum}
	STATUS                          current
	DESCRIPTION
		"The application encountered an extremely urgent
		situation and requires an immediate response."

	::= { netapp 0 151 }

	appAlert                        NOTIFICATION-TYPE
	OBJECTS                         {productTrapData, productSerialNum}
	STATUS                          current
	DESCRIPTION
		"The application is in a condition that should
		be corrected immediately."

	::= { netapp 0 152 }

	appCritical                     NOTIFICATION-TYPE
	OBJECTS                         {productTrapData, productSerialNum}
	STATUS                          current
	DESCRIPTION
		"The application encountered a critical condition."

	::= { netapp 0 153 }

	appError                        NOTIFICATION-TYPE
	OBJECTS                         {productTrapData, productSerialNum}
	STATUS                          current
	DESCRIPTION
		"The application encountered an error condition."

	::= { netapp 0 154 }

	appWarning                      NOTIFICATION-TYPE
	OBJECTS                         {productTrapData, productSerialNum}
	STATUS                          current
	DESCRIPTION
		"The application is in a condition which is not an
		error, but which may require special handling."

        ::= { netapp 0 155 }

	appNotice                       NOTIFICATION-TYPE
	OBJECTS                         {productTrapData, productSerialNum}
	STATUS                          current
	DESCRIPTION
		"The application is notifying of a certain event."

        ::= { netapp 0 156 }

	appInfo                         NOTIFICATION-TYPE
	OBJECTS                         {productTrapData, productSerialNum}
	STATUS                          current
	DESCRIPTION
		"The application's message is meant for informational
		purposes."

        ::= { netapp 0 157 }

	appTrap                         NOTIFICATION-TYPE
	OBJECTS                         {productTrapData, productSerialNum}
	STATUS                          current
	DESCRIPTION
		"The application requires to be debugged."

        ::= { netapp 0 158 }

	-- -- -- -- -- -- -- -- -- -- -- -- -- -- -- -- -- -- -- -- -- --
	--
	--  This section contains traps related to auto saving NT EVT files.
	--
	-- -- -- -- -- -- -- -- -- -- -- -- -- -- -- -- -- -- -- -- -- --

	alfFilewrap                     NOTIFICATION-TYPE
	OBJECTS                         {productTrapData, productSerialNum}
	STATUS                          current
	DESCRIPTION
		"The internal audit file has wrapped. You are currently losing event
		records.  Warning the user."

        ::= { netapp 0 162 }


	alfFileSaved                    NOTIFICATION-TYPE
	OBJECTS                         {productTrapData, productSerialNum}
	STATUS                          current
	DESCRIPTION
		"The internal audit log has been auto saved to an external evt file.
		Notifying the user."

        ::= { netapp 0 166 }

	alfFileNearlyFull               NOTIFICATION-TYPE
	OBJECTS                         {productTrapData, productSerialNum}
	STATUS                          current
	DESCRIPTION
		"The internal audit log file is nearly full. The file is going to
		wrap. Notifying the user."

        ::= { netapp 0 167 }

	-- -- -- -- -- -- -- -- -- -- -- -- -- -- -- -- -- -- -- -- -- --
	--
	--  This section contains traps related to generalized quota events.
	--
	-- -- -- -- -- -- -- -- -- -- -- -- -- -- -- -- -- -- -- -- -- --

        quotaExceeded                   NOTIFICATION-TYPE
	OBJECTS                         {productTrapData, productSerialNum}
	STATUS                          current
        DESCRIPTION
            "One of the quota limits has been exceeded.
	    The trap includes a string describing the specific event
	    which triggered the trap.  The string is structured
	    in the following form:

		Quota Event: status=exceeded, type={hard|soft|threshold},
		user={username}, volume={volume}, limit_item={files|disk},
		limit_value={#files|#kilobytes}
		[ , treeid={tree-id} ] [ , vfiler={vfiler} ]

	    An example of a complete message would be:

		Quota Event: status=exceeded, type=soft,
		user=admin, volume=vol1, limit_item=disk, limit_value=1000000,
		treeid=8

	    Additional key=value items may, in the future, be appended
	    to this message."

        ::= { netapp 0 176 }

        quotaNormal                     NOTIFICATION-TYPE
	OBJECTS                         {productTrapData, productSerialNum}
	STATUS                          current
        DESCRIPTION
            "One of the quota limits has gone back down to a normal level.
	    The trap includes a string describing the specific event
	    which triggered the trap.  The string is structured
	    in the following form:

		Quota Event: status=normal, type={hard|soft|threshold},
		user={username}, volume={volume}, limit_item={files|disk},
		limit_value={#files|#kilobytes}
		[ , treeid={tree-id} ] [ , vfiler={vfiler} ]

	    An example of a complete message would be:

		Quota Event: status=normal, type=soft,
		user=admin, volume=vol1, limit_item=disk, limit_value=1000000,
		treeid=8

	    Additional key=value items may, in the future, be appended
	    to this message."

        ::= { netapp 0 177 }

        -- -- -- -- -- -- -- -- -- -- -- -- -- -- -- -- -- -- -- -- -- --
	--
	--  This section contains traps related to alerting when 64MB directory
	--  limit is nearly reached or has been reached.
	--
	-- -- -- -- -- -- -- -- -- -- -- -- -- -- -- -- -- -- -- -- -- --

	waflDirFull                     NOTIFICATION-TYPE
	OBJECTS                         {productTrapData, productSerialNum}
	STATUS                          current
	DESCRIPTION
		"The directory has been filled to its limit"

        ::= { netapp 0 187 }

	-- -- -- -- -- -- -- -- -- -- -- -- -- -- -- -- -- -- -- -- -- -- -- --
	--
	--  This section contains traps related to Correctable Memory ECC
	--  errors
	--
	-- -- -- -- -- -- -- -- -- -- -- -- -- -- -- -- -- -- -- -- -- -- -- --

	eccSummary                      NOTIFICATION-TYPE
	OBJECTS                         {productTrapData, productSerialNum}
	STATUS                          current
	DESCRIPTION
		"Memory ECC: number of new correctable ECC errors"

	::= { netapp 0 192 }

	eccMasked                       NOTIFICATION-TYPE
	OBJECTS                         {productTrapData, productSerialNum}
	STATUS                          current
	DESCRIPTION
		"Memory ECC: High frequency of ECC errors"

	::= { netapp 0 195 }

       	-- -- -- -- -- -- -- -- -- -- -- -- -- -- -- -- -- -- -- -- -- --
	--
	--  This section contains traps related to ftpd service
	--
	-- -- -- -- -- -- -- -- -- -- -- -- -- -- -- -- -- -- -- -- -- --

	ftpdError                       NOTIFICATION-TYPE
	OBJECTS                         {productTrapData, productSerialNum}
	STATUS                          current
	DESCRIPTION
		"Ftp daemon: service stopped"

        ::= { netapp 0 204 }

	ftpdMaxConnNotice               NOTIFICATION-TYPE
	OBJECTS                         {productTrapData, productSerialNum}
	STATUS                          current
	DESCRIPTION
		"Ftp daemon: number of connections hits maximum number"

        ::= { netapp 0 206 }

       	-- -- -- -- -- -- -- -- -- -- -- -- -- -- -- -- -- -- -- -- -- --
	--
	--  This section contains additional traps related to ftpd service
	--
	-- -- -- -- -- -- -- -- -- -- -- -- -- -- -- -- -- -- -- -- -- --

	ftpdMaxConnThresholdNotice      NOTIFICATION-TYPE
	OBJECTS                         {productTrapData, productSerialNum}
	STATUS                          current
	DESCRIPTION
		"Ftp daemon: number of connections nearly hits maximum number"

        ::= { netapp 0 216 }

	-- -- -- -- -- -- -- -- -- -- -- -- -- -- -- -- -- -- -- -- -- -- -- --
	--
	--  This section contains traps related to SCSI Target
	--
	-- -- -- -- -- -- -- -- -- -- -- -- -- -- -- -- -- -- -- -- -- -- -- --

	scsitgtFCPLinkBreak             NOTIFICATION-TYPE
	OBJECTS                         {productTrapData, productSerialNum}
	STATUS                          current
	DESCRIPTION
		"SCSI Target: Link Break on FCP adapter"

	::= { netapp 0 222 }

	scsitgtPartnerPathMisconfigured NOTIFICATION-TYPE
	OBJECTS                         {productTrapData, productSerialNum}
	STATUS                          current
	DESCRIPTION
		"SCSI Target: FCP Partner Path Misconfigured"

	::= { netapp 0 224 }

	scsitgtThrottleNotice           NOTIFICATION-TYPE
	OBJECTS                         {productTrapData, productSerialNum}
	STATUS                          current
	DESCRIPTION
		"SCSI Target: Throttle limit event notification"

	::= { netapp 0 226 }

	-- -- -- -- -- -- -- -- -- -- -- -- -- -- -- -- -- -- -- -- -- -- -- --
	--
	--  This section contains traps related to VIF Failover & Link Status
	--
	-- -- -- -- -- -- -- -- -- -- -- -- -- -- -- -- -- -- -- -- -- -- -- --

	vifPrimaryLinkFailed            NOTIFICATION-TYPE
	OBJECTS                         {productTrapData, productSerialNum}
	STATUS                          deprecated
	DESCRIPTION
		"Vif: The primary Interface on a Single mode vif has failed"

	::= { netapp 0 237 }

	vifAllLinksFailed               NOTIFICATION-TYPE
	OBJECTS                         {productTrapData, productSerialNum}
	STATUS                          deprecated
	DESCRIPTION
		"Vif: All the links of the vif have failed"

	::= { netapp 0 238 }

	-- -- -- -- -- -- -- -- -- -- -- -- -- -- -- -- -- -- -- -- -- -- -- --
	--
	--  This section contains traps related to Vfiler status
	--
	-- -- -- -- -- -- -- -- -- -- -- -- -- -- -- -- -- -- -- -- -- -- -- --

        vfStopped                       NOTIFICATION-TYPE
	OBJECTS                         {productTrapData, productSerialNum}
	STATUS                          current
        DESCRIPTION
		"A vFiler has stopped."

	::= { netapp 0 245 }

        vfStarted                       NOTIFICATION-TYPE
	OBJECTS                         {productTrapData, productSerialNum}
	STATUS                          current
        DESCRIPTION
		"A vFiler has started."

	::= { netapp 0 246 }

	-- -- -- -- -- -- -- -- -- -- -- -- -- -- -- -- -- -- -- -- -- -- -- --
	--
	--  This section contains traps related to Virus Scanning
	--
	-- -- -- -- -- -- -- -- -- -- -- -- -- -- -- -- -- -- -- -- -- -- -- --

	vscanVirusDetectedError         NOTIFICATION-TYPE
	OBJECTS                         {productTrapData, productSerialNum}
	STATUS                          current
	DESCRIPTION
		"VScan: A virus scanner has detected a virus on the Filer"

	::= { netapp 0 254 }

	vscanDisConnection              NOTIFICATION-TYPE
	OBJECTS                         {productTrapData, productSerialNum}
	STATUS                          current
	DESCRIPTION
		"VScan: A virus scanner has dropped its connection from the Filer"

	::= { netapp 0 255 }

	vscanConfigurationChange        NOTIFICATION-TYPE
	OBJECTS                         {productTrapData, productSerialNum}
	STATUS                          current
	DESCRIPTION
		"VScan: There has been a change to the vscan configuration"
	::= { netapp 0 256 }

	vscanConnection                 NOTIFICATION-TYPE
	OBJECTS                         {productTrapData, productSerialNum}
	STATUS                          current
	DESCRIPTION
		"VScan: A virus scanner has made a connection to the Filer"

	::= { netapp 0 257 }
	-- -- -- -- -- -- -- -- -- -- -- -- -- -- -- -- -- -- -- -- -- -- -- --
	--
	--  This section contains additional traps related to Virus Scanning
	--
	-- -- -- -- -- -- -- -- -- -- -- -- -- -- -- -- -- -- -- -- -- -- -- --

	vscanServerUpgrade              NOTIFICATION-TYPE
	OBJECTS                         {productTrapData, productSerialNum}
	STATUS                          current
	DESCRIPTION
		"VScan: The Vscan server has been upgraded"

	::= { netapp 0 266 }

        -- -- -- -- -- -- -- -- -- -- -- -- -- -- -- -- -- -- -- -- -- -- -- -
	--
	--  This section contains traps related to volume status being offline,
	--  online or restricted
	--
	-- -- -- -- -- -- -- -- -- -- -- -- -- -- -- -- -- -- -- -- -- -- -- -

	volumeRestrictedByMirrorBigIo   NOTIFICATION-TYPE
	OBJECTS                         {productTrapData, productSerialNum}
	STATUS                          current
	DESCRIPTION
		"A volume that experienced a medium error during reconstruction
		is restricted and marked wafl-inconsistent, but starting
		wafliron has failed. This trap is issued to alert operator
		that a volume is not accessible and wafliron must be started
		to allow access to it."

	::= { netapp 0 272 }

	volumeInconsistentUmount        NOTIFICATION-TYPE
	OBJECTS                         {productTrapData, productSerialNum}
	STATUS                          current
	DESCRIPTION
		"This trap is issued when we unmount a volume due to an
		inconsistency."

	::= { netapp 0 274 }

	volumeStateChanged              NOTIFICATION-TYPE
	OBJECTS                         {productTrapData, productSerialNum}
	STATUS                          current
	DESCRIPTION
		"Volume is being taken offline or being restricted.
		The string sent with trap specifies name of affected volume
		and its state."

	::= { netapp 0 275 }

	volumeOnline                    NOTIFICATION-TYPE
	OBJECTS                         {productTrapData, productSerialNum}
	STATUS                          current
	DESCRIPTION
		"Volume is online now. The string sent with trap specifies
		name of volume which is online now."

	::= { netapp 0 276 }

	-- -- -- -- -- -- -- -- -- -- -- -- -- -- -- -- -- -- -- -- -- -- -- -
	--
	--  This section contains traps related to remote management
	--  controller (RMC) card status
	--
	-- -- -- -- -- -- -- -- -- -- -- -- -- -- -- -- -- -- -- -- -- -- -- -

	rmcCardNeedsReplacement         NOTIFICATION-TYPE
	OBJECTS                         {productTrapData, productSerialNum}
	STATUS                          current
	DESCRIPTION
		"Remote Management Controller card needs replacement. The trap
		includes a string specifying the reason for replacement"

	::= { netapp 0 283 }

	rmcCardMissingCables            NOTIFICATION-TYPE
	OBJECTS                         {productTrapData, productSerialNum}
	STATUS                          current
	DESCRIPTION
		"Remote Management Controller card is missing its internal
		cable, or LAN cable or power supply cable. The trap includes
		a string specifying the missing component."

	::= { netapp 0 284 }

        -- -- -- -- -- -- -- -- -- -- -- -- -- -- -- -- -- -- -- -- -- -- -- -
	--
	--  This section contains traps related to remote volume
	--
	-- -- -- -- -- -- -- -- -- -- -- -- -- -- -- -- -- -- -- -- -- -- -- -

	volumeRemoteUnreachable         NOTIFICATION-TYPE
	OBJECTS                         {productTrapData, productSerialNum}
	STATUS                          current
	DESCRIPTION
		"Local volume encountered an error while communicating
		to remote volume."

	::= { netapp 0 294 }

	volumeRemoteOk                  NOTIFICATION-TYPE
	OBJECTS                         {productTrapData, productSerialNum}
	STATUS                          current
	DESCRIPTION
		"The communication between remote volume and local volume
		returned to normal."

	::= { netapp 0 296 }

	volumeRemoteRestored            NOTIFICATION-TYPE
	OBJECTS                         {productTrapData, productSerialNum}
	STATUS                          current
	DESCRIPTION
		"The data on remote volume has been fully restored to local
		volume."

	::= { netapp 0 297 }

	volumeRemoteRestoreBegin        NOTIFICATION-TYPE
	OBJECTS                         {productTrapData, productSerialNum}
	STATUS                          current
	DESCRIPTION
		"The data on remote volume has started being restored to local
		volume by Restore-on-Demand."

	::= { netapp 0 298 }

	-- -- -- -- -- -- -- -- -- -- -- -- -- -- -- -- -- -- -- -- -- -- -- -
	--
	--  This section contains more traps related to volume status being
	--  offline, online or restricted
	--
	-- -- -- -- -- -- -- -- -- -- -- -- -- -- -- -- -- -- -- -- -- -- -- -

	volumeRestrictedRootConflict    NOTIFICATION-TYPE
	OBJECTS                         {productTrapData, productSerialNum}
	STATUS                          current
	DESCRIPTION
		"Volume is restricted due to a root volume conflict. The
		string sent with trap specifies name of conflicting volume
		which is being restricted."

	::= { netapp 0 304 }

	volumeOfflineTooBig             NOTIFICATION-TYPE
	OBJECTS                         {productTrapData, productSerialNum}
	STATUS                          current
	DESCRIPTION
		"Volume cannot be brought online because its raw size is
		larger than maximum allowed size. The string sent with trap
		specifies name of affected volume and its raw size, and
		maximum allowed size."

	::= { netapp 0 314 }

	volumeOffline                   NOTIFICATION-TYPE
	OBJECTS                         {productTrapData, productSerialNum}
	STATUS                          current
	DESCRIPTION
		"Volume is being taken offline. The string sent with trap
		specifies name of affected volume and reason for being
		taken offline."

	::= { netapp 0 324 }

	volumeRestricted                NOTIFICATION-TYPE
	OBJECTS                         {productTrapData, productSerialNum}
	STATUS                          current
	DESCRIPTION
		"Volume is being restricted. The string sent with trap
		specifies name of affected volume and reason for being
		restricted."

	::= { netapp 0 334 }

	volumeDegradedDirty             NOTIFICATION-TYPE
	OBJECTS                         {productTrapData, productSerialNum}
	STATUS                          current
	DESCRIPTION
		"Volume is degraded and has dirty parity. WAFL_check must be
		run on this volume before it can be brought online. The string
		sent with trap specifies name of affected volume."

	::= { netapp 0 344 }

	volumeError                     NOTIFICATION-TYPE
	OBJECTS                         {productTrapData, productSerialNum}
	STATUS                          current
	DESCRIPTION
		"This trap is issued when a volume cannot be brought online
		due to an error.  The string sent with trap specifies name of
		affected volume and error description."

	::= { netapp 0 354 }

	volumeSelectedRootConflict      NOTIFICATION-TYPE
	OBJECTS                         {productTrapData, productSerialNum}
	STATUS                          current
	DESCRIPTION
		"This trap is issued when multiple root volumes are detected
		at boot time and one is selected as the root by default. The
		string sent with the trap specifies the name of the selected
		volume and the reason."

	::= { netapp 0 356 }

	-- -- -- -- -- -- -- -- -- -- -- -- -- -- -- -- -- -- -- -- -- -- -- -
	--
	--  This section contains traps related to synchronous SnapMirror
	--
	-- -- -- -- -- -- -- -- -- -- -- -- -- -- -- -- -- -- -- -- -- -- -- -
	snapmirrorSyncFailed            NOTIFICATION-TYPE
	OBJECTS                         {productTrapData, productSerialNum}
	STATUS                          current
	DESCRIPTION
	        "Synchronous SnapMirror failed and went into asynchronous mode."
        ::= { netapp 0 364 }

	snapmirrorSyncOk                NOTIFICATION-TYPE
	OBJECTS                         {productTrapData, productSerialNum}
	STATUS                          current
	DESCRIPTION
	        "Synchronous SnapMirror went into synchronous mode."
        ::= { netapp 0 366 }

	-- -- -- -- -- -- -- -- -- -- -- -- -- -- -- -- -- -- -- -- -- -- -- -
	--
	--  New environmental traps
	--
	--  A series of new environmental traps are constructed
	--  to disambiguate many of the older traps (which are antiquated
	--  but remain until they are completely removed from EMS usage).
	--
	-- -- -- -- -- -- -- -- -- -- -- -- -- -- -- -- -- -- -- -- -- -- -- -

	-- -- -- -- -- -- -- -- -- -- -- -- -- -- -- -- -- -- -- -- -- -- -- -
	-- Chassis Temperature
	-- -- -- -- -- -- -- -- -- -- -- -- -- -- -- -- -- -- -- -- -- -- -- -

	chassisTemperatureShutdown      NOTIFICATION-TYPE
	OBJECTS                         {productTrapData, productSerialNum}
	STATUS                          current
	DESCRIPTION
		"The chassis temperature is extreme.  The appliance has
		initiated a shutdown to protect itself.  The operating
		environment should be monitored and corrected before
		restarting the appliance."

	::= { netapp 0 371 }

	chassisTemperatureWarning       NOTIFICATION-TYPE
	OBJECTS                         {productTrapData, productSerialNum}
	STATUS                          current
	DESCRIPTION
		"The chassis temperature is either too high or too low.
		The temperature should be monitored and, if possible, corrected."

	::= { netapp 0 372 }

	chassisTemperatureUnknown       NOTIFICATION-TYPE
	OBJECTS                         {productTrapData, productSerialNum}
	STATUS                          current
	DESCRIPTION
		"The chassis temperature is unknown, because reading can't be
		obtained from the chassis temperature sensor."

	::= { netapp 0 375 }

	chassisTemperatureOk            NOTIFICATION-TYPE
	OBJECTS                         {productTrapData, productSerialNum}
	STATUS                          current
	DESCRIPTION
		"The chassis temperature is OK."

	::= { netapp 0 376 }

	-- -- -- -- -- -- -- -- -- -- -- -- -- -- -- -- -- -- -- -- -- -- -- -
	-- CPU Fans
	-- -- -- -- -- -- -- -- -- -- -- -- -- -- -- -- -- -- -- -- -- -- -- -

	chassisCPUFanStopped            NOTIFICATION-TYPE
	OBJECTS                         {productTrapData, productSerialNum}
	STATUS                          current
	DESCRIPTION
		"One or more CPU fans have stopped.  The appliance
		has initiated a shutdown to protect itself.  A new
		motherboard may be required to correct the fan.
		Contact customer support for direction."

	::= { netapp 0 381 }

	chassisCPUFanSlow               NOTIFICATION-TYPE
	OBJECTS                         {productTrapData, productSerialNum}
	STATUS                          current
	DESCRIPTION
		"A CPU fan is spinning too slowly.  A new motherboard
		may be required to correct the fan.  Contact customer
		support for direction."

	::= { netapp 0 383 }

	chassisCPUFanOk                 NOTIFICATION-TYPE
	OBJECTS                         {productTrapData, productSerialNum}
	STATUS                          current
	DESCRIPTION
		"All CPU fan(s) are properly functioning."

	::= { netapp 0 386 }

	-- -- -- -- -- -- -- -- -- -- -- -- -- -- -- -- -- -- -- -- -- -- -- -
	-- Power Supplies
	-- -- -- -- -- -- -- -- -- -- -- -- -- -- -- -- -- -- -- -- -- -- -- -

	chassisPowerSuppliesFailed      NOTIFICATION-TYPE
	OBJECTS                         {productTrapData, productSerialNum}
	STATUS                          current
	DESCRIPTION
		"Multiple chassis power supplies failed."

	::= { netapp 0 391 }

	chassisPowerSupplyDegraded      NOTIFICATION-TYPE
	OBJECTS                         {productTrapData, productSerialNum}
	STATUS                          current
	DESCRIPTION
		"One or more chassis power supplies are degraded.
		A description of the degraded state has been
		logged to the console and message log file."

	::= { netapp 0 392 }

	chassisPowerSupplyFailed        NOTIFICATION-TYPE
	OBJECTS                         {productTrapData, productSerialNum}
	STATUS                          current
	DESCRIPTION
		"One chassis power supply failed."

	::= { netapp 0 393 }

	chassisPowerSupplyRemoved       NOTIFICATION-TYPE
	OBJECTS                         {productTrapData, productSerialNum}
	STATUS                          current
	DESCRIPTION
		"One or more chassis power supplies are removed."

	::= { netapp 0 394 }

	chassisPowerSupplyOff           NOTIFICATION-TYPE
	OBJECTS                         {productTrapData, productSerialNum}
	STATUS                          current
	DESCRIPTION
		"One or more chassis power supplies are off."

	::= { netapp 0 395 }

	chassisPowerSuppliesOk          NOTIFICATION-TYPE
	OBJECTS                         {productTrapData, productSerialNum}
	STATUS                          current
	DESCRIPTION
		"The chassis power supplies are all functioning properly."

	::= { netapp 0 396 }

	chassisPowerSupplyOk            NOTIFICATION-TYPE
	OBJECTS                         {productTrapData, productSerialNum}
	STATUS                          current
	DESCRIPTION
		"This chassis power supply is functioning properly."

	::= { netapp 0 397 }



	-- -- -- -- -- -- -- -- -- -- -- -- -- -- -- -- -- -- -- -- -- -- -- -
	-- Power Rails
	-- -- -- -- -- -- -- -- -- -- -- -- -- -- -- -- -- -- -- -- -- -- -- -

	chassisPowerDegraded            NOTIFICATION-TYPE
	OBJECTS                         {productTrapData, productSerialNum}
	STATUS                          current
	DESCRIPTION
		"The power within the chassis is degraded.
		A description of the degraded state has been
		logged to the console and message log file."

	::= { netapp 0 403 }

	chassisPowerOk                  NOTIFICATION-TYPE
	OBJECTS                         {productTrapData, productSerialNum}
	STATUS                          current
	DESCRIPTION
		"The power within the chassis is functioning properly."

	::= { netapp 0 406 }

	-- -- -- -- -- -- -- -- -- -- -- -- -- -- -- -- -- -- -- -- -- -- -- -
	-- Chassis Fans
	-- -- -- -- -- -- -- -- -- -- -- -- -- -- -- -- -- -- -- -- -- -- -- -

	chassisFanDegraded              NOTIFICATION-TYPE
	OBJECTS                         {productTrapData, productSerialNum}
	STATUS                          current
	DESCRIPTION
		"A chassis fan has been degraded."

	::= { netapp 0 412 }

	chassisFanRemoved               NOTIFICATION-TYPE
	OBJECTS                         {productTrapData, productSerialNum}
	STATUS                          current
	DESCRIPTION
		"A chassis fan FRU has been removed."

	::= { netapp 0 413 }

	chassisFanStopped               NOTIFICATION-TYPE
	OBJECTS                         {productTrapData, productSerialNum}
	STATUS                          current
	DESCRIPTION
		"One or more chassis fans have stopped."

	::= { netapp 0 414 }

	chassisFanWarning               NOTIFICATION-TYPE
	OBJECTS                         {productTrapData, productSerialNum}
	STATUS                          current
	DESCRIPTION
		"One or more chassis fans is spinning slowly or too fast."

	::= { netapp 0 415 }

	chassisFanOk                    NOTIFICATION-TYPE
	OBJECTS                         {productTrapData, productSerialNum}
	STATUS                          current
	DESCRIPTION
		"All chassis fans are functioning properly."

	::= { netapp 0 416 }

	-- -- -- -- -- -- -- -- -- -- -- -- -- -- -- -- -- -- -- -- -- -- -- -
	-- Volume SnapValidator errors
	-- -- -- -- -- -- -- -- -- -- -- -- -- -- -- -- -- -- -- -- -- -- -- -

	writeVerificationFailed         NOTIFICATION-TYPE
	OBJECTS                         {productTrapData, productSerialNum}
	STATUS                          current
	DESCRIPTION
		"A write has failed a verification test
		on a SnapValidator enabled volume."
	::= { netapp 0 424 }

	-- -- -- -- -- -- -- -- -- -- -- -- -- -- -- -- -- -- -- -- -- -- -- -
	-- CIFS domain controller-related traps
	-- -- -- -- -- -- -- -- -- -- -- -- -- -- -- -- -- -- -- -- -- -- -- -

	prefDCDisconnect                NOTIFICATION-TYPE
	OBJECTS                         {productTrapData, productSerialNum}
	STATUS                          deprecated
	DESCRIPTION
		"All connections to domain controllers in the preferred domain
		controllers list have been lost."
	::= { netapp 0 434 }

	domainControllerDisconnect      NOTIFICATION-TYPE
	OBJECTS                         {productTrapData, productSerialNum}
	STATUS                          current
	DESCRIPTION
		"A CIFS domain controller connection to the filer has failed."
	::= { netapp 0 435 }

        dcPasswdChangeFailed            NOTIFICATION-TYPE
        OBJECTS                         {productTrapData, productSerialNum}
	STATUS                          current
        DESCRIPTION
                "An attempt to change the storage system's password with the domain
                controller has failed."
        ::= { netapp 0 436 }

	domainControllerConnected       NOTIFICATION-TYPE
	OBJECTS                         {productTrapData, productSerialNum}
	STATUS                          current
	DESCRIPTION
		"A CIFS domain controller connection to the filer has been
		established."
	::= { netapp 0 437 }

	-- -- -- -- -- -- -- -- -- -- -- -- -- -- -- -- -- -- -- -- -- -- -- -
	--  This section contains traps related to plex state
	-- -- -- -- -- -- -- -- -- -- -- -- -- -- -- -- -- -- -- -- -- -- -- -

	plexFailed                      NOTIFICATION-TYPE
	OBJECTS                         {productTrapData, productSerialNum}
	STATUS                          current
	DESCRIPTION
		"This trap is issued when one plex of a mirrored
		aggregate is failed. The string sent with
		this trap specifies name of affected plex or
		mirrored aggregate."
	::= { netapp 0 444 }

	plexOffline                     NOTIFICATION-TYPE
	OBJECTS                         {productTrapData, productSerialNum}
	STATUS                          current
	DESCRIPTION
		"This trap is issued when a plex becomes offline.
		The string sent with this trap specifies name of
		affected plex or mirrored aggregate."
	::= { netapp 0 454 }

	-- -- -- -- -- -- -- -- -- -- -- -- -- -- -- -- -- -- -- -- -- -- -- -
	--  This section contains traps related to shelf Electronics Elements
	--  and intelligent fibre channel interface modules such as LRC,
	--  ESH, AT-FC, and AT-FCX.
	-- -- -- -- -- -- -- -- -- -- -- -- -- -- -- -- -- -- -- -- -- -- -- -

	shelfSESElectronicsFailed       NOTIFICATION-TYPE
	OBJECTS                         {productTrapData, productSerialNum}
	STATUS                          current
	DESCRIPTION
		"One or more of the enclosure services devices in a
		disk shelf has failed.  Some shelf designs combine
		the enclosure monitoring hardware function into the
		module that provides  the storage interface to
		the shelf.  A failure in the enclosure monitoring
		section of these combined modules does not necessarily
		indicate a failure in disk or loop or bus operation,
		which may be able to continue."
	::= { netapp 0 464 }

	shelfSESElectronicsWarning	NOTIFICATION-TYPE
	OBJECTS				{productTrapData, productSerialNum}
	STATUS				current
	DESCRIPTION
		"One or more of the enclosure services devices in a
		disk shelf has reported a problem.  Some shelf designs
		combine the enclosure monitoring hardware function into
		the module that provides  the storage interface to
		the shelf.  A failure in the enclosure monitoring
		section of these combined modules does not necessarily
		indicate a failure in disk or loop or bus operation,
		which may be able to continue."
	::= { netapp 0 465 }

	shelfSESElectronicsInfo         NOTIFICATION-TYPE
	OBJECTS                         {productTrapData, productSerialNum}
	STATUS                          current
	DESCRIPTION
		"A previously reported failure of an enclosure
		services device in a disk shelf has been corrected,
		or the device has reported information that does not
		necessarily require customer action."
	::= { netapp 0 467 }

	shelfIFModuleFailed             NOTIFICATION-TYPE
	OBJECTS                         {productTrapData, productSerialNum}
	STATUS                          current
	DESCRIPTION
		"One or more of the storage interface modules in a
		disk shelf has failed.  Some shelf designs combine the
		enclosure monitoring hardware function into the module
		that operates the fibre channel loop or SCSI in the
		shelf.  This failure is of the storage interface
		itself, not a failure of the enclosure monitoring,
		which may be able to continue.  This failure may make
		one or more disks in the shelf or in the loop or bus
		unavailable."
	::= { netapp 0 473 }

 	shelfIFModuleWarning            NOTIFICATION-TYPE
	OBJECTS                         {productTrapData, productSerialNum}
	STATUS                          current
	DESCRIPTION
		"One or more of the storage interface modules in a
		disk shelf has a warning condition.  Some shelf designs combine the
		enclosure monitoring hardware function into the module
		that operates the fibre channel loop or SCSI in the
		shelf.  This warning condition is of the storage interface
		itself, not a failure of the enclosure monitoring,
		which may be able to continue."
	::= { netapp 0 475 }

 	shelfIFModuleInfo               NOTIFICATION-TYPE
	OBJECTS                         {productTrapData, productSerialNum}
	STATUS                          current
	DESCRIPTION
		"A previously reported failure of a disk shelf
		interface module has been corrected, or the module has
		reported information that does not necessarily require
		customer action."
	::= { netapp 0 477 }

	-- -- -- -- -- -- -- -- -- -- -- -- -- -- -- -- -- -- -- -- -- -- -- -
	--  This section contains traps related to maxdirsize.
	-- -- -- -- -- -- -- -- -- -- -- -- -- -- -- -- -- -- -- -- -- -- -- -

 	maxDirSizeAlert                 NOTIFICATION-TYPE
	OBJECTS                         {productTrapData, productSerialNum}
	STATUS                          current
	DESCRIPTION
		"A directory has reached its maxdirsize limit. Either
		increase the maxdirsize or clean up the directory."
	::= { netapp 0 482 }

 	maxDirSizeWarning               NOTIFICATION-TYPE
	OBJECTS                         {productTrapData, productSerialNum}
	STATUS                          current
	DESCRIPTION
		"A directory is getting close to its maxdirsize limit. Either
		increase the maxdirsize or clean up the directory."
	::= { netapp 0 485 }

        -- -- -- -- -- -- -- -- -- -- -- -- -- -- -- -- -- -- -- -- -- -- -- -
        -- CIFS statistics related traps
        -- -- -- -- -- -- -- -- -- -- -- -- -- -- -- -- -- -- -- -- -- -- -- -

        cifsStatsExhaustMemCtrlBlk      NOTIFICATION-TYPE
        OBJECTS                         {productTrapData, productSerialNum}
	STATUS                          deprecated
        DESCRIPTION
                "A request for a CIFS control block cannot be granted. All
                control blocks are in use."
        ::= { netapp 0 497 }

        -- -- -- -- -- -- -- -- -- -- -- -- -- -- -- -- -- -- -- -- -- -- -- -
        -- New Environmental Subsystem Traps
        -- -- -- -- -- -- -- -- -- -- -- -- -- -- -- -- -- -- -- -- -- -- -- -


	chassisPSRemovedxMinShutdown    NOTIFICATION-TYPE
	OBJECTS                         {productTrapData, productSerialNum}
	STATUS                          current
	DESCRIPTION
		"Power Supply Unit is removed from the system. System will
		be shutdown in x minutes if it is not put back."

	::= { netapp 0 501 }

	chassisPSUsMismatch             NOTIFICATION-TYPE
	OBJECTS                         {productTrapData, productSerialNum}
	STATUS                          deprecated
	DESCRIPTION
		"Power Supply Units in the system are of different type.
		 Please replace them with correct Power Supply Units."

	::= { netapp 0 505 }

	chassisFanFailxMinShutdown      NOTIFICATION-TYPE
	OBJECTS                         {productTrapData, productSerialNum}
	STATUS                          current
	DESCRIPTION
		"Multiple chassis fan failure. System will
		shut down in a few minutes if not corrected."

	::= { netapp 0 511 }

	chassisPSUwrongInput            NOTIFICATION-TYPE
	OBJECTS                         {productTrapData, productSerialNum}
	STATUS                          deprecated
	DESCRIPTION
		"Power Supply Unit (PSU) in the system is connected to an
		 incompatible external power source. Please change
		 the power source being used or replace the PSU
		 with one that matches the current power source."

	::= { netapp 0 515 }

	powerSupplyFanFailxMinShutdown  NOTIFICATION-TYPE
	OBJECTS                         {productTrapData, productSerialNum}
	STATUS                          deprecated
	DESCRIPTION
		"Multiple  power supply fans failure.
		System will shut down in a few minutes if not corrected."

	::= { netapp 0 521 }

	ioCardFailed			NOTIFICATION-TYPE
	OBJECTS				{productTrapData, productSerialNum}
	STATUS				current
	DESCRIPTION
		"An IO card is degraded.
		The trap includes a string describing
		the degraded IO card."

	::= { netapp 0 525 }

	ioCardOk			 NOTIFICATION-TYPE
	OBJECTS				{productTrapData, productSerialNum}
	STATUS				current
	DESCRIPTION
		"The IO card is functioning properly.
		The trap includes a string containing the slot number
		of the IO card."

	::= { netapp 0 526 }

        -- -- -- -- -- -- -- -- -- -- -- -- -- -- -- -- -- -- -- -- -- -- -- -
        -- New Remote Management Subsystem Traps
        -- -- -- -- -- -- -- -- -- -- -- -- -- -- -- -- -- -- -- -- -- -- -- -

	remoteSystemMgtAlert            NOTIFICATION-TYPE
	OBJECTS                         {productTrapData, productSerialNum}
	STATUS                          current
	DESCRIPTION
		"system remote management detected a system down event.
		The trap includes a string describing the specific event
		which triggered the trap.  The string is structured in the
		following form:
		Remote Management Event: type={system_down|system_up|test|keep_alive},
 		severity={alert|warning|notice|normal|debug|info},
		event={post_error|watchdog_reset|power_loss|abnormal_reboot},
		key=value

		An example of a complete message would be:
		Remote Management Event: type=system_down, severity=alert,
		event=watchdog_reset, ss=16bytes

		Additional key=value items may, in the future, be appended
		to this message.

		The events that would generate this trap would be:
		post_error: Fatal POST error on boot
		power_loss: Loss of power to system
		abnormal_reboot:
		l2_watchdog_reset"

	::= { netapp 0 532 }

	remoteSystemMgmtWarning         NOTIFICATION-TYPE
	OBJECTS                         {productTrapData, productSerialNum}
	STATUS                          current
	DESCRIPTION
		"system remote management detected a system down event.
		The trap includes a string describing the specific event
		which triggered the trap.  The string is structured in the
		following form:
		Remote Management Event: type={system_down|system_up|test|keep_alive},
 		severity={alert|warning|notice|normal|debug|info},
		event={loss-of-heartbeat},
		key=value

		An example of a complete message would be:
		Remote Management Event: type=system_down, severity=warning,
		event=loss_of_heartbeat, ss=16bytes

		Additional key=value items may, in the future, be appended
		to this message.

		The events that would generate this trap would be:
		loss_of_heartbeat: Loss of heartbeat to the RLM."

	::= { netapp 0 535 }

	remoteSystemMgmtNotification    NOTIFICATION-TYPE
	OBJECTS                         {productTrapData, productSerialNum}
	STATUS                          current
	DESCRIPTION
		"system remote management detected a system down event.
		The trap includes a string describing the specific event
		which triggered the trap.  The string is structured in the
		following form:
		Remote Management Event: type={system_down|system_up|test|keep_alive},
 		severity={alert|warning|notice|normal|debug|info},
		event={power_off_via_rlm,power_cycle_via_rlm,reset_via_rlm},
		key=value

		An example of a complete message would be:
		Remote Management Event: type=system_down, severity=notice,
		event=power_off_via_rlm, ss=16bytes

		Additional key=value items may, in the future, be appended
		to this message.

		The events that would generate this trap would be:
		power_off_via_rlm: This indicates system power off
		power_cycle_via_rlm: This indicates system power cycle
		reset_via_rlm: This indicates system reset."

	::= { netapp 0 536 }

	remoteSystemMgmtPeriodic        NOTIFICATION-TYPE
	OBJECTS                         {productTrapData, productSerialNum}
	STATUS                          current
	DESCRIPTION
		"This is a periodic keep alive from system remote management.
		The trap includes a string describing the specific event
		which triggered the trap.  The string is structured in the
		following form:
		Remote Management Event: type={system_down|system_up|test|keep_alive},
 		severity={alert|warning|notice|normal|debug|info},
		event={periodic_message}

		An example of a complete message would be:
		Remote Management Event: type=keep_alive, severity=info,
		event=periodic_message

		Additional key=value items may, in the future, be appended
		to this message."

	::= { netapp 0 547 }

	remotesystemMgmtTest            NOTIFICATION-TYPE
        OBJECTS                         {productTrapData, productSerialNum}
	STATUS                          current
        DESCRIPTION
                "This is a test trap from system remote management.
                The trap includes a string describing the specific event
                which triggered the trap.  The string is structured in the
                following form:
       		Remote Management Event: type={system_down|system_up|test|keep_alive},
                severity={alert|warning|notice|normal|debug|info},
	        event={periodic_message}

                An example of a complete message would be:
                Remote Management Event: type=test, severity=notice, event=test

                Additional key=value items may, in the future, be appended
                to this message."

        ::= { netapp 0 556 }

        -- -- -- -- -- -- -- -- -- -- -- -- -- -- -- -- -- -- -- -- -- -- -- -
        -- Disk Multipath Traps
        -- -- -- -- -- -- -- -- -- -- -- -- -- -- -- -- -- -- -- -- -- -- -- -

	diskMultipathOneSwitch          NOTIFICATION-TYPE
        OBJECTS                         {productTrapData, productSerialNum}
	STATUS                          current
        DESCRIPTION
                "A multipathed disk is only connected to one switch."

        ::= { netapp 0 562 }

	diskMultipathNoTakeover         NOTIFICATION-TYPE
        OBJECTS                         {productTrapData, productSerialNum}
	STATUS                          current
        DESCRIPTION
                "Multipath disks or luns could not be detected for the partner.
		The node will be unable to takeover correctly."

        ::= { netapp 0 563 }

	diskMultipathWarning            NOTIFICATION-TYPE
        OBJECTS                         {productTrapData, productSerialNum}
	STATUS                          current
        DESCRIPTION
                "Synchronous mirroring is enabled, even though disks are not
		multipathed."

        ::= { netapp 0 565 }

        -- -- -- -- -- -- -- -- -- -- -- -- -- -- -- -- -- -- -- -- -- -- -- -
        -- Disk Disable Traps
        -- -- -- -- -- -- -- -- -- -- -- -- -- -- -- -- -- -- -- -- -- -- -- -

 	driveDisableErr                 NOTIFICATION-TYPE
	OBJECTS                         {productTrapData, productSerialNum}
	STATUS                          current
	DESCRIPTION
		"A drive has been disabled by the shelf module due to
		 hardware errors.  If it is the only drive in the shelf
		 that is disabled, replace the drive."

	::= { netapp 0 574 }

        -- -- -- -- -- -- -- -- -- -- -- -- -- -- -- -- -- -- -- -- -- -- -- -
        -- HBA Offline Traps
        -- -- -- -- -- -- -- -- -- -- -- -- -- -- -- -- -- -- -- -- -- -- -- -

        hbaOfflineInformation		NOTIFICATION-TYPE
	OBJECTS                         {productTrapData, productSerialNum}
	STATUS                          current
	DESCRIPTION
		"A host bus adapter (HBA) port has been disabled.
		This state may be caused either by user command or by
		errors that make the interface unable to communicate
		with attached devices."

	::= { netapp 0 587 }

        -- -- -- -- -- -- -- -- -- -- -- -- -- -- -- -- -- -- -- -- -- -- -- -
        -- FC Adapter Traps
        -- -- -- -- -- -- -- -- -- -- -- -- -- -- -- -- -- -- -- -- -- -- -- -

        fcOfflineError			NOTIFICATION-TYPE
	OBJECTS                         {productTrapData, productSerialNum}
	STATUS                          current
	DESCRIPTION
		"A FibreChannel adapter port has gone off-line due to
		an error condition."

	::= { netapp 0 594 }

        fcOnlineFailWarning		NOTIFICATION-TYPE
	OBJECTS                         {productTrapData, productSerialNum}
	STATUS                          current
	DESCRIPTION
		"A FibreChannel adapter has failed to come on-line due
		to some error condition.  Check the cables for proper
		connections."

	::= { netapp 0 595 }

	fcOffLineNotification		NOTIFICATION-TYPE
	OBJECTS				{productTrapData, productSerialNum}
	STATUS				current
	DESCRIPTION
		"A FibreChannel adapter has gone off line.
		 This state may be caused either by user command or by
		 errors that make the interface unable to communicate
		 with attached devices."

	::= { netapp 0 596 }

        fcOnlineInformation		NOTIFICATION-TYPE
	OBJECTS                         {productTrapData, productSerialNum}
	STATUS                          current
	DESCRIPTION
		"A FibreChannel adapter port has come on-line."

	::= { netapp 0 597 }

        -- -- -- -- -- -- -- -- -- -- -- -- -- -- -- -- -- -- -- -- -- -- -- -
	-- LUN Snap Restore Notice
        -- -- -- -- -- -- -- -- -- -- -- -- -- -- -- -- -- -- -- -- -- -- -- -

 	lunSnapRestoreStatus	        NOTIFICATION-TYPE
	OBJECTS				{productTrapData, productSerialNum}
	STATUS                          current
	DESCRIPTION
		"Status of the Snap Restore"

	::= { netapp 0 606 }

        -- -- -- -- -- -- -- -- -- -- -- -- -- -- -- -- -- -- -- -- -- -- -- -
	-- LUN Clone Create Notice
        -- -- -- -- -- -- -- -- -- -- -- -- -- -- -- -- -- -- -- -- -- -- -- -

 	lunCloneCreate			NOTIFICATION-TYPE
	OBJECTS				{productTrapData, productSerialNum}
	STATUS                          current
	DESCRIPTION
		"Created a LUN Clone"

	::= { netapp 0 616 }

        -- -- -- -- -- -- -- -- -- -- -- -- -- -- -- -- -- -- -- -- -- -- -- -
	-- LUN Clone Split Notice
        -- -- -- -- -- -- -- -- -- -- -- -- -- -- -- -- -- -- -- -- -- -- -- -

 	lunCloneSplitStart		NOTIFICATION-TYPE
	OBJECTS				{productTrapData, productSerialNum}
	STATUS                          current
	DESCRIPTION
		"LUN Clone Split started"

	::= { netapp 0 626 }

 	lunCloneSplitComplete		NOTIFICATION-TYPE
	OBJECTS				{productTrapData, productSerialNum}
	STATUS                          current
	DESCRIPTION
		"LUN Clone Split completed"

	::= { netapp 0 627 }

        -- -- -- -- -- -- -- -- -- -- -- -- -- -- -- -- -- -- -- -- -- -- -- -
	-- Flex Clone Split Notice
        -- -- -- -- -- -- -- -- -- -- -- -- -- -- -- -- -- -- -- -- -- -- -- -

 	flexCloneSplitStart		NOTIFICATION-TYPE
	OBJECTS			{productTrapData, productSerialNum}
	STATUS                          current
	DESCRIPTION
		"Flex Clone Split started"

	::= { netapp 0 636 }

 	flexCloneSplitComplete		NOTIFICATION-TYPE
	OBJECTS				{productTrapData, productSerialNum}
	STATUS                          current
	DESCRIPTION
		"Flex Clone Split completed"

	::= { netapp 0 637 }

        -- -- -- -- -- -- -- -- -- -- -- -- -- -- -- -- -- -- -- -- -- -- -- -
	-- Volume Clone Create Notice
        -- -- -- -- -- -- -- -- -- -- -- -- -- -- -- -- -- -- -- -- -- -- -- -

 	volumeCloneCreate		NOTIFICATION-TYPE
	OBJECTS				{productTrapData, productSerialNum}
	STATUS                          current
	DESCRIPTION
		"Created a Volume Clone"

	::= { netapp 0 646 }

        -- -- -- -- -- -- -- -- -- -- -- -- -- -- -- -- -- -- -- -- -- -- -- -
	-- Snap Auto Delete Notice
        -- -- -- -- -- -- -- -- -- -- -- -- -- -- -- -- -- -- -- -- -- -- -- -

 	snapAutoDelete			NOTIFICATION-TYPE
	OBJECTS				{productTrapData, productSerialNum}
	STATUS                          current
	DESCRIPTION
		"Snapshot Auto Deleted"

	::= { netapp 0 656 }

        -- -- -- -- -- -- -- -- -- -- -- -- -- -- -- -- -- -- -- -- -- -- -- -
	-- Volume Auto Grow Notice
        -- -- -- -- -- -- -- -- -- -- -- -- -- -- -- -- -- -- -- -- -- -- -- -

 	volumeAutogrow			NOTIFICATION-TYPE
	OBJECTS				{productTrapData, productSerialNum}
	STATUS                          current
	DESCRIPTION
		"Volume is Auto Grown"

	::= { netapp 0 666 }

        -- -- -- -- -- -- -- -- -- -- -- -- -- -- -- -- -- -- -- -- -- -- -- -
	-- Time Daemon Target(s) Not Responding Notice
        -- -- -- -- -- -- -- -- -- -- -- -- -- -- -- -- -- -- -- -- -- -- -- -

 	timedTargetNotResponding	NOTIFICATION-TYPE
	OBJECTS				{productTrapData, productSerialNum}
	STATUS                          current
	DESCRIPTION
		"NTP Time Daemon lost contact with the configured target"

	::= { netapp 0 674 }

        -- -- -- -- -- -- -- -- -- -- -- -- -- -- -- -- -- -- -- -- -- -- -- -
	-- External cache device error Notice
        -- -- -- -- -- -- -- -- -- -- -- -- -- -- -- -- -- -- -- -- -- -- -- -

	extcacheCardError		NOTIFICATION-TYPE
	OBJECTS				{productTrapData, productSerialNum}
	STATUS                          current
	DESCRIPTION
		"External cache card failure"

	::= { netapp 0 676 }

        -- -- -- -- -- -- -- -- -- -- -- -- -- -- -- -- -- -- -- -- -- -- -- -
	-- External cache offline Notice
        -- -- -- -- -- -- -- -- -- -- -- -- -- -- -- -- -- -- -- -- -- -- -- -

	extcacheCardOffline		NOTIFICATION-TYPE
	OBJECTS				{productTrapData, productSerialNum}
	STATUS                          current
	DESCRIPTION
		"External cache is taken offline"

	::= { netapp 0 686 }

	-- -- -- -- -- -- -- -- -- -- -- -- -- -- -- -- -- -- -- -- -- -- -- -
	--
	--  This section contains traps related to snapvault
	--
	-- -- -- -- -- -- -- -- -- -- -- -- -- -- -- -- -- -- -- -- -- -- -- -

	-- -- -- -- -- -- -- -- -- -- -- -- -- -- -- -- -- -- -- -- -- -- -- -
        -- SnapVault Snapshot limit warning
	-- -- -- -- -- -- -- -- -- -- -- -- -- -- -- -- -- -- -- -- -- -- -- -

	svBackupSnapWarningLimit        NOTIFICATION-TYPE
	OBJECTS				{productTrapData, productSerialNum}
	STATUS                          current
	DESCRIPTION
		"The remaining number of Snapshot copies for a backup
		schedule is below warning limit specified."

	::= { netapp 0 695 }


         -- -- -- -- -- -- -- -- -- -- -- -- -- -- -- -- -- -- -- -- -- -- -- -
         -- Antivirus Traps
         -- -- -- -- -- -- -- -- -- -- -- -- -- -- -- -- -- -- -- -- -- -- -- -

         avTrendLicenseExpired   NOTIFICATION-TYPE
         OBJECTS                 {productTrapData, productSerialNum}
         STATUS                  current
         DESCRIPTION
                 "Trend Micro antivirus license has expired"

         ::= { netapp 0 705 }

         avTrendLicenseExpiring  NOTIFICATION-TYPE
         OBJECTS                 {productTrapData, productSerialNum}
         STATUS                  current
         DESCRIPTION
                 "Trend Micro antivirus license is about to expire"

         ::= { netapp 0 706 }

         -- -- -- -- -- -- -- -- -- -- -- -- -- -- -- -- -- -- -- -- -- -- -- -
         -- System Traps
         -- -- -- -- -- -- -- -- -- -- -- -- -- -- -- -- -- -- -- -- -- -- -- -

         rebootAbnormal          NOTIFICATION-TYPE
         OBJECTS                 {productTrapData, productSerialNum}
         STATUS                  current
         DESCRIPTION
                 "System rebooted abnormally after any of the following
                  events:
		  event = watchdog reset, agent watchdog reset, panic,
                  power-glitch."

         ::= { netapp 0 712 }

         rebootNormal            NOTIFICATION-TYPE
         OBJECTS                 {productTrapData, productSerialNum}
         STATUS                  current
         DESCRIPTION
                 "System rebooted normally after any of the following
                  events:
		  event = giveback, revert, WAFL check, power-on,
                  internal reboot, internal halt, rlm system reset, operator
                  initiated halt and reboot."

         ::= { netapp 0 716 }


        -- -- -- -- -- -- -- -- -- -- -- -- -- -- -- -- -- -- -- -- -- -- -- -
        --
        --  This section contains traps related to volume move
        --
        -- -- -- -- -- -- -- -- -- -- -- -- -- -- -- -- -- -- -- -- -- -- -- -

        -- -- -- -- -- -- -- -- -- -- -- -- -- -- -- -- -- -- -- -- -- -- -- -
        -- Volume Move Cutover Deferred
        -- -- -- -- -- -- -- -- -- -- -- -- -- -- -- -- -- -- -- -- -- -- -- -

        volMoveCutoverDeferred          NOTIFICATION-TYPE
        OBJECTS             {productTrapData, productSerialNum}
        STATUS                          current
        DESCRIPTION
            "A volume move job cannot be completed because cutover phase
            has been deferred."

        ::= { netapp 0 724 }

        -- -- -- -- -- -- -- -- -- -- -- -- -- -- -- -- -- -- -- -- -- -- -- -
        -- Volume Move Cutover Failed
        -- -- -- -- -- -- -- -- -- -- -- -- -- -- -- -- -- -- -- -- -- -- -- -

        volMoveCutoverFailed            NOTIFICATION-TYPE
        OBJECTS                         {productTrapData, productSerialNum}
        STATUS                          current
        DESCRIPTION
            "A volume move job cannot be completed because the cutover
            attempt resulted in failure."

        ::= { netapp 0 734 }

        -- -- -- -- -- -- -- -- -- -- -- -- -- -- -- -- -- -- -- -- -- -- -- -
        -- Volume Move Complete
        -- -- -- -- -- -- -- -- -- -- -- -- -- -- -- -- -- -- -- -- -- -- -- -

        volMoveDone             NOTIFICATION-TYPE
        OBJECTS                 {productTrapData, productSerialNum}
        STATUS                  current
        DESCRIPTION
            "A volume move job completed successfully."

        ::= { netapp 0 736 }

        -- -- -- -- -- -- -- -- -- -- -- -- -- -- -- -- -- -- -- -- -- -- -- -
        -- Volume Move Cutover Deferred Wait
        -- -- -- -- -- -- -- -- -- -- -- -- -- -- -- -- -- -- -- -- -- -- -- -

        volMoveCutoverDeferredWait          NOTIFICATION-TYPE
        OBJECTS                             {productTrapData, productSerialNum}
        STATUS                              current
        DESCRIPTION
            "A volume move has reached the cutover phase and is waiting
            for the user to trigger cutover because the user specified
            wait for cutover-action"

        ::= { netapp 0 737 }

	-- -- -- -- -- -- -- -- -- -- -- -- -- -- -- -- -- --
	-- C-Mode SAN Begin
	-- -- -- -- -- -- -- -- -- -- -- -- -- -- -- -- -- --

	-- -- -- -- -- -- -- -- -- -- -- -- -- -- -- -- -- --
	--
	--  Node Out of CLAM Quorum Trap
	--
	-- -- -- -- -- -- -- -- -- -- -- -- -- -- -- -- -- --

	scsibladeOutOfQuorum            NOTIFICATION-TYPE
	OBJECTS                         {productTrapData, productSerialNum}
	STATUS                          current
	DESCRIPTION
            "The node has lost connectivity with the other nodes
	     in the cluster. Both fcp and iscsi traffic have been disabled
	     on this node. The corrective action is to reboot the node, and
	     if the node is waiting for giveback then perform a giveback."

	::= { netapp 0 741 }

	-- -- -- -- -- -- -- -- -- -- -- -- -- -- -- -- -- --
	--
	--  Node In CLAM Quorum Trap
	--
	-- -- -- -- -- -- -- -- -- -- -- -- -- -- -- -- -- --

	scsibladeInQuorum               NOTIFICATION-TYPE
	OBJECTS                         {productTrapData, productSerialNum}
	STATUS                          current
	DESCRIPTION
            "The node established connectivity with the other nodes
	     in the cluster."

	::= { netapp 0 746 }

	-- -- -- -- -- -- -- -- -- -- -- -- -- -- -- -- -- --
	-- C-Mode SAN End
	-- -- -- -- -- -- -- -- -- -- -- -- -- -- -- -- -- --

    -- -- -- -- -- -- -- -- -- -- -- -- -- -- -- -- -- -- -- -- -- -- -- -
    --
    --  This section contains traps related to QoS Monitor
    --
    -- -- -- -- -- -- -- -- -- -- -- -- -- -- -- -- -- -- -- -- -- -- -- -

    -- -- -- -- -- -- -- -- -- -- -- -- -- -- -- -- -- -- -- -- -- -- -- -
    -- QoS Monitor Memory Maxed
    -- -- -- -- -- -- -- -- -- -- -- -- -- -- -- -- -- -- -- -- -- -- -- -

    qosMonitorMemoryMaxed   NOTIFICATION-TYPE
    OBJECTS                 {productTrapData, productSerialNum}
    STATUS                  current
    DESCRIPTION
        "QoS dynamic memory has reached its limit. Some QoS features
        may operate in a limited capacity."

    ::= { netapp 0 755 }

    -- -- -- -- -- -- -- -- -- -- -- -- -- -- -- -- -- -- -- -- -- -- -- -
    -- QoS Monitor Memory Abated
    -- -- -- -- -- -- -- -- -- -- -- -- -- -- -- -- -- -- -- -- -- -- -- -

    qosMonitorMemoryAbated  NOTIFICATION-TYPE
    OBJECTS                 {productTrapData, productSerialNum}
    STATUS                  current
    DESCRIPTION
        "QoS dynamic memory is no longer at its limit. All QoS features
        will operate as normal."

    ::= { netapp 0 757 }


    -- -- -- -- -- -- -- -- -- -- -- -- -- -- -- -- -- -- -- -- -- -- -- -- --
    --
    -- This section contains traps related to Aggregate Relocation
    --
    -- -- -- -- -- -- -- -- -- -- -- -- -- -- -- -- -- -- -- -- -- -- -- -- --


        -- -- -- -- -- -- -- -- -- -- -- -- -- -- -- -- -- -- -- -- -- -- -- --
        -- SFO Aggregate Relocated Successfully
        -- -- -- -- -- -- -- -- -- -- -- -- -- -- -- -- -- -- -- -- -- -- -- --
        sfoAggregateRelocated   NOTIFICATION-TYPE
        OBJECTS                 {productTrapData, productSerialNum}
        STATUS                  current
        DESCRIPTION
            "This trap is issued when an SFO aggregate is relocated permanently
             from one node to another."

        ::= { netapp 0 767 }


    -- -- -- -- -- -- -- -- -- -- -- -- -- -- -- -- -- -- -- -- -- -- -- -- --
    -- End of Aggregate Relocation Traps
    -- -- -- -- -- -- -- -- -- -- -- -- -- -- -- -- -- -- -- -- -- -- -- -- --

     avUpdateFailed          NOTIFICATION-TYPE
     OBJECTS                 {productTrapData, productSerialNum}
     STATUS                  current
     DESCRIPTION
             "The anti-virus software update failed."

     ::= { netapp 0 773 }

     avLicenseCheckFailed    NOTIFICATION-TYPE
     OBJECTS                 {productTrapData, productSerialNum}
     STATUS                  current
     DESCRIPTION
             "The anti-virus software license validation failed."

     ::= { netapp 0 774 }

     avMcAfeeProductExpired  NOTIFICATION-TYPE
     OBJECTS                 {productTrapData, productSerialNum}
     STATUS                  current
     DESCRIPTION
             "McAfee product has expired."

     ::= { netapp 0 775 }

     avRemedy                NOTIFICATION-TYPE
     OBJECTS                 {productTrapData, productSerialNum}
     STATUS                  current
     DESCRIPTION
             "Remedy action taken. The file has been repaired, deleted or quarantined."

     ::= { netapp 0 776 }

     avLicenseCheck          NOTIFICATION-TYPE
     OBJECTS                 {productTrapData, productSerialNum}
     STATUS                  current
     DESCRIPTION
             "License validation was successful."

     ::= { netapp 0 777 }

     avRemedyFailure         NOTIFICATION-TYPE
     OBJECTS                 {productTrapData, productSerialNum}
     STATUS                  current
     DESCRIPTION
             "Remedy action failed. The file was not repaired, deleted or quarantined."

     ::= { netapp 0 783 }

     avMcAfeeEngineExpired   NOTIFICATION-TYPE
     OBJECTS                 {productTrapData, productSerialNum}
     STATUS                  current
     DESCRIPTION
             "McAfee product has expired."

     ::= { netapp 0 785 }

     avMcAfeeProductExpiring NOTIFICATION-TYPE
     OBJECTS                 {productTrapData, productSerialNum}
     STATUS                  current
     DESCRIPTION
             "McAfee product is expiring."

     ::= { netapp 0 786 }

     av2gbFileNotScanned     NOTIFICATION-TYPE
     OBJECTS                 {productTrapData, productSerialNum}
     STATUS                  current
     DESCRIPTION
             "A file larger than 2GB is not scanned and marked as clean."

     ::= { netapp 0 793 }

     avMcAfeeEngineExpiring NOTIFICATION-TYPE
     OBJECTS                 {productTrapData, productSerialNum}
     STATUS                  current
     DESCRIPTION
             "McAfee engine is expiring."

     ::= { netapp 0 796 }

    avVirusfound            NOTIFICATION-TYPE
     OBJECTS                 {productTrapData, productSerialNum}
     STATUS                  current
     DESCRIPTION
             "Virus found while scanning."

     ::= { netapp 0 802 }

     avMcAfeeLicenseFailed   NOTIFICATION-TYPE
     OBJECTS                 {productTrapData, productSerialNum}
     STATUS                  current
     DESCRIPTION
             "McAfee antivirus license activation failed."

     ::= { netapp 0 803 }

     avDisableFailed          NOTIFICATION-TYPE
     OBJECTS                 {productTrapData, productSerialNum}
     STATUS                  current
     DESCRIPTION
             "The anti-virus service disabling failed in the cluster."

     ::= { netapp 0 804 }

     avDisable               NOTIFICATION-TYPE
     OBJECTS                 {productTrapData, productSerialNum}
     STATUS                  current
     DESCRIPTION
             "The anti-virus service is disabled in the cluster."

     ::= { netapp 0 805 }

     avMcAfeeLicenseExpiring   NOTIFICATION-TYPE
     OBJECTS                   {productTrapData, productSerialNum}
     STATUS                    current
     DESCRIPTION
             "McAfee antivirus license is about to expire."

     ::= { netapp 0 806 }

     avEnable                NOTIFICATION-TYPE
     OBJECTS                 {productTrapData, productSerialNum}
     STATUS                  current
     DESCRIPTION
             "The anti-virus service is enabled in the cluster."

     ::= { netapp 0 807 }

     avSpywareFound          NOTIFICATION-TYPE
     OBJECTS                 {productTrapData, productSerialNum}
     STATUS                  current
     DESCRIPTION
             "Spyware found while scanning."

     ::= { netapp 0 812 }

     avEnableFailed          NOTIFICATION-TYPE
     OBJECTS                 {productTrapData, productSerialNum}
     STATUS                  current
     DESCRIPTION
             "The anti-virus service enabling failed in the cluster."

     ::= { netapp 0 813 }

     avRollbackFailed        NOTIFICATION-TYPE
     OBJECTS                 {productTrapData, productSerialNum}
     STATUS                  current
     DESCRIPTION
             "The anti-virus software rollback failed."

     ::= { netapp 0 814 }

     avRollback              NOTIFICATION-TYPE
     OBJECTS                 {productTrapData, productSerialNum}
     STATUS                  current
     DESCRIPTION
             "The anti-virus software is rolled back."

     ::= { netapp 0 816 }

     avUpdate                NOTIFICATION-TYPE
     OBJECTS                 {productTrapData, productSerialNum}
     STATUS                  current
     DESCRIPTION
             "The anti-virus software is updated."

     ::= { netapp 0 817 }

     snmpBusy                NOTIFICATION-TYPE
     OBJECTS                 {productTrapData, productSerialNum}
     STATUS                  current
     DESCRIPTION
             "The SNMP server is too busy."

     ::= { netapp 0 824 }

    lunDestroy               NOTIFICATION-TYPE
    OBJECTS                  {productTrapData, productSerialNum}
    STATUS                   current
    DESCRIPTION
             "A LUN was destroyed."

    ::= { netapp 0 837 }

     -- -- -- -- -- -- -- -- -- -- -- -- -- -- -- -- -- --
     --
     --  Health Monitor Alert EMS trap
     --
     -- -- -- -- -- -- -- -- -- -- -- -- -- -- -- -- -- --
     healthMonitorAlertRaised        NOTIFICATION-TYPE
     OBJECTS                         {productTrapData, productSerialNum}
     STATUS                          current
     DESCRIPTION
            "A Health Monitor has created an alert."

     ::= { netapp 0 862 }

     healthMonitorAlertCleared       NOTIFICATION-TYPE
     OBJECTS                         {productTrapData, productSerialNum}
     STATUS                          current
     DESCRIPTION
            "A Health Monitor has cleared an alert."

     ::= { netapp 0 867 }

     volumeLogicalOverallocated      NOTIFICATION-TYPE
     OBJECTS                         {productTrapData, productSerialNum}
     STATUS                          current
     DESCRIPTION
            "The volume has over allocated space and may not be able to
             honor file reservations or the aggregate has over allocated
             space and may not be able to honor volume guarantees.
             If and when the reserved/guaranteed space is consumed
             there will be insufficient physical space which can
             cause the volume/aggregate to be taken offline."

     ::= { netapp 0 873 }

     volumeReserveGrew               NOTIFICATION-TYPE
     OBJECTS                         {productTrapData, productSerialNum}
     STATUS                          current
     DESCRIPTION
            "At least one volume's WAFL reserve grew because it was
             physically over allocated."

     ::= { netapp 0 875 }

     volumePhysicalOverallocated     NOTIFICATION-TYPE
     OBJECTS                         {productTrapData, productSerialNum}
     STATUS                          current
     DESCRIPTION
            "The volume/aggregate is running dangerously low on
             free blocks to write to."

     ::= { netapp 0 882 }

    -- -- -- -- -- -- -- -- -- -- -- -- -- -- -- -- -- -- -- -- -- -- -- -- --
    --
    -- This section contains traps related to C-mode Snapmirror/Snapvault
    -- Reserve trap from 90x to 96x for C-mode Snapmirror/Snapvault
    -- -- -- -- -- -- -- -- -- -- -- -- -- -- -- -- -- -- -- -- -- -- -- -- --

     smVaultSnapWarnLimit    NOTIFICATION-TYPE
     OBJECTS                 {productTrapData, productSerialNum}
     STATUS                  current
     DESCRIPTION
             "The snapshot count limit on the destination volume has been reached."

     ::= { netapp 0 895 }

      lunRelocationCompletion         NOTIFICATION-TYPE
      OBJECTS                         {productTrapData, productSerialNum}
      STATUS                          current
      DESCRIPTION
                "Lun relocation completed successfully"
     ::= { netapp 0 896 }

     smSyncOutOfSyncWarn           NOTIFICATION-TYPE
     OBJECTS                         {productTrapData, productSerialNum}
     STATUS                          current
     DESCRIPTION
		"A synchronous granular CG relationship has
		transitioned from in-sync to out-of-sync and
		remained out-of-sync for longer than expected."
     ::= { netapp 0 905 }

     clusterLinkDown         NOTIFICATION-TYPE
     OBJECTS                 {productTrapData, productSerialNum}
     STATUS                  current
     DESCRIPTION
             "A cluster link has been lost."

     ::= { netapp 0 973 }

     clusterL2ConnFail       NOTIFICATION-TYPE
     OBJECTS                 {productTrapData, productSerialNum}
     STATUS                  current
     DESCRIPTION
             "The l2ping command is currently failing between cluster ports."

     ::= { netapp 0 983 }

     clusterPingDropLarge    NOTIFICATION-TYPE
     OBJECTS                 {productTrapData, productSerialNum}
     STATUS                  current
     DESCRIPTION
             "Pings of large packets between cluster ports are currently failing."

     ::= { netapp 0 993 }
     -- -- -- -- -- -- -- -- -- -- -- -- -- -- -- -- -- -- -- -- -- -- -- -- --
     --
     -- This section contains traps related to Disks
     -- Reserve trap from 100x to 102x for disk related events.
     -- -- -- -- -- -- -- -- -- -- -- -- -- -- -- -- -- -- -- -- -- -- -- -- --

     diskFailedRemoveCarrier NOTIFICATION-TYPE
     OBJECTS                 {productTrapData, productSerialNum}
     STATUS                  current
     DESCRIPTION
             "All disks in a carrier that contains
             more than one disk are failed by
             Data ONTAP(R) and the carrier can be removed."

     ::= { netapp 0 1002 }

        -- -- -- -- -- -- -- -- -- -- -- -- -- -- -- -- -- -- -- -- -- -- -- -
	--
	-- This section contains traps related to SAS connectors.
	-- Reserve traps 104x for SAS connector traps.
        -- -- -- -- -- -- -- -- -- -- -- -- -- -- -- -- -- -- -- -- -- -- -- -

        sasConnectorWarn		NOTIFICATION-TYPE
	OBJECTS				{productTrapData, productSerialNum}
	STATUS				current
	DESCRIPTION
		"A cable connecting a SAS device to a disk shelf
		has been removed or failed."
	::= { netapp 0 1045 }

	sasConnectorInfo		NOTIFICATION-TYPE
	OBJECTS				{productTrapData, productSerialNum}
	STATUS				current
	DESCRIPTION
		"A previously-existing error condition involving a SAS cable
		has been corrected."
	::= { netapp 0 1047 }


        -- -- -- -- -- -- -- -- -- -- -- -- -- -- -- -- -- -- -- -- -- -- -- -
	--
	-- This section contains traps related to shelf power supply issues
	--
        -- -- -- -- -- -- -- -- -- -- -- -- -- -- -- -- -- -- -- -- -- -- -- -

	sesShelfPowerSupplyError	NOTIFICATION-TYPE
	OBJECTS				{productTrapData, productSerialNum}
	STATUS				current
	DESCRIPTION
		"A shelf power supply has failed or been removed."
	::= { netapp 0 1054 }

	sesShelfPowerSupplyWarn		NOTIFICATION-TYPE
	OBJECTS				{productTrapData, productSerialNum}
	STATUS				current
	DESCRIPTION
		"A shelf power supply has indicated a warning condition."
	::= { netapp 0 1055 }


	sesShelfPowerSupplyInfo		NOTIFICATION-TYPE
	OBJECTS				{productTrapData, productSerialNum}
	STATUS				current
	DESCRIPTION
		"A previously reported error or warning condition
		involving a shelf power supply has been corrected."
	::= { netapp 0 1057 }


        -- -- -- -- -- -- -- -- -- -- -- -- -- -- -- -- -- -- -- -- -- -- -- -
        -- Volume Rehost traps
        -- -- -- -- -- -- -- -- -- -- -- -- -- -- -- -- -- -- -- -- -- -- -- -

        volRehostFailed                     NOTIFICATION-TYPE
        OBJECTS                             {productTrapData, productSerialNum}
        STATUS                              current
        DESCRIPTION
            "A volume rehost attempt has failed. The volume is available
	    under source Vserver."

        ::= { netapp 0 1064 }


        -- -- -- -- -- -- -- -- -- --  -- -- -- -- -- -- -- -- -- -- -- -- -- -
	--
	-- This section contains traps related to shelf voltage issues
	--
        -- -- -- -- -- -- -- -- -- -- -- -- -- -- -- -- -- -- -- -- -- -- -- -

	sesShelfVoltageWarning	        NOTIFICATION-TYPE
	OBJECTS				{productTrapData, productSerialNum}
	STATUS				current
	DESCRIPTION
		"This message occurs when a warning condition is
		 detected in the indicated disk shelf voltage sensor.
		 The shelf might be able to continue operation."
	::= { netapp 0 1065 }


        -- -- -- -- -- -- -- -- -- -- -- -- -- -- -- -- -- -- -- -- -- -- -- -
        -- Volume Rehost traps
        -- -- -- -- -- -- -- -- -- -- -- -- -- -- -- -- -- -- -- -- -- -- -- -

        volRehostSucceeded                  NOTIFICATION-TYPE
        OBJECTS                             {productTrapData, productSerialNum}
        STATUS                              current
        DESCRIPTION
            "A volume rehost attempt is successful."

        ::= { netapp 0 1067 }

    -- -- -- -- -- -- -- -- -- -- -- -- -- -- -- -- -- --
    --
    --  Offbox-AV Traps
    --
    -- -- -- -- -- -- -- -- -- -- -- -- -- -- -- -- -- --
    offboxvscanVirusDetectedError   NOTIFICATION-TYPE
    OBJECTS                         {productTrapData, productSerialNum}
    STATUS                          current
    DESCRIPTION
             "VScan: A possible virus has been detected"

    ::= { netapp 0 1072 }


	snmpTestTraphost                    NOTIFICATION-TYPE
        OBJECTS                             {productTrapData, productSerialNum}
        STATUS                              current
        DESCRIPTION
        "SNMP test trap  is generated."

        ::= { netapp 0 1103 }


        snmpFipsSupport                     NOTIFICATION-TYPE
        OBJECTS                             {productTrapData, productSerialNum}
        STATUS                              current
        DESCRIPTION
            "Data ONTAP is operating in FIPS compliant mode but
            SNMPv3 is configured with non-compliant ciphers or hash algorithms.
            Hence SNMPv3 is disabled."

        ::= { netapp 0 1114 }

     -- -- -- -- -- -- -- -- -- -- -- -- -- -- -- -- -- -- -- -- -- -- -- -- --
     --
     -- This section contains traps when no servers are available (LDAP, NIS, AD)
     -- Reserve trap from 112x to 115x for loss of connection related events.
     -- -- -- -- -- -- -- -- -- -- -- -- -- -- -- -- -- -- -- -- -- -- -- -- --

     noNisServersAvailable   NOTIFICATION-TYPE
     OBJECTS                 {productTrapData, productSerialNum}
     STATUS                  current
     DESCRIPTION
             "None of the configured NIS servers are
             reachable at this point of time. The string
             sent with the trap gives the name of the
             affected Storage Virtual Machine."

     ::= { netapp 0 1121 }

     noLdapServersAvailable   NOTIFICATION-TYPE
     OBJECTS                  {productTrapData, productSerialNum}
     STATUS                   current
     DESCRIPTION
             "None of the configured LDAP servers are
             reachable at this point of time. The string
             sent with the trap gives the name of the
             affected Storage Virtual Machine."

     ::= { netapp 0 1131 }

     noLsaServersAvailable    NOTIFICATION-TYPE
     OBJECTS                  {productTrapData, productSerialNum}
     STATUS                   current
     DESCRIPTION
             "None of the configured LSA servers are
             reachable at this point of time. The string
             sent with the trap gives the name of the
             affected Storage Virtual Machine."

     ::= { netapp 0 1141 }

     noNetlogonServersAvailable    NOTIFICATION-TYPE
     OBJECTS                       {productTrapData, productSerialNum}
     STATUS                        current
     DESCRIPTION
             "None of the configured Netlogon servers are
             reachable at this point of time. The string
             sent with the trap gives the name of the
             affected Storage Virtual Machine."

     ::= { netapp 0 1151 }

        -- -- -- -- -- -- -- -- -- -- -- -- -- -- -- -- -- -- -- -- -- -- -- -
	--
	-- This section contains traps related to shelf dcm issues
	--
        -- -- -- -- -- -- -- -- -- -- -- -- -- -- -- -- -- -- -- -- -- -- -- -

	sesShelfDcmError	NOTIFICATION-TYPE
	OBJECTS				{productTrapData, productSerialNum}
	STATUS				current
	DESCRIPTION
		"A shelf dcm is not installed or not supported."
	::= { netapp 0 1164 }

	sesShelfDcmWarn		NOTIFICATION-TYPE
	OBJECTS				{productTrapData, productSerialNum}
	STATUS				current
	DESCRIPTION
		"A shelf dcm has indicated a warning condition."
	::= { netapp 0 1165 }


	sesShelfDcmInfo		NOTIFICATION-TYPE
	OBJECTS				{productTrapData, productSerialNum}
	STATUS				current
	DESCRIPTION
		"A previously reported error or warning condition
		involving a shelf dcm has been corrected."
	::= { netapp 0 1167 }

     snmpSnmpv3Enable                    NOTIFICATION-TYPE
     OBJECTS                             {productTrapData, productSerialNum}
     STATUS                              current
     DESCRIPTION
             "This message occurs when SNMPv3 is disabled due to a cluster in FIPS
             mode being upgraded to a version of ONTAP(R) software supporting the
             SNMPv3 FIPS feature. FIPS compliance adds more stringent limitations
             on SNMP users and SNMP traphosts, so SNMPv3 access has been disabled
             to allow the current SNMP users and SNMP traphosts to be reevaluated.
             If SNMPv3 functionality is required, you can reenable it; if cluster
             is still in FIPS mode at that time, any existing SNMP users and SNMP
             traphosts that are noncompliant to FIPS will be deleted. Until SNMPv3
             is reenabled, SNMPv3 users cannot be created, SNMPv3 traphosts cannot
             be added and SNMPv3 packets will not be processed."
     ::= { netapp 0 1194 }

     snmpFipsObjsDelFailed               NOTIFICATION-TYPE
     OBJECTS                             {productTrapData, productSerialNum}
     STATUS                              current
     DESCRIPTION
             "The system failed to delete SNMP traphosts and users that were not
             FIPS compliant. It tried to automatically delete them when FIPS was
             configured in the cluster. The SNMP traphosts and users that are
             left have become inoperable."
     ::= { netapp 0 1204 }

     fcBridgeTempEmergency		NOTIFICATION-TYPE
     OBJECTS				{productTrapData, productSerialNum}
     STATUS				current
     DESCRIPTION
     		"The FC-to-SAS bridge has reached the critical temperature
		threshold, and will shut down."
     ::= { netapp 0 1211 }

     fcBridgeTempAlert			NOTIFICATION-TYPE
     OBJECTS				{productTrapData, productSerialNum}
     STATUS				current
     DESCRIPTION
     		"The FC-to-SAS bridge is operating at elevated temperature
		levels and action should be taken to restore proper cooling."
     ::= { netapp 0 1212 }

     fcBridgeTempNotice			NOTIFICATION-TYPE
     OBJECTS				{productTrapData, productSerialNum}
     STATUS				current
     DESCRIPTION
    		"The FC-to-SAS bridge has returned to normal operating temperature."
     ::= { netapp 0 1216 }


     fcBridgeFcPortAlert		NOTIFICATION-TYPE
     OBJECTS				{productTrapData, productSerialNum}
     STATUS				current
     DESCRIPTION
		"This message occurs when an FC port has gone offline."
     ::= { netapp 0 1222 }

     fcBridgeFcPortNotice			NOTIFICATION-TYPE
     OBJECTS				{productTrapData, productSerialNum}
     STATUS				current
     DESCRIPTION
    		"This message occurs when an FC port has come back online"
     ::= { netapp 0 1226 }

     fcBridgeSASPortAlert		NOTIFICATION-TYPE
     OBJECTS				{productTrapData, productSerialNum}
     STATUS				current
     DESCRIPTION
    		"This message occurs when a SAS port has gone offline."
     ::= { netapp 0 1232 }

     fcBridgeSASPortNotice			NOTIFICATION-TYPE
     OBJECTS				{productTrapData, productSerialNum}
     STATUS				current
     DESCRIPTION
    		"This message occurs when a SAS port has come back online"
     ::= { netapp 0 1236 }



     fcBridgeThroughputAlert		NOTIFICATION-TYPE
     OBJECTS				{productTrapData, productSerialNum}
     STATUS				current
     DESCRIPTION
    		"This message occurs when an FC-to-SAS bridge is experiencing
                 degraded throughput."
     ::= { netapp 0 1242 }

     fcBridgeThroughputNotice		NOTIFICATION-TYPE
     OBJECTS				{productTrapData, productSerialNum}
     STATUS				current
     DESCRIPTION
                 "This message occurs when an FC-to-SAS bridge has recovered from
                  degraded throughput."
     ::= { netapp 0 1246 }

     fcBridgePowerSupplyAlert		NOTIFICATION-TYPE
     OBJECTS				{productTrapData, productSerialNum}
     STATUS				current
     DESCRIPTION
         "This message occurs when an FC-to-SAS bridge power supply has failed."
     ::= { netapp 0 1252 }

     fcBridgePowerSupplyNotice		NOTIFICATION-TYPE
     OBJECTS				{productTrapData, productSerialNum}
     STATUS				current
     DESCRIPTION
         "This message occurs when an FC-to-SAS bridge power supply has returned to
	  normal operation."
     ::= { netapp 0 1256 }

     fcBridgeSasPhyTransitionAlert	NOTIFICATION-TYPE
     OBJECTS				{productTrapData, productSerialNum}
     STATUS				current
     DESCRIPTION
         "This message occurs when a SAS port on a bridge has transitioned
	  to offline."
     ::= { netapp 0 1262 }

     fcBridgeSasPhyTransitionNotice	NOTIFICATION-TYPE
     OBJECTS				{productTrapData, productSerialNum}
     STATUS				current
     DESCRIPTION
         "This message occurs when a SAS port on a bridge has transitioned
	  to online."
     ::= { netapp 0 1266 }

     -- -- -- -- -- -- -- -- -- -- -- -- -- -- -- -- -- -- -- -- -- -- -- -- --
     --
     -- This section contains traps for cloud
     -- Reserve trap from 130x to 139x for VSA cloud messages
     -- -- -- -- -- -- -- -- -- -- -- -- -- -- -- -- -- -- -- -- -- -- -- -- --

     vsaCloudProviderScheduledEventScheduled	NOTIFICATION-TYPE
     OBJECTS				{productTrapData, productSerialNum}
     STATUS				current
     DESCRIPTION
         "This message occurs when a cloud-provider maintenance event has
	  been initially scheduled."
     ::= { netapp 0 1302 }


     vsaCloudProviderScheduledEventUpdate	NOTIFICATION-TYPE
     OBJECTS				{productTrapData, productSerialNum}
     STATUS				current
     DESCRIPTION
         "This message occurs when the status of a previously scheduled
          cloud-provider maintenance event has been updated."
     ::= { netapp 0 1303 }



	-- -- -- -- -- -- -- -- -- -- -- -- -- -- -- -- -- -- -- -- -- -- -- -
	-- End of NetApp trap definitions
	--
	-- Note: Please update this comment when adding a new NOTIFICATION-TYPE.
	--       The next trap set range should be: 140x
	--
        --       The 10xxx trap range is used by DataFabric Manager
        --           (netappDataFabricManager) see the DFM MIB for further
        --           information.
        --
	--	 The 20xxx trap range is used by the NetApp Support Console
	--	     (netappSupportConsole) see the NASC MIB for further
	--	     information.
	--
	-- The 'ones' digit of the trap contains the priority of the trap:
	--
	-- 1 emergency
	-- 2 alert
	-- 3 critical
	-- 4 error
	-- 5 warning
	-- 6 notification
	-- 7 information
	-- 8 debug
	--
        -- -- -- -- -- -- -- -- -- -- -- -- -- -- -- -- -- -- -- -- -- -- -- -

	END
