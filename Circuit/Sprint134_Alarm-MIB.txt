ALARM-MIB DEFINITIONS ::= BEGIN

-- ==================================================================
-- Copyright @ 2013 Unify GmbH & Co. KG
--
-- All Rights Reserved.
--
-- Reproduction of this document is authorized on condition that
-- this copyright notice is included.
--
-- This MIB document embodies proprietary intellectual property of Unify,
-- which retains all title and ownership in this MIB, including any revisions.
--
-- This module will be extended, as required.
--
-- Unify reserves the right to make changes in specification and other
-- information contained in this document without prior notice. The reader
-- should consult Unify to determine whether any such changes have been made.
--
-- Copyright @ 2013 Unify GmbH & Co. KG

-- ==================================================================


-- ==================================================================
-- Revision History V1R0                (Date needs to match LAST-UPDATED below)
--  2013-12-18  Uwe Grothe                    Initial issue
--  2014-07-28  Nigel Feavyour (Com US)       V1R0 version of MIB
--  2014-08-18  Nigel Feavyour (Com US)       Automatically generated MIB
--                                            Added alarm04047 alarmC04047
--                                            Added alarm04048 alarmC04048
--  2014-08-29  Nigel Feavyour (Com US)       Automatically generated MIB
--                                            Added alarm01004 alarmC01004
--                                            Added alarm01005 alarmC01005
--                                            Added alarm01006 alarmC01006
--                                            Added alarm01007 alarmC01007
--                                            Added alarm04026 alarmC04026
--                                            Added alarm09009 alarmC09009
--                                            Added alarm13001 alarmC13001
--                                            Added alarm50011 alarmC50011
--                                            Added alarm50015 alarmC50015
--                                            Added alarm50016 alarmC50016
--                                            Added alarm50017 alarmC50017
--                                            Added alarm50018 alarmC50018
--                                            Added alarm56992 alarmC56992
--                                            Added alarm57013 alarmC57013
--                                            Added alarm57014 alarmC57014
--                                            Added alarm57015 alarmC57015
--                                            Added alarm57016 alarmC57016
--                                            Added alarm57017 alarmC57017
--                                            Deprecated alarm50002 alarmC50002
--  2014-09-10  Nigel Feavyour (Com US)       Automatically generated MIB
--                                            Added alarm50021 alarmC50021
--                                            Deprecated alarm08023 alarmC08023
--  2014-09-15  Nigel Feavyour (Com US)       Automatically generated MIB
--                                            Added alarm55002 alarmC55002
--  2014-10-07  Nigel Feavyour (Com US)       Automatically generated MIB
--                                            Added alarm50022 alarmC50022
--                                            Deprecated alarm57001 alarmC57001
--  2014-10-20  Nigel Feavyour (Com US)       Automatically generated MIB
--                                            Added alarm02001 alarmC02001
--                                            Added alarm09010 alarmC09010
--                                            Added alarm09019 alarmC09019
--                                            Added alarm09020 alarmC09020
--                                            Added alarm20006 alarmC20006
--                                            Added alarm59004 alarmC59004
--                                            Added alarm80004 alarmC80004
--                                            Added alarm80005 alarmC80005
--  2014-10-20  Nigel Feavyour (Com US)       Automatically generated MIB
--  2014-10-23  Nigel Feavyour (Com US)       Automatically generated MIB
--                                            Added alarm14011 alarmC14011
--  2014-11-11  Nigel Feavyour (Com US)       Automatically generated MIB
--  2014-11-13  Nigel Feavyour (Com US)       Automatically generated MIB
--                                            Added alarm01011 alarmC01011
--                                            Added alarm08051 alarmC08051
--                                            Added alarm08052 alarmC08052
--                                            Added alarm08053 alarmC08053
--                                            Added alarm08054 alarmC08054
--                                            Added alarm08055 alarmC08055
--                                            Added alarm08056 alarmC08056
--                                            Added alarm08057 alarmC08057
--                                            Added alarm08061 alarmC08061
--                                            Added alarm08062 alarmC08062
--                                            Added alarm08063 alarmC08063
--                                            Added alarm08064 alarmC08064
--                                            Added alarm08065 alarmC08065
--                                            Added alarm08066 alarmC08066
--                                            Added alarm08067 alarmC08067
--  2014-11-17  Nigel Feavyour (Com US)       Automatically generated MIB
--                                            Added alarm04027 alarmC04027
--  2014-11-18  Nigel Feavyour (Com US)       Automatically generated MIB
--                                            Deprecated alarm81001 alarmC81001
--                                            Deprecated alarm82001 alarmC82001
--  2014-11-19  Nigel Feavyour (Com US)       Automatically generated MIB
--                                            Added alarm55003 alarmC55003
--  2014-11-19  Nigel Feavyour (Com US)       Automatically generated MIB
--  2014-12-09  Nigel Feavyour (Com US)       Automatically generated MIB
--  2015-01-29  Nigel Feavyour (Com US)       Automatically generated MIB
--                                            Added alarm05006 alarmC05006
--  2015-02-18  Sathyanarayanan Vittal (Com US)Automatically generated MIB
--                                            Added alarm90001 alarmC90001
--                                            Added alarm90002 alarmC90002
--  2015-03-09  Dimitrios Iosifidis		Automatically generated MIB
--                                            Added alarm57021 alarmC57021
--  2015-03-11  Sathyanarayanan Vittal (Com US)Automatically generated MIB
--                                            Added alarm90003 alarmC90003
--                                            Added alarm90004 alarmC90004
--                                            Added alarm90005 alarmC90005
--                                            Added alarm90006 alarmC90006
--  2015-04-22  Sathyanarayanan Vittal (Com US)Automatically generated MIB
--                                            Added alarm04028 alarmC04028
--                                            Added alarm04029 alarmC04029
--                                            Added alarm04030 alarmC04030
--                                            Added alarm04031 alarmC04031
--                                            Added alarm04032 alarmC04032
--  2015-10-12  Artsiom Hryn                  Automatically generated MIB
--                                            Added alarm90009 alarmC90009
--  2015-11-05  Todor Todorov                 Automatically generated MIB
--                                            Added alarm56994 alarmC56994
--                                            Added alarm56995 alarmC56995
--  2015-11-13  Raman Yelianevich             Automatically generated MIB
--                                            Added alarm90012 alarmC90012
--  2015-12-03  Miltiadou Dimitrios (Com Hellas)Automatically generated MIB
--                                            Added alarm05007 alarmC05007
--  2016-01-26  Martin Bode                   Automatically generated MIB
--  2016-02-19  Dima Maria (Com Hellas)       Automatically generated MIB
--                                            Added alarm57006 alarmC57006
--  2016-07-22  Martin Bode                   Automatically generated MIB
--                                            Added alarm56996 alarmC56996
--  2016-08-17  Geert Fieremans (Com US)      Automatically generated MIB
--                                            Added alarm90013 alarmC90013
--                                            Added alarm90014 alarmC90014
--  2016-08-17  Geert Fieremans (Com US)      Automatically generated MIB
--                                            Added alarm90015 alarmC90015
--  2016-08-29  Dimitrios Iosifidis           Automatically generated MIB
--                                            Added alarm57022 alarmC57022
--  2016-09-19  Jeff Cripe (Com US)           Automatically generated MIB
--                                            Added alarm90016 alarmC90016
--                                            Added alarm90017 alarmC90017
--  2016-09-19  Jeff Cripe (Com US)           Automatically generated MIB
--  2016-09-19  Jeff Cripe (Com US)           Automatically generated MIB
--  2016-09-26  Geert Fieremans (Com US)      Automatically generated MIB
--                                            Added alarm04100 alarmC04100
--  2016-10-05  Nick Tzavalas,,,              Automatically generated MIB
--                                            Added alarm57023 alarmC57023
--  2016-10-20  Dimitris Iosifidis            Automatically generated MIB
--                                            Added alarm57024 alarmC57024
--  2016-11-16  Miltiadou Dimitrios           Automatically generated MIB
--                                            Added alarm57007 alarmC57007
--  2016-12-15  Martin Bode                   Automatically generated MIB
--  2017-01-05  Dima Maria (Com Hellas)       Automatically generated MIB
--                                            Added alarm50052 alarmC50052
--  2017-03-13  Michael Chittka               Automatically generated MIB
--                                            Added alarm90020 alarmC90020
--                                            Added alarm90021 alarmC90021
--  2017-04-25  Eleftherios Bampaletakis (PH Hellas Git)Automatically generated MIB
--                                            Added alarm57025 alarmC57025
--  2017-06-29  Jeff Cripe (Com US)           Automatically generated MIB
--  2017-09-27  Eleftherios Dalamagkas (COM Hellas Git)Automatically generated MIB
--                                            Added alarm57026 alarmC57026
--  2017-10-26  Dima Maria (Com Hellas)       Automatically generated MIB
--                                            Added alarm60010 alarmC60010
--  2017-11-10  Symeon Makris (Com Hellas)    Automatically generated MIB
--                                            Added alarm57027 alarmC57027
--  2017-11-23  Symeon Makris (Com Hellas)    Automatically generated MIB
--                                            Added alarm57028 alarmC57028
--  2017-11-28  Dimitris Iosifidis            Automatically generated MIB
--                                            Added alarm57029 alarmC57029
--  2018-01-17  Lazaros,,,                    Automatically generated MIB
--                                            Added alarm04076 alarmC04076
--  2018-01-18  root                          Automatically generated MIB
--                                            Added alarm04090 alarmC04090
--  2018-01-22  Todor Todorov                 Automatically generated MIB
--                                            Added alarm56997 alarmC56997
--  2018-02-07  Dimitris Iosifidis            Automatically generated MIB
--                                            Added alarm04073 alarmC04073
--  2016-09-26  Paul Beatty (Com US)          Automatically generated MIB
--                                            Added alarm04101 alarmC04101
--  2018-03-14  Lars Hermanns,,,              Automatically generated MIB
--                                            Added alarm61100 alarmC61100
--  2018-04-02  Lazaros,,,                    Automatically generated MIB
--                                            Added alarm04120 alarmC04120
--                                            Added alarm04121 alarmC04121
--                                            Added alarm04122 alarmC04122
--  2018-04-18  Michalis Douskas (PH Hellas Git)Automatically generated MIB
--  2018-05-03  Michalis Douskas (PH Hellas Git)Automatically generated MIB
--                                            Deprecated alarm04083 alarmC04083
--  2018-05-10  Lazaros,,,                    Automatically generated MIB
--  2018-05-16  lefteris,,,                   Automatically generated MIB
--                                            Added alarm09009 alarmC09009
--                                            Added alarm09010 alarmC09010
--  2018-05-24  Stefan Wuttich                Automatically generated MIB
--                                            Added alarm56998 alarmC56998
--  2018-06-29  Dimitris Iosifidis            Automatically generated MIB
--                                            Added alarm57030 alarmC57030
--  2018-07-04  Konstantinos Kontopoulos (Com Hellas Git)Automatically generated MIB
--                                            Added alarm05008 alarmC05008
--  2018-07-23  Nick Tzavalas,,,              Automatically generated MIB
--                                            Added alarm62001 alarmC62001
--  2018-07-23  Nick Tzavalas,,,              Automatically generated MIB
--  2018-08-29  Nick Tzavalas,,,              Automatically generated MIB
--                                            Added alarm57033 alarmC57033
--                                            Added alarm57034 alarmC57034
--  2019-01-31  Todor Todorov                 Automatically generated MIB
--                                            Added alarm56999 alarmC56999
--  2019-03-11  Sathyanarayanan Vittal (Com US)Automatically generated MIB
--                                            Added alarm10018 alarmC10018
--  2019-04-08                                Automatically generated MIB
--                                            Added alarm56510 alarmC56510
--                                            Added alarm56511 alarmC56511
--                                            Added alarm56520 alarmC56520
--                                            Added alarm56521 alarmC56521
--  2019-05-09  Lars,,,                       Automatically generated MIB
--                                            Added alarm61101 alarmC61101
--                                            Added alarm61102 alarmC61102
--                                            Added alarm61103 alarmC61103
--  2019-05-16                                Automatically generated MIB 510,511,520,521 - Minor -> Major
--  2019-06-21  Dimitrios Iosifidis,,,        Automatically generated MIB
-- ==================================================================


IMPORTS
    MODULE-IDENTITY, OBJECT-TYPE, Integer32, NOTIFICATION-TYPE, enterprises        FROM SNMPv2-SMI
    DisplayString, RowStatus                                                                                     FROM SNMPv2-TC
    senProducts                                                                                                        FROM SEN-ROOT-MIB;

        ansible                OBJECT IDENTIFIER ::= { senProducts 6 }
                                -- Ansible product-specific MIBs
                                --                = senProducts         6
                                --                = enterprises sen   1 6
                                --                = enterprises 32804 1 6
                                --                = 1 3 6 1 4 1 32804 1 6


        alarms                MODULE-IDENTITY
        LAST-UPDATED        "201906210000Z"
        ORGANIZATION        "Unify"
        CONTACT-INFO        "Uwe Grothe
                                        Postal:        5500 Broken Sound Blvd NW
                                                        Boca Raton, FL 33487-3501
                                        E-mail:        uwe.grothe@unify.com"

        DESCRIPTION        "This MIB module implements SNMP Alarms.
                            An alarm is uniquely identified by the trap name
                            (mainly the last two numbers of the trap OID)
                            and the neName.
                            An alarm trap is a trap with a non-cleared severity.
                            It is cleared by the same trap
                            with the same neName and a severity of clear.
                            An existing alarm can be modified by a trap with the
                            same OID and neName but with one or more modified values,
                            e.g. for severity, nodes, or faultyObject"

        ::= { ansible 1 }

        trapParameters              OBJECT IDENTIFIER ::= { alarms 1 }
        eventCommon                 OBJECT IDENTIFIER ::= { alarms 2 }
        eventGroups                 OBJECT IDENTIFIER ::= { alarms 3 }
        eventGroupsC                OBJECT IDENTIFIER ::= { alarms 4 }

        eventGroup01                OBJECT IDENTIFIER ::= { eventGroups  1 }
        eventGroup02                OBJECT IDENTIFIER ::= { eventGroups  2 }
        eventGroup03                OBJECT IDENTIFIER ::= { eventGroups  3 }
        eventGroup04                OBJECT IDENTIFIER ::= { eventGroups  4 }
        eventGroup05                OBJECT IDENTIFIER ::= { eventGroups  5 }
        eventGroup06                OBJECT IDENTIFIER ::= { eventGroups  6 }
        eventGroup07                OBJECT IDENTIFIER ::= { eventGroups  7 }        -- deprecated
        eventGroup08                OBJECT IDENTIFIER ::= { eventGroups  8 }
        eventGroup09                OBJECT IDENTIFIER ::= { eventGroups  9 }
        eventGroup10                OBJECT IDENTIFIER ::= { eventGroups 10 }
        eventGroup11                OBJECT IDENTIFIER ::= { eventGroups 11 }        -- deprecated
        eventGroup12                OBJECT IDENTIFIER ::= { eventGroups 12 }
        eventGroup13                OBJECT IDENTIFIER ::= { eventGroups 13 }
        eventGroup14                OBJECT IDENTIFIER ::= { eventGroups 14 }
        eventGroup15                OBJECT IDENTIFIER ::= { eventGroups 15 }        -- deprecated
        eventGroup16                OBJECT IDENTIFIER ::= { eventGroups 16 }        -- deprecated
        eventGroup17                OBJECT IDENTIFIER ::= { eventGroups 17 }
        eventGroup18                OBJECT IDENTIFIER ::= { eventGroups 18 }        -- deprecated
        eventGroup19                OBJECT IDENTIFIER ::= { eventGroups 19 }        -- deprecated
        eventGroup20                OBJECT IDENTIFIER ::= { eventGroups 20 }
        eventGroup21                OBJECT IDENTIFIER ::= { eventGroups 21 }
        eventGroup22                OBJECT IDENTIFIER ::= { eventGroups 22 }
        eventGroup23                OBJECT IDENTIFIER ::= { eventGroups 23 }
        eventGroup50                OBJECT IDENTIFIER ::= { eventGroups 50 }
        eventGroup53                OBJECT IDENTIFIER ::= { eventGroups 53 }
        eventGroup54                OBJECT IDENTIFIER ::= { eventGroups 54 }
        eventGroup55                OBJECT IDENTIFIER ::= { eventGroups 55 }        -- deprecated
        eventGroup56                OBJECT IDENTIFIER ::= { eventGroups 56 }
        eventGroup57                OBJECT IDENTIFIER ::= { eventGroups 57 }
        eventGroup58                OBJECT IDENTIFIER ::= { eventGroups 58 }
        eventGroup59                OBJECT IDENTIFIER ::= { eventGroups 59 }
        eventGroup60                OBJECT IDENTIFIER ::= { eventGroups 60 }
        eventGroup61                OBJECT IDENTIFIER ::= { eventGroups 61 }
        eventGroup62                OBJECT IDENTIFIER ::= { eventGroups 62 }
        eventGroup80                OBJECT IDENTIFIER ::= { eventGroups 80 }
        eventGroup81                OBJECT IDENTIFIER ::= { eventGroups 81 }        -- deprecated
        eventGroup82                OBJECT IDENTIFIER ::= { eventGroups 82 }        -- deprecated
        eventGroup90                OBJECT IDENTIFIER ::= { eventGroups 90 }

        eventGroupC01               OBJECT IDENTIFIER ::= { eventGroupsC  1 }
        eventGroupC02               OBJECT IDENTIFIER ::= { eventGroupsC  2 }
        eventGroupC03               OBJECT IDENTIFIER ::= { eventGroupsC  3 }
        eventGroupC04               OBJECT IDENTIFIER ::= { eventGroupsC  4 }
        eventGroupC05               OBJECT IDENTIFIER ::= { eventGroupsC  5 }
        eventGroupC06               OBJECT IDENTIFIER ::= { eventGroupsC  6 }
        eventGroupC07               OBJECT IDENTIFIER ::= { eventGroupsC  7 }        -- deprecated
        eventGroupC08               OBJECT IDENTIFIER ::= { eventGroupsC  8 }
        eventGroupC09               OBJECT IDENTIFIER ::= { eventGroupsC  9 }
        eventGroupC10               OBJECT IDENTIFIER ::= { eventGroupsC 10 }
        eventGroupC11               OBJECT IDENTIFIER ::= { eventGroupsC 11 }        -- deprecated
        eventGroupC12               OBJECT IDENTIFIER ::= { eventGroupsC 12 }
        eventGroupC13               OBJECT IDENTIFIER ::= { eventGroupsC 13 }
        eventGroupC14               OBJECT IDENTIFIER ::= { eventGroupsC 14 }
        eventGroupC15               OBJECT IDENTIFIER ::= { eventGroupsC 15 }        -- deprecated
        eventGroupC16               OBJECT IDENTIFIER ::= { eventGroupsC 16 }        -- deprecated
        eventGroupC17               OBJECT IDENTIFIER ::= { eventGroupsC 17 }
        eventGroupC18               OBJECT IDENTIFIER ::= { eventGroupsC 18 }        -- deprecated
        eventGroupC19               OBJECT IDENTIFIER ::= { eventGroupsC 19 }        -- deprecated
        eventGroupC20               OBJECT IDENTIFIER ::= { eventGroupsC 20 }
        eventGroupC21               OBJECT IDENTIFIER ::= { eventGroupsC 21 }
        eventGroupC22               OBJECT IDENTIFIER ::= { eventGroupsC 22 }
        eventGroupC23               OBJECT IDENTIFIER ::= { eventGroupsC 23 }
        eventGroupC50               OBJECT IDENTIFIER ::= { eventGroupsC 50 }
        eventGroupC53               OBJECT IDENTIFIER ::= { eventGroupsC 53 }
        eventGroupC54               OBJECT IDENTIFIER ::= { eventGroupsC 54 }
        eventGroupC55               OBJECT IDENTIFIER ::= { eventGroupsC 55 }        -- deprecated
        eventGroupC56               OBJECT IDENTIFIER ::= { eventGroupsC 56 }
        eventGroupC57               OBJECT IDENTIFIER ::= { eventGroupsC 57 }
        eventGroupC58               OBJECT IDENTIFIER ::= { eventGroupsC 58 }
        eventGroupC59               OBJECT IDENTIFIER ::= { eventGroupsC 59 }
        eventGroupC60               OBJECT IDENTIFIER ::= { eventGroupsC 60 }
        eventGroupC61               OBJECT IDENTIFIER ::= { eventGroupsC 61 }
        eventGroupC62               OBJECT IDENTIFIER ::= { eventGroupsC 62 }
        eventGroupC80               OBJECT IDENTIFIER ::= { eventGroupsC 80 }
        eventGroupC81               OBJECT IDENTIFIER ::= { eventGroupsC 81 }        -- deprecated
        eventGroupC82               OBJECT IDENTIFIER ::= { eventGroupsC 82 }        -- deprecated
        eventGroupC90               OBJECT IDENTIFIER ::= { eventGroupsC 90 }

        --********************************************************************
        -- Alarm Trap Parameters:
        --********************************************************************

        neName                     OBJECT-TYPE
        SYNTAX                     DisplayString
        MAX-ACCESS                 not-accessible
        STATUS                     current
        DESCRIPTION                "name of the network element sending the alarm"
        ::= { trapParameters 1 }


        neType                     OBJECT-TYPE
        SYNTAX                     DisplayString
        MAX-ACCESS                 not-accessible
        STATUS                     current
        DESCRIPTION                "Indicate the network element type"
        ::= { trapParameters 2 }


        eventGroupName             OBJECT-TYPE
        SYNTAX                     DisplayString
        MAX-ACCESS                 not-accessible
        STATUS                     current
        DESCRIPTION                "corresponds to the eventGroup,
                                    the second last number of the trap OID."
        ::= { trapParameters 3 }


        eventName                  OBJECT-TYPE
        SYNTAX                     DisplayString
        MAX-ACCESS                 not-accessible
        STATUS                     current
        DESCRIPTION                "corresponds to the event within the eventGroup
                                    reported by the trap, the last number of the trap OID."
        ::= { trapParameters 4 }


        correlationId              OBJECT-TYPE
        SYNTAX                     DisplayString
        MAX-ACCESS                 not-accessible
        STATUS                     current
        DESCRIPTION                "same value for traps associated with the same active alarm."
        ::= { trapParameters 5 }


        severity                   OBJECT-TYPE
        SYNTAX                     INTEGER        {indeterminate(0),   -- not used
                                        critical(1),
                                        major(2),
                                        minor(3),
                                        warning(4),                    -- not used
                                        cleared(5) }
        MAX-ACCESS                 not-accessible
        STATUS                     current
        DESCRIPTION                "corresponds to X.721/X.733:PerceivedSeverity.
                                    indeterminate and warning are not used.
                                    critical, major, ,and minor correspond to an alarm.
                                    cleared corresponds to an alarm clearance event, which clears
                                    all alarms of the network element that
                                    had been reported by this trap."
        ::= { trapParameters 6 }


        eventTime                  OBJECT-TYPE
        SYNTAX                     DisplayString
        MAX-ACCESS                 not-accessible
        STATUS                     current
        DESCRIPTION                "An element of X.710: Parameter contains
                                    the time of generation of the event,
                                    The EventTime is a GeneralizedTime (defined in X.208),
                                    format is YYYYMMDDhhmmss.f+hhmm where
                                    Y year
                                    M month in year
                                    D day in month
                                    h hour in day (0-23)
                                    m minute in hour
                                    s second in minute
                                    f tenth part of second
                                    +hhmm        local time offset(+-) to UTC time.
                                    Time represents the local time (t1), and the time
                                    differential (t2) enables UTC time to be determined as follows:
                                    UTC time = t1 - t2"
        ::= { trapParameters 7 }


        nodes                      OBJECT-TYPE
        SYNTAX                     DisplayString
        MAX-ACCESS                 not-accessible
        STATUS                     current
        DESCRIPTION                "comma delimited list of node names associated with the alarm"
        ::= { trapParameters 8 }


        faultyObject               OBJECT-TYPE
        SYNTAX                     DisplayString
        MAX-ACCESS                 not-accessible
        STATUS                     current
        DESCRIPTION                "Specifies the component of the network element at fault."
        ::= { trapParameters 9 }


        monitoredValue             OBJECT-TYPE
        SYNTAX                     DisplayString
        MAX-ACCESS                 not-accessible
        STATUS                     current
        DESCRIPTION                "Specifies the value of the current condition of the system
                                    for this particular alarm"
        ::= { trapParameters 10 }


        thresholdValues            OBJECT-TYPE
        SYNTAX                     DisplayString
        MAX-ACCESS                 not-accessible
        STATUS                     current
        DESCRIPTION                "Specifies the values that needs to be crossed by
                                    monitored-value for an alarm to be generated.
                                    Up to 3 values separated by comma can be defined
                                    associated with the severities minor,major,critical.
                                    e.g. ,3,8 means major alarm when monitored value is 3 or higher
                                    and critical alarm when 8 or higher. No minor alarm"
        ::= { trapParameters 11 }


        info                       OBJECT-TYPE
        SYNTAX                     DisplayString
        MAX-ACCESS                 not-accessible
        STATUS                     current
        DESCRIPTION                "Indicate the network element type"
        ::= { trapParameters 12 }


        --********************************************************************
        -- Common Trap Definitions
        --********************************************************************


        networkElementStarting     NOTIFICATION-TYPE
        OBJECTS        {        neName,
                                neType,
                                eventTime }
        STATUS                     current
        DESCRIPTION                "This trap reports that the network element is starting up.
                                    All alarms of this network element shall be deleted."
        ::= { eventCommon 1 }

        --********************************************************************
        -- Alarm Trap Definitions for alarms sent by a particular node
        -- (using eventGroup)
        --********************************************************************

        --********************************************************************
        -- Alarm Trap Definitions for event group 01: Platform
        --********************************************************************

        alarm01001 NOTIFICATION-TYPE
        OBJECTS        {        neName,
                                neType,
                                eventGroupName,                        -- 01: Platform
                                eventName,                             -- 001: InvalidAlarmConfiguration
                                correlationId,
                                severity,
                                eventTime,
                                faultyObject,
                                monitoredValue,
                                thresholdValues,
                                info   }
        STATUS                current
        DESCRIPTION        "Spontaneous Alarm from the managed network element:
                            The alarm configuration has problems.
                            Check the problem listed in the faulty object and correct."
        ::= { eventGroup01 1 }

        alarm01002 NOTIFICATION-TYPE
        OBJECTS        {        neName,
                                neType,
                                eventGroupName,                        -- 01: Platform
                                eventName,                             -- 002: InvalidTimezoneConfiguration
                                correlationId,
                                severity,
                                eventTime,
                                faultyObject,
                                monitoredValue,
                                thresholdValues,
                                info   }
        STATUS                current
        DESCRIPTION        "Spontaneous Alarm from the managed network element:
                            The timezone configured in the datacenter configuration in the ZooKeeper database is not one of values supported by the Linux Operating System. An invalid timezone will be ignored so the timezone will remain as the default timezone (UTC) or the last valid timezone that was successfully configured.
                            Manually change the timezone in the datacenter configuration in the ZooKeeper database to a valid timezone. Valid timezones can be found under directory /usr/share/zoneinfo (e.g. US/Eastern)."
        ::= { eventGroup01 2 }

        alarm01003 NOTIFICATION-TYPE
        OBJECTS        {        neName,
                                neType,
                                eventGroupName,                        -- 01: Platform
                                eventName,                             -- 003: UnknownAlarmId
                                correlationId,
                                severity,
                                eventTime,
                                faultyObject,
                                monitoredValue,
                                thresholdValues,
                                info   }
        STATUS                current
        DESCRIPTION        "Spontaneous Alarm from the managed network element:
                            An alarm has been raised or used with an unknown group ID and/or event ID.
                            Check if the alarm should be raised/used. If correct, add alarm to alarm configuration."
        ::= { eventGroup01 3 }

        alarm01004 NOTIFICATION-TYPE
        OBJECTS        {        neName,
                                neType,
                                eventGroupName,                        -- 01: Platform
                                eventName,                             -- 004: InvalidMonitoredValue
                                correlationId,
                                severity,
                                eventTime,
                                faultyObject,
                                monitoredValue,
                                thresholdValues,
                                info   }
        STATUS                current
        DESCRIPTION        "Spontaneous Alarm from the managed network element:
                            An alarm has been raised or used with an invalid monitored attribute value.
                            Correct code raising the alarm."
        ::= { eventGroup01 4 }

        alarm01005 NOTIFICATION-TYPE
        OBJECTS        {        neName,
                                neType,
                                eventGroupName,                        -- 01: Platform
                                eventName,                             -- 005: FaultyObjectTooLong
                                correlationId,
                                severity,
                                eventTime,
                                faultyObject,
                                monitoredValue,
                                thresholdValues,
                                info   }
        STATUS                current
        DESCRIPTION        "Spontaneous Alarm from the managed network element:
                            An alarm has been raised with a FaultyObject string that is longer than 255. It has been truncated.
                            Correct code raising the alarm."
        ::= { eventGroup01 5 }

        alarm01006 NOTIFICATION-TYPE
        OBJECTS        {        neName,
                                neType,
                                eventGroupName,                        -- 01: Platform
                                eventName,                             -- 006: AddlInfoTooLong
                                correlationId,
                                severity,
                                eventTime,
                                faultyObject,
                                monitoredValue,
                                thresholdValues,
                                info   }
        STATUS                current
        DESCRIPTION        "Spontaneous Alarm from the managed network element:
                            An alarm has been raised with an Addl Info string that is longer than 255. It has been truncated.
                            Correct code raising the alarm."
        ::= { eventGroup01 6 }

        alarm01007 NOTIFICATION-TYPE
        OBJECTS        {        neName,
                                neType,
                                eventGroupName,                        -- 01: Platform
                                eventName,                             -- 007: TooManyAlarmParameters
                                correlationId,
                                severity,
                                eventTime,
                                faultyObject,
                                monitoredValue,
                                thresholdValues,
                                info   }
        STATUS                current
        DESCRIPTION        "Spontaneous Alarm from the managed network element:
                            There is additional text after AddlInfo in the reported alarm string.
                            Correct code raising the alarm."
        ::= { eventGroup01 7 }

        alarm01011 NOTIFICATION-TYPE
        OBJECTS        {        neName,
                                neType,
                                eventGroupName,                        -- 01: Platform
                                eventName,                             -- 011: NodeCrashed
                                correlationId,
                                severity,
                                eventTime,
                                faultyObject,
                                monitoredValue,
                                thresholdValues,
                                info   }
        STATUS                current
        DESCRIPTION        "Spontaneous Alarm from the managed network element:
                            The node rebooted because of a Linux O/S crash. The crashes of the last 8 hours are listed under FaultyObject. The addl. Info field contains the content of the README.txt file of the last crash.
                            Check the status of the node and collect debug files. Escalate to development for analysis."
        ::= { eventGroup01 11 }


        --********************************************************************
        -- Alarm Trap Definitions for event group 02: Configuration
        --********************************************************************

        alarm02001 NOTIFICATION-TYPE
        OBJECTS        {        neName,
                                neType,
                                eventGroupName,                        -- 02: Configuration
                                eventName,                             -- 001: InvalidZooData
                                correlationId,
                                severity,
                                eventTime,
                                faultyObject,
                                monitoredValue,
                                thresholdValues,
                                info   }
        STATUS                current
        DESCRIPTION        "Spontaneous Alarm from the managed network element:
                            The node reconfiguration software has found invalid zookeeper data. The node has ignored the zookeeper data and continues with the current old data. The faulty object parameter contains the names of the reconfiguration scripts that found an error.
There is a mismatch between zookeeper stored data as displayed on the mgmt node and the data that are actually stored and used on the node!
                            Check zookeeper data for invalid values, especially in the areas associated with the scripts listed in the faulty object.
Correct faulty data and check that the alarm goes away.
The platform reconfiguration script returns an alarm clear when it reports success to PM."
        ::= { eventGroup02 1 }


        --********************************************************************
        -- Alarm Trap Definitions for event group 03: FileTransfer
        --********************************************************************

        alarm03001 NOTIFICATION-TYPE
        OBJECTS        {        neName,
                                neType,
                                eventGroupName,                        -- 03: FileTransfer
                                eventName,                             -- 001: ExportFailing
                                correlationId,
                                severity,
                                eventTime,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroup03 1 }

        alarm03002 NOTIFICATION-TYPE
        OBJECTS        {        neName,
                                neType,
                                eventGroupName,                        -- 03: FileTransfer
                                eventName,                             -- 002: ExportFailing
                                correlationId,
                                severity,
                                eventTime,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroup03 2 }

        alarm03003 NOTIFICATION-TYPE
        OBJECTS        {        neName,
                                neType,
                                eventGroupName,                        -- 03: FileTransfer
                                eventName,                             -- 003: ExportFailing
                                correlationId,
                                severity,
                                eventTime,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroup03 3 }


        --********************************************************************
        -- Alarm Trap Definitions for event group 04: Process
        --********************************************************************

        alarm04001 NOTIFICATION-TYPE
        OBJECTS        {        neName,
                                neType,
                                eventGroupName,                        -- 04: Process
                                eventName,                             -- 001: PmAborted
                                correlationId,
                                severity,
                                eventTime,
                                faultyObject,
                                monitoredValue,
                                thresholdValues,
                                info   }
        STATUS                current
        DESCRIPTION        "Spontaneous Alarm from the managed network element:
                            Process Monitoring has aborted.
                            Check configuration files and get logs in debug level 7."
        ::= { eventGroup04 1 }

        alarm04002 NOTIFICATION-TYPE
        OBJECTS        {        neName,
                                neType,
                                eventGroupName,                        -- 04: Process
                                eventName,                             -- 002: NetworkNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 2 }

        alarm04003 NOTIFICATION-TYPE
        OBJECTS        {        neName,
                                neType,
                                eventGroupName,                        -- 04: Process
                                eventName,                             -- 003: RoutesNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 3 }

        alarm04004 NOTIFICATION-TYPE
        OBJECTS        {        neName,
                                neType,
                                eventGroupName,                        -- 04: Process
                                eventName,                             -- 004: GmondNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 4 }

        alarm04005 NOTIFICATION-TYPE
        OBJECTS        {        neName,
                                neType,
                                eventGroupName,                        -- 04: Process
                                eventName,                             -- 005: hsflowdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 5 }

        alarm04006 NOTIFICATION-TYPE
        OBJECTS        {        neName,
                                neType,
                                eventGroupName,                        -- 04: Process
                                eventName,                             -- 006: jmxtransNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 6 }

        alarm04007 NOTIFICATION-TYPE
        OBJECTS        {        neName,
                                neType,
                                eventGroupName,                        -- 04: Process
                                eventName,                             -- 007: ntpNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 7 }

        alarm04008 NOTIFICATION-TYPE
        OBJECTS        {        neName,
                                neType,
                                eventGroupName,                        -- 04: Process
                                eventName,                             -- 008: syslogNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 8 }

        alarm04009 NOTIFICATION-TYPE
        OBJECTS        {        neName,
                                neType,
                                eventGroupName,                        -- 04: Process
                                eventName,                             -- 009: sshdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 9 }

        alarm04010 NOTIFICATION-TYPE
        OBJECTS        {        neName,
                                neType,
                                eventGroupName,                        -- 04: Process
                                eventName,                             -- 010: snmpdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 10 }

        alarm04011 NOTIFICATION-TYPE
        OBJECTS        {        neName,
                                neType,
                                eventGroupName,                        -- 04: Process
                                eventName,                             -- 011: idsNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 11 }

        alarm04012 NOTIFICATION-TYPE
        OBJECTS        {        neName,
                                neType,
                                eventGroupName,                        -- 04: Process
                                eventName,                             -- 012: logstashNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 12 }

        alarm04013 NOTIFICATION-TYPE
        OBJECTS        {        neName,
                                neType,
                                eventGroupName,                        -- 04: Process
                                eventName,                             -- 013: TraceDriverNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 13 }

        alarm04014 NOTIFICATION-TYPE
        OBJECTS        {        neName,
                                neType,
                                eventGroupName,                        -- 04: Process
                                eventName,                             -- 014: LoggingDriverNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 14 }

        alarm04015 NOTIFICATION-TYPE
        OBJECTS        {        neName,
                                neType,
                                eventGroupName,                        -- 04: Process
                                eventName,                             -- 015: LoggingProcessNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 15 }

        alarm04016 NOTIFICATION-TYPE
        OBJECTS        {        neName,
                                neType,
                                eventGroupName,                        -- 04: Process
                                eventName,                             -- 016: PlatAlarmNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 16 }

        alarm04017 NOTIFICATION-TYPE
        OBJECTS        {        neName,
                                neType,
                                eventGroupName,                        -- 04: Process
                                eventName,                             -- 017: PlatZooClientNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 17 }

        alarm04018 NOTIFICATION-TYPE
        OBJECTS        {        neName,
                                neType,
                                eventGroupName,                        -- 04: Process
                                eventName,                             -- 018: PlatPsrNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 18 }

        alarm04019 NOTIFICATION-TYPE
        OBJECTS        {        neName,
                                neType,
                                eventGroupName,                        -- 04: Process
                                eventName,                             -- 019: PlatFileExportNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 19 }

        alarm04020 NOTIFICATION-TYPE
        OBJECTS        {        neName,
                                neType,
                                eventGroupName,                        -- 04: Process
                                eventName,                             -- 020: PlatPstackNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 20 }

        alarm04021 NOTIFICATION-TYPE
        OBJECTS        {        neName,
                                neType,
                                eventGroupName,                        -- 04: Process
                                eventName,                             -- 021: PlatMonitorNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 21 }

        alarm04022 NOTIFICATION-TYPE
        OBJECTS        {        neName,
                                neType,
                                eventGroupName,                        -- 04: Process
                                eventName,                             -- 022: NetReceiverNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 22 }

        alarm04023 NOTIFICATION-TYPE
        OBJECTS        {        neName,
                                neType,
                                eventGroupName,                        -- 04: Process
                                eventName,                             -- 023: TcaNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 23 }

        alarm04024 NOTIFICATION-TYPE
        OBJECTS        {        neName,
                                neType,
                                eventGroupName,                        -- 04: Process
                                eventName,                             -- 024: FileExportScannerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 24 }

        alarm04025 NOTIFICATION-TYPE
        OBJECTS        {        neName,
                                neType,
                                eventGroupName,                        -- 04: Process
                                eventName,                             -- 025: PlatAuditSumNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 25 }

        alarm04026 NOTIFICATION-TYPE
        OBJECTS        {        neName,
                                neType,
                                eventGroupName,                        -- 04: Process
                                eventName,                             -- 026: PlatLogRotateNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 26 }

        alarm04027 NOTIFICATION-TYPE
        OBJECTS        {        neName,
                                neType,
                                eventGroupName,                        -- 04: Process
                                eventName,                             -- 027: PlatFllNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 27 }

        alarm04028 NOTIFICATION-TYPE
        OBJECTS        {        neName,
                                neType,
                                eventGroupName,                        -- 04: Process
                                eventName,                             -- 028: PlatXtreemDirNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 28 }

        alarm04029 NOTIFICATION-TYPE
        OBJECTS        {        neName,
                                neType,
                                eventGroupName,                        -- 04: Process
                                eventName,                             -- 029: PlatXtreemMrcNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 29 }

        alarm04030 NOTIFICATION-TYPE
        OBJECTS        {        neName,
                                neType,
                                eventGroupName,                        -- 04: Process
                                eventName,                             -- 030: PlatXtreemOsdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 30 }

        alarm04031 NOTIFICATION-TYPE
        OBJECTS        {        neName,
                                neType,
                                eventGroupName,                        -- 04: Process
                                eventName,                             -- 031: PlatCassandraNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 31 }

        alarm04032 NOTIFICATION-TYPE
        OBJECTS        {        neName,
                                neType,
                                eventGroupName,                        -- 04: Process
                                eventName,                             -- 032: PlatElasticSearchNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 32 }

        alarm04033 NOTIFICATION-TYPE
        OBJECTS        {        neName,
                                neType,
                                eventGroupName,                        -- 04: Process
                                eventName,                             -- 033: PlatClamAVNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 33 }

        alarm04034 NOTIFICATION-TYPE
        OBJECTS        {        neName,
                                neType,
                                eventGroupName,                        -- 04: Process
                                eventName,                             -- 034: PlatStatsServerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 34 }

        alarm04035 NOTIFICATION-TYPE
        OBJECTS        {        neName,
                                neType,
                                eventGroupName,                        -- 04: Process
                                eventName,                             -- 035: ZooKeeperServerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 35 }

        alarm04040 NOTIFICATION-TYPE
        OBJECTS        {        neName,
                                neType,
                                eventGroupName,                        -- 04: Process
                                eventName,                             -- 040: AccessRedisNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 40 }

        alarm04041 NOTIFICATION-TYPE
        OBJECTS        {        neName,
                                neType,
                                eventGroupName,                        -- 04: Process
                                eventName,                             -- 041: AccessRedis-clusterNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Redis-cluster configuration."
        ::= { eventGroup04 41 }

        alarm04042 NOTIFICATION-TYPE
        OBJECTS        {        neName,
                                neType,
                                eventGroupName,                        -- 04: Process
                                eventName,                             -- 042: AccessTurnServerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check TurnServer configuration."
        ::= { eventGroup04 42 }

        alarm04043 NOTIFICATION-TYPE
        OBJECTS        {        neName,
                                neType,
                                eventGroupName,                        -- 04: Process
                                eventName,                             -- 043: AccessNodeAppNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check NodeApp configuration."
        ::= { eventGroup04 43 }

        alarm04044 NOTIFICATION-TYPE
        OBJECTS        {        neName,
                                neType,
                                eventGroupName,                        -- 04: Process
                                eventName,                             -- 044: AccessLvsNodeNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check LvsNode configuration."
        ::= { eventGroup04 44 }

        alarm04045 NOTIFICATION-TYPE
        OBJECTS        {        neName,
                                neType,
                                eventGroupName,                        -- 04: Process
                                eventName,                             -- 045: AccessNginxNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Nginx configuration."
        ::= { eventGroup04 45 }

        alarm04046 NOTIFICATION-TYPE
        OBJECTS        {        neName,
                                neType,
                                eventGroupName,                        -- 04: Process
                                eventName,                             -- 046: AccessMetricsNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Metrics configuration."
        ::= { eventGroup04 46 }

        alarm04047 NOTIFICATION-TYPE
        OBJECTS        {        neName,
                                neType,
                                eventGroupName,                        -- 04: Process
                                eventName,                             -- 047: AccessAuditAppNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Audit configuration."
        ::= { eventGroup04 47 }

        alarm04048 NOTIFICATION-TYPE
        OBJECTS        {        neName,
                                neType,
                                eventGroupName,                        -- 04: Process
                                eventName,                             -- 048: AccessRedis-auditNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Redis configuration."
        ::= { eventGroup04 48 }

        alarm04060 NOTIFICATION-TYPE
        OBJECTS        {        neName,
                                neType,
                                eventGroupName,                        -- 04: Process
                                eventName,                             -- 060: LoadBalancerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Load Balancer configuration."
        ::= { eventGroup04 60 }

        alarm04070 NOTIFICATION-TYPE
        OBJECTS        {        neName,
                                neType,
                                eventGroupName,                        -- 04: Process
                                eventName,                             -- 070: AnsibleVirgoNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroup04 70 }

        alarm04071 NOTIFICATION-TYPE
        OBJECTS        {        neName,
                                neType,
                                eventGroupName,                        -- 04: Process
                                eventName,                             -- 071: HazelcastNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroup04 71 }

        alarm04072 NOTIFICATION-TYPE
        OBJECTS        {        neName,
                                neType,
                                eventGroupName,                        -- 04: Process
                                eventName,                             -- 072: RabbitMQNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroup04 72 }

        alarm04073 NOTIFICATION-TYPE
        OBJECTS        {        neName,
                                neType,
                                eventGroupName,                        -- 04: Process
                                eventName,                             -- 073: RabbitMQBootNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Process configuration at Zookeeper Nodes."
        ::= { eventGroup04 73 }

        alarm04075 NOTIFICATION-TYPE
        OBJECTS        {        neName,
                                neType,
                                eventGroupName,                        -- 04: Process
                                eventName,                             -- 075: MediaServerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroup04 75 }

        alarm04076 NOTIFICATION-TYPE
        OBJECTS        {        neName,
                                neType,
                                eventGroupName,                        -- 04: Process
                                eventName,                             -- 076: MacLvsNodeNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check LvsNode configuration on MAC node."
        ::= { eventGroup04 76 }

        alarm04080 NOTIFICATION-TYPE
        OBJECTS        {        neName,
                                neType,
                                eventGroupName,                        -- 04: Process
                                eventName,                             -- 080: PostgresqlNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 80 }

        alarm04082 NOTIFICATION-TYPE
        OBJECTS        {        neName,
                                neType,
                                eventGroupName,                        -- 04: Process
                                eventName,                             -- 082: TomcatNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 82 }

        alarm04084 NOTIFICATION-TYPE
        OBJECTS        {        neName,
                                neType,
                                eventGroupName,                        -- 04: Process
                                eventName,                             -- 084: AlarmManagerDNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 84 }

        alarm04085 NOTIFICATION-TYPE
        OBJECTS        {        neName,
                                neType,
                                eventGroupName,                        -- 04: Process
                                eventName,                             -- 085: SolrdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 85 }

        alarm04086 NOTIFICATION-TYPE
        OBJECTS        {        neName,
                                neType,
                                eventGroupName,                        -- 04: Process
                                eventName,                             -- 086: FilemgrdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 86 }

        alarm04087 NOTIFICATION-TYPE
        OBJECTS        {        neName,
                                neType,
                                eventGroupName,                        -- 04: Process
                                eventName,                             -- 087: LogmgrdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 87 }

        alarm04088 NOTIFICATION-TYPE
        OBJECTS        {        neName,
                                neType,
                                eventGroupName,                        -- 04: Process
                                eventName,                             -- 088: Apache2NotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 88 }

        alarm04089 NOTIFICATION-TYPE
        OBJECTS        {        neName,
                                neType,
                                eventGroupName,                        -- 04: Process
                                eventName,                             -- 089: GmetadNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 89 }

        alarm04083 NOTIFICATION-TYPE
        OBJECTS        {        neName,
                                neType,
                                eventGroupName,                        -- 04: Process
                                eventName,                             -- 083: RRDCachedNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 83 }

        alarm04090 NOTIFICATION-TYPE
        OBJECTS        {        neName,
                                neType,
                                eventGroupName,                        -- 04: Process
                                eventName,                             -- 090: CassandraReaperNotRunning
                                correlationId,
                                severity,
                                eventTime,
                                faultyObject,
                                monitoredValue,
                                thresholdValues,
                                info   }
        STATUS                current
        DESCRIPTION        "Spontaneous Alarm from the managed network element:
                            The node process manager has found that the Cassandra Reaper process/application is not running. It either could not be started during startup or it failed during normal operation. Usually the process is restarted automatically. In some cases the problem might even escalate to a full node restart.
                            Check Management configuration."
        ::= { eventGroup04 90 }

        alarm04095 NOTIFICATION-TYPE
        OBJECTS        {        neName,
                                neType,
                                eventGroupName,                        -- 04: Process
                                eventName,                             -- 095: ImpManagementNotRunning
                                correlationId,
                                severity,
                                eventTime,
                                faultyObject,
                                monitoredValue,
                                thresholdValues,
                                info   }
        STATUS                current
        DESCRIPTION        "Spontaneous Alarm from the managed network element:
                            The node process manager has found the IMP Management application is not running. It either could not be started during startup or it failed during normal operation. Usually the process is restarted automatically. In some cases the problem might even escalate to a full node restart.
                            Check Management configuration."
        ::= { eventGroup04 95 }

        alarm04100 NOTIFICATION-TYPE
        OBJECTS        {        neName,
                                neType,
                                eventGroupName,                        -- 04: Process
                                eventName,                             -- 100: PlatBackupServerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 100 }

        alarm04101 NOTIFICATION-TYPE
        OBJECTS        {        neName,
                                neType,
                                eventGroupName,                        -- 04: Process
                                eventName,                             -- 101: TikaServerNotRunning
                                correlationId,
                                severity,
                                eventTime,
                                faultyObject,
                                monitoredValue,
                                thresholdValues,
                                info   }
        STATUS                current
        DESCRIPTION        "Spontaneous Alarm from the managed network element:
                            The node process manager has found the Tika Server is not running. It either could not be started during startup or it failed during normal operation. Usually the process is restarted automatically. In some cases the problem might even escalate to a full node restart.
                            Check Management configuration."
        ::= { eventGroup04 101 }

        alarm04120 NOTIFICATION-TYPE
        OBJECTS        {        neName,
                                neType,
                                eventGroupName,                        -- 04: Process
                                eventName,                             -- 120: XMPPRedisNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 120 }

        alarm04121 NOTIFICATION-TYPE
        OBJECTS        {        neName,
                                neType,
                                eventGroupName,                        -- 04: Process
                                eventName,                             -- 121: XMPPNginxNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Nginx configuration."
        ::= { eventGroup04 121 }

        alarm04122 NOTIFICATION-TYPE
        OBJECTS        {        neName,
                                neType,
                                eventGroupName,                        -- 04: Process
                                eventName,                             -- 122: XMPPAppNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check XMPP app logs."
        ::= { eventGroup04 122 }


        --********************************************************************
        -- Alarm Trap Definitions for event group 05: ProcessManager
        --********************************************************************

        alarm05001 NOTIFICATION-TYPE
        OBJECTS        {        neName,
                                neType,
                                eventGroupName,                        -- 05: ProcessManager
                                eventName,                             -- 001: InvalidPlatConfiguration
                                correlationId,
                                severity,
                                eventTime,
                                faultyObject,
                                monitoredValue,
                                thresholdValues,
                                info   }
        STATUS                current
        DESCRIPTION        "Spontaneous Alarm from the managed network element:
                            Platform configuration has invalid parameters:
A failure type of 1 means a missing or wrong configuration. PM can run.
2 means missing or wrong process configuration. PM can run but a process has potential problems.
3 means that the configuration file was rejected.
                            Check faulty object to know where the problem is located."
        ::= { eventGroup05 1 }

        alarm05002 NOTIFICATION-TYPE
        OBJECTS        {        neName,
                                neType,
                                eventGroupName,                        -- 05: ProcessManager
                                eventName,                             -- 002: InvalidServerConfiguration
                                correlationId,
                                severity,
                                eventTime,
                                faultyObject,
                                monitoredValue,
                                thresholdValues,
                                info   }
        STATUS                current
        DESCRIPTION        "Spontaneous Alarm from the managed network element:
                            Server configuration has invalid parameters:
A failure type of 1 means a missing or wrong configuration. PM can run.
2 means missing or wrong process configuration. PM can run but a process has potential problems.
3 means that the configuration file was rejected.
                            Check faulty object to know where the problem is located."
        ::= { eventGroup05 2 }

        alarm05003 NOTIFICATION-TYPE
        OBJECTS        {        neName,
                                neType,
                                eventGroupName,                        -- 05: ProcessManager
                                eventName,                             -- 003: CanNotExecuteCommand
                                correlationId,
                                severity,
                                eventTime,
                                faultyObject,
                                monitoredValue,
                                thresholdValues,
                                info   }
        STATUS                current
        DESCRIPTION        "Spontaneous Alarm from the managed network element:
                            One command could not be executed:
Command capabilities = 2 means that the command is important for PM operation and 3 means that it affects node operation.
                            Check faulty object and try to execute it by hand."
        ::= { eventGroup05 3 }

        alarm05004 NOTIFICATION-TYPE
        OBJECTS        {        neName,
                                neType,
                                eventGroupName,                        -- 05: ProcessManager
                                eventName,                             -- 004: UnexpectedBehaviour
                                correlationId,
                                severity,
                                eventTime,
                                faultyObject,
                                monitoredValue,
                                thresholdValues,
                                info   }
        STATUS                current
        DESCRIPTION        "Spontaneous Alarm from the managed network element:
                            PM has found an unexpected behavior during its execution.
1 means that PM is still running and only a feature affected.
2 means that PM is still running, but that process control is affected.
3 means that PM will abort and restart.
                            Check faulty object for function name and line number of the problem."
        ::= { eventGroup05 4 }

        alarm05005 NOTIFICATION-TYPE
        OBJECTS        {        neName,
                                neType,
                                eventGroupName,                        -- 05: ProcessManager
                                eventName,                             -- 005: RecoverEscalation
                                correlationId,
                                severity,
                                eventTime,
                                faultyObject,
                                monitoredValue,
                                thresholdValues,
                                info   }
        STATUS                current
        DESCRIPTION        "Spontaneous Alarm from the managed network element:
                            One or more process cannot be started.
If server Health State is 1 and the process continues to fail, all applicaton processes (Lvl 3) will be restarted.
If the HealthState is 2, the application restart did not work and all platform and all application processes (Lvl 1 and 2 will be restarted.
If the HealthState is 3, the node will be rebooted within 5 minutes.
                            Check which processe(s) are not working. Look for alarms reporting pstacks and coredumps. Collect debug files and send them to the next level of support for analysis."
        ::= { eventGroup05 5 }

        alarm05006 NOTIFICATION-TYPE
        OBJECTS        {        neName,
                                neType,
                                eventGroupName,                        -- 05: ProcessManager
                                eventName,                             -- 006: RebootBecauseofFailedStop
                                correlationId,
                                severity,
                                eventTime,
                                faultyObject,
                                monitoredValue,
                                thresholdValues,
                                info   }
        STATUS                current
        DESCRIPTION        "Spontaneous Alarm from the managed network element:
                            The specified process/application did not react to the stop command called by the  process manager process PM. The node will be rebooted.
                            Collect debug files and escalate to next level of support for fault analysis."
        ::= { eventGroup05 6 }

        alarm05007 NOTIFICATION-TYPE
        OBJECTS        {        neName,
                                neType,
                                eventGroupName,                        -- 05: ProcessManager
                                eventName,                             -- 007: RebootBecauseofPMnotRunning
                                correlationId,
                                severity,
                                eventTime,
                                faultyObject,
                                monitoredValue,
                                thresholdValues,
                                info   }
        STATUS                current
        DESCRIPTION        "Spontaneous Alarm from the managed network element:
                            The process manager process PM is not running. The node will be rebooted.
                            Collect debug files and escalate to next level of support for fault analysis."
        ::= { eventGroup05 7 }

        alarm05008 NOTIFICATION-TYPE
        OBJECTS        {        neName,
                                neType,
                                eventGroupName,                        -- 05: ProcessManager
                                eventName,                             -- 008: DroppedFromL3
                                correlationId,
                                severity,
                                eventTime,
                                faultyObject,
                                monitoredValue,
                                thresholdValues,
                                info   }
        STATUS                current
        DESCRIPTION        "Spontaneous Alarm from the managed network element:
                            The process manager process PM is not running on L3. 
                            Try bringing node up to L3. If unsucessful/unsure collect debug files and escalate to the next level of support for further analysis."
        ::= { eventGroup05 8 }


        --********************************************************************
        -- Alarm Trap Definitions for event group 06: CoreDump
        --********************************************************************

        alarm06001 NOTIFICATION-TYPE
        OBJECTS        {        neName,
                                neType,
                                eventGroupName,                        -- 06: CoreDump
                                eventName,                             -- 001: PstackFound1
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 1 }

        alarm06002 NOTIFICATION-TYPE
        OBJECTS        {        neName,
                                neType,
                                eventGroupName,                        -- 06: CoreDump
                                eventName,                             -- 002: PstackFound2
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 2 }

        alarm06003 NOTIFICATION-TYPE
        OBJECTS        {        neName,
                                neType,
                                eventGroupName,                        -- 06: CoreDump
                                eventName,                             -- 003: PstackFound3
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 3 }

        alarm06004 NOTIFICATION-TYPE
        OBJECTS        {        neName,
                                neType,
                                eventGroupName,                        -- 06: CoreDump
                                eventName,                             -- 004: PstackFound4
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 4 }

        alarm06005 NOTIFICATION-TYPE
        OBJECTS        {        neName,
                                neType,
                                eventGroupName,                        -- 06: CoreDump
                                eventName,                             -- 005: PstackFound5
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 5 }

        alarm06006 NOTIFICATION-TYPE
        OBJECTS        {        neName,
                                neType,
                                eventGroupName,                        -- 06: CoreDump
                                eventName,                             -- 006: CoreDumpFound1
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 6 }

        alarm06007 NOTIFICATION-TYPE
        OBJECTS        {        neName,
                                neType,
                                eventGroupName,                        -- 06: CoreDump
                                eventName,                             -- 007: CoreDumpFound2
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 7 }

        alarm06008 NOTIFICATION-TYPE
        OBJECTS        {        neName,
                                neType,
                                eventGroupName,                        -- 06: CoreDump
                                eventName,                             -- 008: CoreDumpFound3
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 8 }

        alarm06009 NOTIFICATION-TYPE
        OBJECTS        {        neName,
                                neType,
                                eventGroupName,                        -- 06: CoreDump
                                eventName,                             -- 009: CoreDumpFound4
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 9 }

        alarm06010 NOTIFICATION-TYPE
        OBJECTS        {        neName,
                                neType,
                                eventGroupName,                        -- 06: CoreDump
                                eventName,                             -- 010: CoreDumpFound5
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 10 }

        alarm06011 NOTIFICATION-TYPE
        OBJECTS        {        neName,
                                neType,
                                eventGroupName,                        -- 06: CoreDump
                                eventName,                             -- 011: JavaDumpFound1
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 11 }

        alarm06012 NOTIFICATION-TYPE
        OBJECTS        {        neName,
                                neType,
                                eventGroupName,                        -- 06: CoreDump
                                eventName,                             -- 012: JavaDumpFound2
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 12 }

        alarm06013 NOTIFICATION-TYPE
        OBJECTS        {        neName,
                                neType,
                                eventGroupName,                        -- 06: CoreDump
                                eventName,                             -- 013: JavaDumpFound3
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 13 }

        alarm06014 NOTIFICATION-TYPE
        OBJECTS        {        neName,
                                neType,
                                eventGroupName,                        -- 06: CoreDump
                                eventName,                             -- 014: JavaDumpFound4
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 14 }

        alarm06015 NOTIFICATION-TYPE
        OBJECTS        {        neName,
                                neType,
                                eventGroupName,                        -- 06: CoreDump
                                eventName,                             -- 015: JavaDumpFound5
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 15 }


        --********************************************************************
        -- Alarm Trap Definitions for event group 08: Security
        --********************************************************************

        alarm08001 NOTIFICATION-TYPE
        OBJECTS        {        neName,
                                neType,
                                eventGroupName,                        -- 08: Security
                                eventName,                             -- 001: PFRConfigurationFileMissing
                                correlationId,
                                severity,
                                eventTime,
                                faultyObject,
                                monitoredValue,
                                thresholdValues,
                                info   }
        STATUS                current
        DESCRIPTION        "Spontaneous Alarm from the managed network element:
                            The configuration files listed under faultyObject are missing. The packet filter rules for the firewall may not be defined properly, and/or the node's security may be impacted.
                            Log in directly to the node and check the listed files. Escalate to the next level of support, if necessary to find the root cause for the missing file."
        ::= { eventGroup08 1 }

        alarm08002 NOTIFICATION-TYPE
        OBJECTS        {        neName,
                                neType,
                                eventGroupName,                        -- 08: Security
                                eventName,                             -- 002: PFRConfigurationDataMismatch
                                correlationId,
                                severity,
                                eventTime,
                                faultyObject,
                                monitoredValue,
                                thresholdValues,
                                info   }
        STATUS                current
        DESCRIPTION        "Spontaneous Alarm from the managed network element:
                            The packet filter rules that have the names listed under faultyObject are faulty. The packet filter rules for the firewall may not be defined properly, and/or the node's security may be impacted.
                            Log in directly to the node and check the data listed in the faulty object and additional information. Escalate to the next level of support, if necessary to find the root cause for the wrong rules."
        ::= { eventGroup08 2 }

        alarm08003 NOTIFICATION-TYPE
        OBJECTS        {        neName,
                                neType,
                                eventGroupName,                        -- 08: Security
                                eventName,                             -- 003: OutgoingPacketDropped
                                correlationId,
                                severity,
                                eventTime,
                                faultyObject,
                                monitoredValue,
                                thresholdValues,
                                info   }
        STATUS                current
        DESCRIPTION        "Spontaneous Alarm from the managed network element:
                            The node firewall has dropped outgoing IP packets and the number of dropped packets per minute has crossed a threshold. Dropping a packet may be:

(*) valid
(*) A SW error causing invalid packets to be sent
(*) A misconfigured node packet filter rule
(*) indicate a virus.
                            Use the mgmt node debug file collection function to upload debug files from the node that reported the alarm.

Analyze the dropped packets stored in the firewall log file to determine whether the IMP node sends invalid packets. If the packets are sent by valid IMP software escalate to development to either correct the packet filter rules or to modify the IMP SW not to send these packets.

If not, escalate to the next level of service to investigate whether there is a SW virus."
        ::= { eventGroup08 3 }

        alarm08004 NOTIFICATION-TYPE
        OBJECTS        {        neName,
                                neType,
                                eventGroupName,                        -- 08: Security
                                eventName,                             -- 004: IncomingPacketDropped
                                correlationId,
                                severity,
                                eventTime,
                                faultyObject,
                                monitoredValue,
                                thresholdValues,
                                info   }
        STATUS                current
        DESCRIPTION        "Spontaneous Alarm from the managed network element:
                            The node firewall has dropped incoming IP packets and the number of dropped packets per minute has crossed a threshold. Dropping a packet may be:

(*) valid
(*) indicate a misconfiguration of the datacenter firewall
(*) A SW error in a partner IMP node causing invalid packets to be sent
(*) A misconfigured node packet filter rule
(*) indicate an attack.
                            Use the mgmt node debug file collection function to upload debug files from the node that reported the alarm.

Analyze the dropped packets stored in the firewall log file to determine whether the external firewall is mis-configured or whether IMP nodes send invalid packets. In the first case correct the external firewall and in latter case escalate to development to either correct the packet filter rules or to modify the IMP SW not to send these packets."
        ::= { eventGroup08 4 }

        alarm08011 NOTIFICATION-TYPE
        OBJECTS        {        neName,
                                neType,
                                eventGroupName,                        -- 08: Security
                                eventName,                             -- 011: ConfigurationFileMissing
                                correlationId,
                                severity,
                                eventTime,
                                faultyObject,
                                monitoredValue,
                                thresholdValues,
                                info   }
        STATUS                current
        DESCRIPTION        "Spontaneous Alarm from the managed network element:
                            The security files listed under faultyObject are missing. The node may not start properly, not function properly, and/or its security will be impacted.
                            Log in directly to the node and check the listed files. Escalate to the next level of support, if necessary to find the root cause for the missing file."
        ::= { eventGroup08 11 }

        alarm08012 NOTIFICATION-TYPE
        OBJECTS        {        neName,
                                neType,
                                eventGroupName,                        -- 08: Security
                                eventName,                             -- 012: ConfigurationDataMismatch
                                correlationId,
                                severity,
                                eventTime,
                                faultyObject,
                                monitoredValue,
                                thresholdValues,
                                info   }
        STATUS                current
        DESCRIPTION        "Spontaneous Alarm from the managed network element:
                            Data in the security files listed under faultyObject are wrong, missing or implausible. The node may not start properly, not function properly, and/or its security will be impacted.
                            Log in directly to the node and check the listed files. Escalate to the next level of support, if necessary to find the root cause for the wrong data."
        ::= { eventGroup08 12 }

        alarm08013 NOTIFICATION-TYPE
        OBJECTS        {        neName,
                                neType,
                                eventGroupName,                        -- 08: Security
                                eventName,                             -- 013: FilePermissionsError
                                correlationId,
                                severity,
                                eventTime,
                                faultyObject,
                                monitoredValue,
                                thresholdValues,
                                info   }
        STATUS                current
        DESCRIPTION        "Spontaneous Alarm from the managed network element:
                            The file permission of the listed files are incorrect.
                            Log in directly to the node and change the file permissions to the proper values."
        ::= { eventGroup08 13 }

        alarm08014 NOTIFICATION-TYPE
        OBJECTS        {        neName,
                                neType,
                                eventGroupName,                        -- 08: Security
                                eventName,                             -- 014: IPSECDataFaulty
                                correlationId,
                                severity,
                                eventTime,
                                faultyObject,
                                monitoredValue,
                                thresholdValues,
                                info   }
        STATUS                current
        DESCRIPTION        "Spontaneous Alarm from the managed network element:
                            IPSEC is not configured properly.
                            Escalate to SW development."
        ::= { eventGroup08 14 }

        alarm08015 NOTIFICATION-TYPE
        OBJECTS        {        neName,
                                neType,
                                eventGroupName,                        -- 08: Security
                                eventName,                             -- 015: UserKeyMismatch
                                correlationId,
                                severity,
                                eventTime,
                                faultyObject,
                                monitoredValue,
                                thresholdValues,
                                info   }
        STATUS                current
        DESCRIPTION        "Spontaneous Alarm from the managed network element:
                            User keys do not match.
                            Escalate to SW development."
        ::= { eventGroup08 15 }

        alarm08021 NOTIFICATION-TYPE
        OBJECTS        {        neName,
                                neType,
                                eventGroupName,                        -- 08: Security
                                eventName,                             -- 021: UserAccountDisabled
                                correlationId,
                                severity,
                                eventTime,
                                faultyObject,
                                monitoredValue,
                                thresholdValues,
                                info   }
        STATUS                current
        DESCRIPTION        "Spontaneous Alarm from the managed network element:
                            The specified user accounts are disabled.
                            Review the disabled accounts and either enable or delete them."
        ::= { eventGroup08 21 }

        alarm08022 NOTIFICATION-TYPE
        OBJECTS        {        neName,
                                neType,
                                eventGroupName,                        -- 08: Security
                                eventName,                             -- 022: SystemAccountDisabled
                                correlationId,
                                severity,
                                eventTime,
                                faultyObject,
                                monitoredValue,
                                thresholdValues,
                                info   }
        STATUS                current
        DESCRIPTION        "Spontaneous Alarm from the managed network element:
                            The specified system accounts are disabled.
                            Review the disabled accounts and either enable or delete them.

If all system accounts are disabled and login to the node is not possible, use cloud/hypervisor tools to access the console and use the root account.
A last correction is to terminate the VM and re-launch it."
        ::= { eventGroup08 22 }

        alarm08023 NOTIFICATION-TYPE
        OBJECTS        {        neName,
                                neType,
                                eventGroupName,                        -- 08: Security
                                eventName,                             -- 023: SystemAccountNotDisabled
                                correlationId,
                                severity,
                                eventTime,
                                faultyObject,
                                monitoredValue,
                                thresholdValues,
                                info   }
        STATUS                current
        DESCRIPTION        "Spontaneous Alarm from the managed network element:
                            The specified system accounts should be disabled.
                            Review these system accounts (should be either sysad or secad) and disable them after verifying that an individual system administrator or security administrator exists."
        ::= { eventGroup08 23 }

        alarm08024 NOTIFICATION-TYPE
        OBJECTS        {        neName,
                                neType,
                                eventGroupName,                        -- 08: Security
                                eventName,                             -- 024: PasswordExpired
                                correlationId,
                                severity,
                                eventTime,
                                faultyObject,
                                monitoredValue,
                                thresholdValues,
                                info   }
        STATUS                current
        DESCRIPTION        "Spontaneous Alarm from the managed network element:
                            The password for the specified accounts has expired.
                            Delete the accounts or change the password."
        ::= { eventGroup08 24 }

        alarm08041 NOTIFICATION-TYPE
        OBJECTS        {        neName,
                                neType,
                                eventGroupName,                        -- 08: Security
                                eventName,                             -- 041: FailedAuthenticationAttempt
                                correlationId,
                                severity,
                                eventTime,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroup08 41 }

        alarm08042 NOTIFICATION-TYPE
        OBJECTS        {        neName,
                                neType,
                                eventGroupName,                        -- 08: Security
                                eventName,                             -- 042: AccessDenied
                                correlationId,
                                severity,
                                eventTime,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroup08 42 }

        alarm08051 NOTIFICATION-TYPE
        OBJECTS        {        neName,
                                neType,
                                eventGroupName,                        -- 08: Security
                                eventName,                             -- 051: FailedAuthenticationAttemptPlatf
                                correlationId,
                                severity,
                                eventTime,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroup08 51 }

        alarm08052 NOTIFICATION-TYPE
        OBJECTS        {        neName,
                                neType,
                                eventGroupName,                        -- 08: Security
                                eventName,                             -- 052: FailedAuthenticationAttemptRoot
                                correlationId,
                                severity,
                                eventTime,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroup08 52 }

        alarm08053 NOTIFICATION-TYPE
        OBJECTS        {        neName,
                                neType,
                                eventGroupName,                        -- 08: Security
                                eventName,                             -- 053: FailedAuthenticationAttemptSecad
                                correlationId,
                                severity,
                                eventTime,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroup08 53 }

        alarm08054 NOTIFICATION-TYPE
        OBJECTS        {        neName,
                                neType,
                                eventGroupName,                        -- 08: Security
                                eventName,                             -- 054: FailedAuthenticationAttemptApp
                                correlationId,
                                severity,
                                eventTime,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroup08 54 }

        alarm08055 NOTIFICATION-TYPE
        OBJECTS        {        neName,
                                neType,
                                eventGroupName,                        -- 08: Security
                                eventName,                             -- 055: FailedAuthenticationAttemptSysad
                                correlationId,
                                severity,
                                eventTime,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroup08 55 }

        alarm08056 NOTIFICATION-TYPE
        OBJECTS        {        neName,
                                neType,
                                eventGroupName,                        -- 08: Security
                                eventName,                             -- 056: FailedAuthenticationAttemptPostgres
                                correlationId,
                                severity,
                                eventTime,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroup08 56 }

        alarm08061 NOTIFICATION-TYPE
        OBJECTS        {        neName,
                                neType,
                                eventGroupName,                        -- 08: Security
                                eventName,                             -- 061: AccessDeniedPlatf
                                correlationId,
                                severity,
                                eventTime,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroup08 61 }

        alarm08062 NOTIFICATION-TYPE
        OBJECTS        {        neName,
                                neType,
                                eventGroupName,                        -- 08: Security
                                eventName,                             -- 062: AccessDeniedRoot
                                correlationId,
                                severity,
                                eventTime,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroup08 62 }

        alarm08063 NOTIFICATION-TYPE
        OBJECTS        {        neName,
                                neType,
                                eventGroupName,                        -- 08: Security
                                eventName,                             -- 063: AccessDeniedSecad
                                correlationId,
                                severity,
                                eventTime,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroup08 63 }

        alarm08064 NOTIFICATION-TYPE
        OBJECTS        {        neName,
                                neType,
                                eventGroupName,                        -- 08: Security
                                eventName,                             -- 064: AccessDeniedApp
                                correlationId,
                                severity,
                                eventTime,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroup08 64 }

        alarm08065 NOTIFICATION-TYPE
        OBJECTS        {        neName,
                                neType,
                                eventGroupName,                        -- 08: Security
                                eventName,                             -- 065: AccessDeniedSysad
                                correlationId,
                                severity,
                                eventTime,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroup08 65 }

        alarm08066 NOTIFICATION-TYPE
        OBJECTS        {        neName,
                                neType,
                                eventGroupName,                        -- 08: Security
                                eventName,                             -- 066: AccessDeniedPostgres
                                correlationId,
                                severity,
                                eventTime,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroup08 66 }


        --********************************************************************
        -- Alarm Trap Definitions for event group 09: Resources
        --********************************************************************

        alarm09001 NOTIFICATION-TYPE
        OBJECTS        {        neName,
                                neType,
                                eventGroupName,                        -- 09: Resources
                                eventName,                             -- 001: CPU
                                correlationId,
                                severity,
                                eventTime,
                                faultyObject,
                                monitoredValue,
                                thresholdValues,
                                info   }
        STATUS                current
        DESCRIPTION        "Spontaneous Alarm from the managed network element:
                            CPU percentage usage in the last minute.
                            Check CPU usage with 'top'. It shows the processes that use the most CPU resource. Repair depending on the activities of the offending process(es), e.g. if they are in a loop then restart process might help."
        ::= { eventGroup09 1 }

        alarm09002 NOTIFICATION-TYPE
        OBJECTS        {        neName,
                                neType,
                                eventGroupName,                        -- 09: Resources
                                eventName,                             -- 002: RAM
                                correlationId,
                                severity,
                                eventTime,
                                faultyObject,
                                monitoredValue,
                                thresholdValues,
                                info   }
        STATUS                current
        DESCRIPTION        "Spontaneous Alarm from the managed network element:
                            RAM percentage usage in the last minute. Used Memory is defined as:
used = total - free - buffers - cached.
                            Display processes that uses large amount of RAM with 'top' (Enter 'top' then Shift+f then n then Enter key). Processes that uses unreasonable large RAM may have a memory leak. If no process shows unreasonable larger RAM usage, additional RAM should be added to the system."
        ::= { eventGroup09 2 }

        alarm09003 NOTIFICATION-TYPE
        OBJECTS        {        neName,
                                neType,
                                eventGroupName,                        -- 09: Resources
                                eventName,                             -- 003: SwapFequency
                                correlationId,
                                severity,
                                eventTime,
                                faultyObject,
                                monitoredValue,
                                thresholdValues,
                                info   }
        STATUS                current
        DESCRIPTION        "Spontaneous Alarm from the managed network element:
                            Total number of pages swapped in the last minute.
                            The system is low of RAM. Do not allow intensive processes running concurrently."
        ::= { eventGroup09 3 }

        alarm09004 NOTIFICATION-TYPE
        OBJECTS        {        neName,
                                neType,
                                eventGroupName,                        -- 09: Resources
                                eventName,                             -- 004: DiskPartitionSwap
                                correlationId,
                                severity,
                                eventTime,
                                faultyObject,
                                monitoredValue,
                                thresholdValues,
                                info   }
        STATUS                current
        DESCRIPTION        "Spontaneous Alarm from the managed network element:
                            Swap partition percentage usage.
If too high the node will reboot.
                            System may be low on memory. Check whether RAM intensive processes are/were running."
        ::= { eventGroup09 4 }

        alarm09005 NOTIFICATION-TYPE
        OBJECTS        {        neName,
                                neType,
                                eventGroupName,                        -- 09: Resources
                                eventName,                             -- 005: DiskPartitionRoot
                                correlationId,
                                severity,
                                eventTime,
                                faultyObject,
                                monitoredValue,
                                thresholdValues,
                                info   }
        STATUS                current
        DESCRIPTION        "Spontaneous Alarm from the managed network element:
                            Root (/) partition percentage usage.
If too high the node will reboot.
                            Delete unused files."
        ::= { eventGroup09 5 }

        alarm09006 NOTIFICATION-TYPE
        OBJECTS        {        neName,
                                neType,
                                eventGroupName,                        -- 09: Resources
                                eventName,                             -- 006: DiskPartitionVar
                                correlationId,
                                severity,
                                eventTime,
                                faultyObject,
                                monitoredValue,
                                thresholdValues,
                                info   }
        STATUS                current
        DESCRIPTION        "Spontaneous Alarm from the managed network element:
                            /var partition percentage usage.
                            Delete unused files."
        ::= { eventGroup09 6 }

        alarm09007 NOTIFICATION-TYPE
        OBJECTS        {        neName,
                                neType,
                                eventGroupName,                        -- 09: Resources
                                eventName,                             -- 007: DiskPartitionDb
                                correlationId,
                                severity,
                                eventTime,
                                faultyObject,
                                monitoredValue,
                                thresholdValues,
                                info   }
        STATUS                current
        DESCRIPTION        "Spontaneous Alarm from the managed network element:
                            /db partition percentage usage.
                            Delete unused files."
        ::= { eventGroup09 7 }

        alarm09008 NOTIFICATION-TYPE
        OBJECTS        {        neName,
                                neType,
                                eventGroupName,                        -- 09: Resources
                                eventName,                             -- 008: DiskPartitionTmp
                                correlationId,
                                severity,
                                eventTime,
                                faultyObject,
                                monitoredValue,
                                thresholdValues,
                                info   }
        STATUS                current
        DESCRIPTION        "Spontaneous Alarm from the managed network element:
                            /tmp partition percentage usage.
If too high the node will reboot.
                            Delete unused files (check if wireshark is using up /tmp)."
        ::= { eventGroup09 8 }

        alarm09009 NOTIFICATION-TYPE
        OBJECTS        {        neName,
                                neType,
                                eventGroupName,                        -- 09: Resources
                                eventName,                             -- 009: DiskPartitionShared
                                correlationId,
                                severity,
                                eventTime,
                                faultyObject,
                                monitoredValue,
                                thresholdValues,
                                info   }
        STATUS                current
        DESCRIPTION        "Spontaneous Alarm from the managed network element:
                            The remote shared storage of the operations node has crossed a fill level threshold. Once full log files cannot be stored anymore and analysis of instrumentation data cannot be performed anymore.
                            Check whether amount and content of stored data is justified. If yes, increase storage space. If not, delete files from storage and escalate the issue to development to check for SW errors."
        ::= { eventGroup09 9 }

        alarm09010 NOTIFICATION-TYPE
        OBJECTS        {        neName,
                                neType,
                                eventGroupName,                        -- 09: Resources
                                eventName,                             -- 010: DiskPartitionRemote
                                correlationId,
                                severity,
                                eventTime,
                                faultyObject,
                                monitoredValue,
                                thresholdValues,
                                info   }
        STATUS                current
        DESCRIPTION        "Spontaneous Alarm from the managed network element:
                            The remote shared storage of the operations node has crossed a fill level threshold. Once full log files cannot be stored anymore and analysis of instrumentation data cannot be performed anymore.
                            Check whether amount and content of stored data is justified. If yes, increase storage space. If not, delete files from storage and escalate the issue to development to check for SW errors."
        ::= { eventGroup09 10 }

        alarm09011 NOTIFICATION-TYPE
        OBJECTS        {        neName,
                                neType,
                                eventGroupName,                        -- 09: Resources
                                eventName,                             -- 011: LogDirectory
                                correlationId,
                                severity,
                                eventTime,
                                faultyObject,
                                monitoredValue,
                                thresholdValues,
                                info   }
        STATUS                current
        DESCRIPTION        "Spontaneous Alarm from the managed network element:
                            Total space usage (GB) of /var/log partition.
                            Delete unused files."
        ::= { eventGroup09 11 }

        alarm09012 NOTIFICATION-TYPE
        OBJECTS        {        neName,
                                neType,
                                eventGroupName,                        -- 09: Resources
                                eventName,                             -- 012: CoreDirectory
                                correlationId,
                                severity,
                                eventTime,
                                faultyObject,
                                monitoredValue,
                                thresholdValues,
                                info   }
        STATUS                current
        DESCRIPTION        "Spontaneous Alarm from the managed network element:
                            Total space usage (GB) of /var/cores partition.
                            Delete unused files."
        ::= { eventGroup09 12 }

        alarm09019 NOTIFICATION-TYPE
        OBJECTS        {        neName,
                                neType,
                                eventGroupName,                        -- 09: Resources
                                eventName,                             -- 019: DiskPartitionSharedUnavailable
                                correlationId,
                                severity,
                                eventTime,
                                faultyObject,
                                monitoredValue,
                                thresholdValues,
                                info   }
        STATUS                current
        DESCRIPTION        "Spontaneous Alarm from the managed network element:
                            The shared storage is not available. It contains the log file archive and analytics data. Without this storage log files may get lost and analytics data will be incomplete. Processes accessing these file may hang and restart eventually.
                            Check storage device and accessibility. Check configuration."
        ::= { eventGroup09 19 }

        alarm09020 NOTIFICATION-TYPE
        OBJECTS        {        neName,
                                neType,
                                eventGroupName,                        -- 09: Resources
                                eventName,                             -- 020: DiskPartitionRemoteUnavailable
                                correlationId,
                                severity,
                                eventTime,
                                faultyObject,
                                monitoredValue,
                                thresholdValues,
                                info   }
        STATUS                current
        DESCRIPTION        "Spontaneous Alarm from the managed network element:
                            The remote storage is not available. It contains collected debug files, trace files and core dump files. Processes accessing these file may hang and restart eventually.
                            Check storage device and accessibility. Check configuration."
        ::= { eventGroup09 20 }

        alarm09031 NOTIFICATION-TYPE
        OBJECTS        {        neName,
                                neType,
                                eventGroupName,                        -- 09: Resources
                                eventName,                             -- 031: BandwidthOAMP
                                correlationId,
                                severity,
                                eventTime,
                                faultyObject,
                                monitoredValue,
                                thresholdValues,
                                info   }
        STATUS                current
        DESCRIPTION        "Spontaneous Alarm from the managed network element:
                            Bandwidth OAMP Average transmitted Mbit/s of the last minute.
                            Verify if the number is justified for this interface."
        ::= { eventGroup09 31 }

        alarm09032 NOTIFICATION-TYPE
        OBJECTS        {        neName,
                                neType,
                                eventGroupName,                        -- 09: Resources
                                eventName,                             -- 032: BandwidthApp
                                correlationId,
                                severity,
                                eventTime,
                                faultyObject,
                                monitoredValue,
                                thresholdValues,
                                info   }
        STATUS                current
        DESCRIPTION        "Spontaneous Alarm from the managed network element:
                            Bandwidth App Average transmitted Mbit/s of the last minute.
                            Verify if the number is justified for this interface."
        ::= { eventGroup09 32 }

        alarm09033 NOTIFICATION-TYPE
        OBJECTS        {        neName,
                                neType,
                                eventGroupName,                        -- 09: Resources
                                eventName,                             -- 033: BandwidthExt
                                correlationId,
                                severity,
                                eventTime,
                                faultyObject,
                                monitoredValue,
                                thresholdValues,
                                info   }
        STATUS                current
        DESCRIPTION        "Spontaneous Alarm from the managed network element:
                            Bandwidth Ext Average transmitted Mbit/s of the last minute.
                            Verify if the number is justified for this interface."
        ::= { eventGroup09 33 }


        --********************************************************************
        -- Alarm Trap Definitions for event group 10: Network
        --********************************************************************

        alarm10001 NOTIFICATION-TYPE
        OBJECTS        {        neName,
                                neType,
                                eventGroupName,                        -- 10: Network
                                eventName,                             -- 001: RouterOAMP
                                correlationId,
                                severity,
                                eventTime,
                                faultyObject,
                                monitoredValue,
                                thresholdValues,
                                info   }
        STATUS                current
        DESCRIPTION        "Spontaneous Alarm from the managed network element:
                            The OAMP network router is not available as it is not responding to ARP requests which it had previously.
                            Check OAMP network. Is the router available? Is the IP address correct?"
        ::= { eventGroup10 1 }

        alarm10002 NOTIFICATION-TYPE
        OBJECTS        {        neName,
                                neType,
                                eventGroupName,                        -- 10: Network
                                eventName,                             -- 002: RouterApp
                                correlationId,
                                severity,
                                eventTime,
                                faultyObject,
                                monitoredValue,
                                thresholdValues,
                                info   }
        STATUS                current
        DESCRIPTION        "Spontaneous Alarm from the managed network element:
                            The application network router is not available as it is not responding to ARP requests which it had previously.
                            Check application network. Is the router available? Is the IP address correct?"
        ::= { eventGroup10 2 }

        alarm10003 NOTIFICATION-TYPE
        OBJECTS        {        neName,
                                neType,
                                eventGroupName,                        -- 10: Network
                                eventName,                             -- 003: RouterExt
                                correlationId,
                                severity,
                                eventTime,
                                faultyObject,
                                monitoredValue,
                                thresholdValues,
                                info   }
        STATUS                current
        DESCRIPTION        "Spontaneous Alarm from the managed network element:
                            The external network router is not available as it is not responding to ARP requests which it had previously.
                            Check external network. Is the router available? Is the IP address correct?"
        ::= { eventGroup10 3 }

        alarm10004 NOTIFICATION-TYPE
        OBJECTS        {        neName,
                                neType,
                                eventGroupName,                        -- 10: Network
                                eventName,                             -- 004: DNS
                                correlationId,
                                severity,
                                eventTime,
                                faultyObject,
                                monitoredValue,
                                thresholdValues,
                                info   }
        STATUS                current
        DESCRIPTION        "Spontaneous Alarm from the managed network element:
                            A DNS server is not available as it is not responding to ARP requests which it had previously.
                            Check network. Is the DNS available? Is the IP address correct? Is the DNS reachable via the OAMP network?"
        ::= { eventGroup10 4 }

        alarm10005 NOTIFICATION-TYPE
        OBJECTS        {        neName,
                                neType,
                                eventGroupName,                        -- 10: Network
                                eventName,                             -- 005: NTPLossOfCommunication
                                correlationId,
                                severity,
                                eventTime,
                                faultyObject,
                                monitoredValue,
                                thresholdValues,
                                info   }
        STATUS                current
        DESCRIPTION        "Spontaneous Alarm from the managed network element:
                            The reporting node cannot communicate with the NTP server(s) listed in the faultyObject.
                            The command 'ntpq -pn' can be used to show the status of the NTP server. Most communication alarms will be cleared automatically when communication is restored with the partner. If the problem causing the communication failure cannot be determined and corrected, provide Ethereal/Wireshark trace files obtained from both the reporting node as well as the communication partner in order to help determine the point of failure."
        ::= { eventGroup10 5 }

        alarm10006 NOTIFICATION-TYPE
        OBJECTS        {        neName,
                                neType,
                                eventGroupName,                        -- 10: Network
                                eventName,                             -- 006: NTPSynchronizationFailure
                                correlationId,
                                severity,
                                eventTime,
                                faultyObject,
                                monitoredValue,
                                thresholdValues,
                                info   }
        STATUS                current
        DESCRIPTION        "Spontaneous Alarm from the managed network element:
                            The reporting node cannot synchronize the system clock with any NTP server.
                             The command 'ntpq -pn' can be used to show the status of the NTP server. Verify that the list of NTP servers is correct and analyze the command output to determine why the node could not synchronize with any listed server."
        ::= { eventGroup10 6 }

        alarm10007 NOTIFICATION-TYPE
        OBJECTS        {        neName,
                                neType,
                                eventGroupName,                        -- 10: Network
                                eventName,                             -- 007: NTPDaemonFailure
                                correlationId,
                                severity,
                                eventTime,
                                faultyObject,
                                monitoredValue,
                                thresholdValues,
                                info   }
        STATUS                current
        DESCRIPTION        "Spontaneous Alarm from the managed network element:
                            The reporting node could not execute the ntpq -pn command. This is likely because the NTP daemon is inactive.
                             Review /var/log/messages for ntp messages and determine why the daemon exited. Execute the command 'plat_pmc show .' verify that the ntp process is not blocked. If it is, execute 'plat_pmc start ntp'."
        ::= { eventGroup10 7 }

        alarm10008 NOTIFICATION-TYPE
        OBJECTS        {        neName,
                                neType,
                                eventGroupName,                        -- 10: Network
                                eventName,                             -- 008: eth0LinkDown
                                correlationId,
                                severity,
                                eventTime,
                                faultyObject,
                                monitoredValue,
                                thresholdValues,
                                info   }
        STATUS                current
        DESCRIPTION        "Spontaneous Alarm from the managed network element:
                            The Ethernet interface eth0 is inactive.
                            On a Virtual Machine, configure the Ethernet interface to connect to a valid port/switch. On physical hardware verify physical connectivity between the specified Ethernet port and the adjacent networking device."
        ::= { eventGroup10 8 }

        alarm10009 NOTIFICATION-TYPE
        OBJECTS        {        neName,
                                neType,
                                eventGroupName,                        -- 10: Network
                                eventName,                             -- 009: eth1LinkDown
                                correlationId,
                                severity,
                                eventTime,
                                faultyObject,
                                monitoredValue,
                                thresholdValues,
                                info   }
        STATUS                current
        DESCRIPTION        "Spontaneous Alarm from the managed network element:
                            The Ethernet interface eth1 is inactive.
                            On a Virtual Machine, configure the Ethernet interface to connect to a valid port/switch. On physical hardware verify physical connectivity between the specified Ethernet port and the adjacent networking device."
        ::= { eventGroup10 9 }

        alarm10010 NOTIFICATION-TYPE
        OBJECTS        {        neName,
                                neType,
                                eventGroupName,                        -- 10: Network
                                eventName,                             -- 010: eth2LinkDown
                                correlationId,
                                severity,
                                eventTime,
                                faultyObject,
                                monitoredValue,
                                thresholdValues,
                                info   }
        STATUS                current
        DESCRIPTION        "Spontaneous Alarm from the managed network element:
                            The Ethernet interface eth2 is inactive.
                            On a Virtual Machine, configure the Ethernet interface to connect to a valid port/switch. On physical hardware verify physical connectivity between the specified Ethernet port and the adjacent networking device."
        ::= { eventGroup10 10 }

        alarm10011 NOTIFICATION-TYPE
        OBJECTS        {        neName,
                                neType,
                                eventGroupName,                        -- 10: Network
                                eventName,                             -- 011: HardwareClockOffset
                                correlationId,
                                severity,
                                eventTime,
                                faultyObject,
                                monitoredValue,
                                thresholdValues,
                                info   }
        STATUS                current
        DESCRIPTION        "Spontaneous Alarm from the managed network element:
                            The system time and the time from the hardware clock are different by the specified number of seconds.
                            Follow the documented procedures for changing the time."
        ::= { eventGroup10 11 }

        alarm10012 NOTIFICATION-TYPE
        OBJECTS        {        neName,
                                neType,
                                eventGroupName,                        -- 10: Network
                                eventName,                             -- 012: DNS1Response
                                correlationId,
                                severity,
                                eventTime,
                                faultyObject,
                                monitoredValue,
                                thresholdValues,
                                info   }
        STATUS                current
        DESCRIPTION        "Spontaneous Alarm from the managed network element:
                            Response time from DNS1 is greater than one of the alarm thresolds.
                            Check network."
        ::= { eventGroup10 12 }

        alarm10013 NOTIFICATION-TYPE
        OBJECTS        {        neName,
                                neType,
                                eventGroupName,                        -- 10: Network
                                eventName,                             -- 013: DNS1Resolver
                                correlationId,
                                severity,
                                eventTime,
                                faultyObject,
                                monitoredValue,
                                thresholdValues,
                                info   }
        STATUS                current
        DESCRIPTION        "Spontaneous Alarm from the managed network element:
                            FQDNs could not be resolved.
                            Check FQDNs that failed to be resolved."
        ::= { eventGroup10 13 }

        alarm10014 NOTIFICATION-TYPE
        OBJECTS        {        neName,
                                neType,
                                eventGroupName,                        -- 10: Network
                                eventName,                             -- 014: DNS2Response
                                correlationId,
                                severity,
                                eventTime,
                                faultyObject,
                                monitoredValue,
                                thresholdValues,
                                info   }
        STATUS                current
        DESCRIPTION        "Spontaneous Alarm from the managed network element:
                            Response time from DNS2 is greater than one of the alarm thresolds.
                            Check network."
        ::= { eventGroup10 14 }

        alarm10015 NOTIFICATION-TYPE
        OBJECTS        {        neName,
                                neType,
                                eventGroupName,                        -- 10: Network
                                eventName,                             -- 015: DNS2Resolver
                                correlationId,
                                severity,
                                eventTime,
                                faultyObject,
                                monitoredValue,
                                thresholdValues,
                                info   }
        STATUS                current
        DESCRIPTION        "Spontaneous Alarm from the managed network element:
                            FQDNs could not be resolved.
                            Check FQDNs that failed to be resolved."
        ::= { eventGroup10 15 }

        alarm10016 NOTIFICATION-TYPE
        OBJECTS        {        neName,
                                neType,
                                eventGroupName,                        -- 10: Network
                                eventName,                             -- 016: IPSECConnection
                                correlationId,
                                severity,
                                eventTime,
                                faultyObject,
                                monitoredValue,
                                thresholdValues,
                                info   }
        STATUS                current
        DESCRIPTION        "Spontaneous Alarm from the managed network element:
                            Dropped ipsec connections detected
                            Check ipsec connections on the box."
        ::= { eventGroup10 16 }

        alarm10017 NOTIFICATION-TYPE
        OBJECTS        {        neName,
                                neType,
                                eventGroupName,                        -- 10: Network
                                eventName,                             -- 017: TCPEstablished
                                correlationId,
                                severity,
                                eventTime,
                                faultyObject,
                                monitoredValue,
                                thresholdValues,
                                info   }
        STATUS                current
        DESCRIPTION        "Spontaneous Alarm from the managed network element:
                            TCP Established exceeding accepted rate.
                            Check tcp_established in ganglia for this node."
        ::= { eventGroup10 17 }

        alarm10018 NOTIFICATION-TYPE
        OBJECTS        {        neName,
                                neType,
                                eventGroupName,                        -- 10: Network
                                eventName,                             -- 018: RemoteHAProxyConnection
                                correlationId,
                                severity,
                                eventTime,
                                faultyObject,
                                monitoredValue,
                                thresholdValues,
                                info   }
        STATUS                current
        DESCRIPTION        "Spontaneous Alarm from the managed network element:
                            Remote HAProxy peer is down.
                            Check connectivity to remote HAProxy node."
        ::= { eventGroup10 18 }


        --********************************************************************
        -- Alarm Trap Definitions for event group 12: RapidStat
        --********************************************************************

        alarm12001 NOTIFICATION-TYPE
        OBJECTS        {        neName,
                                neType,
                                eventGroupName,                        -- 12: RapidStat
                                eventName,                             -- 001: HwClockNotSetToUTC
                                correlationId,
                                severity,
                                eventTime,
                                faultyObject,
                                monitoredValue,
                                thresholdValues,
                                info   }
        STATUS                current
        DESCRIPTION        "Spontaneous Alarm from the managed network element:
                            HW clock is not set to UTC.
                            Verify that the non UTC setting is required. If not, set it back to UTC."
        ::= { eventGroup12 1 }

        alarm12002 NOTIFICATION-TYPE
        OBJECTS        {        neName,
                                neType,
                                eventGroupName,                        -- 12: RapidStat
                                eventName,                             -- 002: DNSrespTime
                                correlationId,
                                severity,
                                eventTime,
                                faultyObject,
                                monitoredValue,
                                thresholdValues,
                                info   }
        STATUS                current
        DESCRIPTION        "Spontaneous Alarm from the managed network element:
                            DNS response time was longer than threshold.
                            Check network."
        ::= { eventGroup12 2 }

        alarm12003 NOTIFICATION-TYPE
        OBJECTS        {        neName,
                                neType,
                                eventGroupName,                        -- 12: RapidStat
                                eventName,                             -- 003: MailSize
                                correlationId,
                                severity,
                                eventTime,
                                faultyObject,
                                monitoredValue,
                                thresholdValues,
                                info   }
        STATUS                current
        DESCRIPTION        "Spontaneous Alarm from the managed network element:
                            There are large files in /var/mail.
                            Delete the files."
        ::= { eventGroup12 3 }

        alarm12004 NOTIFICATION-TYPE
        OBJECTS        {        neName,
                                neType,
                                eventGroupName,                        -- 12: RapidStat
                                eventName,                             -- 004: etcVsNodecfg
                                correlationId,
                                severity,
                                eventTime,
                                faultyObject,
                                monitoredValue,
                                thresholdValues,
                                info   }
        STATUS                current
        DESCRIPTION        "Spontaneous Alarm from the managed network element:
                            There are mismatched values between /etc/hosts and /etc/.xml files.
                            Escalate to next level of support."
        ::= { eventGroup12 4 }

        alarm12005 NOTIFICATION-TYPE
        OBJECTS        {        neName,
                                neType,
                                eventGroupName,                        -- 12: RapidStat
                                eventName,                             -- 005: ntpresolv
                                correlationId,
                                severity,
                                eventTime,
                                faultyObject,
                                monitoredValue,
                                thresholdValues,
                                info   }
        STATUS                current
        DESCRIPTION        "Spontaneous Alarm from the managed network element:
                            System time not synchronized with any NTP server.
                            See repair text for NTP alarms."
        ::= { eventGroup12 5 }

        alarm12006 NOTIFICATION-TYPE
        OBJECTS        {        neName,
                                neType,
                                eventGroupName,                        -- 12: RapidStat
                                eventName,                             -- 006: ActAlrms
                                correlationId,
                                severity,
                                eventTime,
                                faultyObject,
                                monitoredValue,
                                thresholdValues,
                                info   }
        STATUS                current
        DESCRIPTION        "Spontaneous Alarm from the managed network element:
                            There are active alarms on the system.
                            Correct the problems reported in the active alarms. If the alarm does not clear automatically delete it manually."
        ::= { eventGroup12 6 }

        alarm12007 NOTIFICATION-TYPE
        OBJECTS        {        neName,
                                neType,
                                eventGroupName,                        -- 12: RapidStat
                                eventName,                             -- 007: Num_pstacks
                                correlationId,
                                severity,
                                eventTime,
                                faultyObject,
                                monitoredValue,
                                thresholdValues,
                                info   }
        STATUS                current
        DESCRIPTION        "Spontaneous Alarm from the managed network element:
                            Pstacks found.
                            See repair text of pstack alarms."
        ::= { eventGroup12 7 }

        alarm12008 NOTIFICATION-TYPE
        OBJECTS        {        neName,
                                neType,
                                eventGroupName,                        -- 12: RapidStat
                                eventName,                             -- 008: TracingOn
                                correlationId,
                                severity,
                                eventTime,
                                faultyObject,
                                monitoredValue,
                                thresholdValues,
                                info   }
        STATUS                current
        DESCRIPTION        "Spontaneous Alarm from the managed network element:
                            Found active tracing.
                            Verify that tracing is still needed. If not stop tracing."
        ::= { eventGroup12 8 }


        --********************************************************************
        -- Alarm Trap Definitions for event group 13: Logging
        --********************************************************************

        alarm13001 NOTIFICATION-TYPE
        OBJECTS        {        neName,
                                neType,
                                eventGroupName,                        -- 13: Logging
                                eventName,                             -- 001: DeletedOpenFile
                                correlationId,
                                severity,
                                eventTime,
                                faultyObject,
                                monitoredValue,
                                thresholdValues,
                                info   }
        STATUS                current
        DESCRIPTION        "Spontaneous Alarm from the managed network element:
                            A large deleted file has been detected that is still open. The associated process will be restarted. The faultyObject parameter shows file name and associated process.
                            If this happens often, escalate the alarm to development for analysis. The alarm is automatically removed after a couple of hours."
        ::= { eventGroup13 1 }


        --********************************************************************
        -- Alarm Trap Definitions for event group 14: LogTCA
        --********************************************************************

        alarm14001 NOTIFICATION-TYPE
        OBJECTS        {        neName,
                                neType,
                                eventGroupName,                        -- 14: LogTCA
                                eventName,                             -- 001: Platform
                                correlationId,
                                severity,
                                eventTime,
                                faultyObject,
                                monitoredValue,
                                thresholdValues,
                                info   }
        STATUS                current
        DESCRIPTION        "Spontaneous Alarm from the managed network element:
                            The number of events has crossed one of the thresholds within the last 15 minutes for the category PLATFORM. See log file /var/log/platform/logging/LogNonIssues.log.
                            Review log file entries to determine source of problem."
        ::= { eventGroup14 1 }

        alarm14002 NOTIFICATION-TYPE
        OBJECTS        {        neName,
                                neType,
                                eventGroupName,                        -- 14: LogTCA
                                eventName,                             -- 002: Platform_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category PLATFORM_ERR. See log file /var/log/platform/logging/LogIssues.log.
                            Review log file entries to determine source of problem."
        ::= { eventGroup14 2 }

        alarm14003 NOTIFICATION-TYPE
        OBJECTS        {        neName,
                                neType,
                                eventGroupName,                        -- 14: LogTCA
                                eventName,                             -- 003: Audit
                                correlationId,
                                severity,
                                eventTime,
                                faultyObject,
                                monitoredValue,
                                thresholdValues,
                                info   }
        STATUS                current
        DESCRIPTION        "Spontaneous Alarm from the managed network element:
                            The number of events has crossed one of the thresholds within the last 15 minutes for the category AUDIT. See log file /var/log/platform/logging/LogNonIssues.log.
                            Review log file entries to determine source of problem."
        ::= { eventGroup14 3 }

        alarm14004 NOTIFICATION-TYPE
        OBJECTS        {        neName,
                                neType,
                                eventGroupName,                        -- 14: LogTCA
                                eventName,                             -- 004: Audit_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category AUDIT_ERR. See log file /var/log/platform/logging/LogIssues.log.
                            Review log file entries to determine source of problem."
        ::= { eventGroup14 4 }

        alarm14005 NOTIFICATION-TYPE
        OBJECTS        {        neName,
                                neType,
                                eventGroupName,                        -- 14: LogTCA
                                eventName,                             -- 005: Com_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category COM_ERR. See log file /var/log/platform/logging/LogIssues.log.
                            Review log file entries to determine source of problem."
        ::= { eventGroup14 5 }

        alarm14006 NOTIFICATION-TYPE
        OBJECTS        {        neName,
                                neType,
                                eventGroupName,                        -- 14: LogTCA
                                eventName,                             -- 006: SW_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category SW_ERR. See log file /var/log/platform/logging/LogIssues.log.
                            Review log file entries to determine source of problem."
        ::= { eventGroup14 6 }

        alarm14007 NOTIFICATION-TYPE
        OBJECTS        {        neName,
                                neType,
                                eventGroupName,                        -- 14: LogTCA
                                eventName,                             -- 007: Data_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category DATA_ERR. See log file /var/log/platform/logging/LogIssues.log.
                            Review log file entries to determine source of problem."
        ::= { eventGroup14 7 }

        alarm14008 NOTIFICATION-TYPE
        OBJECTS        {        neName,
                                neType,
                                eventGroupName,                        -- 14: LogTCA
                                eventName,                             -- 008: Alarm
                                correlationId,
                                severity,
                                eventTime,
                                faultyObject,
                                monitoredValue,
                                thresholdValues,
                                info   }
        STATUS                current
        DESCRIPTION        "Spontaneous Alarm from the managed network element:
                            The number of events has crossed one of the thresholds within the last 15 minutes for the category ALARM. See log file /var/log/platform/logging/LogAlarm.log.
                            Review log file entries to determine source of problem."
        ::= { eventGroup14 8 }

        alarm14009 NOTIFICATION-TYPE
        OBJECTS        {        neName,
                                neType,
                                eventGroupName,                        -- 14: LogTCA
                                eventName,                             -- 009: Alarm_Clear
                                correlationId,
                                severity,
                                eventTime,
                                faultyObject,
                                monitoredValue,
                                thresholdValues,
                                info   }
        STATUS                current
        DESCRIPTION        "Spontaneous Alarm from the managed network element:
                            The number of events has crossed one of the thresholds within the last 15 minutes for the category ALARM_CLEAR. See log file /var/log/platform/logging/LogAlarm.log.
                            Review log file entries to determine source of problem."
        ::= { eventGroup14 9 }

        alarm14010 NOTIFICATION-TYPE
        OBJECTS        {        neName,
                                neType,
                                eventGroupName,                        -- 14: LogTCA
                                eventName,                             -- 010: Alarm_Mgr
                                correlationId,
                                severity,
                                eventTime,
                                faultyObject,
                                monitoredValue,
                                thresholdValues,
                                info   }
        STATUS                current
        DESCRIPTION        "Spontaneous Alarm from the managed network element:
                            The number of events has crossed one of the thresholds within the last 15 minutes for the category ALARM_MGR. See log file /var/log/platform/logging/LogAlarm.log.
                            Review log file entries to determine source of problem."
        ::= { eventGroup14 10 }

        alarm14011 NOTIFICATION-TYPE
        OBJECTS        {        neName,
                                neType,
                                eventGroupName,                        -- 14: LogTCA
                                eventName,                             -- 011: Security
                                correlationId,
                                severity,
                                eventTime,
                                faultyObject,
                                monitoredValue,
                                thresholdValues,
                                info   }
        STATUS                current
        DESCRIPTION        "Spontaneous Alarm from the managed network element:
                            The number of events has crossed one of the thresholds within the last 15 minutes for the category SECURITY. See log file /var/log/platform/logging/LogSecurity.log.
                            Review log file entries to determine source of problem."
        ::= { eventGroup14 11 }


        --********************************************************************
        -- Alarm Trap Definitions for event group 17: SNMPTrap
        --********************************************************************

        alarm17001 NOTIFICATION-TYPE
        OBJECTS        {        neName,
                                neType,
                                eventGroupName,                        -- 17: SNMPTrap
                                eventName,                             -- 001: SnmpOpenFailure
                                correlationId,
                                severity,
                                eventTime,
                                faultyObject,
                                monitoredValue,
                                thresholdValues,
                                info   }
        STATUS                current
        DESCRIPTION        "Spontaneous Alarm from the managed network element:
                            Call to snmp_open failed.
                            Look at faulty object and correct accordingly (if possible)."
        ::= { eventGroup17 1 }

        alarm17002 NOTIFICATION-TYPE
        OBJECTS        {        neName,
                                neType,
                                eventGroupName,                        -- 17: SNMPTrap
                                eventName,                             -- 002: SnmpSendFailure
                                correlationId,
                                severity,
                                eventTime,
                                faultyObject,
                                monitoredValue,
                                thresholdValues,
                                info   }
        STATUS                current
        DESCRIPTION        "Spontaneous Alarm from the managed network element:
                            Call to snmp_synch_response failed.
                            Look at faulty object and correct accordingly (if possible)."
        ::= { eventGroup17 2 }


        --********************************************************************
        -- Alarm Trap Definitions for event group 20: Zoo
        --********************************************************************

        alarm20001 NOTIFICATION-TYPE
        OBJECTS        {        neName,
                                neType,
                                eventGroupName,                        -- 20: Zoo
                                eventName,                             -- 001: ZooConnectionFailure
                                correlationId,
                                severity,
                                eventTime,
                                faultyObject,
                                monitoredValue,
                                thresholdValues,
                                info   }
        STATUS                current
        DESCRIPTION        "Spontaneous Alarm from the managed network element:
                            A connection from the platform ZooKeeper Client to a ZooKeeper server could not be established. A quorum of ZooKeeper servers may not be active or may be misconfigured. The ZooKeeper client on the platform may not have a valid configuration. Network failures can also cause this alarm.
                            Ping the ZooKeeper servers from the reporting node to determine if a network problem exists. Verify that a quorum of ZooKeeper servers is active (e.g. at least two servers are active in a three-zookeeper-node ensemble). Verify that the reporting node was deployed correctly and has received the correct configuration in the 'goahead' message. If problem persists, execute 'plat_rapidstat -c' to collect data on the reporting node, all of the ZooKeeper servers."
        ::= { eventGroup20 1 }

        alarm20002 NOTIFICATION-TYPE
        OBJECTS        {        neName,
                                neType,
                                eventGroupName,                        -- 20: Zoo
                                eventName,                             -- 002: ZooConfigCorrupted
                                correlationId,
                                severity,
                                eventTime,
                                faultyObject,
                                monitoredValue,
                                thresholdValues,
                                info   }
        STATUS                current
        DESCRIPTION        "Spontaneous Alarm from the managed network element:
                            Configuration retrieved via ZooKeeper server was corrupt and cannot be parsed.
                            The ZooKeeper znodes that are corrupt are listed with the alarm. Use the Management node application to correct the node configuration. If problem persists, execute 'plat_rapidstat -c' to collect data on the reporting node, Management node, and one of the active ZooKeeper servers."
        ::= { eventGroup20 2 }

        alarm20003 NOTIFICATION-TYPE
        OBJECTS        {        neName,
                                neType,
                                eventGroupName,                        -- 20: Zoo
                                eventName,                             -- 003: ZooConfigUnavailable
                                correlationId,
                                severity,
                                eventTime,
                                faultyObject,
                                monitoredValue,
                                thresholdValues,
                                info   }
        STATUS                current
        DESCRIPTION        "Spontaneous Alarm from the managed network element:
                            Configuration could not be retrieved from a ZooKeeper server.
                            The ZooKeeper znodes that could not be retrieved are listed with the alarm. If data has not been populated on the ZooKeeper servers, use the Management node to configure and populate the data. If problem persists, execute 'plat_rapidstat -c' to collect data on the reporting node as well as one of the active ZooKeeper servers."
        ::= { eventGroup20 3 }

        alarm20004 NOTIFICATION-TYPE
        OBJECTS        {        neName,
                                neType,
                                eventGroupName,                        -- 20: Zoo
                                eventName,                             -- 004: ZookeeperResponseTime
                                correlationId,
                                severity,
                                eventTime,
                                faultyObject,
                                monitoredValue,
                                thresholdValues,
                                info   }
        STATUS                current
        DESCRIPTION        "Spontaneous Alarm from the managed network element:
                            A ZooKeeper server did not respond to a request from the client within the expected response time.
                            The problem could be caused by network problems or by an overloaded ZooKeeper server. If problem persists, execute 'plat_rapidstat -c' to collection data on the reporting node and on each active ZooKeeper server node."
        ::= { eventGroup20 4 }

        alarm20005 NOTIFICATION-TYPE
        OBJECTS        {        neName,
                                neType,
                                eventGroupName,                        -- 20: Zoo
                                eventName,                             -- 005: WrongNodeTypeInGoAhead
                                correlationId,
                                severity,
                                eventTime,
                                faultyObject,
                                monitoredValue,
                                thresholdValues,
                                info   }
        STATUS                current
        DESCRIPTION        "Spontaneous Alarm from the managed network element:
                            The node name received in the GoAhead configuration does not match the node type set by production in the file /etc/platform/type.
                            If the GoAhead was sent to this node in error, send the correct GoAhead to this node. If the node was deployed with the wrong OVF/OVA, redeploy with the correct one and re-send the GoAhead."
        ::= { eventGroup20 5 }

        alarm20006 NOTIFICATION-TYPE
        OBJECTS        {        neName,
                                neType,
                                eventGroupName,                        -- 20: Zoo
                                eventName,                             -- 006: ZooEnsembleFault
                                correlationId,
                                severity,
                                eventTime,
                                faultyObject,
                                monitoredValue,
                                thresholdValues,
                                info   }
        STATUS                current
        DESCRIPTION        "Spontaneous Alarm from the managed network element:
                            The reporting ZooKeeper server is not currently connected to a ZooKeeper server ensemble.
                            The ZooKeeper server may not be able to communicate with some or all of the other ZooKeeper servers configured in the ensemble.  The other ZooKeeper servers in the ensemble may be down or a network problem may be blocking communication.   IPSec or packet filter rule configuration may be blocking communication with the other ZooKeeper servers.  Run plat_rapidstat and look for ZooKeeper errors or warnings.  Correct the blocking condition."
        ::= { eventGroup20 6 }


        --********************************************************************
        -- Alarm Trap Definitions for event group 21: IDS
        --********************************************************************

        alarm21001 NOTIFICATION-TYPE
        OBJECTS        {        neName,
                                neType,
                                eventGroupName,                        -- 21: IDS
                                eventName,                             -- 001: DoS
                                correlationId,
                                severity,
                                eventTime,
                                faultyObject,
                                monitoredValue,
                                thresholdValues,
                                info   }
        STATUS                current
        DESCRIPTION        "Spontaneous Alarm from the managed network element:
                            Denial Of Service Attempt Detected.
                            None."
        ::= { eventGroup21 1 }


        --********************************************************************
        -- Alarm Trap Definitions for event group 22: SNMP
        --********************************************************************

        alarm22001 NOTIFICATION-TYPE
        OBJECTS        {        neName,
                                neType,
                                eventGroupName,                        -- 22: SNMP
                                eventName,                             -- 001: SnmpReconfigError
                                correlationId,
                                severity,
                                eventTime,
                                faultyObject,
                                monitoredValue,
                                thresholdValues,
                                info   }
        STATUS                current
        DESCRIPTION        "Spontaneous Alarm from the managed network element:
                            SnmpV3 Users not created successfully
                            Check if all necessary credentials for SnmpV3 Users are defined in Network.xml.If not update file."
        ::= { eventGroup22 1 }


        --********************************************************************
        -- Alarm Trap Definitions for event group 23: Syslog
        --********************************************************************

        alarm23001 NOTIFICATION-TYPE
        OBJECTS        {        neName,
                                neType,
                                eventGroupName,                        -- 23: Syslog
                                eventName,                             -- 001: Emerg
                                correlationId,
                                severity,
                                eventTime,
                                faultyObject,
                                monitoredValue,
                                thresholdValues,
                                info   }
        STATUS                current
        DESCRIPTION        "Spontaneous Alarm from the managed network element:
                            Emgergency syslog failure.
                            Look at syslog entries and correct problem."
        ::= { eventGroup23 1 }

        alarm23002 NOTIFICATION-TYPE
        OBJECTS        {        neName,
                                neType,
                                eventGroupName,                        -- 23: Syslog
                                eventName,                             -- 002: Alert
                                correlationId,
                                severity,
                                eventTime,
                                faultyObject,
                                monitoredValue,
                                thresholdValues,
                                info   }
        STATUS                current
        DESCRIPTION        "Spontaneous Alarm from the managed network element:
                            Alert syslog failure.
                            Look at syslog entries and correct problem."
        ::= { eventGroup23 2 }

        alarm23003 NOTIFICATION-TYPE
        OBJECTS        {        neName,
                                neType,
                                eventGroupName,                        -- 23: Syslog
                                eventName,                             -- 003: Crit
                                correlationId,
                                severity,
                                eventTime,
                                faultyObject,
                                monitoredValue,
                                thresholdValues,
                                info   }
        STATUS                current
        DESCRIPTION        "Spontaneous Alarm from the managed network element:
                            Critical syslog failure.
                            Look at syslog entries and correct problem."
        ::= { eventGroup23 3 }

        alarm23004 NOTIFICATION-TYPE
        OBJECTS        {        neName,
                                neType,
                                eventGroupName,                        -- 23: Syslog
                                eventName,                             -- 004: Error
                                correlationId,
                                severity,
                                eventTime,
                                faultyObject,
                                monitoredValue,
                                thresholdValues,
                                info   }
        STATUS                current
        DESCRIPTION        "Spontaneous Alarm from the managed network element:
                            Error syslog failure.
                            Look at syslog entries and correct problem."
        ::= { eventGroup23 4 }


        --********************************************************************
        -- Alarm Trap Definitions for event group 50: Connectivity
        --********************************************************************

        alarm50001 NOTIFICATION-TYPE
        OBJECTS        {        neName,
                                neType,
                                eventGroupName,                        -- 50: Connectivity
                                eventName,                             -- 001: SmartCloudConnectionFailure
                                correlationId,
                                severity,
                                eventTime,
                                faultyObject,
                                monitoredValue,
                                thresholdValues,
                                info   }
        STATUS                current
        DESCRIPTION        "Spontaneous Alarm from the managed network element:
                            Smart Cloud Connection failure.
                            Check if the Access node has internet connection and can reach the Cloud server."
        ::= { eventGroup50 1 }

        alarm50002 NOTIFICATION-TYPE
        OBJECTS        {        neName,
                                neType,
                                eventGroupName,                        -- 50: Connectivity
                                eventName,                             -- 002: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup50 2 }

        alarm50003 NOTIFICATION-TYPE
        OBJECTS        {        neName,
                                neType,
                                eventGroupName,                        -- 50: Connectivity
                                eventName,                             -- 003: FileApiSocketsUsage
                                correlationId,
                                severity,
                                eventTime,
                                faultyObject,
                                monitoredValue,
                                thresholdValues,
                                info   }
        STATUS                current
        DESCRIPTION        "Spontaneous Alarm from the managed network element:
                            The percentage of used concurrent sockets in fileApi between Access Server and IBM crossed the defined threshold.
                            Check if it is necessary to increase the number of concurrent sockets in fileApi."
        ::= { eventGroup50 3 }

        alarm50005 NOTIFICATION-TYPE
        OBJECTS        {        neName,
                                neType,
                                eventGroupName,                        -- 50: Connectivity
                                eventName,                             -- 005: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup50 5 }

        alarm50006 NOTIFICATION-TYPE
        OBJECTS        {        neName,
                                neType,
                                eventGroupName,                        -- 50: Connectivity
                                eventName,                             -- 006: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup50 6 }

        alarm50007 NOTIFICATION-TYPE
        OBJECTS        {        neName,
                                neType,
                                eventGroupName,                        -- 50: Connectivity
                                eventName,                             -- 007: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup50 7 }

        alarm50011 NOTIFICATION-TYPE
        OBJECTS        {        neName,
                                neType,
                                eventGroupName,                        -- 50: Connectivity
                                eventName,                             -- 011: ConnectionsResponseTime
                                correlationId,
                                severity,
                                eventTime,
                                faultyObject,
                                monitoredValue,
                                thresholdValues,
                                info   }
        STATUS                current
        DESCRIPTION        "Spontaneous Alarm from the managed network element:
                            Smart Cloud Connection response time too high.
                            Check whether the high response time is justified. If not check the network and processed traffic. Are additional nodes needed? Is Smart Cloud overloaded?"
        ::= { eventGroup50 11 }

        alarm50015 NOTIFICATION-TYPE
        OBJECTS        {        neName,
                                neType,
                                eventGroupName,                        -- 50: Connectivity
                                eventName,                             -- 015: ConnectionsActivityServiceFailure
                                correlationId,
                                severity,
                                eventTime,
                                faultyObject,
                                monitoredValue,
                                thresholdValues,
                                info   }
        STATUS                current
        DESCRIPTION        "Spontaneous Alarm from the managed network element:
                            Connectivity could not be established with the IBM Connections Activity Service.
                            Check if the node has internet connection and can reach the Cloud server."
        ::= { eventGroup50 15 }

        alarm50016 NOTIFICATION-TYPE
        OBJECTS        {        neName,
                                neType,
                                eventGroupName,                        -- 50: Connectivity
                                eventName,                             -- 016: ConnectionsFileServiceFailure
                                correlationId,
                                severity,
                                eventTime,
                                faultyObject,
                                monitoredValue,
                                thresholdValues,
                                info   }
        STATUS                current
        DESCRIPTION        "Spontaneous Alarm from the managed network element:
                            Connectivity could not be established with the IBM Connections File Service.
                            Check if the node has internet connection and can reach the Cloud server."
        ::= { eventGroup50 16 }

        alarm50017 NOTIFICATION-TYPE
        OBJECTS        {        neName,
                                neType,
                                eventGroupName,                        -- 50: Connectivity
                                eventName,                             -- 017: ConnectionsBSSServiceFailure
                                correlationId,
                                severity,
                                eventTime,
                                faultyObject,
                                monitoredValue,
                                thresholdValues,
                                info   }
        STATUS                current
        DESCRIPTION        "Spontaneous Alarm from the managed network element:
                            Connectivity could not be established with the IBM Connections BSS Service.
                            Check if the node has internet connection and can reach the Cloud server."
        ::= { eventGroup50 17 }

        alarm50018 NOTIFICATION-TYPE
        OBJECTS        {        neName,
                                neType,
                                eventGroupName,                        -- 50: Connectivity
                                eventName,                             -- 018: ConnectionsSearchServiceFailure
                                correlationId,
                                severity,
                                eventTime,
                                faultyObject,
                                monitoredValue,
                                thresholdValues,
                                info   }
        STATUS                current
        DESCRIPTION        "Spontaneous Alarm from the managed network element:
                            Connectivity could not be established with the IBM Connections Search Service.
                            Check if the node has internet connection and can reach the Cloud server."
        ::= { eventGroup50 18 }

        alarm50021 NOTIFICATION-TYPE
        OBJECTS        {        neName,
                                neType,
                                eventGroupName,                        -- 50: Connectivity
                                eventName,                             -- 021: LossOfComSMTP
                                correlationId,
                                severity,
                                eventTime,
                                faultyObject,
                                monitoredValue,
                                thresholdValues,
                                info   }
        STATUS                current
        DESCRIPTION        "Spontaneous Alarm from the managed network element:
                            The IMP application node has lost connectivity with the SMTP server identified in the faultyObject parameter.
                            Check the network (router, firewall, LAN). Check whether the SMTP server is out of service."
        ::= { eventGroup50 21 }

        alarm50022 NOTIFICATION-TYPE
        OBJECTS        {        neName,
                                neType,
                                eventGroupName,                        -- 50: Connectivity
                                eventName,                             -- 022: LossOfComActex
                                correlationId,
                                severity,
                                eventTime,
                                faultyObject,
                                monitoredValue,
                                thresholdValues,
                                info   }
        STATUS                current
        DESCRIPTION        "Spontaneous Alarm from the managed network element:
                            The IMP application node has lost connectivity with the Actex server identified in the faultyObject parameter.
                            Check the network (router, firewall, LAN). Check whether the Actex server is out of service."
        ::= { eventGroup50 22 }

        alarm50051 NOTIFICATION-TYPE
        OBJECTS        {        neName,
                                neType,
                                eventGroupName,                        -- 50: Connectivity
                                eventName,                             -- 051: LossOfComApp
                                correlationId,
                                severity,
                                eventTime,
                                faultyObject,
                                monitoredValue,
                                thresholdValues,
                                info   }
        STATUS                current
        DESCRIPTION        "Spontaneous Alarm from the managed network element:
                            Access server lost communication with Application node.
                            The Application node maybe down, check the network setup. Also check the node configuration files and logs."
        ::= { eventGroup50 51 }

        alarm50052 NOTIFICATION-TYPE
        OBJECTS        {        neName,
                                neType,
                                eventGroupName,                        -- 50: Connectivity
                                eventName,                             -- 052: LossOfComSto
                                correlationId,
                                severity,
                                eventTime,
                                faultyObject,
                                monitoredValue,
                                thresholdValues,
                                info   }
        STATUS                current
        DESCRIPTION        "Spontaneous Alarm from the managed network element:
                            Access server lost communication with Storage node.
                            The Storage node maybe down, check the network setup. Also check the node configuration files and logs."
        ::= { eventGroup50 52 }

        alarm50061 NOTIFICATION-TYPE
        OBJECTS        {        neName,
                                neType,
                                eventGroupName,                        -- 50: Connectivity
                                eventName,                             -- 061: LossOfComAccClient
                                correlationId,
                                severity,
                                eventTime,
                                faultyObject,
                                monitoredValue,
                                thresholdValues,
                                info   }
        STATUS                current
        DESCRIPTION        "Spontaneous Alarm from the managed network element:
                            Access server lost communication with Access Client node.
                            Check that all nodes of the solution are active."
        ::= { eventGroup50 61 }

        alarm50062 NOTIFICATION-TYPE
        OBJECTS        {        neName,
                                neType,
                                eventGroupName,                        -- 50: Connectivity
                                eventName,                             -- 062: LossOfComAccServer
                                correlationId,
                                severity,
                                eventTime,
                                faultyObject,
                                monitoredValue,
                                thresholdValues,
                                info   }
        STATUS                current
        DESCRIPTION        "Spontaneous Alarm from the managed network element:
                            Access server lost communication with Access Server node.
                            Check that all nodes of the solution are active."
        ::= { eventGroup50 62 }

        alarm50071 NOTIFICATION-TYPE
        OBJECTS        {        neName,
                                neType,
                                eventGroupName,                        -- 50: Connectivity
                                eventName,                             -- 071: LossOfComAcc
                                correlationId,
                                severity,
                                eventTime,
                                faultyObject,
                                monitoredValue,
                                thresholdValues,
                                info   }
        STATUS                current
        DESCRIPTION        "Spontaneous Alarm from the managed network element:
                            Server lost communication with Access node.
                            The Access node maybe down, check the network setup. Also check the node configuration files and logs."
        ::= { eventGroup50 71 }

        alarm50072 NOTIFICATION-TYPE
        OBJECTS        {        neName,
                                neType,
                                eventGroupName,                        -- 50: Connectivity
                                eventName,                             -- 072: LossOfComHazelcast
                                correlationId,
                                severity,
                                eventTime,
                                faultyObject,
                                monitoredValue,
                                thresholdValues,
                                info   }
        STATUS                current
        DESCRIPTION        "Spontaneous Alarm from the managed network element:
                            The IMP application node has lost connectivity with the Hazelcast service.
                            Check the status of the Hazelcast service."
        ::= { eventGroup50 72 }

        alarm50073 NOTIFICATION-TYPE
        OBJECTS        {        neName,
                                neType,
                                eventGroupName,                        -- 50: Connectivity
                                eventName,                             -- 073: LossOfComKMS
                                correlationId,
                                severity,
                                eventTime,
                                faultyObject,
                                monitoredValue,
                                thresholdValues,
                                info   }
        STATUS                current
        DESCRIPTION        "Spontaneous Alarm from the managed network element:
                            The IMP application node has lost connectivity with one of the Key Management servers.
                            Review log file entries to determine source of problem"
        ::= { eventGroup50 73 }


        --********************************************************************
        -- Alarm Trap Definitions for event group 53: Turn
        --********************************************************************

        alarm53001 NOTIFICATION-TYPE
        OBJECTS        {        neName,
                                neType,
                                eventGroupName,                        -- 53: Turn
                                eventName,                             -- 001: LackOfUDPPorts
                                correlationId,
                                severity,
                                eventTime,
                                faultyObject,
                                monitoredValue,
                                thresholdValues,
                                info   }
        STATUS                current
        DESCRIPTION        "Spontaneous Alarm from the managed network element:
                            Turn has used more UDP ports than one of the configured thresholds.
                            Escalate to next level of support to analyze the traffic."
        ::= { eventGroup53 1 }


        --********************************************************************
        -- Alarm Trap Definitions for event group 54: LB
        --********************************************************************

        alarm54001 NOTIFICATION-TYPE
        OBJECTS        {        neName,
                                neType,
                                eventGroupName,                        -- 54: LB
                                eventName,                             -- 001: LossOfRedundancy
                                correlationId,
                                severity,
                                eventTime,
                                faultyObject,
                                monitoredValue,
                                thresholdValues,
                                info   }
        STATUS                current
        DESCRIPTION        "Spontaneous Alarm from the managed network element:
                            LB node lost its partner and now runs as master without backup.
                            Repair the LB partner node."
        ::= { eventGroup54 1 }

        alarm54002 NOTIFICATION-TYPE
        OBJECTS        {        neName,
                                neType,
                                eventGroupName,                        -- 54: LB
                                eventName,                             -- 002: FaultyConfiguration
                                correlationId,
                                severity,
                                eventTime,
                                faultyObject,
                                monitoredValue,
                                thresholdValues,
                                info   }
        STATUS                current
        DESCRIPTION        "Spontaneous Alarm from the managed network element:
                            LB configuration file is faulty. LB functionality is restricted.
                            Review log file entries to determine source of problem."
        ::= { eventGroup54 2 }


        --********************************************************************
        -- Alarm Trap Definitions for event group 56: MediaServer
        --********************************************************************

        alarm56001 NOTIFICATION-TYPE
        OBJECTS        {        neName,
                                neType,
                                eventGroupName,                        -- 56: MediaServer
                                eventName,                             -- 001: SIPTrunkMissing
                                correlationId,
                                severity,
                                eventTime,
                                faultyObject,
                                monitoredValue,
                                thresholdValues,
                                info   }
        STATUS                current
        DESCRIPTION        "Spontaneous Alarm from the managed network element:
                            Wrong SIP trunk configuration.
                            Escalate to next level of support."
        ::= { eventGroup56 1 }

        alarm56002 NOTIFICATION-TYPE
        OBJECTS        {        neName,
                                neType,
                                eventGroupName,                        -- 56: MediaServer
                                eventName,                             -- 002: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 2 }

        alarm56003 NOTIFICATION-TYPE
        OBJECTS        {        neName,
                                neType,
                                eventGroupName,                        -- 56: MediaServer
                                eventName,                             -- 003: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 3 }

        alarm56004 NOTIFICATION-TYPE
        OBJECTS        {        neName,
                                neType,
                                eventGroupName,                        -- 56: MediaServer
                                eventName,                             -- 004: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 4 }

        alarm56005 NOTIFICATION-TYPE
        OBJECTS        {        neName,
                                neType,
                                eventGroupName,                        -- 56: MediaServer
                                eventName,                             -- 005: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 5 }

        alarm56010 NOTIFICATION-TYPE
        OBJECTS        {        neName,
                                neType,
                                eventGroupName,                        -- 56: MediaServer
                                eventName,                             -- 010: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 10 }

        alarm56011 NOTIFICATION-TYPE
        OBJECTS        {        neName,
                                neType,
                                eventGroupName,                        -- 56: MediaServer
                                eventName,                             -- 011: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 11 }

        alarm56020 NOTIFICATION-TYPE
        OBJECTS        {        neName,
                                neType,
                                eventGroupName,                        -- 56: MediaServer
                                eventName,                             -- 020: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 20 }

        alarm56021 NOTIFICATION-TYPE
        OBJECTS        {        neName,
                                neType,
                                eventGroupName,                        -- 56: MediaServer
                                eventName,                             -- 021: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 21 }

        alarm56030 NOTIFICATION-TYPE
        OBJECTS        {        neName,
                                neType,
                                eventGroupName,                        -- 56: MediaServer
                                eventName,                             -- 030: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 30 }

        alarm56031 NOTIFICATION-TYPE
        OBJECTS        {        neName,
                                neType,
                                eventGroupName,                        -- 56: MediaServer
                                eventName,                             -- 031: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 31 }

        alarm56033 NOTIFICATION-TYPE
        OBJECTS        {        neName,
                                neType,
                                eventGroupName,                        -- 56: MediaServer
                                eventName,                             -- 033: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 33 }

        alarm56040 NOTIFICATION-TYPE
        OBJECTS        {        neName,
                                neType,
                                eventGroupName,                        -- 56: MediaServer
                                eventName,                             -- 040: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 40 }

        alarm56041 NOTIFICATION-TYPE
        OBJECTS        {        neName,
                                neType,
                                eventGroupName,                        -- 56: MediaServer
                                eventName,                             -- 041: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 41 }

        alarm56042 NOTIFICATION-TYPE
        OBJECTS        {        neName,
                                neType,
                                eventGroupName,                        -- 56: MediaServer
                                eventName,                             -- 042: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 42 }

        alarm56050 NOTIFICATION-TYPE
        OBJECTS        {        neName,
                                neType,
                                eventGroupName,                        -- 56: MediaServer
                                eventName,                             -- 050: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 50 }

        alarm56100 NOTIFICATION-TYPE
        OBJECTS        {        neName,
                                neType,
                                eventGroupName,                        -- 56: MediaServer
                                eventName,                             -- 100: SipStackStartupProblem
                                correlationId,
                                severity,
                                eventTime,
                                faultyObject,
                                monitoredValue,
                                thresholdValues,
                                info   }
        STATUS                current
        DESCRIPTION        "Spontaneous Alarm from the managed network element:
                            SIP stack startup problem
SIP Connectivity Provider,Failed to create a sip stack instance.
                            Please check the log for further information."
        ::= { eventGroup56 100 }

        alarm56101 NOTIFICATION-TYPE
        OBJECTS        {        neName,
                                neType,
                                eventGroupName,                        -- 56: MediaServer
                                eventName,                             -- 101: SipStackStartupProblemListening
                                correlationId,
                                severity,
                                eventTime,
                                faultyObject,
                                monitoredValue,
                                thresholdValues,
                                info   }
        STATUS                current
        DESCRIPTION        "Spontaneous Alarm from the managed network element:
                            Startup problem with a SIP stack listening point

Failed to create a listening point. Maybe address or port is in use.
                            Please check listeningPoint settings in the management UI or in the sip-connectivity.xml file."
        ::= { eventGroup56 101 }

        alarm56102 NOTIFICATION-TYPE
        OBJECTS        {        neName,
                                neType,
                                eventGroupName,                        -- 56: MediaServer
                                eventName,                             -- 102: SipStackStartupProblemInternal
                                correlationId,
                                severity,
                                eventTime,
                                faultyObject,
                                monitoredValue,
                                thresholdValues,
                                info   }
        STATUS                current
        DESCRIPTION        "Spontaneous Alarm from the managed network element:
                            Startup problem due to internal SIP stack error

Failed to create sip provider instance.
                            Please check the log for further information."
        ::= { eventGroup56 102 }

        alarm56103 NOTIFICATION-TYPE
        OBJECTS        {        neName,
                                neType,
                                eventGroupName,                        -- 56: MediaServer
                                eventName,                             -- 103: SipStackStartupProblemInternal2
                                correlationId,
                                severity,
                                eventTime,
                                faultyObject,
                                monitoredValue,
                                thresholdValues,
                                info   }
        STATUS                current
        DESCRIPTION        "Spontaneous Alarm from the managed network element:
                            Startup problem due to internal SIP stack error

Failed to register SipManager as a SIP listener.
                            Please check the log for further information."
        ::= { eventGroup56 103 }

        alarm56104 NOTIFICATION-TYPE
        OBJECTS        {        neName,
                                neType,
                                eventGroupName,                        -- 56: MediaServer
                                eventName,                             -- 104: SipStackShutdownProblem
                                correlationId,
                                severity,
                                eventTime,
                                faultyObject,
                                monitoredValue,
                                thresholdValues,
                                info   }
        STATUS                current
        DESCRIPTION        "Spontaneous Alarm from the managed network element:
                            SIP stack shutdown problem

Failed to delete a SipProvider instance from sip stack.
                            Please check the log for further information."
        ::= { eventGroup56 104 }

        alarm56105 NOTIFICATION-TYPE
        OBJECTS        {        neName,
                                neType,
                                eventGroupName,                        -- 56: MediaServer
                                eventName,                             -- 105: SipStackShutdownProblem2
                                correlationId,
                                severity,
                                eventTime,
                                faultyObject,
                                monitoredValue,
                                thresholdValues,
                                info   }
        STATUS                current
        DESCRIPTION        "Spontaneous Alarm from the managed network element:
                            SIP stack shutdown problem

Failed to delete a listening point from sip stack.
                            Please check the log for further information."
        ::= { eventGroup56 105 }

        alarm56106 NOTIFICATION-TYPE
        OBJECTS        {        neName,
                                neType,
                                eventGroupName,                        -- 56: MediaServer
                                eventName,                             -- 106: SipProviderConfMissing
                                correlationId,
                                severity,
                                eventTime,
                                faultyObject,
                                monitoredValue,
                                thresholdValues,
                                info   }
        STATUS                current
        DESCRIPTION        "Spontaneous Alarm from the managed network element:
                            SIP provider startup failed: configuration is missing

Failed to start SIP provider due to missing configuration.
                            Please check the log for further information."
        ::= { eventGroup56 106 }

        alarm56107 NOTIFICATION-TYPE
        OBJECTS        {        neName,
                                neType,
                                eventGroupName,                        -- 56: MediaServer
                                eventName,                             -- 107: SipProviderSdpParserMissing
                                correlationId,
                                severity,
                                eventTime,
                                faultyObject,
                                monitoredValue,
                                thresholdValues,
                                info   }
        STATUS                current
        DESCRIPTION        "Spontaneous Alarm from the managed network element:
                            SIP provider startup failed: SDP parser missing

Failed to start SIP provider due to missing SDP parser component.
                            Please check the log for further information."
        ::= { eventGroup56 107 }

        alarm56108 NOTIFICATION-TYPE
        OBJECTS        {        neName,
                                neType,
                                eventGroupName,                        -- 56: MediaServer
                                eventName,                             -- 108: SipProviderAddrTransCompMissing
                                correlationId,
                                severity,
                                eventTime,
                                faultyObject,
                                monitoredValue,
                                thresholdValues,
                                info   }
        STATUS                current
        DESCRIPTION        "Spontaneous Alarm from the managed network element:
                            SIP provider startup failed: Address Translation component missing.

Failed to start SIP provider due to missing Address Translation component.
                            Please check the log for further information."
        ::= { eventGroup56 108 }

        alarm56109 NOTIFICATION-TYPE
        OBJECTS        {        neName,
                                neType,
                                eventGroupName,                        -- 56: MediaServer
                                eventName,                             -- 109: SipProviderLocationDBCompMissing
                                correlationId,
                                severity,
                                eventTime,
                                faultyObject,
                                monitoredValue,
                                thresholdValues,
                                info   }
        STATUS                current
        DESCRIPTION        "Spontaneous Alarm from the managed network element:
                            SIP provider startup failed: Location Database component missing

Failed to start SIP provider due to missing Location Database component.
                            Please check the log for further information."
        ::= { eventGroup56 109 }

        alarm56110 NOTIFICATION-TYPE
        OBJECTS        {        neName,
                                neType,
                                eventGroupName,                        -- 56: MediaServer
                                eventName,                             -- 110: SipProviderStartFailure
                                correlationId,
                                severity,
                                eventTime,
                                faultyObject,
                                monitoredValue,
                                thresholdValues,
                                info   }
        STATUS                current
        DESCRIPTION        "Spontaneous Alarm from the managed network element:
                            Failed to start sip provider

Internal SIP manager startup problem.
                            Please check the log for further information."
        ::= { eventGroup56 110 }

        alarm56200 NOTIFICATION-TYPE
        OBJECTS        {        neName,
                                neType,
                                eventGroupName,                        -- 56: MediaServer
                                eventName,                             -- 200: MFWProviderMissing
                                correlationId,
                                severity,
                                eventTime,
                                faultyObject,
                                monitoredValue,
                                thresholdValues,
                                info   }
        STATUS                current
        DESCRIPTION        "Spontaneous Alarm from the managed network element:
                            Missing MFW provider

Could not get MediaFramework (MFW) provider from Application Host. Processing of streaming data will not work.
                            Check log-output for more details."
        ::= { eventGroup56 200 }

        alarm56202 NOTIFICATION-TYPE
        OBJECTS        {        neName,
                                neType,
                                eventGroupName,                        -- 56: MediaServer
                                eventName,                             -- 202: MPSMediaProcessingProviderInitFailure
                                correlationId,
                                severity,
                                eventTime,
                                faultyObject,
                                monitoredValue,
                                thresholdValues,
                                info   }
        STATUS                current
        DESCRIPTION        "Spontaneous Alarm from the managed network element:
                            Failed to initialize MPS Media Processing Provider

Failed to initialize the Media Processing (MPS) Provider. Processing of streaming data will not work.
                            Check log-output for more details."
        ::= { eventGroup56 202 }

        alarm56203 NOTIFICATION-TYPE
        OBJECTS        {        neName,
                                neType,
                                eventGroupName,                        -- 56: MediaServer
                                eventName,                             -- 203: NoMoreAvailableRTPChannel
                                correlationId,
                                severity,
                                eventTime,
                                faultyObject,
                                monitoredValue,
                                thresholdValues,
                                info   }
        STATUS                current
        DESCRIPTION        "Spontaneous Alarm from the managed network element:
                            No more RTP channel available

Failed to allocate a RTP channel resource to handle call.
                            Please check the ResourceManagement configuration for this application."
        ::= { eventGroup56 203 }

        alarm56204 NOTIFICATION-TYPE
        OBJECTS        {        neName,
                                neType,
                                eventGroupName,                        -- 56: MediaServer
                                eventName,                             -- 204: NoMorAvailableTTSLicens
                                correlationId,
                                severity,
                                eventTime,
                                faultyObject,
                                monitoredValue,
                                thresholdValues,
                                info   }
        STATUS                current
        DESCRIPTION        "Spontaneous Alarm from the managed network element:
                            No (more) TTS license available

Failed to allocate Text-To-Speech port license.
                            Please make sure that there are enough licenses installed and that the 'licensing service' is running."
        ::= { eventGroup56 204 }

        alarm56205 NOTIFICATION-TYPE
        OBJECTS        {        neName,
                                neType,
                                eventGroupName,                        -- 56: MediaServer
                                eventName,                             -- 205: NoMoreAvailableASRLicense
                                correlationId,
                                severity,
                                eventTime,
                                faultyObject,
                                monitoredValue,
                                thresholdValues,
                                info   }
        STATUS                current
        DESCRIPTION        "Spontaneous Alarm from the managed network element:
                            No (more) ASR license available

Failed to allocate Speech-Recognition port license.
                            Please make sure that there are enough licenses installed and that the 'licensing service' is running."
        ::= { eventGroup56 205 }

        alarm56210 NOTIFICATION-TYPE
        OBJECTS        {        neName,
                                neType,
                                eventGroupName,                        -- 56: MediaServer
                                eventName,                             -- 210: NoDiscSpaceLeft
                                correlationId,
                                severity,
                                eventTime,
                                faultyObject,
                                monitoredValue,
                                thresholdValues,
                                info   }
        STATUS                current
        DESCRIPTION        "Spontaneous Alarm from the managed network element:
                            No disc space left

Unable to write further samples for recording, since there is no more disc space available.
                            Run debug file collection and escalate to next level of support."
        ::= { eventGroup56 210 }

        alarm56211 NOTIFICATION-TYPE
        OBJECTS        {        neName,
                                neType,
                                eventGroupName,                        -- 56: MediaServer
                                eventName,                             -- 211: NoAvaiableResource
                                correlationId,
                                severity,
                                eventTime,
                                faultyObject,
                                monitoredValue,
                                thresholdValues,
                                info   }
        STATUS                current
        DESCRIPTION        "Spontaneous Alarm from the managed network element:
                            Resource no longer available

Failed to write samples for recording, because the file path is not available or the file not writeable.
                            Run debug file collection and escalate to next level of support."
        ::= { eventGroup56 211 }

        alarm56300 NOTIFICATION-TYPE
        OBJECTS        {        neName,
                                neType,
                                eventGroupName,                        -- 56: MediaServer
                                eventName,                             -- 300: MediaGatewayProviderInitFailure
                                correlationId,
                                severity,
                                eventTime,
                                faultyObject,
                                monitoredValue,
                                thresholdValues,
                                info   }
        STATUS                current
        DESCRIPTION        "Spontaneous Alarm from the managed network element:
                            Failed to initialize Media Gateway Provider

An error occurred while starting Media Gateway Provider.
                            Please verify Media Gateway Configuration and assure that the PromptDB provider is running."
        ::= { eventGroup56 300 }

        alarm56301 NOTIFICATION-TYPE
        OBJECTS        {        neName,
                                neType,
                                eventGroupName,                        -- 56: MediaServer
                                eventName,                             -- 301: ConfChangesActivationFailure
                                correlationId,
                                severity,
                                eventTime,
                                faultyObject,
                                monitoredValue,
                                thresholdValues,
                                info   }
        STATUS                current
        DESCRIPTION        "Spontaneous Alarm from the managed network element:
                            Failed to activate configuration changes

An error occurred while activating configuration changes.
                            Please fix Media Gateway Configuration and restart provider."
        ::= { eventGroup56 301 }

        alarm56302 NOTIFICATION-TYPE
        OBJECTS        {        neName,
                                neType,
                                eventGroupName,                        -- 56: MediaServer
                                eventName,                             -- 302: MediaGatewayDeactivationFailure
                                correlationId,
                                severity,
                                eventTime,
                                faultyObject,
                                monitoredValue,
                                thresholdValues,
                                info   }
        STATUS                current
        DESCRIPTION        "Spontaneous Alarm from the managed network element:
                            Failed to deactivate Media Gateway Provider

An unexpected error occurred while stopping Media Gateway Provider.
                            Run debug file collection and escalate to next level of support."
        ::= { eventGroup56 302 }

        alarm56303 NOTIFICATION-TYPE
        OBJECTS        {        neName,
                                neType,
                                eventGroupName,                        -- 56: MediaServer
                                eventName,                             -- 303: MediaGatewayActivationFailure
                                correlationId,
                                severity,
                                eventTime,
                                faultyObject,
                                monitoredValue,
                                thresholdValues,
                                info   }
        STATUS                current
        DESCRIPTION        "Spontaneous Alarm from the managed network element:
                            Failed to activate media gateways

No listening point is defined in Media Gateway configuration.
                            Please add at least one listening point."
        ::= { eventGroup56 303 }

        alarm56304 NOTIFICATION-TYPE
        OBJECTS        {        neName,
                                neType,
                                eventGroupName,                        -- 56: MediaServer
                                eventName,                             -- 304: ConnectionCreationFailure
                                correlationId,
                                severity,
                                eventTime,
                                faultyObject,
                                monitoredValue,
                                thresholdValues,
                                info   }
        STATUS                current
        DESCRIPTION        "Spontaneous Alarm from the managed network element:
                            Failed to create connection

Ignoring create connection command, since no incoming connection listener is registered.
                            Please assure that the terminal binder is running."
        ::= { eventGroup56 304 }

        alarm56310 NOTIFICATION-TYPE
        OBJECTS        {        neName,
                                neType,
                                eventGroupName,                        -- 56: MediaServer
                                eventName,                             -- 310: ConnectionCreationFailure2
                                correlationId,
                                severity,
                                eventTime,
                                faultyObject,
                                monitoredValue,
                                thresholdValues,
                                info   }
        STATUS                current
        DESCRIPTION        "Spontaneous Alarm from the managed network element:
                            Failed to create connection

A new connection can not be created due to a non-recoverable problem.
                            Please check the log-output to get more detailed informations (logger: com.cycos.media)."
        ::= { eventGroup56 310 }

        alarm56311 NOTIFICATION-TYPE
        OBJECTS        {        neName,
                                neType,
                                eventGroupName,                        -- 56: MediaServer
                                eventName,                             -- 311: ConnectionModificationFailure
                                correlationId,
                                severity,
                                eventTime,
                                faultyObject,
                                monitoredValue,
                                thresholdValues,
                                info   }
        STATUS                current
        DESCRIPTION        "Spontaneous Alarm from the managed network element:
                            Failed to modify connection

Existing connection can not be modified due to a non-recoverable problem.
                            Please check the log-output to get more detailed informations (logger: com.cycos.media)."
        ::= { eventGroup56 311 }

        alarm56312 NOTIFICATION-TYPE
        OBJECTS        {        neName,
                                neType,
                                eventGroupName,                        -- 56: MediaServer
                                eventName,                             -- 312: ConnectionDeletionFailure
                                correlationId,
                                severity,
                                eventTime,
                                faultyObject,
                                monitoredValue,
                                thresholdValues,
                                info   }
        STATUS                current
        DESCRIPTION        "Spontaneous Alarm from the managed network element:
                            Failed to delete connection

Request to delete a connection can not be handled correctly due to a non-recoverable problem.
                            Please check the log-output to get more detailed informations (logger: com.cycos.media)."
        ::= { eventGroup56 312 }

        alarm56313 NOTIFICATION-TYPE
        OBJECTS        {        neName,
                                neType,
                                eventGroupName,                        -- 56: MediaServer
                                eventName,                             -- 313: NotificationRequestProcessingFailure
                                correlationId,
                                severity,
                                eventTime,
                                faultyObject,
                                monitoredValue,
                                thresholdValues,
                                info   }
        STATUS                current
        DESCRIPTION        "Spontaneous Alarm from the managed network element:
                            Failed to process notification request

An internal problem occurred during the handling of a request for notification.
                            Escalate to next level of support."
        ::= { eventGroup56 313 }

        alarm56330 NOTIFICATION-TYPE
        OBJECTS        {        neName,
                                neType,
                                eventGroupName,                        -- 56: MediaServer
                                eventName,                             -- 330: ResourceAssociatedWithConnectionLost
                                correlationId,
                                severity,
                                eventTime,
                                faultyObject,
                                monitoredValue,
                                thresholdValues,
                                info   }
        STATUS                current
        DESCRIPTION        "Spontaneous Alarm from the managed network element:
                            Lost the resource associated with the connection

An internal problem occurred and the gateway is terminating the connection.
                            Escalate to next level of support."
        ::= { eventGroup56 330 }

        alarm56400 NOTIFICATION-TYPE
        OBJECTS        {        neName,
                                neType,
                                eventGroupName,                        -- 56: MediaServer
                                eventName,                             -- 400: UnknownMFWFault
                                correlationId,
                                severity,
                                eventTime,
                                faultyObject,
                                monitoredValue,
                                thresholdValues,
                                info   }
        STATUS                current
        DESCRIPTION        "Spontaneous Alarm from the managed network element:
                            Unknown MFW fault

Unspecified Media Framework Component fault.
                            Escalate to next level of support."
        ::= { eventGroup56 400 }

        alarm56401 NOTIFICATION-TYPE
        OBJECTS        {        neName,
                                neType,
                                eventGroupName,                        -- 56: MediaServer
                                eventName,                             -- 401: NativeMediaFrameworkStartupFailure
                                correlationId,
                                severity,
                                eventTime,
                                faultyObject,
                                monitoredValue,
                                thresholdValues,
                                info   }
        STATUS                current
        DESCRIPTION        "Spontaneous Alarm from the managed network element:
                            Native Media Framework startup failed

Native part of Media Framework could not be started by Java.
                            Escalate to next level of support."
        ::= { eventGroup56 401 }

        alarm56402 NOTIFICATION-TYPE
        OBJECTS        {        neName,
                                neType,
                                eventGroupName,                        -- 56: MediaServer
                                eventName,                             -- 402: NativeMediaFrameworkNotResponding
                                correlationId,
                                severity,
                                eventTime,
                                faultyObject,
                                monitoredValue,
                                thresholdValues,
                                info   }
        STATUS                current
        DESCRIPTION        "Spontaneous Alarm from the managed network element:
                            Native Media Framework not responding

Native part of Media Framework has crashed or is unable to respond.
                            Escalate to next level of support."
        ::= { eventGroup56 402 }

        alarm56403 NOTIFICATION-TYPE
        OBJECTS        {        neName,
                                neType,
                                eventGroupName,                        -- 56: MediaServer
                                eventName,                             -- 403: JavaMediaFrameworkReceiveSocketOverrun
                                correlationId,
                                severity,
                                eventTime,
                                faultyObject,
                                monitoredValue,
                                thresholdValues,
                                info   }
        STATUS                current
        DESCRIPTION        "Spontaneous Alarm from the managed network element:
                            Java Media Framework receive socket overrun

Receive socket of java part of Media Framework is overloaded.
                            Escalate to next level of support."
        ::= { eventGroup56 403 }

        alarm56404 NOTIFICATION-TYPE
        OBJECTS        {        neName,
                                neType,
                                eventGroupName,                        -- 56: MediaServer
                                eventName,                             -- 404: NativeMediaFrameworkRecieveSocketOverrun
                                correlationId,
                                severity,
                                eventTime,
                                faultyObject,
                                monitoredValue,
                                thresholdValues,
                                info   }
        STATUS                current
        DESCRIPTION        "Spontaneous Alarm from the managed network element:
                            Native Media Framework receive socket overrun

Receive socket of native part of Media Framework is overloaded.
                            Escalate to next level of support."
        ::= { eventGroup56 404 }

        alarm56405 NOTIFICATION-TYPE
        OBJECTS        {        neName,
                                neType,
                                eventGroupName,                        -- 56: MediaServer
                                eventName,                             -- 405: JavaMediaFrameworkReceiveSocketSequencError
                                correlationId,
                                severity,
                                eventTime,
                                faultyObject,
                                monitoredValue,
                                thresholdValues,
                                info   }
        STATUS                current
        DESCRIPTION        "Spontaneous Alarm from the managed network element:
                            Java Media Framework receive socket sequence error

Messages lost on receive socket in java part of Media Framework.
                            Escalate to next level of support."
        ::= { eventGroup56 405 }

        alarm56406 NOTIFICATION-TYPE
        OBJECTS        {        neName,
                                neType,
                                eventGroupName,                        -- 56: MediaServer
                                eventName,                             -- 406: NativeMediaFrameworkReceiveSocketSequencError
                                correlationId,
                                severity,
                                eventTime,
                                faultyObject,
                                monitoredValue,
                                thresholdValues,
                                info   }
        STATUS                current
        DESCRIPTION        "Spontaneous Alarm from the managed network element:
                            Native Media Framework receive socket sequence error

Messages lost on receive socket in native part of Media Framework.
                            Escalate to next level of support."
        ::= { eventGroup56 406 }

        alarm56407 NOTIFICATION-TYPE
        OBJECTS        {        neName,
                                neType,
                                eventGroupName,                        -- 56: MediaServer
                                eventName,                             -- 407: NativeMediaFrameworkSocketError
                                correlationId,
                                severity,
                                eventTime,
                                faultyObject,
                                monitoredValue,
                                thresholdValues,
                                info   }
        STATUS                current
        DESCRIPTION        "Spontaneous Alarm from the managed network element:
                            Native Media Framework socket error

Bind of socket failed in native part of Media Framework.
                            Escalate to next level of support."
        ::= { eventGroup56 407 }

        alarm56408 NOTIFICATION-TYPE
        OBJECTS        {        neName,
                                neType,
                                eventGroupName,                        -- 56: MediaServer
                                eventName,                             -- 408: JavaMediaFrameworkUnrecoverableError
                                correlationId,
                                severity,
                                eventTime,
                                faultyObject,
                                monitoredValue,
                                thresholdValues,
                                info   }
        STATUS                current
        DESCRIPTION        "Spontaneous Alarm from the managed network element:
                            Java Media Framework unrecoverable error

Unrecoverable error in java part of Media Framework leading to permanent service degradation. Any processing of streaming data won't work.
                            Escalate to next level of support."
        ::= { eventGroup56 408 }

        alarm56409 NOTIFICATION-TYPE
        OBJECTS        {        neName,
                                neType,
                                eventGroupName,                        -- 56: MediaServer
                                eventName,                             -- 409: NatvieMediaFrameworkUnrecoverableError
                                correlationId,
                                severity,
                                eventTime,
                                faultyObject,
                                monitoredValue,
                                thresholdValues,
                                info   }
        STATUS                current
        DESCRIPTION        "Spontaneous Alarm from the managed network element:
                            Native Media Framework unrecoverable error

Unrecoverable error in native part of Media Framework leading to permanent service degradation. Any processing of streaming data won't work.
                            Escalate to next level of support."
        ::= { eventGroup56 409 }

        alarm56410 NOTIFICATION-TYPE
        OBJECTS        {        neName,
                                neType,
                                eventGroupName,                        -- 56: MediaServer
                                eventName,                             -- 410: NativeMediaFrameworkOutOfMemory
                                correlationId,
                                severity,
                                eventTime,
                                faultyObject,
                                monitoredValue,
                                thresholdValues,
                                info   }
        STATUS                current
        DESCRIPTION        "Spontaneous Alarm from the managed network element:
                            Native Media Framework out of memory

Memory allocation failed in native part of Media Framework.
                            Escalate to next level of support."
        ::= { eventGroup56 410 }

        alarm56411 NOTIFICATION-TYPE
        OBJECTS        {        neName,
                                neType,
                                eventGroupName,                        -- 56: MediaServer
                                eventName,                             -- 411: NativeMediaFrameworkOutOfUDPPorts
                                correlationId,
                                severity,
                                eventTime,
                                faultyObject,
                                monitoredValue,
                                thresholdValues,
                                info   }
        STATUS                current
        DESCRIPTION        "Spontaneous Alarm from the managed network element:
                            Native Media Framework out of UDP ports

Port allocation failed in native part of Media Framework.
                            Escalate to next level of support."
        ::= { eventGroup56 411 }

        alarm56412 NOTIFICATION-TYPE
        OBJECTS        {        neName,
                                neType,
                                eventGroupName,                        -- 56: MediaServer
                                eventName,                             -- 412: NativeMediaFrameworkCryptoSessionNotFound
                                correlationId,
                                severity,
                                eventTime,
                                faultyObject,
                                monitoredValue,
                                thresholdValues,
                                info   }
        STATUS                current
        DESCRIPTION        "Spontaneous Alarm from the managed network element:
                            Native Media Framework crypto session not found

KeyManagement has no matching crypto session. Processing of encrypted streaming data will be affected.
                            Escalate to next level of support."
        ::= { eventGroup56 412 }

        alarm56413 NOTIFICATION-TYPE
        OBJECTS        {        neName,
                                neType,
                                eventGroupName,                        -- 56: MediaServer
                                eventName,                             -- 413: NativeMediaFrameworkSRTPError
                                correlationId,
                                severity,
                                eventTime,
                                faultyObject,
                                monitoredValue,
                                thresholdValues,
                                info   }
        STATUS                current
        DESCRIPTION        "Spontaneous Alarm from the managed network element:
                            Native Media Framework srtp error

Srtp stack returned error. Processing of encrypted streaming data will be affected.
                            Escalate to next level of support."
        ::= { eventGroup56 413 }

        alarm56414 NOTIFICATION-TYPE
        OBJECTS        {        neName,
                                neType,
                                eventGroupName,                        -- 56: MediaServer
                                eventName,                             -- 414: NativeMediaFrameworkJeyManagementFatalErro
                                correlationId,
                                severity,
                                eventTime,
                                faultyObject,
                                monitoredValue,
                                thresholdValues,
                                info   }
        STATUS                current
        DESCRIPTION        "Spontaneous Alarm from the managed network element:
                            Native Media Framework keyManagement fatal error

KeyManagement in unrecoverable error state. Processing of encrypted streaming data will be affected.
                            Escalate to next level of support."
        ::= { eventGroup56 414 }

        alarm56415 NOTIFICATION-TYPE
        OBJECTS        {        neName,
                                neType,
                                eventGroupName,                        -- 56: MediaServer
                                eventName,                             -- 415: NativeMediaFrameworkControlPortBindError
                                correlationId,
                                severity,
                                eventTime,
                                faultyObject,
                                monitoredValue,
                                thresholdValues,
                                info   }
        STATUS                current
        DESCRIPTION        "Spontaneous Alarm from the managed network element:
                            Media Framework control port bind error

Control port for Java-native communication could not be opened - check port configuration or other processes using conflicting ports.
                            Escalate to next level of support."
        ::= { eventGroup56 415 }

        alarm56416 NOTIFICATION-TYPE
        OBJECTS        {        neName,
                                neType,
                                eventGroupName,                        -- 56: MediaServer
                                eventName,                             -- 416: NativeMediaFrameworkRealtimeError
                                correlationId,
                                severity,
                                eventTime,
                                faultyObject,
                                monitoredValue,
                                thresholdValues,
                                info   }
        STATUS                current
        DESCRIPTION        "Spontaneous Alarm from the managed network element:
                            Native Media Framework realtime error

Native MFW process could not be started in realtime mode: this may lead to bad voice quality.
                            Check access rights for native image."
        ::= { eventGroup56 416 }

        alarm56417 NOTIFICATION-TYPE
        OBJECTS        {        neName,
                                neType,
                                eventGroupName,                        -- 56: MediaServer
                                eventName,                             -- 417: NativeMediaFrameworksRTCError
                                correlationId,
                                severity,
                                eventTime,
                                faultyObject,
                                monitoredValue,
                                thresholdValues,
                                info   }
        STATUS                current
        DESCRIPTION        "Spontaneous Alarm from the managed network element:
                            Native Media Framework RTC error

Realtime clock could not be initialized: this may degrade voice quality.
                            Check for configuration or conflicting usage of RTC by another process."
        ::= { eventGroup56 417 }

        alarm56418 NOTIFICATION-TYPE
        OBJECTS        {        neName,
                                neType,
                                eventGroupName,                        -- 56: MediaServer
                                eventName,                             -- 418: UDPPortBindError
                                correlationId,
                                severity,
                                eventTime,
                                faultyObject,
                                monitoredValue,
                                thresholdValues,
                                info   }
        STATUS                current
        DESCRIPTION        "Spontaneous Alarm from the managed network element:
                            UDP port bind error

Bind of a UDP port failed.
                            If this error persists check port range configuration."
        ::= { eventGroup56 418 }

        alarm56419 NOTIFICATION-TYPE
        OBJECTS        {        neName,
                                neType,
                                eventGroupName,                        -- 56: MediaServer
                                eventName,                             -- 419: IllegalCommandOption
                                correlationId,
                                severity,
                                eventTime,
                                faultyObject,
                                monitoredValue,
                                thresholdValues,
                                info   }
        STATUS                current
        DESCRIPTION        "Spontaneous Alarm from the managed network element:
                            Illegal command option

Media Framework was started with an illegal command option.
                            Check configuration in Media Framework configuration file 'mfw.component.xml'."
        ::= { eventGroup56 419 }

        alarm56420 NOTIFICATION-TYPE
        OBJECTS        {        neName,
                                neType,
                                eventGroupName,                        -- 56: MediaServer
                                eventName,                             -- 420: NoMoreAvailableUDPPorts
                                correlationId,
                                severity,
                                eventTime,
                                faultyObject,
                                monitoredValue,
                                thresholdValues,
                                info   }
        STATUS                current
        DESCRIPTION        "Spontaneous Alarm from the managed network element:
                            No more free UDP ports available

The media framework (MFW) has run out of free UDP ports.
                            Please make sure that the media servers configured port range is sufficient."
        ::= { eventGroup56 420 }

        alarm56422 NOTIFICATION-TYPE
        OBJECTS        {        neName,
                                neType,
                                eventGroupName,                        -- 56: MediaServer
                                eventName,                             -- 422: NoMoreAvailableNetworkPorts
                                correlationId,
                                severity,
                                eventTime,
                                faultyObject,
                                monitoredValue,
                                thresholdValues,
                                info   }
        STATUS                current
        DESCRIPTION        "Spontaneous Alarm from the managed network element:
                            stream ports (nearly) exhausted

At least 1 stream route is (nearly) out of free network ports. Probably no more connections could be established. Check log-output for more details.
                            The alarm is cleared automatically as soon as enough network ports are available again."
        ::= { eventGroup56 422 }

        alarm56423 NOTIFICATION-TYPE
        OBJECTS        {        neName,
                                neType,
                                eventGroupName,                        -- 56: MediaServer
                                eventName,                             -- 423: TurnServiceConfigurationError
                                correlationId,
                                severity,
                                eventTime,
                                faultyObject,
                                monitoredValue,
                                thresholdValues,
                                info   }
        STATUS                current
        DESCRIPTION        "Spontaneous Alarm from the managed network element:
                            TURN service configuration error

TURN service will not work. Check log-output for more details.
                            Check the TURN service configuration and try to fix it."
        ::= { eventGroup56 423 }

        alarm56424 NOTIFICATION-TYPE
        OBJECTS        {        neName,
                                neType,
                                eventGroupName,                        -- 56: MediaServer
                                eventName,                             -- 424: TurnServiceResourceError
                                correlationId,
                                severity,
                                eventTime,
                                faultyObject,
                                monitoredValue,
                                thresholdValues,
                                info   }
        STATUS                current
        DESCRIPTION        "Spontaneous Alarm from the managed network element:
                            TURN service resource error

One or more (possibly all) TURN service ports couldn't be bound. Check log-output for more details.
                            There could be many causes that the configured ports couldn't be used, e. g. access restrictions, port already in use etc."
        ::= { eventGroup56 424 }

        alarm56425 NOTIFICATION-TYPE
        OBJECTS        {        neName,
                                neType,
                                eventGroupName,                        -- 56: MediaServer
                                eventName,                             -- 425: NoMoreAvailableTurnRelayPorts
                                correlationId,
                                severity,
                                eventTime,
                                faultyObject,
                                monitoredValue,
                                thresholdValues,
                                info   }
        STATUS                current
        DESCRIPTION        "Spontaneous Alarm from the managed network element:
                            TURN relay ports (nearly) exhausted

At least 1 TURN relay address type is (nearly) out of free network ports. Probably no more TURN connections could be established. Check log-output for more details.
                            The alarm is cleared automatically as soon as enough network ports are available again."
        ::= { eventGroup56 425 }

        alarm56500 NOTIFICATION-TYPE
        OBJECTS        {        neName,
                                neType,
                                eventGroupName,                        -- 56: MediaServer
                                eventName,                             -- 500: MRCPServerConnectionSetupError
                                correlationId,
                                severity,
                                eventTime,
                                faultyObject,
                                monitoredValue,
                                thresholdValues,
                                info   }
        STATUS                current
        DESCRIPTION        "Spontaneous Alarm from the managed network element:
                            Unable to setup a connection with MRCP server

Unable to setup a connection with MRCP server. No TTS or ASR services may be used within the media server's applications.
                            Escalate to next level of support."
        ::= { eventGroup56 500 }

        alarm56510 NOTIFICATION-TYPE
        OBJECTS        {        neName,
                                neType,
                                eventGroupName,                        -- 56: MediaServer
                                eventName,                             -- 510: AMQPWebkitConnector
                                correlationId,
                                severity,
                                eventTime,
                                faultyObject,
                                monitoredValue,
                                thresholdValues,
                                info   }
        STATUS                current
        DESCRIPTION        "Spontaneous Alarm from the managed network element:
                            AMQP channel shutdown

MediaServer webkit connectivity over AMQP is temporaly broken. It should autorecover as soon as the AMQP cluster is accessible again.
                            Check network connectivity to the AMQP cluster. Escalate to next level of support."
        ::= { eventGroup56 510 }

        alarm56511 NOTIFICATION-TYPE
        OBJECTS        {        neName,
                                neType,
                                eventGroupName,                        -- 56: MediaServer
                                eventName,                             -- 511: AMQPWebkitConnector
                                correlationId,
                                severity,
                                eventTime,
                                faultyObject,
                                monitoredValue,
                                thresholdValues,
                                info   }
        STATUS                current
        DESCRIPTION        "Spontaneous Alarm from the managed network element:
                            An AMQP WebKit resource has been released

MediaServer might have to be restarted.
                            Check network connectivity to AMQP cluster. Escalate to next level of support."
        ::= { eventGroup56 511 }

        alarm56520 NOTIFICATION-TYPE
        OBJECTS        {        neName,
                                neType,
                                eventGroupName,                        -- 56: MediaServer
                                eventName,                             -- 520: AMQPWebkitTransport
                                correlationId,
                                severity,
                                eventTime,
                                faultyObject,
                                monitoredValue,
                                thresholdValues,
                                info   }
        STATUS                current
        DESCRIPTION        "Spontaneous Alarm from the managed network element:
                            AMQP channel shutdown

MediaServer webkit connectivity over AMQP is temporaly broken. It should autorecover as soon as the AMQP cluster is accessible again.
                            Check network connectivity to tha AMQP cluster. Escalate to next level of support."
        ::= { eventGroup56 520 }

        alarm56521 NOTIFICATION-TYPE
        OBJECTS        {        neName,
                                neType,
                                eventGroupName,                        -- 56: MediaServer
                                eventName,                             -- 521: AMQPWebkitTransport
                                correlationId,
                                severity,
                                eventTime,
                                faultyObject,
                                monitoredValue,
                                thresholdValues,
                                info   }
        STATUS                current
        DESCRIPTION        "Spontaneous Alarm from the managed network element:
                            MediaServer paas replies are timing out. Check AMQP messaging in MS Webkit (async-proxy).
                            Check Network Connectivity to the AMQP cluster. Escalate to next level of support."
        ::= { eventGroup56 521 }

        alarm56990 NOTIFICATION-TYPE
        OBJECTS        {        neName,
                                neType,
                                eventGroupName,                        -- 56: MediaServer
                                eventName,                             -- 990: TooManyRTCParticipants
                                correlationId,
                                severity,
                                eventTime,
                                faultyObject,
                                monitoredValue,
                                thresholdValues,
                                info   }
        STATUS                current
        DESCRIPTION        "Spontaneous Alarm from the managed network element:
                            A new RTC participant tried to enter an RTC conference and the limit is reached. The new participant is removed.
                            The alarm is not cleared manually."
        ::= { eventGroup56 990 }

        alarm56991 NOTIFICATION-TYPE
        OBJECTS        {        neName,
                                neType,
                                eventGroupName,                        -- 56: MediaServer
                                eventName,                             -- 991: TooManyPSTNParticipants
                                correlationId,
                                severity,
                                eventTime,
                                faultyObject,
                                monitoredValue,
                                thresholdValues,
                                info   }
        STATUS                current
        DESCRIPTION        "Spontaneous Alarm from the managed network element:
                            A new PSTN participant tried to enter an RTC conference and the limit is reached. The new participant is removed.
                            The alarm is not cleared manually."
        ::= { eventGroup56 991 }

        alarm56992 NOTIFICATION-TYPE
        OBJECTS        {        neName,
                                neType,
                                eventGroupName,                        -- 56: MediaServer
                                eventName,                             -- 992: Overload
                                correlationId,
                                severity,
                                eventTime,
                                faultyObject,
                                monitoredValue,
                                thresholdValues,
                                info   }
        STATUS                current
        DESCRIPTION        "Spontaneous Alarm from the managed network element:
                            The media server has too much load. If possible new conference calls are assigned to other media servers, if not they are rejected.
                            If the alarm condition remains over a longer period of time review installation sizing. If the installation is sized properly escalate to development to check for SW problems."
        ::= { eventGroup56 992 }

        alarm56993 NOTIFICATION-TYPE
        OBJECTS        {        neName,
                                neType,
                                eventGroupName,                        -- 56: MediaServer
                                eventName,                             -- 993: AttachmentUploadFailed
                                correlationId,
                                severity,
                                eventTime,
                                faultyObject,
                                monitoredValue,
                                thresholdValues,
                                info   }
        STATUS                current
        DESCRIPTION        "Spontaneous Alarm from the managed network element:
                            The mediaserver was not able to upload an attachment in several tries. The attachment is going to be lost on next Circuit update. The operations team has to rescue the attachment from mediaserver and wait if the customer requests this lost attachment.
                            The alarm is not cleared automatically. It must be cleared by operations team. Please save the attachment before clearing the alarm ! If the attachment is not saved externally, it is erased during next Circuit update !"
        ::= { eventGroup56 993 }

        alarm56994 NOTIFICATION-TYPE
        OBJECTS        {        neName,
                                neType,
                                eventGroupName,                        -- 56: MediaServer
                                eventName,                             -- 994: ConnectionLost
                                correlationId,
                                severity,
                                eventTime,
                                faultyObject,
                                monitoredValue,
                                thresholdValues,
                                info   }
        STATUS                current
        DESCRIPTION        "Spontaneous Alarm from the managed network element:
                            RTC Controller cannot connect to selected Media Server.
                            If the alarm condition remains check if the Media Server specified in the faulty object is running."
        ::= { eventGroup56 994 }

        alarm56995 NOTIFICATION-TYPE
        OBJECTS        {        neName,
                                neType,
                                eventGroupName,                        -- 56: MediaServer
                                eventName,                             -- 995: NotAvailable
                                correlationId,
                                severity,
                                eventTime,
                                faultyObject,
                                monitoredValue,
                                thresholdValues,
                                info   }
        STATUS                current
        DESCRIPTION        "Spontaneous Alarm from the managed network element:
                            No Media Server is reachable by the RTC Controller.
                            If the alarm condition remains check if there is a media node running and registered to zookeeper. Also check the connectivity from application node to zookeeper nodes."
        ::= { eventGroup56 995 }

        alarm56996 NOTIFICATION-TYPE
        OBJECTS        {        neName,
                                neType,
                                eventGroupName,                        -- 56: MediaServer
                                eventName,                             -- 996: MediaserverRediscoveryFailed
                                correlationId,
                                severity,
                                eventTime,
                                faultyObject,
                                monitoredValue,
                                thresholdValues,
                                info   }
        STATUS                current
        DESCRIPTION        "Spontaneous Alarm from the managed network element:
                            There are some configured Media Servers not available for use by the RTC Controller.
                            If the alarm condition remains check if all mediaservers are running and the zookeeper configuration is correct. Check the tracelogs on the application node."
        ::= { eventGroup56 996 }

        alarm56997 NOTIFICATION-TYPE
        OBJECTS        {        neName,
                                neType,
                                eventGroupName,                        -- 56: MediaServer
                                eventName,                             -- 997: NoMonitoringRtcNode
                                correlationId,
                                severity,
                                eventTime,
                                faultyObject,
                                monitoredValue,
                                thresholdValues,
                                info   }
        STATUS                current
        DESCRIPTION        "Spontaneous Alarm from the managed network element:
                            The monitoring RTC node is down.
                            If the alarm condition remains check if there is an application node with RTC Controller running on it and the zookeeper configuration is correct. Check the tracelogs on the application node."
        ::= { eventGroup56 997 }

        alarm56998 NOTIFICATION-TYPE
        OBJECTS        {        neName,
                                neType,
                                eventGroupName,                        -- 56: MediaServer
                                eventName,                             -- 998: NoNodesInRegion
                                correlationId,
                                severity,
                                eventTime,
                                faultyObject,
                                monitoredValue,
                                thresholdValues,
                                info   }
        STATUS                current
        DESCRIPTION        "Spontaneous Alarm from the managed network element:
                            No Media Server found in region.
                            There are either no nodes configured for this region or all nodes are busy. This is just informational as there will be a fallback to default region."
        ::= { eventGroup56 998 }

        alarm56999 NOTIFICATION-TYPE
        OBJECTS        {        neName,
                                neType,
                                eventGroupName,                        -- 56: MediaServer
                                eventName,                             -- 999: JoinFailures
                                correlationId,
                                severity,
                                eventTime,
                                faultyObject,
                                monitoredValue,
                                thresholdValues,
                                info   }
        STATUS                current
        DESCRIPTION        "Spontaneous Alarm from the managed network element:
                            More than 10 users failed to join for the last minute.
                            If the alarm condition remains check if there is a need to restart Virgo container. Check the tracelogs on the application node and look for unexpected exception cause the join failure."
        ::= { eventGroup56 999 }


        --********************************************************************
        -- Alarm Trap Definitions for event group 57: IMPApplication
        --********************************************************************

        alarm57001 NOTIFICATION-TYPE
        OBJECTS        {        neName,
                                neType,
                                eventGroupName,                        -- 57: IMPApplication
                                eventName,                             -- 001: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup57 1 }

        alarm57003 NOTIFICATION-TYPE
        OBJECTS        {        neName,
                                neType,
                                eventGroupName,                        -- 57: IMPApplication
                                eventName,                             -- 003: ClientAPITimeHigh
                                correlationId,
                                severity,
                                eventTime,
                                faultyObject,
                                monitoredValue,
                                thresholdValues,
                                info   }
        STATUS                current
        DESCRIPTION        "Spontaneous Alarm from the managed network element:
                            Client API average response time.
                            Escalate to next level of support."
        ::= { eventGroup57 3 }

        alarm57004 NOTIFICATION-TYPE
        OBJECTS        {        neName,
                                neType,
                                eventGroupName,                        -- 57: IMPApplication
                                eventName,                             -- 004: ClientAPIFailure
                                correlationId,
                                severity,
                                eventTime,
                                faultyObject,
                                monitoredValue,
                                thresholdValues,
                                info   }
        STATUS                current
        DESCRIPTION        "Spontaneous Alarm from the managed network element:
                            Client API times out, no response.
                            Escalate to next level of support."
        ::= { eventGroup57 4 }

        alarm57005 NOTIFICATION-TYPE
        OBJECTS        {        neName,
                                neType,
                                eventGroupName,                        -- 57: IMPApplication
                                eventName,                             -- 005: ClientAPIZpoolFull
                                correlationId,
                                severity,
                                eventTime,
                                faultyObject,
                                monitoredValue,
                                thresholdValues,
                                info   }
        STATUS                current
        DESCRIPTION        "Spontaneous Alarm from the managed network element:
                            The zpool contains data.

A high fill level may cause issues and failed conversions once 100% reached.
                            If the alarm condition remains over a longer period of time review installation sizing. If the installation is sized properly escalate to development to check for SW problems."
        ::= { eventGroup57 5 }

        alarm57006 NOTIFICATION-TYPE
        OBJECTS        {        neName,
                                neType,
                                eventGroupName,                        -- 57: IMPApplication
                                eventName,                             -- 006: ClientAPIOverload
                                correlationId,
                                severity,
                                eventTime,
                                faultyObject,
                                monitoredValue,
                                thresholdValues,
                                info   }
        STATUS                current
        DESCRIPTION        "Spontaneous Alarm from the managed network element:
                            Client API overload condition.
                            Check the application node usage and escalate to next level of support. A node addition could be considered."
        ::= { eventGroup57 6 }

        alarm57007 NOTIFICATION-TYPE
        OBJECTS        {        neName,
                                neType,
                                eventGroupName,                        -- 57: IMPApplication
                                eventName,                             -- 007: ClientAPIRestApiSDKUsage
                                correlationId,
                                severity,
                                eventTime,
                                faultyObject,
                                monitoredValue,
                                thresholdValues,
                                info   }
        STATUS                current
        DESCRIPTION        "Spontaneous Alarm from the managed network element:
                            RestAPI or JS SDK Usage Violation detection.
                            Check the RestAPI and JS SDK usage and escalate to next level of support."
        ::= { eventGroup57 7 }

        alarm57013 NOTIFICATION-TYPE
        OBJECTS        {        neName,
                                neType,
                                eventGroupName,                        -- 57: IMPApplication
                                eventName,                             -- 013: UnknownAlarmId
                                correlationId,
                                severity,
                                eventTime,
                                faultyObject,
                                monitoredValue,
                                thresholdValues,
                                info   }
        STATUS                current
        DESCRIPTION        "Spontaneous Alarm from the managed network element:
                            The platform alarm configuration file could not be found.
                            Check installation. If correct, check permissions on alarm configuration file."
        ::= { eventGroup57 13 }

        alarm57014 NOTIFICATION-TYPE
        OBJECTS        {        neName,
                                neType,
                                eventGroupName,                        -- 57: IMPApplication
                                eventName,                             -- 014: InvalidMonitoredValue
                                correlationId,
                                severity,
                                eventTime,
                                faultyObject,
                                monitoredValue,
                                thresholdValues,
                                info   }
        STATUS                current
        DESCRIPTION        "Spontaneous Alarm from the managed network element:
                            An alarm has been raised or used with an invalid monitored attribute value.
                            Correct code raising the alarm."
        ::= { eventGroup57 14 }

        alarm57015 NOTIFICATION-TYPE
        OBJECTS        {        neName,
                                neType,
                                eventGroupName,                        -- 57: IMPApplication
                                eventName,                             -- 015: FaultyObjectTooLong
                                correlationId,
                                severity,
                                eventTime,
                                faultyObject,
                                monitoredValue,
                                thresholdValues,
                                info   }
        STATUS                current
        DESCRIPTION        "Spontaneous Alarm from the managed network element:
                            An alarm has been raised with a FaultyObject string that is longer than 255. It has been truncated.
                            Correct code raising the alarm."
        ::= { eventGroup57 15 }

        alarm57016 NOTIFICATION-TYPE
        OBJECTS        {        neName,
                                neType,
                                eventGroupName,                        -- 57: IMPApplication
                                eventName,                             -- 016: AddlInfoTooLong
                                correlationId,
                                severity,
                                eventTime,
                                faultyObject,
                                monitoredValue,
                                thresholdValues,
                                info   }
        STATUS                current
        DESCRIPTION        "Spontaneous Alarm from the managed network element:
                            An alarm has been raised with an Addl Info string that is longer than 255. It has been truncated.
                            Correct code raising the alarm."
        ::= { eventGroup57 16 }

        alarm57017 NOTIFICATION-TYPE
        OBJECTS        {        neName,
                                neType,
                                eventGroupName,                        -- 57: IMPApplication
                                eventName,                             -- 017: UnknownAlarmId
                                correlationId,
                                severity,
                                eventTime,
                                faultyObject,
                                monitoredValue,
                                thresholdValues,
                                info   }
        STATUS                current
        DESCRIPTION        "Spontaneous Alarm from the managed network element:
                            An alarm has been raised or used with an unknown group ID and/or event ID.
                            Check if the alarm should be raised/used. If correct, add alarm to alarm configuration."
        ::= { eventGroup57 17 }

        alarm57021 NOTIFICATION-TYPE
        OBJECTS        {        neName,
                                neType,
                                eventGroupName,                        -- 57: IMPApplication
                                eventName,                             -- 021: UnexpectedRMQPartitions
                                correlationId,
                                severity,
                                eventTime,
                                faultyObject,
                                monitoredValue,
                                thresholdValues,
                                info   }
        STATUS                current
        DESCRIPTION        "Spontaneous Alarm from the managed network element:
                            RabbitMQ Partitions have been detected. Application Nodes may be operating independently of others.
                            Manual action is required in order to recover. Please bring all nodes down, clean up mnesia database and start all nodes again."
        ::= { eventGroup57 21 }

        alarm57022 NOTIFICATION-TYPE
        OBJECTS        {        neName,
                                neType,
                                eventGroupName,                        -- 57: IMPApplication
                                eventName,                             -- 022: UnexpectedRMQClusterError
                                correlationId,
                                severity,
                                eventTime,
                                faultyObject,
                                monitoredValue,
                                thresholdValues,
                                info   }
        STATUS                current
        DESCRIPTION        "Spontaneous Alarm from the managed network element:
                            RabbitMQ join_cluster command has failed, application node(s) may be operating independently of others.
                            Manual action is required in order to recover. Please restart virgo application server process."
        ::= { eventGroup57 22 }

        alarm57023 NOTIFICATION-TYPE
        OBJECTS        {        neName,
                                neType,
                                eventGroupName,                        -- 57: IMPApplication
                                eventName,                             -- 023: UnexpectedRMQConnectivityLost
                                correlationId,
                                severity,
                                eventTime,
                                faultyObject,
                                monitoredValue,
                                thresholdValues,
                                info   }
        STATUS                current
        DESCRIPTION        "Spontaneous Alarm from the managed network element:
                            Messaging controller has lost connectivity to RabbitMQ broker.
                            Manually action is required in order to recover. Check Virgo/RabbitMQ processes."
        ::= { eventGroup57 23 }

        alarm57024 NOTIFICATION-TYPE
        OBJECTS        {        neName,
                                neType,
                                eventGroupName,                        -- 57: IMPApplication
                                eventName,                             -- 024: HazelcastPartitionMigrationIssue
                                correlationId,
                                severity,
                                eventTime,
                                faultyObject,
                                monitoredValue,
                                thresholdValues,
                                info   }
        STATUS                current
        DESCRIPTION        "Spontaneous Alarm from the managed network element:
                            Hazelcast partition migration reported an error.
                            Manual action is required for checking Hazelcast cluster status. Please check the logs and if needed, restart Hazelcast process (pmc restart ansible-hazelcast)."
        ::= { eventGroup57 24 }

        alarm57025 NOTIFICATION-TYPE
        OBJECTS        {        neName,
                                neType,
                                eventGroupName,                        -- 57: IMPApplication
                                eventName,                             -- 025: VirgoHeapIssue
                                correlationId,
                                severity,
                                eventTime,
                                faultyObject,
                                monitoredValue,
                                thresholdValues,
                                info   }
        STATUS                current
        DESCRIPTION        "Spontaneous Alarm from the managed network element:
                            Virgo heap usage is high. The root cause of this incident may be a slow memory leak. The user impact effect is that some of these Virgo containers will be unresponsive (but not down) for several minutes.
                            Manually action maybe required in order to recover. Check the process and the heap memory usage of Virgo."
        ::= { eventGroup57 25 }

        alarm57026 NOTIFICATION-TYPE
        OBJECTS        {        neName,
                                neType,
                                eventGroupName,                        -- 57: IMPApplication
                                eventName,                             -- 026: ApplicationNodeStateChanged
                                correlationId,
                                severity,
                                eventTime,
                                faultyObject,
                                monitoredValue,
                                thresholdValues,
                                info   }
        STATUS                current
        DESCRIPTION        "Spontaneous Alarm from the managed network element:
                            Application node state changed to BUSY or BLOCKED due to high resource usage.
                            Manual action may be required in order to recover."
        ::= { eventGroup57 26 }

        alarm57027 NOTIFICATION-TYPE
        OBJECTS        {        neName,
                                neType,
                                eventGroupName,                        -- 57: IMPApplication
                                eventName,                             -- 027: HazelcastHeapIssue
                                correlationId,
                                severity,
                                eventTime,
                                faultyObject,
                                monitoredValue,
                                thresholdValues,
                                info   }
        STATUS                current
        DESCRIPTION        "Spontaneous Alarm from the managed network element:
                            Hazelcast heap usage is high. The root cause of this incident may be a slow memory leak.
                            Manually action maybe required in order to recover. Check the process and the heap memory usage of Hazelcast."
        ::= { eventGroup57 27 }

        alarm57028 NOTIFICATION-TYPE
        OBJECTS        {        neName,
                                neType,
                                eventGroupName,                        -- 57: IMPApplication
                                eventName,                             -- 028: ZookeeperHeapIssue
                                correlationId,
                                severity,
                                eventTime,
                                faultyObject,
                                monitoredValue,
                                thresholdValues,
                                info   }
        STATUS                current
        DESCRIPTION        "Spontaneous Alarm from the managed network element:
                            Zookeeper heap usage is high. The root cause of this incident may be a slow memory leak.
                            Manually action maybe required in order to recover. Check the process and the heap memory usage of Zookeeper."
        ::= { eventGroup57 28 }

        alarm57029 NOTIFICATION-TYPE
        OBJECTS        {        neName,
                                neType,
                                eventGroupName,                        -- 57: IMPApplication
                                eventName,                             -- 029: RMQBlockedConnection
                                correlationId,
                                severity,
                                eventTime,
                                faultyObject,
                                monitoredValue,
                                thresholdValues,
                                info   }
        STATUS                current
        DESCRIPTION        "Spontaneous Alarm from the managed network element:
                            The connection is blocked due to the broker running low on resources (memory or disk).
                            Manual action may be required in order to recover. Check RabbitMQ processes."
        ::= { eventGroup57 29 }

        alarm57030 NOTIFICATION-TYPE
        OBJECTS        {        neName,
                                neType,
                                eventGroupName,                        -- 57: IMPApplication
                                eventName,                             -- 030: RMQClusterStatusUnknown
                                correlationId,
                                severity,
                                eventTime,
                                faultyObject,
                                monitoredValue,
                                thresholdValues,
                                info   }
        STATUS                current
        DESCRIPTION        "Spontaneous Alarm from the managed network element:
                            Rabbitmq management plugin is down. Broker status is unknown, partition check cannot be completed.
                            Please check manually the broker's status and the cluster's health."
        ::= { eventGroup57 30 }

        alarm57031 NOTIFICATION-TYPE
        OBJECTS        {        neName,
                                neType,
                                eventGroupName,                        -- 57: IMPApplication
                                eventName,                             -- 031: UserSessionTokens
                                correlationId,
                                severity,
                                eventTime,
                                faultyObject,
                                monitoredValue,
                                thresholdValues,
                                info   }
        STATUS                current
        DESCRIPTION        "Spontaneous Alarm from the managed network element:
                            A user is creating too many session tokens caused by too many login requests.
                            Check the user id in the fault object and suspend the user if needed."
        ::= { eventGroup57 31 }

        alarm57032 NOTIFICATION-TYPE
        OBJECTS        {        neName,
                                neType,
                                eventGroupName,                        -- 57: IMPApplication
                                eventName,                             -- 032: SecurityKeyEventing
                                correlationId,
                                severity,
                                eventTime,
                                faultyObject,
                                monitoredValue,
                                thresholdValues,
                                info   }
        STATUS                current
        DESCRIPTION        "Spontaneous Alarm from the managed network element:
                            New security keys are not distributed across the APP-nodes caused by an error with the eventing system.
                            Check the RabbitMQ status, the type of the key in the fault object and the error description in the additional information."
        ::= { eventGroup57 32 }

        alarm57033 NOTIFICATION-TYPE
        OBJECTS        {        neName,
                                neType,
                                eventGroupName,                        -- 57: IMPApplication
                                eventName,                             -- 033: HazelcastClusterZooInconsistency
                                correlationId,
                                severity,
                                eventTime,
                                faultyObject,
                                monitoredValue,
                                thresholdValues,
                                info   }
        STATUS                current
        DESCRIPTION        "Spontaneous Alarm from the managed network element:
                            Hazelcast cluster inconsistency with Zookeeper entries.
                            Hazelcast cluster status failed. Please check the connection between hazelcast members and zookeeper ephemeral services entries and if needed, restart Hazelcast process (pmc restart ansible-hazelcast)."
        ::= { eventGroup57 33 }

        alarm57034 NOTIFICATION-TYPE
        OBJECTS        {        neName,
                                neType,
                                eventGroupName,                        -- 57: IMPApplication
                                eventName,                             -- 034: HazelcastClusterMembersError
                                correlationId,
                                severity,
                                eventTime,
                                faultyObject,
                                monitoredValue,
                                thresholdValues,
                                info   }
        STATUS                current
        DESCRIPTION        "Spontaneous Alarm from the managed network element:
                            Hazelcast cluster members error.
                            Hazelcast cluster status failed. Please check the logs for hazelcast members multiple removal operations and if needed, restart Hazelcast process (pmc restart ansible-hazelcast)."
        ::= { eventGroup57 34 }

        alarm57035 NOTIFICATION-TYPE
        OBJECTS        {        neName,
                                neType,
                                eventGroupName,                        -- 57: IMPApplication
                                eventName,                             -- 035: NettyOutOfDirectMemory
                                correlationId,
                                severity,
                                eventTime,
                                faultyObject,
                                monitoredValue,
                                thresholdValues,
                                info   }
        STATUS                current
        DESCRIPTION        "Spontaneous Alarm from the managed network element:
                            The Netty network communication framework is out of memory.
                            NONE"
        ::= { eventGroup57 35 }

        alarm57036 NOTIFICATION-TYPE
        OBJECTS        {        neName,
                                neType,
                                eventGroupName,                        -- 57: IMPApplication
                                eventName,                             -- 036: NettyError
                                correlationId,
                                severity,
                                eventTime,
                                faultyObject,
                                monitoredValue,
                                thresholdValues,
                                info   }
        STATUS                current
        DESCRIPTION        "Spontaneous Alarm from the managed network element:
                            The Netty network communication framework has a problem.
                            The Netty network communication framework has a problem. Check the error description in the additional information to find out what caused the error. Probably you have to restart the Virgo container on the APP node (pmc restart ansible-virgo)."
        ::= { eventGroup57 36 }

        alarm57050 NOTIFICATION-TYPE
        OBJECTS        {        neName,
                                neType,
                                eventGroupName,                        -- 57: IMPApplication
                                eventName,                             -- 050: UCaaSCreateITSPFailed
                                correlationId,
                                severity,
                                eventTime,
                                faultyObject,
                                monitoredValue,
                                thresholdValues,
                                info   }
        STATUS                current
        DESCRIPTION        "Spontaneous Alarm from the managed network element:
                            Create Openscape Telephony Provider failed.
                            Create Openscape Telephony Provider failed. Please check the faulty object for the tenantId and ITSP information. Cleanup of SBC/OSV resources may be needed."
        ::= { eventGroup57 50 }


        --********************************************************************
        -- Alarm Trap Definitions for event group 58: Redis
        --********************************************************************

        alarm58001 NOTIFICATION-TYPE
        OBJECTS        {        neName,
                                neType,
                                eventGroupName,                        -- 58: Redis
                                eventName,                             -- 001: RedisClusterFail
                                correlationId,
                                severity,
                                eventTime,
                                faultyObject,
                                monitoredValue,
                                thresholdValues,
                                info   }
        STATUS                current
        DESCRIPTION        "Spontaneous Alarm from the managed network element:
                            Redis cluster is in fail state and can not recover by itself. As a result all requests to the data center is not being processed. Human intervention is needed immediately.
                            This alarm can occur during system startup and cluster formation. If this is not the case, check if all nodes are running. Check also if redis-cluster and redis-audit are running. If everything looks good then probably the cluster will not recover by itself. To recover the system lock all nodes (pmc state locked) then run '/etc/init.d/redis-audit clean' in all nodes, afterwards unlock the nodes (pmc state locked) - this way a fresh redis-cluster will start."
        ::= { eventGroup58 1 }

        alarm58002 NOTIFICATION-TYPE
        OBJECTS        {        neName,
                                neType,
                                eventGroupName,                        -- 58: Redis
                                eventName,                             -- 002: RedisClusterFailOver
                                correlationId,
                                severity,
                                eventTime,
                                faultyObject,
                                monitoredValue,
                                thresholdValues,
                                info   }
        STATUS                current
        DESCRIPTION        "Spontaneous Alarm from the managed network element:
                            One of the redis node is down so a failover just happened.
                            This alarm can happen temporarily if some other Access node is restarting. Please check if all nodes are running or if there are network issues. The redis audit will try to rebalance the cluster once the Access node is available again (then the alarm will be automatically cleared). The process of rebalancing can take about 5 to 15 minutes to complete."
        ::= { eventGroup58 2 }

        alarm58003 NOTIFICATION-TYPE
        OBJECTS        {        neName,
                                neType,
                                eventGroupName,                        -- 58: Redis
                                eventName,                             -- 003: RedisClusterRebalancing
                                correlationId,
                                severity,
                                eventTime,
                                faultyObject,
                                monitoredValue,
                                thresholdValues,
                                info   }
        STATUS                current
        DESCRIPTION        "Spontaneous Alarm from the managed network element:
                            A resharding is started, do not stop the nodes participating in the resharding until the alarm is cleared.
                            The redis audit is moving hash slots (resharding). This happens if nodes are added or removed, the alarm will be automatically cleared once the resharding process is complete. The process of resharding can take about 5 to 15 minutes to complete."
        ::= { eventGroup58 3 }

        alarm58004 NOTIFICATION-TYPE
        OBJECTS        {        neName,
                                neType,
                                eventGroupName,                        -- 58: Redis
                                eventName,                             -- 004: RedisClusterInit
                                correlationId,
                                severity,
                                eventTime,
                                faultyObject,
                                monitoredValue,
                                thresholdValues,
                                info   }
        STATUS                current
        DESCRIPTION        "Spontaneous Alarm from the managed network element:
                            Redis Cluster is in the process of reinitializing, all data will be erased and a new cluster will be formed.
                            The redis audit is in process of creating a new cluster, allocating hash slots for each node and defining the Master/Slave roles. This alarm can also happen temporarily after resharding and rebalancing. The alarm will be automatically cleared once the cluster formation process is complete, this process can take about 5 minutes to complete."
        ::= { eventGroup58 4 }


        --********************************************************************
        -- Alarm Trap Definitions for event group 59: LogManager
        --********************************************************************

        alarm59001 NOTIFICATION-TYPE
        OBJECTS        {        neName,
                                neType,
                                eventGroupName,                        -- 59: LogManager
                                eventName,                             -- 001: PostAlarmFailure
                                correlationId,
                                severity,
                                eventTime,
                                faultyObject,
                                monitoredValue,
                                thresholdValues,
                                info   }
        STATUS                current
        DESCRIPTION        "Spontaneous Alarm from the managed network element:
                            The log manger could not store an alarm record in the alarm database. The alarm is not reported as SNMP trap and not displayed in the active alarm database.
                            Run debug file collection of the operations node and escalate to SW development."
        ::= { eventGroup59 1 }

        alarm59002 NOTIFICATION-TYPE
        OBJECTS        {        neName,
                                neType,
                                eventGroupName,                        -- 59: LogManager
                                eventName,                             -- 002: PostSolrFailure
                                correlationId,
                                severity,
                                eventTime,
                                faultyObject,
                                monitoredValue,
                                thresholdValues,
                                info   }
        STATUS                current
        DESCRIPTION        "Spontaneous Alarm from the managed network element:
                            The log manger could not store a log record in Solr. The log is not shown in the log manager GUI and it is not archived in hadoop.
                            Check the partition fill level and accessibility of the /db/logmg directory. Run debug file collection of the operations node and escalate to SW development."
        ::= { eventGroup59 2 }

        alarm59004 NOTIFICATION-TYPE
        OBJECTS        {        neName,
                                neType,
                                eventGroupName,                        -- 59: LogManager
                                eventName,                             -- 004: CorruptedLogFile
                                correlationId,
                                severity,
                                eventTime,
                                faultyObject,
                                monitoredValue,
                                thresholdValues,
                                info   }
        STATUS                current
        DESCRIPTION        "Spontaneous Alarm from the managed network element:
                            Log Manager has detected a corrupted log file and renamed it. The original file name is shown in the faulty object, while the new name is shown in the additional info field.
The content of the log file is not shown in log manager GUI and is not available for analytics.
                            Escalate to development to investigate the reason for file corruption.
Attach the corrupted log file to the fault report."
        ::= { eventGroup59 4 }


        --********************************************************************
        -- Alarm Trap Definitions for event group 60: Access
        --********************************************************************

        alarm60001 NOTIFICATION-TYPE
        OBJECTS        {        neName,
                                neType,
                                eventGroupName,                        -- 60: Access
                                eventName,                             -- 001: FaultyConfiguraton
                                correlationId,
                                severity,
                                eventTime,
                                faultyObject,
                                monitoredValue,
                                thresholdValues,
                                info   }
        STATUS                current
        DESCRIPTION        "Spontaneous Alarm from the managed network element:
                            Access node configuration file is faulty. Access node functionality is restricted.
                            Review log file entries, especially /var/log/access.log, to determine source of problem."
        ::= { eventGroup60 1 }

        alarm60010 NOTIFICATION-TYPE
        OBJECTS        {        neName,
                                neType,
                                eventGroupName,                        -- 60: Access
                                eventName,                             -- 010: NodeJSHeapUsed
                                correlationId,
                                severity,
                                eventTime,
                                faultyObject,
                                monitoredValue,
                                thresholdValues,
                                info   }
        STATUS                current
        DESCRIPTION        "Spontaneous Alarm from the managed network element:
                            Node.js process consumes high memory
                            Escalate to development for investigation (possible memory leak or we reached the user service limit)."
        ::= { eventGroup60 10 }


        --********************************************************************
        -- Alarm Trap Definitions for event group 61: CLV
        --********************************************************************

        alarm61100 NOTIFICATION-TYPE
        OBJECTS        {        neName,
                                neType,
                                eventGroupName,                        -- 61: CLV
                                eventName,                             -- 100: ClvLostConnToDB
                                correlationId,
                                severity,
                                eventTime,
                                faultyObject,
                                monitoredValue,
                                thresholdValues,
                                info   }
        STATUS                current
        DESCRIPTION        "Spontaneous Alarm from the managed network element:
                            CLV lost connection to postgres DB
                            Ensure Postgres is running. When postgres is already running and CLV does not connect within 30 seconds, escalate to development with /var/log/clv/clvserver.log"
        ::= { eventGroup61 100 }

        alarm61101 NOTIFICATION-TYPE
        OBJECTS        {        neName,
                                neType,
                                eventGroupName,                        -- 61: CLV
                                eventName,                             -- 101: ClvLostConnToRabbitMQ
                                correlationId,
                                severity,
                                eventTime,
                                faultyObject,
                                monitoredValue,
                                thresholdValues,
                                info   }
        STATUS                current
        DESCRIPTION        "Spontaneous Alarm from the managed network element:
                            CLV lost connection to RabbitMQ
                            Ensure RabbitMQ service is running on Zookeeper node and reachable. If CLV still cannot connect, escalate to development with /var/log/clv/clvserver.log"
        ::= { eventGroup61 101 }

        alarm61102 NOTIFICATION-TYPE
        OBJECTS        {        neName,
                                neType,
                                eventGroupName,                        -- 61: CLV
                                eventName,                             -- 102: ClvLostConnToZookeeper
                                correlationId,
                                severity,
                                eventTime,
                                faultyObject,
                                monitoredValue,
                                thresholdValues,
                                info   }
        STATUS                current
        DESCRIPTION        "Spontaneous Alarm from the managed network element:
                            CLV lost connection to Zookeeper
                            Ensure Zookeeper service is running on Zookeeper node and reachable. If CLV still cannot connect, escalate to development with /var/log/clv/clvserver.log"
        ::= { eventGroup61 102 }

        alarm61103 NOTIFICATION-TYPE
        OBJECTS        {        neName,
                                neType,
                                eventGroupName,                        -- 61: CLV
                                eventName,                             -- 103: ClvLostConnToAdminAPI
                                correlationId,
                                severity,
                                eventTime,
                                faultyObject,
                                monitoredValue,
                                thresholdValues,
                                info   }
        STATUS                current
        DESCRIPTION        "Spontaneous Alarm from the managed network element:
                            CLV lost connection to AdminAPI (REST)
                            Ensure virgo is running on App node and reachable. If CLV still cannot connect, escalate to development with /var/log/clv/clvserver.log"
        ::= { eventGroup61 103 }


        --********************************************************************
        -- Alarm Trap Definitions for event group 62: XMPP
        --********************************************************************

        alarm62001 NOTIFICATION-TYPE
        OBJECTS        {        neName,
                                neType,
                                eventGroupName,                        -- 62: XMPP
                                eventName,                             -- 001: NoMoreAvailableProvisionLicense
                                correlationId,
                                severity,
                                eventTime,
                                faultyObject,
                                monitoredValue,
                                thresholdValues,
                                info   }
        STATUS                current
        DESCRIPTION        "Spontaneous Alarm from the managed network element:
                            Failed to provision user due to license limit
                            Please make sure that there are enough tenant licenses. If not add more licenses to the tenant."
        ::= { eventGroup62 1 }


        --********************************************************************
        -- Alarm Trap Definitions for event group 80: NetworkCom
        --********************************************************************

        alarm80001 NOTIFICATION-TYPE
        OBJECTS        {        neName,
                                neType,
                                eventGroupName,                        -- 80: NetworkCom
                                eventName,                             -- 001: NodesUnavailable
                                correlationId,
                                severity,
                                eventTime,
                                faultyObject,
                                monitoredValue,
                                thresholdValues,
                                info   }
        STATUS                current
        DESCRIPTION        "Spontaneous Alarm from the managed network element:
                            The listed nodes are not reported as active in the zookeeper database.
                            Check the administrative and operational status. Try to access the node directly via ssh and run rapidstat."
        ::= { eventGroup80 1 }

        alarm80002 NOTIFICATION-TYPE
        OBJECTS        {        neName,
                                neType,
                                eventGroupName,                        -- 80: NetworkCom
                                eventName,                             -- 002: LocalResponseTime
                                correlationId,
                                severity,
                                eventTime,
                                faultyObject,
                                monitoredValue,
                                thresholdValues,
                                info   }
        STATUS                current
        DESCRIPTION        "Spontaneous Alarm from the managed network element:
                            The node's response time to a test message sent by the operations node was too high.
                            If this alarm persists escalate to next level of support to determine whether is response time is justified. Ether the SW needs to be corrected or the threshold be changed."
        ::= { eventGroup80 2 }

        alarm80003 NOTIFICATION-TYPE
        OBJECTS        {        neName,
                                neType,
                                eventGroupName,                        -- 80: NetworkCom
                                eventName,                             -- 003: RemoteResponseTime
                                correlationId,
                                severity,
                                eventTime,
                                faultyObject,
                                monitoredValue,
                                thresholdValues,
                                info   }
        STATUS                current
        DESCRIPTION        "Spontaneous Alarm from the managed network element:
                            Future.
                            Future."
        ::= { eventGroup80 3 }

        alarm80004 NOTIFICATION-TYPE
        OBJECTS        {        neName,
                                neType,
                                eventGroupName,                        -- 80: NetworkCom
                                eventName,                             -- 004: NodesNotStarted
                                correlationId,
                                severity,
                                eventTime,
                                faultyObject,
                                monitoredValue,
                                thresholdValues,
                                info   }
        STATUS                current
        DESCRIPTION        "Spontaneous Alarm from the managed network element:
                            The listed nodes have been in an invalid admin - operational state combination for more than 15 minutes. The nodes did not startup to the requested level.
                            Collect log files and sequentially reboot the nodes."
        ::= { eventGroup80 4 }

        alarm80005 NOTIFICATION-TYPE
        OBJECTS        {        neName,
                                neType,
                                eventGroupName,                        -- 80: NetworkCom
                                eventName,                             -- 005: NodesNotStopped
                                correlationId,
                                severity,
                                eventTime,
                                faultyObject,
                                monitoredValue,
                                thresholdValues,
                                info   }
        STATUS                current
        DESCRIPTION        "Spontaneous Alarm from the managed network element:
                            The listed nodes have been in an invalid admin - operational state combination for more than 15 minutes. The nodes did not stop/shutdown to the requested level.
                            Collect log files and sequentially reboot the nodes."
        ::= { eventGroup80 5 }


        --********************************************************************
        -- Alarm Trap Definitions for event group 81: Eventing
        --********************************************************************

        alarm81001 NOTIFICATION-TYPE
        OBJECTS        {        neName,
                                neType,
                                eventGroupName,                        -- 81: Eventing
                                eventName,                             -- 001: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup81 1 }


        --********************************************************************
        -- Alarm Trap Definitions for event group 82: InMemDatabase
        --********************************************************************

        alarm82001 NOTIFICATION-TYPE
        OBJECTS        {        neName,
                                neType,
                                eventGroupName,                        -- 82: InMemDatabase
                                eventName,                             -- 001: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup82 1 }


        --********************************************************************
        -- Alarm Trap Definitions for event group 90: Storage
        --********************************************************************

        alarm90001 NOTIFICATION-TYPE
        OBJECTS        {        neName,
                                neType,
                                eventGroupName,                        -- 90: Storage
                                eventName,                             -- 001: CassandraNodeFailure
                                correlationId,
                                severity,
                                eventTime,
                                faultyObject,
                                monitoredValue,
                                thresholdValues,
                                info   }
        STATUS                current
        DESCRIPTION        "Spontaneous Alarm from the managed network element:
                            Cassandra node is down.
                            Collect log files and contact support."
        ::= { eventGroup90 1 }

        alarm90002 NOTIFICATION-TYPE
        OBJECTS        {        neName,
                                neType,
                                eventGroupName,                        -- 90: Storage
                                eventName,                             -- 002: CassandraClusterFailure
                                correlationId,
                                severity,
                                eventTime,
                                faultyObject,
                                monitoredValue,
                                thresholdValues,
                                info   }
        STATUS                current
        DESCRIPTION        "Spontaneous Alarm from the managed network element:
                            Cassandra cluster is down.
                            Collect log files and contact support."
        ::= { eventGroup90 2 }

        alarm90003 NOTIFICATION-TYPE
        OBJECTS        {        neName,
                                neType,
                                eventGroupName,                        -- 90: Storage
                                eventName,                             -- 003: SchemaValidationFailure
                                correlationId,
                                severity,
                                eventTime,
                                faultyObject,
                                monitoredValue,
                                thresholdValues,
                                info   }
        STATUS                current
        DESCRIPTION        "Spontaneous Alarm from the managed network element:
                            Some needed tables are missing from the schema
                            Collect log files and contact support."
        ::= { eventGroup90 3 }

        alarm90004 NOTIFICATION-TYPE
        OBJECTS        {        neName,
                                neType,
                                eventGroupName,                        -- 90: Storage
                                eventName,                             -- 004: ElasticSearchClusterFailure
                                correlationId,
                                severity,
                                eventTime,
                                faultyObject,
                                monitoredValue,
                                thresholdValues,
                                info   }
        STATUS                current
        DESCRIPTION        "Spontaneous Alarm from the managed network element:
                            ElasticSearch cluster is down
                            No ElasticSearch data nodes are reachable. Check network/firewall and/or bring up ES nodes"
        ::= { eventGroup90 4 }

        alarm90005 NOTIFICATION-TYPE
        OBJECTS        {        neName,
                                neType,
                                eventGroupName,                        -- 90: Storage
                                eventName,                             -- 005: TooManyReadFailures
                                correlationId,
                                severity,
                                eventTime,
                                faultyObject,
                                monitoredValue,
                                thresholdValues,
                                info   }
        STATUS                current
        DESCRIPTION        "Spontaneous Alarm from the managed network element:
                            Too many consecutive file read errors
                            Check that the file system (XTreemFS) where files are stored is functioning properly"
        ::= { eventGroup90 5 }

        alarm90006 NOTIFICATION-TYPE
        OBJECTS        {        neName,
                                neType,
                                eventGroupName,                        -- 90: Storage
                                eventName,                             -- 006: TooManyWriteFailures
                                correlationId,
                                severity,
                                eventTime,
                                faultyObject,
                                monitoredValue,
                                thresholdValues,
                                info   }
        STATUS                current
        DESCRIPTION        "Spontaneous Alarm from the managed network element:
                            Too many consecutive file write errors
                            Check that the file system (XTreemFS) where files are stored is functioning properly"
        ::= { eventGroup90 6 }

        alarm90007 NOTIFICATION-TYPE
        OBJECTS        {        neName,
                                neType,
                                eventGroupName,                        -- 90: Storage
                                eventName,                             -- 007: ElasticSearchIndexInaccessibleFailure
                                correlationId,
                                severity,
                                eventTime,
                                faultyObject,
                                monitoredValue,
                                thresholdValues,
                                info   }
        STATUS                current
        DESCRIPTION        "Spontaneous Alarm from the managed network element:
                            Some indices have missing shards
                            Too many ElasticSearch data nodes are down. Bring them back up"
        ::= { eventGroup90 7 }

        alarm90008 NOTIFICATION-TYPE
        OBJECTS        {        neName,
                                neType,
                                eventGroupName,                        -- 90: Storage
                                eventName,                             -- 008: StorageBackupFailure
                                correlationId,
                                severity,
                                eventTime,
                                faultyObject,
                                monitoredValue,
                                thresholdValues,
                                info   }
        STATUS                current
        DESCRIPTION        "Spontaneous Alarm from the managed network element:
                            Backup of storage data services (Cassandra, ElasticSearch, XtreemFS) failed
                            Check backup status screen in management. Check backup log files on the shared storage to see reason of the failure. If there are no files present on shared storage, then most probably management was not able to connect to storage"
        ::= { eventGroup90 8 }

        alarm90009 NOTIFICATION-TYPE
        OBJECTS        {        neName,
                                neType,
                                eventGroupName,                        -- 90: Storage
                                eventName,                             -- 009: BackupVerificationFailure
                                correlationId,
                                severity,
                                eventTime,
                                faultyObject,
                                monitoredValue,
                                thresholdValues,
                                info   }
        STATUS                current
        DESCRIPTION        "Spontaneous Alarm from the managed network element:
                            Backup verification failed. Backup could be corrupted
                            Check backup verification log file"
        ::= { eventGroup90 9 }

        alarm90010 NOTIFICATION-TYPE
        OBJECTS        {        neName,
                                neType,
                                eventGroupName,                        -- 90: Storage
                                eventName,                             -- 010: BackupSnapshotScheduleFailure
                                correlationId,
                                severity,
                                eventTime,
                                faultyObject,
                                monitoredValue,
                                thresholdValues,
                                info   }
        STATUS                current
        DESCRIPTION        "Spontaneous Alarm from the managed network element:
                            Storage snapshot backup schedule set up on Management node failed
                            Check alarm message and contact support"
        ::= { eventGroup90 10 }

        alarm90011 NOTIFICATION-TYPE
        OBJECTS        {        neName,
                                neType,
                                eventGroupName,                        -- 90: Storage
                                eventName,                             -- 011: BackupIncrementScheduleFailure
                                correlationId,
                                severity,
                                eventTime,
                                faultyObject,
                                monitoredValue,
                                thresholdValues,
                                info   }
        STATUS                current
        DESCRIPTION        "Spontaneous Alarm from the managed network element:
                            Storage increment backup schedule set up on Management node failed
                            Check alarm message and contact support"
        ::= { eventGroup90 11 }

        alarm90012 NOTIFICATION-TYPE
        OBJECTS        {        neName,
                                neType,
                                eventGroupName,                        -- 90: Storage
                                eventName,                             -- 012: StorageRestoreFailure
                                correlationId,
                                severity,
                                eventTime,
                                faultyObject,
                                monitoredValue,
                                thresholdValues,
                                info   }
        STATUS                current
        DESCRIPTION        "Spontaneous Alarm from the managed network element:
                            Restore of storage data services (Cassandra, ElasticSearch, XtreemFS) failed
                            Check alarm message and storage restore status screen on management - then contact support"
        ::= { eventGroup90 12 }

        alarm90013 NOTIFICATION-TYPE
        OBJECTS        {        neName,
                                neType,
                                eventGroupName,                        -- 90: Storage
                                eventName,                             -- 013: VirusUpdateFailure
                                correlationId,
                                severity,
                                eventTime,
                                faultyObject,
                                monitoredValue,
                                thresholdValues,
                                info   }
        STATUS                current
        DESCRIPTION        "Spontaneous Alarm from the managed network element:
                            Virus Update Failed
                            Check alarm message and contact support"
        ::= { eventGroup90 13 }

        alarm90014 NOTIFICATION-TYPE
        OBJECTS        {        neName,
                                neType,
                                eventGroupName,                        -- 90: Storage
                                eventName,                             -- 014: VirusUpdateDisabled
                                correlationId,
                                severity,
                                eventTime,
                                faultyObject,
                                monitoredValue,
                                thresholdValues,
                                info   }
        STATUS                current
        DESCRIPTION        "Spontaneous Alarm from the managed network element:
                            Automatic Virus update is disabled in zookeeper: //Mappings/virusScan/enableAutoUpdate
                            Turn on automatic virus update in zookeeper: //Mappings/virusScan/enableAutoUpdate"
        ::= { eventGroup90 14 }

        alarm90015 NOTIFICATION-TYPE
        OBJECTS        {        neName,
                                neType,
                                eventGroupName,                        -- 90: Storage
                                eventName,                             -- 015: BackupServerDiskSpace
                                correlationId,
                                severity,
                                eventTime,
                                faultyObject,
                                monitoredValue,
                                thresholdValues,
                                info   }
        STATUS                current
        DESCRIPTION        "Spontaneous Alarm from the managed network element:
                            Backup Server disk has crossed a level indicating a need for clean up of old backups
                            Check alarm message - tell support that the backup server is about to run out of space"
        ::= { eventGroup90 15 }

        alarm90016 NOTIFICATION-TYPE
        OBJECTS        {        neName,
                                neType,
                                eventGroupName,                        -- 90: Storage
                                eventName,                             -- 016: ConversationScheduledExportNotComplete
                                correlationId,
                                severity,
                                eventTime,
                                faultyObject,
                                monitoredValue,
                                thresholdValues,
                                info   }
        STATUS                current
        DESCRIPTION        "Spontaneous Alarm from the managed network element:
                            Not all conversations were exported successfully in a scheduled export
                            Check logs for information on which conversations did not export properly"
        ::= { eventGroup90 16 }

        alarm90017 NOTIFICATION-TYPE
        OBJECTS        {        neName,
                                neType,
                                eventGroupName,                        -- 90: Storage
                                eventName,                             -- 017: ConversationScheduledExportFailure
                                correlationId,
                                severity,
                                eventTime,
                                faultyObject,
                                monitoredValue,
                                thresholdValues,
                                info   }
        STATUS                current
        DESCRIPTION        "Spontaneous Alarm from the managed network element:
                            A scheduled export of conversations failed to complete
                            Check alarm message for details.  Verify zookeeper parameters in //serviceConfiguration/net.ansible.nosql.export-service"
        ::= { eventGroup90 17 }

        alarm90018 NOTIFICATION-TYPE
        OBJECTS        {        neName,
                                neType,
                                eventGroupName,                        -- 90: Storage
                                eventName,                             -- 018: StandbyElasticSearchClusterFailure
                                correlationId,
                                severity,
                                eventTime,
                                faultyObject,
                                monitoredValue,
                                thresholdValues,
                                info   }
        STATUS                current
        DESCRIPTION        "Spontaneous Alarm from the managed network element:
                            Standby ElasticSearch cluster is down
                            No Standby ElasticSearch data nodes are reachable. Check network/firewall and/or bring up ES nodes"
        ::= { eventGroup90 18 }

        alarm90019 NOTIFICATION-TYPE
        OBJECTS        {        neName,
                                neType,
                                eventGroupName,                        -- 90: Storage
                                eventName,                             -- 019: StandbyElasticSearchIndexInaccessibleFailure
                                correlationId,
                                severity,
                                eventTime,
                                faultyObject,
                                monitoredValue,
                                thresholdValues,
                                info   }
        STATUS                current
        DESCRIPTION        "Spontaneous Alarm from the managed network element:
                            Some indices in Standby have missing shards
                            Too many Standby ElasticSearch data nodes are down. Bring them back up"
        ::= { eventGroup90 19 }

        alarm90020 NOTIFICATION-TYPE
        OBJECTS        {        neName,
                                neType,
                                eventGroupName,                        -- 90: Storage
                                eventName,                             -- 020: DataRetentionStartFailure
                                correlationId,
                                severity,
                                eventTime,
                                faultyObject,
                                monitoredValue,
                                thresholdValues,
                                info   }
        STATUS                current
        DESCRIPTION        "Spontaneous Alarm from the managed network element:
                            DATA RETENTION TOOL failed to start
                            check DATA RETENTION logfile to check what cause the startup failure"
        ::= { eventGroup90 20 }

        alarm90021 NOTIFICATION-TYPE
        OBJECTS        {        neName,
                                neType,
                                eventGroupName,                        -- 90: Storage
                                eventName,                             -- 021: DataRetentionRunFailure
                                correlationId,
                                severity,
                                eventTime,
                                faultyObject,
                                monitoredValue,
                                thresholdValues,
                                info   }
        STATUS                current
        DESCRIPTION        "Spontaneous Alarm from the managed network element:
                            DATA RETENTION TOOL encountered an error during a run
                            check DATA RETENTION logfile to find out what caused the error"
        ::= { eventGroup90 21 }

        alarm90030 NOTIFICATION-TYPE
        OBJECTS        {        neName,
                                neType,
                                eventGroupName,                        -- 90: Storage
                                eventName,                             -- 030: LongTermStatsAggregationFailure
                                correlationId,
                                severity,
                                eventTime,
                                faultyObject,
                                monitoredValue,
                                thresholdValues,
                                info   }
        STATUS                current
        DESCRIPTION        "Spontaneous Alarm from the managed network element:
                            Long term stats aggregation job did not generate some required metrics
                            check stats-server.log of the node the alarm was fired from to find out what caused the error"
        ::= { eventGroup90 30 }

        alarm90031 NOTIFICATION-TYPE
        OBJECTS        {        neName,
                                neType,
                                eventGroupName,                        -- 90: Storage
                                eventName,                             -- 031: SecurityKey
                                correlationId,
                                severity,
                                eventTime,
                                faultyObject,
                                monitoredValue,
                                thresholdValues,
                                info   }
        STATUS                current
        DESCRIPTION        "Spontaneous Alarm from the managed network element:
                            Retrieving the master keys from the external master key server failed. The data on the server can not be encrypted or decrypted!
                            Check the error description in the additional information to find out what caused the error."
        ::= { eventGroup90 31 }

        alarm90032 NOTIFICATION-TYPE
        OBJECTS        {        neName,
                                neType,
                                eventGroupName,                        -- 90: Storage
                                eventName,                             -- 032: SecurityKey
                                correlationId,
                                severity,
                                eventTime,
                                faultyObject,
                                monitoredValue,
                                thresholdValues,
                                info   }
        STATUS                current
        DESCRIPTION        "Spontaneous Alarm from the managed network element:
                            Retrieving the working keys for data encryption from storage failed. The data on the server can not be encrypted or decrypted!
                            Check the error description in the additional information to find out what caused the error."
        ::= { eventGroup90 32 }

        alarm90033 NOTIFICATION-TYPE
        OBJECTS        {        neName,
                                neType,
                                eventGroupName,                        -- 90: Storage
                                eventName,                             -- 033: SecurityKey
                                correlationId,
                                severity,
                                eventTime,
                                faultyObject,
                                monitoredValue,
                                thresholdValues,
                                info   }
        STATUS                current
        DESCRIPTION        "Spontaneous Alarm from the managed network element:
                            Creating a working key for data encryption failed.
                            Check the error description in the additional information to find out what caused the error."
        ::= { eventGroup90 33 }

        alarm90034 NOTIFICATION-TYPE
        OBJECTS        {        neName,
                                neType,
                                eventGroupName,                        -- 90: Storage
                                eventName,                             -- 034: SecurityKey
                                correlationId,
                                severity,
                                eventTime,
                                faultyObject,
                                monitoredValue,
                                thresholdValues,
                                info   }
        STATUS                current
        DESCRIPTION        "Spontaneous Alarm from the managed network element:
                            Adding a master key for data encryption failed.
                            Check the error description in the additional information to find out what caused the error."
        ::= { eventGroup90 34 }

        alarm90035 NOTIFICATION-TYPE
        OBJECTS        {        neName,
                                neType,
                                eventGroupName,                        -- 90: Storage
                                eventName,                             -- 035: SecurityKey
                                correlationId,
                                severity,
                                eventTime,
                                faultyObject,
                                monitoredValue,
                                thresholdValues,
                                info   }
        STATUS                current
        DESCRIPTION        "Spontaneous Alarm from the managed network element:
                            Adding a working key for data encryption failed.
                            Check the error description in the additional information to find out what caused the error."
        ::= { eventGroup90 35 }

        alarm90036 NOTIFICATION-TYPE
        OBJECTS        {        neName,
                                neType,
                                eventGroupName,                        -- 90: Storage
                                eventName,                             -- 036: Encryption
                                correlationId,
                                severity,
                                eventTime,
                                faultyObject,
                                monitoredValue,
                                thresholdValues,
                                info   }
        STATUS                current
        DESCRIPTION        "Spontaneous Alarm from the managed network element:
                            Encryption of data failed.
                            Check the error description in the additional information to find out what caused the error. Check the fault object to find out what element it is related to."
        ::= { eventGroup90 36 }

        alarm90037 NOTIFICATION-TYPE
        OBJECTS        {        neName,
                                neType,
                                eventGroupName,                        -- 90: Storage
                                eventName,                             -- 037: Encryption
                                correlationId,
                                severity,
                                eventTime,
                                faultyObject,
                                monitoredValue,
                                thresholdValues,
                                info   }
        STATUS                current
        DESCRIPTION        "Spontaneous Alarm from the managed network element:
                            Decryption of data failed.
                            Check the error description in the additional information to find out what caused the error. Check the fault object to find out what element it is related to."
        ::= { eventGroup90 37 }

        alarm90038 NOTIFICATION-TYPE
        OBJECTS        {        neName,
                                neType,
                                eventGroupName,                        -- 90: Storage
                                eventName,                             -- 038: TooManyWriteFailuresIntoStandbyFileStore
                                correlationId,
                                severity,
                                eventTime,
                                faultyObject,
                                monitoredValue,
                                thresholdValues,
                                info   }
        STATUS                current
        DESCRIPTION        "Spontaneous Alarm from the managed network element:
                            Replication to other DC's file storage has failed several times in a row
                            Check the status of the other DC's file storage and the connectivity from this DC to that DC"
        ::= { eventGroup90 38 }

        alarm90039 NOTIFICATION-TYPE
        OBJECTS        {        neName,
                                neType,
                                eventGroupName,                        -- 90: Storage
                                eventName,                             -- 039: SplunkTransferFailed
                                correlationId,
                                severity,
                                eventTime,
                                faultyObject,
                                monitoredValue,
                                thresholdValues,
                                info   }
        STATUS                current
        DESCRIPTION        "Spontaneous Alarm from the managed network element:
                            Failed to do splunk transfer via cron.
                            Check the connectivity to remote endpoint for splunk."
        ::= { eventGroup90 39 }

        alarm90040 NOTIFICATION-TYPE
        OBJECTS        {        neName,
                                neType,
                                eventGroupName,                        -- 90: Storage
                                eventName,                             -- 040: HttpClientForSwiftRestarted
                                correlationId,
                                severity,
                                eventTime,
                                faultyObject,
                                monitoredValue,
                                thresholdValues,
                                info   }
        STATUS                current
        DESCRIPTION        "Spontaneous Alarm from the managed network element:
                            Http client used to communicate with Swift Object Storage is not releasing its connections and has been restarted.
                            Collect virgo trace logs in affected node. Report issue if it crosses the MAJOR threshold."
        ::= { eventGroup90 40 }



        --********************************************************************
        -- Alarm Trap Definitions for alarms potentially sent for multiple nodes
        -- (using eventGroupC)
        --********************************************************************

        --********************************************************************
        -- Alarm Trap Definitions for alarm eventC 01: Platform
        --********************************************************************

        alarmC01001 NOTIFICATION-TYPE
        OBJECTS        {        neName,
                                neType,
                                eventGroupName,                        -- 01: Platform
                                eventName,                             -- 001: InvalidAlarmConfiguration
                                correlationId,
                                severity,
                                eventTime,
                                nodes,
                                faultyObject,
                                monitoredValue,
                                thresholdValues,
                                info   }
        STATUS                current
        DESCRIPTION        "Spontaneous Alarm from the managed network element:
                            The alarm configuration has problems.
                            Check the problem listed in the faulty object and correct."
        ::= { eventGroupC01 1 }

        alarmC01002 NOTIFICATION-TYPE
        OBJECTS        {        neName,
                                neType,
                                eventGroupName,                        -- 01: Platform
                                eventName,                             -- 002: InvalidTimezoneConfiguration
                                correlationId,
                                severity,
                                eventTime,
                                nodes,
                                faultyObject,
                                monitoredValue,
                                thresholdValues,
                                info   }
        STATUS                current
        DESCRIPTION        "Spontaneous Alarm from the managed network element:
                            The timezone configured in the datacenter configuration in the ZooKeeper database is not one of values supported by the Linux Operating System. An invalid timezone will be ignored so the timezone will remain as the default timezone (UTC) or the last valid timezone that was successfully configured.
                            Manually change the timezone in the datacenter configuration in the ZooKeeper database to a valid timezone. Valid timezones can be found under directory /usr/share/zoneinfo (e.g. US/Eastern)."
        ::= { eventGroupC01 2 }

        alarmC01003 NOTIFICATION-TYPE
        OBJECTS        {        neName,
                                neType,
                                eventGroupName,                        -- 01: Platform
                                eventName,                             -- 003: UnknownAlarmId
                                correlationId,
                                severity,
                                eventTime,
                                nodes,
                                faultyObject,
                                monitoredValue,
                                thresholdValues,
                                info   }
        STATUS                current
        DESCRIPTION        "Spontaneous Alarm from the managed network element:
                            An alarm has been raised or used with an unknown group ID and/or event ID.
                            Check if the alarm should be raised/used. If correct, add alarm to alarm configuration."
        ::= { eventGroupC01 3 }

        alarmC01004 NOTIFICATION-TYPE
        OBJECTS        {        neName,
                                neType,
                                eventGroupName,                        -- 01: Platform
                                eventName,                             -- 004: InvalidMonitoredValue
                                correlationId,
                                severity,
                                eventTime,
                                nodes,
                                faultyObject,
                                monitoredValue,
                                thresholdValues,
                                info   }
        STATUS                current
        DESCRIPTION        "Spontaneous Alarm from the managed network element:
                            An alarm has been raised or used with an invalid monitored attribute value.
                            Correct code raising the alarm."
        ::= { eventGroupC01 4 }

        alarmC01005 NOTIFICATION-TYPE
        OBJECTS        {        neName,
                                neType,
                                eventGroupName,                        -- 01: Platform
                                eventName,                             -- 005: FaultyObjectTooLong
                                correlationId,
                                severity,
                                eventTime,
                                nodes,
                                faultyObject,
                                monitoredValue,
                                thresholdValues,
                                info   }
        STATUS                current
        DESCRIPTION        "Spontaneous Alarm from the managed network element:
                            An alarm has been raised with a FaultyObject string that is longer than 255. It has been truncated.
                            Correct code raising the alarm."
        ::= { eventGroupC01 5 }

        alarmC01006 NOTIFICATION-TYPE
        OBJECTS        {        neName,
                                neType,
                                eventGroupName,                        -- 01: Platform
                                eventName,                             -- 006: AddlInfoTooLong
                                correlationId,
                                severity,
                                eventTime,
                                nodes,
                                faultyObject,
                                monitoredValue,
                                thresholdValues,
                                info   }
        STATUS                current
        DESCRIPTION        "Spontaneous Alarm from the managed network element:
                            An alarm has been raised with an Addl Info string that is longer than 255. It has been truncated.
                            Correct code raising the alarm."
        ::= { eventGroupC01 6 }

        alarmC01007 NOTIFICATION-TYPE
        OBJECTS        {        neName,
                                neType,
                                eventGroupName,                        -- 01: Platform
                                eventName,                             -- 007: TooManyAlarmParameters
                                correlationId,
                                severity,
                                eventTime,
                                nodes,
                                faultyObject,
                                monitoredValue,
                                thresholdValues,
                                info   }
        STATUS                current
        DESCRIPTION        "Spontaneous Alarm from the managed network element:
                            There is additional text after AddlInfo in the reported alarm string.
                            Correct code raising the alarm."
        ::= { eventGroupC01 7 }

        alarmC01011 NOTIFICATION-TYPE
        OBJECTS        {        neName,
                                neType,
                                eventGroupName,                        -- 01: Platform
                                eventName,                             -- 011: NodeCrashed
                                correlationId,
                                severity,
                                eventTime,
                                nodes,
                                faultyObject,
                                monitoredValue,
                                thresholdValues,
                                info   }
        STATUS                current
        DESCRIPTION        "Spontaneous Alarm from the managed network element:
                            The node rebooted because of a Linux O/S crash. The crashes of the last 8 hours are listed under FaultyObject. The addl. Info field contains the content of the README.txt file of the last crash.
                            Check the status of the node and collect debug files. Escalate to development for analysis."
        ::= { eventGroupC01 11 }


        --********************************************************************
        -- Alarm Trap Definitions for alarm eventC 02: Configuration
        --********************************************************************

        alarmC02001 NOTIFICATION-TYPE
        OBJECTS        {        neName,
                                neType,
                                eventGroupName,                        -- 02: Configuration
                                eventName,                             -- 001: InvalidZooData
                                correlationId,
                                severity,
                                eventTime,
                                nodes,
                                faultyObject,
                                monitoredValue,
                                thresholdValues,
                                info   }
        STATUS                current
        DESCRIPTION        "Spontaneous Alarm from the managed network element:
                            The node reconfiguration software has found invalid zookeeper data. The node has ignored the zookeeper data and continues with the current old data. The faulty object parameter contains the names of the reconfiguration scripts that found an error.
There is a mismatch between zookeeper stored data as displayed on the mgmt node and the data that are actually stored and used on the node!
                            Check zookeeper data for invalid values, especially in the areas associated with the scripts listed in the faulty object.
Correct faulty data and check that the alarm goes away.
The platform reconfiguration script returns an alarm clear when it reports success to PM."
        ::= { eventGroupC02 1 }


        --********************************************************************
        -- Alarm Trap Definitions for alarm eventC 03: FileTransfer
        --********************************************************************

        alarmC03001 NOTIFICATION-TYPE
        OBJECTS        {        neName,
                                neType,
                                eventGroupName,                        -- 03: FileTransfer
                                eventName,                             -- 001: ExportFailing
                                correlationId,
                                severity,
                                eventTime,
                                nodes,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroupC03 1 }

        alarmC03002 NOTIFICATION-TYPE
        OBJECTS        {        neName,
                                neType,
                                eventGroupName,                        -- 03: FileTransfer
                                eventName,                             -- 002: ExportFailing
                                correlationId,
                                severity,
                                eventTime,
                                nodes,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroupC03 2 }

        alarmC03003 NOTIFICATION-TYPE
        OBJECTS        {        neName,
                                neType,
                                eventGroupName,                        -- 03: FileTransfer
                                eventName,                             -- 003: ExportFailing
                                correlationId,
                                severity,
                                eventTime,
                                nodes,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroupC03 3 }


        --********************************************************************
        -- Alarm Trap Definitions for alarm eventC 04: Process
        --********************************************************************

        alarmC04001 NOTIFICATION-TYPE
        OBJECTS        {        neName,
                                neType,
                                eventGroupName,                        -- 04: Process
                                eventName,                             -- 001: PmAborted
                                correlationId,
                                severity,
                                eventTime,
                                nodes,
                                faultyObject,
                                monitoredValue,
                                thresholdValues,
                                info   }
        STATUS                current
        DESCRIPTION        "Spontaneous Alarm from the managed network element:
                            Process Monitoring has aborted.
                            Check configuration files and get logs in debug level 7."
        ::= { eventGroupC04 1 }

        alarmC04002 NOTIFICATION-TYPE
        OBJECTS        {        neName,
                                neType,
                                eventGroupName,                        -- 04: Process
                                eventName,                             -- 002: NetworkNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 2 }

        alarmC04003 NOTIFICATION-TYPE
        OBJECTS        {        neName,
                                neType,
                                eventGroupName,                        -- 04: Process
                                eventName,                             -- 003: RoutesNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 3 }

        alarmC04004 NOTIFICATION-TYPE
        OBJECTS        {        neName,
                                neType,
                                eventGroupName,                        -- 04: Process
                                eventName,                             -- 004: GmondNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 4 }

        alarmC04005 NOTIFICATION-TYPE
        OBJECTS        {        neName,
                                neType,
                                eventGroupName,                        -- 04: Process
                                eventName,                             -- 005: hsflowdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 5 }

        alarmC04006 NOTIFICATION-TYPE
        OBJECTS        {        neName,
                                neType,
                                eventGroupName,                        -- 04: Process
                                eventName,                             -- 006: jmxtransNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 6 }

        alarmC04007 NOTIFICATION-TYPE
        OBJECTS        {        neName,
                                neType,
                                eventGroupName,                        -- 04: Process
                                eventName,                             -- 007: ntpNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 7 }

        alarmC04008 NOTIFICATION-TYPE
        OBJECTS        {        neName,
                                neType,
                                eventGroupName,                        -- 04: Process
                                eventName,                             -- 008: syslogNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 8 }

        alarmC04009 NOTIFICATION-TYPE
        OBJECTS        {        neName,
                                neType,
                                eventGroupName,                        -- 04: Process
                                eventName,                             -- 009: sshdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 9 }

        alarmC04010 NOTIFICATION-TYPE
        OBJECTS        {        neName,
                                neType,
                                eventGroupName,                        -- 04: Process
                                eventName,                             -- 010: snmpdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 10 }

        alarmC04011 NOTIFICATION-TYPE
        OBJECTS        {        neName,
                                neType,
                                eventGroupName,                        -- 04: Process
                                eventName,                             -- 011: idsNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 11 }

        alarmC04012 NOTIFICATION-TYPE
        OBJECTS        {        neName,
                                neType,
                                eventGroupName,                        -- 04: Process
                                eventName,                             -- 012: logstashNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 12 }

        alarmC04013 NOTIFICATION-TYPE
        OBJECTS        {        neName,
                                neType,
                                eventGroupName,                        -- 04: Process
                                eventName,                             -- 013: TraceDriverNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 13 }

        alarmC04014 NOTIFICATION-TYPE
        OBJECTS        {        neName,
                                neType,
                                eventGroupName,                        -- 04: Process
                                eventName,                             -- 014: LoggingDriverNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 14 }

        alarmC04015 NOTIFICATION-TYPE
        OBJECTS        {        neName,
                                neType,
                                eventGroupName,                        -- 04: Process
                                eventName,                             -- 015: LoggingProcessNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 15 }

        alarmC04016 NOTIFICATION-TYPE
        OBJECTS        {        neName,
                                neType,
                                eventGroupName,                        -- 04: Process
                                eventName,                             -- 016: PlatAlarmNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 16 }

        alarmC04017 NOTIFICATION-TYPE
        OBJECTS        {        neName,
                                neType,
                                eventGroupName,                        -- 04: Process
                                eventName,                             -- 017: PlatZooClientNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 17 }

        alarmC04018 NOTIFICATION-TYPE
        OBJECTS        {        neName,
                                neType,
                                eventGroupName,                        -- 04: Process
                                eventName,                             -- 018: PlatPsrNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 18 }

        alarmC04019 NOTIFICATION-TYPE
        OBJECTS        {        neName,
                                neType,
                                eventGroupName,                        -- 04: Process
                                eventName,                             -- 019: PlatFileExportNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 19 }

        alarmC04020 NOTIFICATION-TYPE
        OBJECTS        {        neName,
                                neType,
                                eventGroupName,                        -- 04: Process
                                eventName,                             -- 020: PlatPstackNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 20 }

        alarmC04021 NOTIFICATION-TYPE
        OBJECTS        {        neName,
                                neType,
                                eventGroupName,                        -- 04: Process
                                eventName,                             -- 021: PlatMonitorNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 21 }

        alarmC04022 NOTIFICATION-TYPE
        OBJECTS        {        neName,
                                neType,
                                eventGroupName,                        -- 04: Process
                                eventName,                             -- 022: NetReceiverNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 22 }

        alarmC04023 NOTIFICATION-TYPE
        OBJECTS        {        neName,
                                neType,
                                eventGroupName,                        -- 04: Process
                                eventName,                             -- 023: TcaNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 23 }

        alarmC04024 NOTIFICATION-TYPE
        OBJECTS        {        neName,
                                neType,
                                eventGroupName,                        -- 04: Process
                                eventName,                             -- 024: FileExportScannerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 24 }

        alarmC04025 NOTIFICATION-TYPE
        OBJECTS        {        neName,
                                neType,
                                eventGroupName,                        -- 04: Process
                                eventName,                             -- 025: PlatAuditSumNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 25 }

        alarmC04026 NOTIFICATION-TYPE
        OBJECTS        {        neName,
                                neType,
                                eventGroupName,                        -- 04: Process
                                eventName,                             -- 026: PlatLogRotateNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 26 }

        alarmC04027 NOTIFICATION-TYPE
        OBJECTS        {        neName,
                                neType,
                                eventGroupName,                        -- 04: Process
                                eventName,                             -- 027: PlatFllNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 27 }

        alarmC04028 NOTIFICATION-TYPE
        OBJECTS        {        neName,
                                neType,
                                eventGroupName,                        -- 04: Process
                                eventName,                             -- 028: PlatXtreemDirNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 28 }

        alarmC04029 NOTIFICATION-TYPE
        OBJECTS        {        neName,
                                neType,
                                eventGroupName,                        -- 04: Process
                                eventName,                             -- 029: PlatXtreemMrcNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 29 }

        alarmC04030 NOTIFICATION-TYPE
        OBJECTS        {        neName,
                                neType,
                                eventGroupName,                        -- 04: Process
                                eventName,                             -- 030: PlatXtreemOsdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 30 }

        alarmC04031 NOTIFICATION-TYPE
        OBJECTS        {        neName,
                                neType,
                                eventGroupName,                        -- 04: Process
                                eventName,                             -- 031: PlatCassandraNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 31 }

        alarmC04032 NOTIFICATION-TYPE
        OBJECTS        {        neName,
                                neType,
                                eventGroupName,                        -- 04: Process
                                eventName,                             -- 032: PlatElasticSearchNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 32 }

        alarmC04033 NOTIFICATION-TYPE
        OBJECTS        {        neName,
                                neType,
                                eventGroupName,                        -- 04: Process
                                eventName,                             -- 033: PlatClamAVNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 33 }

        alarmC04034 NOTIFICATION-TYPE
        OBJECTS        {        neName,
                                neType,
                                eventGroupName,                        -- 04: Process
                                eventName,                             -- 034: PlatStatsServerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 34 }

        alarmC04035 NOTIFICATION-TYPE
        OBJECTS        {        neName,
                                neType,
                                eventGroupName,                        -- 04: Process
                                eventName,                             -- 035: ZooKeeperServerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 35 }

        alarmC04040 NOTIFICATION-TYPE
        OBJECTS        {        neName,
                                neType,
                                eventGroupName,                        -- 04: Process
                                eventName,                             -- 040: AccessRedisNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 40 }

        alarmC04041 NOTIFICATION-TYPE
        OBJECTS        {        neName,
                                neType,
                                eventGroupName,                        -- 04: Process
                                eventName,                             -- 041: AccessRedis-clusterNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Redis-cluster configuration."
        ::= { eventGroupC04 41 }

        alarmC04042 NOTIFICATION-TYPE
        OBJECTS        {        neName,
                                neType,
                                eventGroupName,                        -- 04: Process
                                eventName,                             -- 042: AccessTurnServerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check TurnServer configuration."
        ::= { eventGroupC04 42 }

        alarmC04043 NOTIFICATION-TYPE
        OBJECTS        {        neName,
                                neType,
                                eventGroupName,                        -- 04: Process
                                eventName,                             -- 043: AccessNodeAppNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check NodeApp configuration."
        ::= { eventGroupC04 43 }

        alarmC04044 NOTIFICATION-TYPE
        OBJECTS        {        neName,
                                neType,
                                eventGroupName,                        -- 04: Process
                                eventName,                             -- 044: AccessLvsNodeNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check LvsNode configuration."
        ::= { eventGroupC04 44 }

        alarmC04045 NOTIFICATION-TYPE
        OBJECTS        {        neName,
                                neType,
                                eventGroupName,                        -- 04: Process
                                eventName,                             -- 045: AccessNginxNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Nginx configuration."
        ::= { eventGroupC04 45 }

        alarmC04046 NOTIFICATION-TYPE
        OBJECTS        {        neName,
                                neType,
                                eventGroupName,                        -- 04: Process
                                eventName,                             -- 046: AccessMetricsNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Metrics configuration."
        ::= { eventGroupC04 46 }

        alarmC04047 NOTIFICATION-TYPE
        OBJECTS        {        neName,
                                neType,
                                eventGroupName,                        -- 04: Process
                                eventName,                             -- 047: AccessAuditAppNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Audit configuration."
        ::= { eventGroupC04 47 }

        alarmC04048 NOTIFICATION-TYPE
        OBJECTS        {        neName,
                                neType,
                                eventGroupName,                        -- 04: Process
                                eventName,                             -- 048: AccessRedis-auditNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Redis configuration."
        ::= { eventGroupC04 48 }

        alarmC04060 NOTIFICATION-TYPE
        OBJECTS        {        neName,
                                neType,
                                eventGroupName,                        -- 04: Process
                                eventName,                             -- 060: LoadBalancerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Load Balancer configuration."
        ::= { eventGroupC04 60 }

        alarmC04070 NOTIFICATION-TYPE
        OBJECTS        {        neName,
                                neType,
                                eventGroupName,                        -- 04: Process
                                eventName,                             -- 070: AnsibleVirgoNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroupC04 70 }

        alarmC04071 NOTIFICATION-TYPE
        OBJECTS        {        neName,
                                neType,
                                eventGroupName,                        -- 04: Process
                                eventName,                             -- 071: HazelcastNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroupC04 71 }

        alarmC04072 NOTIFICATION-TYPE
        OBJECTS        {        neName,
                                neType,
                                eventGroupName,                        -- 04: Process
                                eventName,                             -- 072: RabbitMQNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroupC04 72 }

        alarmC04073 NOTIFICATION-TYPE
        OBJECTS        {        neName,
                                neType,
                                eventGroupName,                        -- 04: Process
                                eventName,                             -- 073: RabbitMQBootNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Process configuration at Zookeeper Nodes."
        ::= { eventGroupC04 73 }

        alarmC04075 NOTIFICATION-TYPE
        OBJECTS        {        neName,
                                neType,
                                eventGroupName,                        -- 04: Process
                                eventName,                             -- 075: MediaServerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroupC04 75 }

        alarmC04076 NOTIFICATION-TYPE
        OBJECTS        {        neName,
                                neType,
                                eventGroupName,                        -- 04: Process
                                eventName,                             -- 076: MacLvsNodeNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check LvsNode configuration on MAC node."
        ::= { eventGroupC04 76 }

        alarmC04080 NOTIFICATION-TYPE
        OBJECTS        {        neName,
                                neType,
                                eventGroupName,                        -- 04: Process
                                eventName,                             -- 080: PostgresqlNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 80 }

        alarmC04082 NOTIFICATION-TYPE
        OBJECTS        {        neName,
                                neType,
                                eventGroupName,                        -- 04: Process
                                eventName,                             -- 082: TomcatNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 82 }

        alarmC04084 NOTIFICATION-TYPE
        OBJECTS        {        neName,
                                neType,
                                eventGroupName,                        -- 04: Process
                                eventName,                             -- 084: AlarmManagerDNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 84 }

        alarmC04085 NOTIFICATION-TYPE
        OBJECTS        {        neName,
                                neType,
                                eventGroupName,                        -- 04: Process
                                eventName,                             -- 085: SolrdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 85 }

        alarmC04086 NOTIFICATION-TYPE
        OBJECTS        {        neName,
                                neType,
                                eventGroupName,                        -- 04: Process
                                eventName,                             -- 086: FilemgrdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 86 }

        alarmC04087 NOTIFICATION-TYPE
        OBJECTS        {        neName,
                                neType,
                                eventGroupName,                        -- 04: Process
                                eventName,                             -- 087: LogmgrdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 87 }

        alarmC04088 NOTIFICATION-TYPE
        OBJECTS        {        neName,
                                neType,
                                eventGroupName,                        -- 04: Process
                                eventName,                             -- 088: Apache2NotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 88 }

        alarmC04089 NOTIFICATION-TYPE
        OBJECTS        {        neName,
                                neType,
                                eventGroupName,                        -- 04: Process
                                eventName,                             -- 089: GmetadNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 89 }

        alarmC04083 NOTIFICATION-TYPE
        OBJECTS        {        neName,
                                neType,
                                eventGroupName,                        -- 04: Process
                                eventName,                             -- 083: RRDCachedNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 83 }

        alarmC04090 NOTIFICATION-TYPE
        OBJECTS        {        neName,
                                neType,
                                eventGroupName,                        -- 04: Process
                                eventName,                             -- 090: CassandraReaperNotRunning
                                correlationId,
                                severity,
                                eventTime,
                                nodes,
                                faultyObject,
                                monitoredValue,
                                thresholdValues,
                                info   }
        STATUS                current
        DESCRIPTION        "Spontaneous Alarm from the managed network element:
                            The node process manager has found that the Cassandra Reaper process/application is not running. It either could not be started during startup or it failed during normal operation. Usually the process is restarted automatically. In some cases the problem might even escalate to a full node restart.
                            Check Management configuration."
        ::= { eventGroupC04 90 }

        alarmC04095 NOTIFICATION-TYPE
        OBJECTS        {        neName,
                                neType,
                                eventGroupName,                        -- 04: Process
                                eventName,                             -- 095: ImpManagementNotRunning
                                correlationId,
                                severity,
                                eventTime,
                                nodes,
                                faultyObject,
                                monitoredValue,
                                thresholdValues,
                                info   }
        STATUS                current
        DESCRIPTION        "Spontaneous Alarm from the managed network element:
                            The node process manager has found the IMP Management application is not running. It either could not be started during startup or it failed during normal operation. Usually the process is restarted automatically. In some cases the problem might even escalate to a full node restart.
                            Check Management configuration."
        ::= { eventGroupC04 95 }

        alarmC04100 NOTIFICATION-TYPE
        OBJECTS        {        neName,
                                neType,
                                eventGroupName,                        -- 04: Process
                                eventName,                             -- 100: PlatBackupServerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 100 }

        alarmC04101 NOTIFICATION-TYPE
        OBJECTS        {        neName,
                                neType,
                                eventGroupName,                        -- 04: Process
                                eventName,                             -- 101: TikaServerNotRunning
                                correlationId,
                                severity,
                                eventTime,
                                nodes,
                                faultyObject,
                                monitoredValue,
                                thresholdValues,
                                info   }
        STATUS                current
        DESCRIPTION        "Spontaneous Alarm from the managed network element:
                            The node process manager has found the Tika Server is not running. It either could not be started during startup or it failed during normal operation. Usually the process is restarted automatically. In some cases the problem might even escalate to a full node restart.
                            Check Management configuration."
        ::= { eventGroupC04 101 }

        alarmC04120 NOTIFICATION-TYPE
        OBJECTS        {        neName,
                                neType,
                                eventGroupName,                        -- 04: Process
                                eventName,                             -- 120: XMPPRedisNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 120 }

        alarmC04121 NOTIFICATION-TYPE
        OBJECTS        {        neName,
                                neType,
                                eventGroupName,                        -- 04: Process
                                eventName,                             -- 121: XMPPNginxNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Nginx configuration."
        ::= { eventGroupC04 121 }

        alarmC04122 NOTIFICATION-TYPE
        OBJECTS        {        neName,
                                neType,
                                eventGroupName,                        -- 04: Process
                                eventName,                             -- 122: XMPPAppNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check XMPP app logs."
        ::= { eventGroupC04 122 }


        --********************************************************************
        -- Alarm Trap Definitions for alarm eventC 05: ProcessManager
        --********************************************************************

        alarmC05001 NOTIFICATION-TYPE
        OBJECTS        {        neName,
                                neType,
                                eventGroupName,                        -- 05: ProcessManager
                                eventName,                             -- 001: InvalidPlatConfiguration
                                correlationId,
                                severity,
                                eventTime,
                                nodes,
                                faultyObject,
                                monitoredValue,
                                thresholdValues,
                                info   }
        STATUS                current
        DESCRIPTION        "Spontaneous Alarm from the managed network element:
                            Platform configuration has invalid parameters:
A failure type of 1 means a missing or wrong configuration. PM can run.
2 means missing or wrong process configuration. PM can run but a process has potential problems.
3 means that the configuration file was rejected.
                            Check faulty object to know where the problem is located."
        ::= { eventGroupC05 1 }

        alarmC05002 NOTIFICATION-TYPE
        OBJECTS        {        neName,
                                neType,
                                eventGroupName,                        -- 05: ProcessManager
                                eventName,                             -- 002: InvalidServerConfiguration
                                correlationId,
                                severity,
                                eventTime,
                                nodes,
                                faultyObject,
                                monitoredValue,
                                thresholdValues,
                                info   }
        STATUS                current
        DESCRIPTION        "Spontaneous Alarm from the managed network element:
                            Server configuration has invalid parameters:
A failure type of 1 means a missing or wrong configuration. PM can run.
2 means missing or wrong process configuration. PM can run but a process has potential problems.
3 means that the configuration file was rejected.
                            Check faulty object to know where the problem is located."
        ::= { eventGroupC05 2 }

        alarmC05003 NOTIFICATION-TYPE
        OBJECTS        {        neName,
                                neType,
                                eventGroupName,                        -- 05: ProcessManager
                                eventName,                             -- 003: CanNotExecuteCommand
                                correlationId,
                                severity,
                                eventTime,
                                nodes,
                                faultyObject,
                                monitoredValue,
                                thresholdValues,
                                info   }
        STATUS                current
        DESCRIPTION        "Spontaneous Alarm from the managed network element:
                            One command could not be executed:
Command capabilities = 2 means that the command is important for PM operation and 3 means that it affects node operation.
                            Check faulty object and try to execute it by hand."
        ::= { eventGroupC05 3 }

        alarmC05004 NOTIFICATION-TYPE
        OBJECTS        {        neName,
                                neType,
                                eventGroupName,                        -- 05: ProcessManager
                                eventName,                             -- 004: UnexpectedBehaviour
                                correlationId,
                                severity,
                                eventTime,
                                nodes,
                                faultyObject,
                                monitoredValue,
                                thresholdValues,
                                info   }
        STATUS                current
        DESCRIPTION        "Spontaneous Alarm from the managed network element:
                            PM has found an unexpected behavior during its execution.
1 means that PM is still running and only a feature affected.
2 means that PM is still running, but that process control is affected.
3 means that PM will abort and restart.
                            Check faulty object for function name and line number of the problem."
        ::= { eventGroupC05 4 }

        alarmC05005 NOTIFICATION-TYPE
        OBJECTS        {        neName,
                                neType,
                                eventGroupName,                        -- 05: ProcessManager
                                eventName,                             -- 005: RecoverEscalation
                                correlationId,
                                severity,
                                eventTime,
                                nodes,
                                faultyObject,
                                monitoredValue,
                                thresholdValues,
                                info   }
        STATUS                current
        DESCRIPTION        "Spontaneous Alarm from the managed network element:
                            One or more process cannot be started.
If server Health State is 1 and the process continues to fail, all applicaton processes (Lvl 3) will be restarted.
If the HealthState is 2, the application restart did not work and all platform and all application processes (Lvl 1 and 2 will be restarted.
If the HealthState is 3, the node will be rebooted within 5 minutes.
                            Check which processe(s) are not working. Look for alarms reporting pstacks and coredumps. Collect debug files and send them to the next level of support for analysis."
        ::= { eventGroupC05 5 }

        alarmC05006 NOTIFICATION-TYPE
        OBJECTS        {        neName,
                                neType,
                                eventGroupName,                        -- 05: ProcessManager
                                eventName,                             -- 006: RebootBecauseofFailedStop
                                correlationId,
                                severity,
                                eventTime,
                                nodes,
                                faultyObject,
                                monitoredValue,
                                thresholdValues,
                                info   }
        STATUS                current
        DESCRIPTION        "Spontaneous Alarm from the managed network element:
                            The specified process/application did not react to the stop command called by the  process manager process PM. The node will be rebooted.
                            Collect debug files and escalate to next level of support for fault analysis."
        ::= { eventGroupC05 6 }

        alarmC05007 NOTIFICATION-TYPE
        OBJECTS        {        neName,
                                neType,
                                eventGroupName,                        -- 05: ProcessManager
                                eventName,                             -- 007: RebootBecauseofPMnotRunning
                                correlationId,
                                severity,
                                eventTime,
                                nodes,
                                faultyObject,
                                monitoredValue,
                                thresholdValues,
                                info   }
        STATUS                current
        DESCRIPTION        "Spontaneous Alarm from the managed network element:
                            The process manager process PM is not running. The node will be rebooted.
                            Collect debug files and escalate to next level of support for fault analysis."
        ::= { eventGroupC05 7 }

        alarmC05008 NOTIFICATION-TYPE
        OBJECTS        {        neName,
                                neType,
                                eventGroupName,                        -- 05: ProcessManager
                                eventName,                             -- 008: DroppedFromL3
                                correlationId,
                                severity,
                                eventTime,
                                nodes,
                                faultyObject,
                                monitoredValue,
                                thresholdValues,
                                info   }
        STATUS                current
        DESCRIPTION        "Spontaneous Alarm from the managed network element:
                            The process manager process PM is not running on L3. 
                            Try bringing node up to L3. If unsucessful/unsure collect debug files and escalate to the next level of support for further analysis."
        ::= { eventGroupC05 8 }


        --********************************************************************
        -- Alarm Trap Definitions for alarm eventC 06: CoreDump
        --********************************************************************

        alarmC06001 NOTIFICATION-TYPE
        OBJECTS        {        neName,
                                neType,
                                eventGroupName,                        -- 06: CoreDump
                                eventName,                             -- 001: PstackFound1
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 1 }

        alarmC06002 NOTIFICATION-TYPE
        OBJECTS        {        neName,
                                neType,
                                eventGroupName,                        -- 06: CoreDump
                                eventName,                             -- 002: PstackFound2
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 2 }

        alarmC06003 NOTIFICATION-TYPE
        OBJECTS        {        neName,
                                neType,
                                eventGroupName,                        -- 06: CoreDump
                                eventName,                             -- 003: PstackFound3
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 3 }

        alarmC06004 NOTIFICATION-TYPE
        OBJECTS        {        neName,
                                neType,
                                eventGroupName,                        -- 06: CoreDump
                                eventName,                             -- 004: PstackFound4
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 4 }

        alarmC06005 NOTIFICATION-TYPE
        OBJECTS        {        neName,
                                neType,
                                eventGroupName,                        -- 06: CoreDump
                                eventName,                             -- 005: PstackFound5
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 5 }

        alarmC06006 NOTIFICATION-TYPE
        OBJECTS        {        neName,
                                neType,
                                eventGroupName,                        -- 06: CoreDump
                                eventName,                             -- 006: CoreDumpFound1
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 6 }

        alarmC06007 NOTIFICATION-TYPE
        OBJECTS        {        neName,
                                neType,
                                eventGroupName,                        -- 06: CoreDump
                                eventName,                             -- 007: CoreDumpFound2
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 7 }

        alarmC06008 NOTIFICATION-TYPE
        OBJECTS        {        neName,
                                neType,
                                eventGroupName,                        -- 06: CoreDump
                                eventName,                             -- 008: CoreDumpFound3
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 8 }

        alarmC06009 NOTIFICATION-TYPE
        OBJECTS        {        neName,
                                neType,
                                eventGroupName,                        -- 06: CoreDump
                                eventName,                             -- 009: CoreDumpFound4
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 9 }

        alarmC06010 NOTIFICATION-TYPE
        OBJECTS        {        neName,
                                neType,
                                eventGroupName,                        -- 06: CoreDump
                                eventName,                             -- 010: CoreDumpFound5
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 10 }

        alarmC06011 NOTIFICATION-TYPE
        OBJECTS        {        neName,
                                neType,
                                eventGroupName,                        -- 06: CoreDump
                                eventName,                             -- 011: JavaDumpFound1
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 11 }

        alarmC06012 NOTIFICATION-TYPE
        OBJECTS        {        neName,
                                neType,
                                eventGroupName,                        -- 06: CoreDump
                                eventName,                             -- 012: JavaDumpFound2
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 12 }

        alarmC06013 NOTIFICATION-TYPE
        OBJECTS        {        neName,
                                neType,
                                eventGroupName,                        -- 06: CoreDump
                                eventName,                             -- 013: JavaDumpFound3
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 13 }

        alarmC06014 NOTIFICATION-TYPE
        OBJECTS        {        neName,
                                neType,
                                eventGroupName,                        -- 06: CoreDump
                                eventName,                             -- 014: JavaDumpFound4
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 14 }

        alarmC06015 NOTIFICATION-TYPE
        OBJECTS        {        neName,
                                neType,
                                eventGroupName,                        -- 06: CoreDump
                                eventName,                             -- 015: JavaDumpFound5
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 15 }


        --********************************************************************
        -- Alarm Trap Definitions for alarm eventC 08: Security
        --********************************************************************

        alarmC08001 NOTIFICATION-TYPE
        OBJECTS        {        neName,
                                neType,
                                eventGroupName,                        -- 08: Security
                                eventName,                             -- 001: PFRConfigurationFileMissing
                                correlationId,
                                severity,
                                eventTime,
                                nodes,
                                faultyObject,
                                monitoredValue,
                                thresholdValues,
                                info   }
        STATUS                current
        DESCRIPTION        "Spontaneous Alarm from the managed network element:
                            The configuration files listed under faultyObject are missing. The packet filter rules for the firewall may not be defined properly, and/or the node's security may be impacted.
                            Log in directly to the node and check the listed files. Escalate to the next level of support, if necessary to find the root cause for the missing file."
        ::= { eventGroupC08 1 }

        alarmC08002 NOTIFICATION-TYPE
        OBJECTS        {        neName,
                                neType,
                                eventGroupName,                        -- 08: Security
                                eventName,                             -- 002: PFRConfigurationDataMismatch
                                correlationId,
                                severity,
                                eventTime,
                                nodes,
                                faultyObject,
                                monitoredValue,
                                thresholdValues,
                                info   }
        STATUS                current
        DESCRIPTION        "Spontaneous Alarm from the managed network element:
                            The packet filter rules that have the names listed under faultyObject are faulty. The packet filter rules for the firewall may not be defined properly, and/or the node's security may be impacted.
                            Log in directly to the node and check the data listed in the faulty object and additional information. Escalate to the next level of support, if necessary to find the root cause for the wrong rules."
        ::= { eventGroupC08 2 }

        alarmC08003 NOTIFICATION-TYPE
        OBJECTS        {        neName,
                                neType,
                                eventGroupName,                        -- 08: Security
                                eventName,                             -- 003: OutgoingPacketDropped
                                correlationId,
                                severity,
                                eventTime,
                                nodes,
                                faultyObject,
                                monitoredValue,
                                thresholdValues,
                                info   }
        STATUS                current
        DESCRIPTION        "Spontaneous Alarm from the managed network element:
                            The node firewall has dropped outgoing IP packets and the number of dropped packets per minute has crossed a threshold. Dropping a packet may be:

(*) valid
(*) A SW error causing invalid packets to be sent
(*) A misconfigured node packet filter rule
(*) indicate a virus.
                            Use the mgmt node debug file collection function to upload debug files from the node that reported the alarm.

Analyze the dropped packets stored in the firewall log file to determine whether the IMP node sends invalid packets. If the packets are sent by valid IMP software escalate to development to either correct the packet filter rules or to modify the IMP SW not to send these packets.

If not, escalate to the next level of service to investigate whether there is a SW virus."
        ::= { eventGroupC08 3 }

        alarmC08004 NOTIFICATION-TYPE
        OBJECTS        {        neName,
                                neType,
                                eventGroupName,                        -- 08: Security
                                eventName,                             -- 004: IncomingPacketDropped
                                correlationId,
                                severity,
                                eventTime,
                                nodes,
                                faultyObject,
                                monitoredValue,
                                thresholdValues,
                                info   }
        STATUS                current
        DESCRIPTION        "Spontaneous Alarm from the managed network element:
                            The node firewall has dropped incoming IP packets and the number of dropped packets per minute has crossed a threshold. Dropping a packet may be:

(*) valid
(*) indicate a misconfiguration of the datacenter firewall
(*) A SW error in a partner IMP node causing invalid packets to be sent
(*) A misconfigured node packet filter rule
(*) indicate an attack.
                            Use the mgmt node debug file collection function to upload debug files from the node that reported the alarm.

Analyze the dropped packets stored in the firewall log file to determine whether the external firewall is mis-configured or whether IMP nodes send invalid packets. In the first case correct the external firewall and in latter case escalate to development to either correct the packet filter rules or to modify the IMP SW not to send these packets."
        ::= { eventGroupC08 4 }

        alarmC08011 NOTIFICATION-TYPE
        OBJECTS        {        neName,
                                neType,
                                eventGroupName,                        -- 08: Security
                                eventName,                             -- 011: ConfigurationFileMissing
                                correlationId,
                                severity,
                                eventTime,
                                nodes,
                                faultyObject,
                                monitoredValue,
                                thresholdValues,
                                info   }
        STATUS                current
        DESCRIPTION        "Spontaneous Alarm from the managed network element:
                            The security files listed under faultyObject are missing. The node may not start properly, not function properly, and/or its security will be impacted.
                            Log in directly to the node and check the listed files. Escalate to the next level of support, if necessary to find the root cause for the missing file."
        ::= { eventGroupC08 11 }

        alarmC08012 NOTIFICATION-TYPE
        OBJECTS        {        neName,
                                neType,
                                eventGroupName,                        -- 08: Security
                                eventName,                             -- 012: ConfigurationDataMismatch
                                correlationId,
                                severity,
                                eventTime,
                                nodes,
                                faultyObject,
                                monitoredValue,
                                thresholdValues,
                                info   }
        STATUS                current
        DESCRIPTION        "Spontaneous Alarm from the managed network element:
                            Data in the security files listed under faultyObject are wrong, missing or implausible. The node may not start properly, not function properly, and/or its security will be impacted.
                            Log in directly to the node and check the listed files. Escalate to the next level of support, if necessary to find the root cause for the wrong data."
        ::= { eventGroupC08 12 }

        alarmC08013 NOTIFICATION-TYPE
        OBJECTS        {        neName,
                                neType,
                                eventGroupName,                        -- 08: Security
                                eventName,                             -- 013: FilePermissionsError
                                correlationId,
                                severity,
                                eventTime,
                                nodes,
                                faultyObject,
                                monitoredValue,
                                thresholdValues,
                                info   }
        STATUS                current
        DESCRIPTION        "Spontaneous Alarm from the managed network element:
                            The file permission of the listed files are incorrect.
                            Log in directly to the node and change the file permissions to the proper values."
        ::= { eventGroupC08 13 }

        alarmC08014 NOTIFICATION-TYPE
        OBJECTS        {        neName,
                                neType,
                                eventGroupName,                        -- 08: Security
                                eventName,                             -- 014: IPSECDataFaulty
                                correlationId,
                                severity,
                                eventTime,
                                nodes,
                                faultyObject,
                                monitoredValue,
                                thresholdValues,
                                info   }
        STATUS                current
        DESCRIPTION        "Spontaneous Alarm from the managed network element:
                            IPSEC is not configured properly.
                            Escalate to SW development."
        ::= { eventGroupC08 14 }

        alarmC08015 NOTIFICATION-TYPE
        OBJECTS        {        neName,
                                neType,
                                eventGroupName,                        -- 08: Security
                                eventName,                             -- 015: UserKeyMismatch
                                correlationId,
                                severity,
                                eventTime,
                                nodes,
                                faultyObject,
                                monitoredValue,
                                thresholdValues,
                                info   }
        STATUS                current
        DESCRIPTION        "Spontaneous Alarm from the managed network element:
                            User keys do not match.
                            Escalate to SW development."
        ::= { eventGroupC08 15 }

        alarmC08021 NOTIFICATION-TYPE
        OBJECTS        {        neName,
                                neType,
                                eventGroupName,                        -- 08: Security
                                eventName,                             -- 021: UserAccountDisabled
                                correlationId,
                                severity,
                                eventTime,
                                nodes,
                                faultyObject,
                                monitoredValue,
                                thresholdValues,
                                info   }
        STATUS                current
        DESCRIPTION        "Spontaneous Alarm from the managed network element:
                            The specified user accounts are disabled.
                            Review the disabled accounts and either enable or delete them."
        ::= { eventGroupC08 21 }

        alarmC08022 NOTIFICATION-TYPE
        OBJECTS        {        neName,
                                neType,
                                eventGroupName,                        -- 08: Security
                                eventName,                             -- 022: SystemAccountDisabled
                                correlationId,
                                severity,
                                eventTime,
                                nodes,
                                faultyObject,
                                monitoredValue,
                                thresholdValues,
                                info   }
        STATUS                current
        DESCRIPTION        "Spontaneous Alarm from the managed network element:
                            The specified system accounts are disabled.
                            Review the disabled accounts and either enable or delete them.

If all system accounts are disabled and login to the node is not possible, use cloud/hypervisor tools to access the console and use the root account.
A last correction is to terminate the VM and re-launch it."
        ::= { eventGroupC08 22 }

        alarmC08023 NOTIFICATION-TYPE
        OBJECTS        {        neName,
                                neType,
                                eventGroupName,                        -- 08: Security
                                eventName,                             -- 023: SystemAccountNotDisabled
                                correlationId,
                                severity,
                                eventTime,
                                nodes,
                                faultyObject,
                                monitoredValue,
                                thresholdValues,
                                info   }
        STATUS                current
        DESCRIPTION        "Spontaneous Alarm from the managed network element:
                            The specified system accounts should be disabled.
                            Review these system accounts (should be either sysad or secad) and disable them after verifying that an individual system administrator or security administrator exists."
        ::= { eventGroupC08 23 }

        alarmC08024 NOTIFICATION-TYPE
        OBJECTS        {        neName,
                                neType,
                                eventGroupName,                        -- 08: Security
                                eventName,                             -- 024: PasswordExpired
                                correlationId,
                                severity,
                                eventTime,
                                nodes,
                                faultyObject,
                                monitoredValue,
                                thresholdValues,
                                info   }
        STATUS                current
        DESCRIPTION        "Spontaneous Alarm from the managed network element:
                            The password for the specified accounts has expired.
                            Delete the accounts or change the password."
        ::= { eventGroupC08 24 }

        alarmC08041 NOTIFICATION-TYPE
        OBJECTS        {        neName,
                                neType,
                                eventGroupName,                        -- 08: Security
                                eventName,                             -- 041: FailedAuthenticationAttempt
                                correlationId,
                                severity,
                                eventTime,
                                nodes,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroupC08 41 }

        alarmC08042 NOTIFICATION-TYPE
        OBJECTS        {        neName,
                                neType,
                                eventGroupName,                        -- 08: Security
                                eventName,                             -- 042: AccessDenied
                                correlationId,
                                severity,
                                eventTime,
                                nodes,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroupC08 42 }

        alarmC08051 NOTIFICATION-TYPE
        OBJECTS        {        neName,
                                neType,
                                eventGroupName,                        -- 08: Security
                                eventName,                             -- 051: FailedAuthenticationAttemptPlatf
                                correlationId,
                                severity,
                                eventTime,
                                nodes,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroupC08 51 }

        alarmC08052 NOTIFICATION-TYPE
        OBJECTS        {        neName,
                                neType,
                                eventGroupName,                        -- 08: Security
                                eventName,                             -- 052: FailedAuthenticationAttemptRoot
                                correlationId,
                                severity,
                                eventTime,
                                nodes,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroupC08 52 }

        alarmC08053 NOTIFICATION-TYPE
        OBJECTS        {        neName,
                                neType,
                                eventGroupName,                        -- 08: Security
                                eventName,                             -- 053: FailedAuthenticationAttemptSecad
                                correlationId,
                                severity,
                                eventTime,
                                nodes,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroupC08 53 }

        alarmC08054 NOTIFICATION-TYPE
        OBJECTS        {        neName,
                                neType,
                                eventGroupName,                        -- 08: Security
                                eventName,                             -- 054: FailedAuthenticationAttemptApp
                                correlationId,
                                severity,
                                eventTime,
                                nodes,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroupC08 54 }

        alarmC08055 NOTIFICATION-TYPE
        OBJECTS        {        neName,
                                neType,
                                eventGroupName,                        -- 08: Security
                                eventName,                             -- 055: FailedAuthenticationAttemptSysad
                                correlationId,
                                severity,
                                eventTime,
                                nodes,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroupC08 55 }

        alarmC08056 NOTIFICATION-TYPE
        OBJECTS        {        neName,
                                neType,
                                eventGroupName,                        -- 08: Security
                                eventName,                             -- 056: FailedAuthenticationAttemptPostgres
                                correlationId,
                                severity,
                                eventTime,
                                nodes,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroupC08 56 }

        alarmC08061 NOTIFICATION-TYPE
        OBJECTS        {        neName,
                                neType,
                                eventGroupName,                        -- 08: Security
                                eventName,                             -- 061: AccessDeniedPlatf
                                correlationId,
                                severity,
                                eventTime,
                                nodes,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroupC08 61 }

        alarmC08062 NOTIFICATION-TYPE
        OBJECTS        {        neName,
                                neType,
                                eventGroupName,                        -- 08: Security
                                eventName,                             -- 062: AccessDeniedRoot
                                correlationId,
                                severity,
                                eventTime,
                                nodes,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroupC08 62 }

        alarmC08063 NOTIFICATION-TYPE
        OBJECTS        {        neName,
                                neType,
                                eventGroupName,                        -- 08: Security
                                eventName,                             -- 063: AccessDeniedSecad
                                correlationId,
                                severity,
                                eventTime,
                                nodes,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroupC08 63 }

        alarmC08064 NOTIFICATION-TYPE
        OBJECTS        {        neName,
                                neType,
                                eventGroupName,                        -- 08: Security
                                eventName,                             -- 064: AccessDeniedApp
                                correlationId,
                                severity,
                                eventTime,
                                nodes,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroupC08 64 }

        alarmC08065 NOTIFICATION-TYPE
        OBJECTS        {        neName,
                                neType,
                                eventGroupName,                        -- 08: Security
                                eventName,                             -- 065: AccessDeniedSysad
                                correlationId,
                                severity,
                                eventTime,
                                nodes,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroupC08 65 }

        alarmC08066 NOTIFICATION-TYPE
        OBJECTS        {        neName,
                                neType,
                                eventGroupName,                        -- 08: Security
                                eventName,                             -- 066: AccessDeniedPostgres
                                correlationId,
                                severity,
                                eventTime,
                                nodes,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroupC08 66 }


        --********************************************************************
        -- Alarm Trap Definitions for alarm eventC 09: Resources
        --********************************************************************

        alarmC09001 NOTIFICATION-TYPE
        OBJECTS        {        neName,
                                neType,
                                eventGroupName,                        -- 09: Resources
                                eventName,                             -- 001: CPU
                                correlationId,
                                severity,
                                eventTime,
                                nodes,
                                faultyObject,
                                monitoredValue,
                                thresholdValues,
                                info   }
        STATUS                current
        DESCRIPTION        "Spontaneous Alarm from the managed network element:
                            CPU percentage usage in the last minute.
                            Check CPU usage with 'top'. It shows the processes that use the most CPU resource. Repair depending on the activities of the offending process(es), e.g. if they are in a loop then restart process might help."
        ::= { eventGroupC09 1 }

        alarmC09002 NOTIFICATION-TYPE
        OBJECTS        {        neName,
                                neType,
                                eventGroupName,                        -- 09: Resources
                                eventName,                             -- 002: RAM
                                correlationId,
                                severity,
                                eventTime,
                                nodes,
                                faultyObject,
                                monitoredValue,
                                thresholdValues,
                                info   }
        STATUS                current
        DESCRIPTION        "Spontaneous Alarm from the managed network element:
                            RAM percentage usage in the last minute. Used Memory is defined as:
used = total - free - buffers - cached.
                            Display processes that uses large amount of RAM with 'top' (Enter 'top' then Shift+f then n then Enter key). Processes that uses unreasonable large RAM may have a memory leak. If no process shows unreasonable larger RAM usage, additional RAM should be added to the system."
        ::= { eventGroupC09 2 }

        alarmC09003 NOTIFICATION-TYPE
        OBJECTS        {        neName,
                                neType,
                                eventGroupName,                        -- 09: Resources
                                eventName,                             -- 003: SwapFequency
                                correlationId,
                                severity,
                                eventTime,
                                nodes,
                                faultyObject,
                                monitoredValue,
                                thresholdValues,
                                info   }
        STATUS                current
        DESCRIPTION        "Spontaneous Alarm from the managed network element:
                            Total number of pages swapped in the last minute.
                            The system is low of RAM. Do not allow intensive processes running concurrently."
        ::= { eventGroupC09 3 }

        alarmC09004 NOTIFICATION-TYPE
        OBJECTS        {        neName,
                                neType,
                                eventGroupName,                        -- 09: Resources
                                eventName,                             -- 004: DiskPartitionSwap
                                correlationId,
                                severity,
                                eventTime,
                                nodes,
                                faultyObject,
                                monitoredValue,
                                thresholdValues,
                                info   }
        STATUS                current
        DESCRIPTION        "Spontaneous Alarm from the managed network element:
                            Swap partition percentage usage.
If too high the node will reboot.
                            System may be low on memory. Check whether RAM intensive processes are/were running."
        ::= { eventGroupC09 4 }

        alarmC09005 NOTIFICATION-TYPE
        OBJECTS        {        neName,
                                neType,
                                eventGroupName,                        -- 09: Resources
                                eventName,                             -- 005: DiskPartitionRoot
                                correlationId,
                                severity,
                                eventTime,
                                nodes,
                                faultyObject,
                                monitoredValue,
                                thresholdValues,
                                info   }
        STATUS                current
        DESCRIPTION        "Spontaneous Alarm from the managed network element:
                            Root (/) partition percentage usage.
If too high the node will reboot.
                            Delete unused files."
        ::= { eventGroupC09 5 }

        alarmC09006 NOTIFICATION-TYPE
        OBJECTS        {        neName,
                                neType,
                                eventGroupName,                        -- 09: Resources
                                eventName,                             -- 006: DiskPartitionVar
                                correlationId,
                                severity,
                                eventTime,
                                nodes,
                                faultyObject,
                                monitoredValue,
                                thresholdValues,
                                info   }
        STATUS                current
        DESCRIPTION        "Spontaneous Alarm from the managed network element:
                            /var partition percentage usage.
                            Delete unused files."
        ::= { eventGroupC09 6 }

        alarmC09007 NOTIFICATION-TYPE
        OBJECTS        {        neName,
                                neType,
                                eventGroupName,                        -- 09: Resources
                                eventName,                             -- 007: DiskPartitionDb
                                correlationId,
                                severity,
                                eventTime,
                                nodes,
                                faultyObject,
                                monitoredValue,
                                thresholdValues,
                                info   }
        STATUS                current
        DESCRIPTION        "Spontaneous Alarm from the managed network element:
                            /db partition percentage usage.
                            Delete unused files."
        ::= { eventGroupC09 7 }

        alarmC09008 NOTIFICATION-TYPE
        OBJECTS        {        neName,
                                neType,
                                eventGroupName,                        -- 09: Resources
                                eventName,                             -- 008: DiskPartitionTmp
                                correlationId,
                                severity,
                                eventTime,
                                nodes,
                                faultyObject,
                                monitoredValue,
                                thresholdValues,
                                info   }
        STATUS                current
        DESCRIPTION        "Spontaneous Alarm from the managed network element:
                            /tmp partition percentage usage.
If too high the node will reboot.
                            Delete unused files (check if wireshark is using up /tmp)."
        ::= { eventGroupC09 8 }

        alarmC09009 NOTIFICATION-TYPE
        OBJECTS        {        neName,
                                neType,
                                eventGroupName,                        -- 09: Resources
                                eventName,                             -- 009: DiskPartitionShared
                                correlationId,
                                severity,
                                eventTime,
                                nodes,
                                faultyObject,
                                monitoredValue,
                                thresholdValues,
                                info   }
        STATUS                current
        DESCRIPTION        "Spontaneous Alarm from the managed network element:
                            The remote shared storage of the operations node has crossed a fill level threshold. Once full log files cannot be stored anymore and analysis of instrumentation data cannot be performed anymore.
                            Check whether amount and content of stored data is justified. If yes, increase storage space. If not, delete files from storage and escalate the issue to development to check for SW errors."
        ::= { eventGroupC09 9 }

        alarmC09010 NOTIFICATION-TYPE
        OBJECTS        {        neName,
                                neType,
                                eventGroupName,                        -- 09: Resources
                                eventName,                             -- 010: DiskPartitionRemote
                                correlationId,
                                severity,
                                eventTime,
                                nodes,
                                faultyObject,
                                monitoredValue,
                                thresholdValues,
                                info   }
        STATUS                current
        DESCRIPTION        "Spontaneous Alarm from the managed network element:
                            The remote shared storage of the operations node has crossed a fill level threshold. Once full log files cannot be stored anymore and analysis of instrumentation data cannot be performed anymore.
                            Check whether amount and content of stored data is justified. If yes, increase storage space. If not, delete files from storage and escalate the issue to development to check for SW errors."
        ::= { eventGroupC09 10 }

        alarmC09011 NOTIFICATION-TYPE
        OBJECTS        {        neName,
                                neType,
                                eventGroupName,                        -- 09: Resources
                                eventName,                             -- 011: LogDirectory
                                correlationId,
                                severity,
                                eventTime,
                                nodes,
                                faultyObject,
                                monitoredValue,
                                thresholdValues,
                                info   }
        STATUS                current
        DESCRIPTION        "Spontaneous Alarm from the managed network element:
                            Total space usage (GB) of /var/log partition.
                            Delete unused files."
        ::= { eventGroupC09 11 }

        alarmC09012 NOTIFICATION-TYPE
        OBJECTS        {        neName,
                                neType,
                                eventGroupName,                        -- 09: Resources
                                eventName,                             -- 012: CoreDirectory
                                correlationId,
                                severity,
                                eventTime,
                                nodes,
                                faultyObject,
                                monitoredValue,
                                thresholdValues,
                                info   }
        STATUS                current
        DESCRIPTION        "Spontaneous Alarm from the managed network element:
                            Total space usage (GB) of /var/cores partition.
                            Delete unused files."
        ::= { eventGroupC09 12 }

        alarmC09019 NOTIFICATION-TYPE
        OBJECTS        {        neName,
                                neType,
                                eventGroupName,                        -- 09: Resources
                                eventName,                             -- 019: DiskPartitionSharedUnavailable
                                correlationId,
                                severity,
                                eventTime,
                                nodes,
                                faultyObject,
                                monitoredValue,
                                thresholdValues,
                                info   }
        STATUS                current
        DESCRIPTION        "Spontaneous Alarm from the managed network element:
                            The shared storage is not available. It contains the log file archive and analytics data. Without this storage log files may get lost and analytics data will be incomplete. Processes accessing these file may hang and restart eventually.
                            Check storage device and accessibility. Check configuration."
        ::= { eventGroupC09 19 }

        alarmC09020 NOTIFICATION-TYPE
        OBJECTS        {        neName,
                                neType,
                                eventGroupName,                        -- 09: Resources
                                eventName,                             -- 020: DiskPartitionRemoteUnavailable
                                correlationId,
                                severity,
                                eventTime,
                                nodes,
                                faultyObject,
                                monitoredValue,
                                thresholdValues,
                                info   }
        STATUS                current
        DESCRIPTION        "Spontaneous Alarm from the managed network element:
                            The remote storage is not available. It contains collected debug files, trace files and core dump files. Processes accessing these file may hang and restart eventually.
                            Check storage device and accessibility. Check configuration."
        ::= { eventGroupC09 20 }

        alarmC09031 NOTIFICATION-TYPE
        OBJECTS        {        neName,
                                neType,
                                eventGroupName,                        -- 09: Resources
                                eventName,                             -- 031: BandwidthOAMP
                                correlationId,
                                severity,
                                eventTime,
                                nodes,
                                faultyObject,
                                monitoredValue,
                                thresholdValues,
                                info   }
        STATUS                current
        DESCRIPTION        "Spontaneous Alarm from the managed network element:
                            Bandwidth OAMP Average transmitted Mbit/s of the last minute.
                            Verify if the number is justified for this interface."
        ::= { eventGroupC09 31 }

        alarmC09032 NOTIFICATION-TYPE
        OBJECTS        {        neName,
                                neType,
                                eventGroupName,                        -- 09: Resources
                                eventName,                             -- 032: BandwidthApp
                                correlationId,
                                severity,
                                eventTime,
                                nodes,
                                faultyObject,
                                monitoredValue,
                                thresholdValues,
                                info   }
        STATUS                current
        DESCRIPTION        "Spontaneous Alarm from the managed network element:
                            Bandwidth App Average transmitted Mbit/s of the last minute.
                            Verify if the number is justified for this interface."
        ::= { eventGroupC09 32 }

        alarmC09033 NOTIFICATION-TYPE
        OBJECTS        {        neName,
                                neType,
                                eventGroupName,                        -- 09: Resources
                                eventName,                             -- 033: BandwidthExt
                                correlationId,
                                severity,
                                eventTime,
                                nodes,
                                faultyObject,
                                monitoredValue,
                                thresholdValues,
                                info   }
        STATUS                current
        DESCRIPTION        "Spontaneous Alarm from the managed network element:
                            Bandwidth Ext Average transmitted Mbit/s of the last minute.
                            Verify if the number is justified for this interface."
        ::= { eventGroupC09 33 }


        --********************************************************************
        -- Alarm Trap Definitions for alarm eventC 10: Network
        --********************************************************************

        alarmC10001 NOTIFICATION-TYPE
        OBJECTS        {        neName,
                                neType,
                                eventGroupName,                        -- 10: Network
                                eventName,                             -- 001: RouterOAMP
                                correlationId,
                                severity,
                                eventTime,
                                nodes,
                                faultyObject,
                                monitoredValue,
                                thresholdValues,
                                info   }
        STATUS                current
        DESCRIPTION        "Spontaneous Alarm from the managed network element:
                            The OAMP network router is not available as it is not responding to ARP requests which it had previously.
                            Check OAMP network. Is the router available? Is the IP address correct?"
        ::= { eventGroupC10 1 }

        alarmC10002 NOTIFICATION-TYPE
        OBJECTS        {        neName,
                                neType,
                                eventGroupName,                        -- 10: Network
                                eventName,                             -- 002: RouterApp
                                correlationId,
                                severity,
                                eventTime,
                                nodes,
                                faultyObject,
                                monitoredValue,
                                thresholdValues,
                                info   }
        STATUS                current
        DESCRIPTION        "Spontaneous Alarm from the managed network element:
                            The application network router is not available as it is not responding to ARP requests which it had previously.
                            Check application network. Is the router available? Is the IP address correct?"
        ::= { eventGroupC10 2 }

        alarmC10003 NOTIFICATION-TYPE
        OBJECTS        {        neName,
                                neType,
                                eventGroupName,                        -- 10: Network
                                eventName,                             -- 003: RouterExt
                                correlationId,
                                severity,
                                eventTime,
                                nodes,
                                faultyObject,
                                monitoredValue,
                                thresholdValues,
                                info   }
        STATUS                current
        DESCRIPTION        "Spontaneous Alarm from the managed network element:
                            The external network router is not available as it is not responding to ARP requests which it had previously.
                            Check external network. Is the router available? Is the IP address correct?"
        ::= { eventGroupC10 3 }

        alarmC10004 NOTIFICATION-TYPE
        OBJECTS        {        neName,
                                neType,
                                eventGroupName,                        -- 10: Network
                                eventName,                             -- 004: DNS
                                correlationId,
                                severity,
                                eventTime,
                                nodes,
                                faultyObject,
                                monitoredValue,
                                thresholdValues,
                                info   }
        STATUS                current
        DESCRIPTION        "Spontaneous Alarm from the managed network element:
                            A DNS server is not available as it is not responding to ARP requests which it had previously.
                            Check network. Is the DNS available? Is the IP address correct? Is the DNS reachable via the OAMP network?"
        ::= { eventGroupC10 4 }

        alarmC10005 NOTIFICATION-TYPE
        OBJECTS        {        neName,
                                neType,
                                eventGroupName,                        -- 10: Network
                                eventName,                             -- 005: NTPLossOfCommunication
                                correlationId,
                                severity,
                                eventTime,
                                nodes,
                                faultyObject,
                                monitoredValue,
                                thresholdValues,
                                info   }
        STATUS                current
        DESCRIPTION        "Spontaneous Alarm from the managed network element:
                            The reporting node cannot communicate with the NTP server(s) listed in the faultyObject.
                            The command 'ntpq -pn' can be used to show the status of the NTP server. Most communication alarms will be cleared automatically when communication is restored with the partner. If the problem causing the communication failure cannot be determined and corrected, provide Ethereal/Wireshark trace files obtained from both the reporting node as well as the communication partner in order to help determine the point of failure."
        ::= { eventGroupC10 5 }

        alarmC10006 NOTIFICATION-TYPE
        OBJECTS        {        neName,
                                neType,
                                eventGroupName,                        -- 10: Network
                                eventName,                             -- 006: NTPSynchronizationFailure
                                correlationId,
                                severity,
                                eventTime,
                                nodes,
                                faultyObject,
                                monitoredValue,
                                thresholdValues,
                                info   }
        STATUS                current
        DESCRIPTION        "Spontaneous Alarm from the managed network element:
                            The reporting node cannot synchronize the system clock with any NTP server.
                             The command 'ntpq -pn' can be used to show the status of the NTP server. Verify that the list of NTP servers is correct and analyze the command output to determine why the node could not synchronize with any listed server."
        ::= { eventGroupC10 6 }

        alarmC10007 NOTIFICATION-TYPE
        OBJECTS        {        neName,
                                neType,
                                eventGroupName,                        -- 10: Network
                                eventName,                             -- 007: NTPDaemonFailure
                                correlationId,
                                severity,
                                eventTime,
                                nodes,
                                faultyObject,
                                monitoredValue,
                                thresholdValues,
                                info   }
        STATUS                current
        DESCRIPTION        "Spontaneous Alarm from the managed network element:
                            The reporting node could not execute the ntpq -pn command. This is likely because the NTP daemon is inactive.
                             Review /var/log/messages for ntp messages and determine why the daemon exited. Execute the command 'plat_pmc show .' verify that the ntp process is not blocked. If it is, execute 'plat_pmc start ntp'."
        ::= { eventGroupC10 7 }

        alarmC10008 NOTIFICATION-TYPE
        OBJECTS        {        neName,
                                neType,
                                eventGroupName,                        -- 10: Network
                                eventName,                             -- 008: eth0LinkDown
                                correlationId,
                                severity,
                                eventTime,
                                nodes,
                                faultyObject,
                                monitoredValue,
                                thresholdValues,
                                info   }
        STATUS                current
        DESCRIPTION        "Spontaneous Alarm from the managed network element:
                            The Ethernet interface eth0 is inactive.
                            On a Virtual Machine, configure the Ethernet interface to connect to a valid port/switch. On physical hardware verify physical connectivity between the specified Ethernet port and the adjacent networking device."
        ::= { eventGroupC10 8 }

        alarmC10009 NOTIFICATION-TYPE
        OBJECTS        {        neName,
                                neType,
                                eventGroupName,                        -- 10: Network
                                eventName,                             -- 009: eth1LinkDown
                                correlationId,
                                severity,
                                eventTime,
                                nodes,
                                faultyObject,
                                monitoredValue,
                                thresholdValues,
                                info   }
        STATUS                current
        DESCRIPTION        "Spontaneous Alarm from the managed network element:
                            The Ethernet interface eth1 is inactive.
                            On a Virtual Machine, configure the Ethernet interface to connect to a valid port/switch. On physical hardware verify physical connectivity between the specified Ethernet port and the adjacent networking device."
        ::= { eventGroupC10 9 }

        alarmC10010 NOTIFICATION-TYPE
        OBJECTS        {        neName,
                                neType,
                                eventGroupName,                        -- 10: Network
                                eventName,                             -- 010: eth2LinkDown
                                correlationId,
                                severity,
                                eventTime,
                                nodes,
                                faultyObject,
                                monitoredValue,
                                thresholdValues,
                                info   }
        STATUS                current
        DESCRIPTION        "Spontaneous Alarm from the managed network element:
                            The Ethernet interface eth2 is inactive.
                            On a Virtual Machine, configure the Ethernet interface to connect to a valid port/switch. On physical hardware verify physical connectivity between the specified Ethernet port and the adjacent networking device."
        ::= { eventGroupC10 10 }

        alarmC10011 NOTIFICATION-TYPE
        OBJECTS        {        neName,
                                neType,
                                eventGroupName,                        -- 10: Network
                                eventName,                             -- 011: HardwareClockOffset
                                correlationId,
                                severity,
                                eventTime,
                                nodes,
                                faultyObject,
                                monitoredValue,
                                thresholdValues,
                                info   }
        STATUS                current
        DESCRIPTION        "Spontaneous Alarm from the managed network element:
                            The system time and the time from the hardware clock are different by the specified number of seconds.
                            Follow the documented procedures for changing the time."
        ::= { eventGroupC10 11 }

        alarmC10012 NOTIFICATION-TYPE
        OBJECTS        {        neName,
                                neType,
                                eventGroupName,                        -- 10: Network
                                eventName,                             -- 012: DNS1Response
                                correlationId,
                                severity,
                                eventTime,
                                nodes,
                                faultyObject,
                                monitoredValue,
                                thresholdValues,
                                info   }
        STATUS                current
        DESCRIPTION        "Spontaneous Alarm from the managed network element:
                            Response time from DNS1 is greater than one of the alarm thresolds.
                            Check network."
        ::= { eventGroupC10 12 }

        alarmC10013 NOTIFICATION-TYPE
        OBJECTS        {        neName,
                                neType,
                                eventGroupName,                        -- 10: Network
                                eventName,                             -- 013: DNS1Resolver
                                correlationId,
                                severity,
                                eventTime,
                                nodes,
                                faultyObject,
                                monitoredValue,
                                thresholdValues,
                                info   }
        STATUS                current
        DESCRIPTION        "Spontaneous Alarm from the managed network element:
                            FQDNs could not be resolved.
                            Check FQDNs that failed to be resolved."
        ::= { eventGroupC10 13 }

        alarmC10014 NOTIFICATION-TYPE
        OBJECTS        {        neName,
                                neType,
                                eventGroupName,                        -- 10: Network
                                eventName,                             -- 014: DNS2Response
                                correlationId,
                                severity,
                                eventTime,
                                nodes,
                                faultyObject,
                                monitoredValue,
                                thresholdValues,
                                info   }
        STATUS                current
        DESCRIPTION        "Spontaneous Alarm from the managed network element:
                            Response time from DNS2 is greater than one of the alarm thresolds.
                            Check network."
        ::= { eventGroupC10 14 }

        alarmC10015 NOTIFICATION-TYPE
        OBJECTS        {        neName,
                                neType,
                                eventGroupName,                        -- 10: Network
                                eventName,                             -- 015: DNS2Resolver
                                correlationId,
                                severity,
                                eventTime,
                                nodes,
                                faultyObject,
                                monitoredValue,
                                thresholdValues,
                                info   }
        STATUS                current
        DESCRIPTION        "Spontaneous Alarm from the managed network element:
                            FQDNs could not be resolved.
                            Check FQDNs that failed to be resolved."
        ::= { eventGroupC10 15 }

        alarmC10016 NOTIFICATION-TYPE
        OBJECTS        {        neName,
                                neType,
                                eventGroupName,                        -- 10: Network
                                eventName,                             -- 016: IPSECConnection
                                correlationId,
                                severity,
                                eventTime,
                                nodes,
                                faultyObject,
                                monitoredValue,
                                thresholdValues,
                                info   }
        STATUS                current
        DESCRIPTION        "Spontaneous Alarm from the managed network element:
                            Dropped ipsec connections detected
                            Check ipsec connections on the box."
        ::= { eventGroupC10 16 }

        alarmC10017 NOTIFICATION-TYPE
        OBJECTS        {        neName,
                                neType,
                                eventGroupName,                        -- 10: Network
                                eventName,                             -- 017: TCPEstablished
                                correlationId,
                                severity,
                                eventTime,
                                nodes,
                                faultyObject,
                                monitoredValue,
                                thresholdValues,
                                info   }
        STATUS                current
        DESCRIPTION        "Spontaneous Alarm from the managed network element:
                            TCP Established exceeding accepted rate.
                            Check tcp_established in ganglia for this node."
        ::= { eventGroupC10 17 }

        alarmC10018 NOTIFICATION-TYPE
        OBJECTS        {        neName,
                                neType,
                                eventGroupName,                        -- 10: Network
                                eventName,                             -- 018: RemoteHAProxyConnection
                                correlationId,
                                severity,
                                eventTime,
                                nodes,
                                faultyObject,
                                monitoredValue,
                                thresholdValues,
                                info   }
        STATUS                current
        DESCRIPTION        "Spontaneous Alarm from the managed network element:
                            Remote HAProxy peer is down.
                            Check connectivity to remote HAProxy node."
        ::= { eventGroupC10 18 }


        --********************************************************************
        -- Alarm Trap Definitions for alarm eventC 12: RapidStat
        --********************************************************************

        alarmC12001 NOTIFICATION-TYPE
        OBJECTS        {        neName,
                                neType,
                                eventGroupName,                        -- 12: RapidStat
                                eventName,                             -- 001: HwClockNotSetToUTC
                                correlationId,
                                severity,
                                eventTime,
                                nodes,
                                faultyObject,
                                monitoredValue,
                                thresholdValues,
                                info   }
        STATUS                current
        DESCRIPTION        "Spontaneous Alarm from the managed network element:
                            HW clock is not set to UTC.
                            Verify that the non UTC setting is required. If not, set it back to UTC."
        ::= { eventGroupC12 1 }

        alarmC12002 NOTIFICATION-TYPE
        OBJECTS        {        neName,
                                neType,
                                eventGroupName,                        -- 12: RapidStat
                                eventName,                             -- 002: DNSrespTime
                                correlationId,
                                severity,
                                eventTime,
                                nodes,
                                faultyObject,
                                monitoredValue,
                                thresholdValues,
                                info   }
        STATUS                current
        DESCRIPTION        "Spontaneous Alarm from the managed network element:
                            DNS response time was longer than threshold.
                            Check network."
        ::= { eventGroupC12 2 }

        alarmC12003 NOTIFICATION-TYPE
        OBJECTS        {        neName,
                                neType,
                                eventGroupName,                        -- 12: RapidStat
                                eventName,                             -- 003: MailSize
                                correlationId,
                                severity,
                                eventTime,
                                nodes,
                                faultyObject,
                                monitoredValue,
                                thresholdValues,
                                info   }
        STATUS                current
        DESCRIPTION        "Spontaneous Alarm from the managed network element:
                            There are large files in /var/mail.
                            Delete the files."
        ::= { eventGroupC12 3 }

        alarmC12004 NOTIFICATION-TYPE
        OBJECTS        {        neName,
                                neType,
                                eventGroupName,                        -- 12: RapidStat
                                eventName,                             -- 004: etcVsNodecfg
                                correlationId,
                                severity,
                                eventTime,
                                nodes,
                                faultyObject,
                                monitoredValue,
                                thresholdValues,
                                info   }
        STATUS                current
        DESCRIPTION        "Spontaneous Alarm from the managed network element:
                            There are mismatched values between /etc/hosts and /etc/.xml files.
                            Escalate to next level of support."
        ::= { eventGroupC12 4 }

        alarmC12005 NOTIFICATION-TYPE
        OBJECTS        {        neName,
                                neType,
                                eventGroupName,                        -- 12: RapidStat
                                eventName,                             -- 005: ntpresolv
                                correlationId,
                                severity,
                                eventTime,
                                nodes,
                                faultyObject,
                                monitoredValue,
                                thresholdValues,
                                info   }
        STATUS                current
        DESCRIPTION        "Spontaneous Alarm from the managed network element:
                            System time not synchronized with any NTP server.
                            See repair text for NTP alarms."
        ::= { eventGroupC12 5 }

        alarmC12006 NOTIFICATION-TYPE
        OBJECTS        {        neName,
                                neType,
                                eventGroupName,                        -- 12: RapidStat
                                eventName,                             -- 006: ActAlrms
                                correlationId,
                                severity,
                                eventTime,
                                nodes,
                                faultyObject,
                                monitoredValue,
                                thresholdValues,
                                info   }
        STATUS                current
        DESCRIPTION        "Spontaneous Alarm from the managed network element:
                            There are active alarms on the system.
                            Correct the problems reported in the active alarms. If the alarm does not clear automatically delete it manually."
        ::= { eventGroupC12 6 }

        alarmC12007 NOTIFICATION-TYPE
        OBJECTS        {        neName,
                                neType,
                                eventGroupName,                        -- 12: RapidStat
                                eventName,                             -- 007: Num_pstacks
                                correlationId,
                                severity,
                                eventTime,
                                nodes,
                                faultyObject,
                                monitoredValue,
                                thresholdValues,
                                info   }
        STATUS                current
        DESCRIPTION        "Spontaneous Alarm from the managed network element:
                            Pstacks found.
                            See repair text of pstack alarms."
        ::= { eventGroupC12 7 }

        alarmC12008 NOTIFICATION-TYPE
        OBJECTS        {        neName,
                                neType,
                                eventGroupName,                        -- 12: RapidStat
                                eventName,                             -- 008: TracingOn
                                correlationId,
                                severity,
                                eventTime,
                                nodes,
                                faultyObject,
                                monitoredValue,
                                thresholdValues,
                                info   }
        STATUS                current
        DESCRIPTION        "Spontaneous Alarm from the managed network element:
                            Found active tracing.
                            Verify that tracing is still needed. If not stop tracing."
        ::= { eventGroupC12 8 }


        --********************************************************************
        -- Alarm Trap Definitions for alarm eventC 13: Logging
        --********************************************************************

        alarmC13001 NOTIFICATION-TYPE
        OBJECTS        {        neName,
                                neType,
                                eventGroupName,                        -- 13: Logging
                                eventName,                             -- 001: DeletedOpenFile
                                correlationId,
                                severity,
                                eventTime,
                                nodes,
                                faultyObject,
                                monitoredValue,
                                thresholdValues,
                                info   }
        STATUS                current
        DESCRIPTION        "Spontaneous Alarm from the managed network element:
                            A large deleted file has been detected that is still open. The associated process will be restarted. The faultyObject parameter shows file name and associated process.
                            If this happens often, escalate the alarm to development for analysis. The alarm is automatically removed after a couple of hours."
        ::= { eventGroupC13 1 }


        --********************************************************************
        -- Alarm Trap Definitions for alarm eventC 14: LogTCA
        --********************************************************************

        alarmC14001 NOTIFICATION-TYPE
        OBJECTS        {        neName,
                                neType,
                                eventGroupName,                        -- 14: LogTCA
                                eventName,                             -- 001: Platform
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category PLATFORM. See log file /var/log/platform/logging/LogNonIssues.log.
                            Review log file entries to determine source of problem."
        ::= { eventGroupC14 1 }

        alarmC14002 NOTIFICATION-TYPE
        OBJECTS        {        neName,
                                neType,
                                eventGroupName,                        -- 14: LogTCA
                                eventName,                             -- 002: Platform_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category PLATFORM_ERR. See log file /var/log/platform/logging/LogIssues.log.
                            Review log file entries to determine source of problem."
        ::= { eventGroupC14 2 }

        alarmC14003 NOTIFICATION-TYPE
        OBJECTS        {        neName,
                                neType,
                                eventGroupName,                        -- 14: LogTCA
                                eventName,                             -- 003: Audit
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category AUDIT. See log file /var/log/platform/logging/LogNonIssues.log.
                            Review log file entries to determine source of problem."
        ::= { eventGroupC14 3 }

        alarmC14004 NOTIFICATION-TYPE
        OBJECTS        {        neName,
                                neType,
                                eventGroupName,                        -- 14: LogTCA
                                eventName,                             -- 004: Audit_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category AUDIT_ERR. See log file /var/log/platform/logging/LogIssues.log.
                            Review log file entries to determine source of problem."
        ::= { eventGroupC14 4 }

        alarmC14005 NOTIFICATION-TYPE
        OBJECTS        {        neName,
                                neType,
                                eventGroupName,                        -- 14: LogTCA
                                eventName,                             -- 005: Com_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category COM_ERR. See log file /var/log/platform/logging/LogIssues.log.
                            Review log file entries to determine source of problem."
        ::= { eventGroupC14 5 }

        alarmC14006 NOTIFICATION-TYPE
        OBJECTS        {        neName,
                                neType,
                                eventGroupName,                        -- 14: LogTCA
                                eventName,                             -- 006: SW_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category SW_ERR. See log file /var/log/platform/logging/LogIssues.log.
                            Review log file entries to determine source of problem."
        ::= { eventGroupC14 6 }

        alarmC14007 NOTIFICATION-TYPE
        OBJECTS        {        neName,
                                neType,
                                eventGroupName,                        -- 14: LogTCA
                                eventName,                             -- 007: Data_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category DATA_ERR. See log file /var/log/platform/logging/LogIssues.log.
                            Review log file entries to determine source of problem."
        ::= { eventGroupC14 7 }

        alarmC14008 NOTIFICATION-TYPE
        OBJECTS        {        neName,
                                neType,
                                eventGroupName,                        -- 14: LogTCA
                                eventName,                             -- 008: Alarm
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category ALARM. See log file /var/log/platform/logging/LogAlarm.log.
                            Review log file entries to determine source of problem."
        ::= { eventGroupC14 8 }

        alarmC14009 NOTIFICATION-TYPE
        OBJECTS        {        neName,
                                neType,
                                eventGroupName,                        -- 14: LogTCA
                                eventName,                             -- 009: Alarm_Clear
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category ALARM_CLEAR. See log file /var/log/platform/logging/LogAlarm.log.
                            Review log file entries to determine source of problem."
        ::= { eventGroupC14 9 }

        alarmC14010 NOTIFICATION-TYPE
        OBJECTS        {        neName,
                                neType,
                                eventGroupName,                        -- 14: LogTCA
                                eventName,                             -- 010: Alarm_Mgr
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category ALARM_MGR. See log file /var/log/platform/logging/LogAlarm.log.
                            Review log file entries to determine source of problem."
        ::= { eventGroupC14 10 }

        alarmC14011 NOTIFICATION-TYPE
        OBJECTS        {        neName,
                                neType,
                                eventGroupName,                        -- 14: LogTCA
                                eventName,                             -- 011: Security
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category SECURITY. See log file /var/log/platform/logging/LogSecurity.log.
                            Review log file entries to determine source of problem."
        ::= { eventGroupC14 11 }


        --********************************************************************
        -- Alarm Trap Definitions for alarm eventC 17: SNMPTrap
        --********************************************************************

        alarmC17001 NOTIFICATION-TYPE
        OBJECTS        {        neName,
                                neType,
                                eventGroupName,                        -- 17: SNMPTrap
                                eventName,                             -- 001: SnmpOpenFailure
                                correlationId,
                                severity,
                                eventTime,
                                nodes,
                                faultyObject,
                                monitoredValue,
                                thresholdValues,
                                info   }
        STATUS                current
        DESCRIPTION        "Spontaneous Alarm from the managed network element:
                            Call to snmp_open failed.
                            Look at faulty object and correct accordingly (if possible)."
        ::= { eventGroupC17 1 }

        alarmC17002 NOTIFICATION-TYPE
        OBJECTS        {        neName,
                                neType,
                                eventGroupName,                        -- 17: SNMPTrap
                                eventName,                             -- 002: SnmpSendFailure
                                correlationId,
                                severity,
                                eventTime,
                                nodes,
                                faultyObject,
                                monitoredValue,
                                thresholdValues,
                                info   }
        STATUS                current
        DESCRIPTION        "Spontaneous Alarm from the managed network element:
                            Call to snmp_synch_response failed.
                            Look at faulty object and correct accordingly (if possible)."
        ::= { eventGroupC17 2 }


        --********************************************************************
        -- Alarm Trap Definitions for alarm eventC 20: Zoo
        --********************************************************************

        alarmC20001 NOTIFICATION-TYPE
        OBJECTS        {        neName,
                                neType,
                                eventGroupName,                        -- 20: Zoo
                                eventName,                             -- 001: ZooConnectionFailure
                                correlationId,
                                severity,
                                eventTime,
                                nodes,
                                faultyObject,
                                monitoredValue,
                                thresholdValues,
                                info   }
        STATUS                current
        DESCRIPTION        "Spontaneous Alarm from the managed network element:
                            A connection from the platform ZooKeeper Client to a ZooKeeper server could not be established. A quorum of ZooKeeper servers may not be active or may be misconfigured. The ZooKeeper client on the platform may not have a valid configuration. Network failures can also cause this alarm.
                            Ping the ZooKeeper servers from the reporting node to determine if a network problem exists. Verify that a quorum of ZooKeeper servers is active (e.g. at least two servers are active in a three-zookeeper-node ensemble). Verify that the reporting node was deployed correctly and has received the correct configuration in the 'goahead' message. If problem persists, execute 'plat_rapidstat -c' to collect data on the reporting node, all of the ZooKeeper servers."
        ::= { eventGroupC20 1 }

        alarmC20002 NOTIFICATION-TYPE
        OBJECTS        {        neName,
                                neType,
                                eventGroupName,                        -- 20: Zoo
                                eventName,                             -- 002: ZooConfigCorrupted
                                correlationId,
                                severity,
                                eventTime,
                                nodes,
                                faultyObject,
                                monitoredValue,
                                thresholdValues,
                                info   }
        STATUS                current
        DESCRIPTION        "Spontaneous Alarm from the managed network element:
                            Configuration retrieved via ZooKeeper server was corrupt and cannot be parsed.
                            The ZooKeeper znodes that are corrupt are listed with the alarm. Use the Management node application to correct the node configuration. If problem persists, execute 'plat_rapidstat -c' to collect data on the reporting node, Management node, and one of the active ZooKeeper servers."
        ::= { eventGroupC20 2 }

        alarmC20003 NOTIFICATION-TYPE
        OBJECTS        {        neName,
                                neType,
                                eventGroupName,                        -- 20: Zoo
                                eventName,                             -- 003: ZooConfigUnavailable
                                correlationId,
                                severity,
                                eventTime,
                                nodes,
                                faultyObject,
                                monitoredValue,
                                thresholdValues,
                                info   }
        STATUS                current
        DESCRIPTION        "Spontaneous Alarm from the managed network element:
                            Configuration could not be retrieved from a ZooKeeper server.
                            The ZooKeeper znodes that could not be retrieved are listed with the alarm. If data has not been populated on the ZooKeeper servers, use the Management node to configure and populate the data. If problem persists, execute 'plat_rapidstat -c' to collect data on the reporting node as well as one of the active ZooKeeper servers."
        ::= { eventGroupC20 3 }

        alarmC20004 NOTIFICATION-TYPE
        OBJECTS        {        neName,
                                neType,
                                eventGroupName,                        -- 20: Zoo
                                eventName,                             -- 004: ZookeeperResponseTime
                                correlationId,
                                severity,
                                eventTime,
                                nodes,
                                faultyObject,
                                monitoredValue,
                                thresholdValues,
                                info   }
        STATUS                current
        DESCRIPTION        "Spontaneous Alarm from the managed network element:
                            A ZooKeeper server did not respond to a request from the client within the expected response time.
                            The problem could be caused by network problems or by an overloaded ZooKeeper server. If problem persists, execute 'plat_rapidstat -c' to collection data on the reporting node and on each active ZooKeeper server node."
        ::= { eventGroupC20 4 }

        alarmC20005 NOTIFICATION-TYPE
        OBJECTS        {        neName,
                                neType,
                                eventGroupName,                        -- 20: Zoo
                                eventName,                             -- 005: WrongNodeTypeInGoAhead
                                correlationId,
                                severity,
                                eventTime,
                                nodes,
                                faultyObject,
                                monitoredValue,
                                thresholdValues,
                                info   }
        STATUS                current
        DESCRIPTION        "Spontaneous Alarm from the managed network element:
                            The node name received in the GoAhead configuration does not match the node type set by production in the file /etc/platform/type.
                            If the GoAhead was sent to this node in error, send the correct GoAhead to this node. If the node was deployed with the wrong OVF/OVA, redeploy with the correct one and re-send the GoAhead."
        ::= { eventGroupC20 5 }

        alarmC20006 NOTIFICATION-TYPE
        OBJECTS        {        neName,
                                neType,
                                eventGroupName,                        -- 20: Zoo
                                eventName,                             -- 006: ZooEnsembleFault
                                correlationId,
                                severity,
                                eventTime,
                                nodes,
                                faultyObject,
                                monitoredValue,
                                thresholdValues,
                                info   }
        STATUS                current
        DESCRIPTION        "Spontaneous Alarm from the managed network element:
                            The reporting ZooKeeper server is not currently connected to a ZooKeeper server ensemble.
                            The ZooKeeper server may not be able to communicate with some or all of the other ZooKeeper servers configured in the ensemble.  The other ZooKeeper servers in the ensemble may be down or a network problem may be blocking communication.   IPSec or packet filter rule configuration may be blocking communication with the other ZooKeeper servers.  Run plat_rapidstat and look for ZooKeeper errors or warnings.  Correct the blocking condition."
        ::= { eventGroupC20 6 }


        --********************************************************************
        -- Alarm Trap Definitions for alarm eventC 21: IDS
        --********************************************************************

        alarmC21001 NOTIFICATION-TYPE
        OBJECTS        {        neName,
                                neType,
                                eventGroupName,                        -- 21: IDS
                                eventName,                             -- 001: DoS
                                correlationId,
                                severity,
                                eventTime,
                                nodes,
                                faultyObject,
                                monitoredValue,
                                thresholdValues,
                                info   }
        STATUS                current
        DESCRIPTION        "Spontaneous Alarm from the managed network element:
                            Denial Of Service Attempt Detected.
                            None."
        ::= { eventGroupC21 1 }


        --********************************************************************
        -- Alarm Trap Definitions for alarm eventC 22: SNMP
        --********************************************************************

        alarmC22001 NOTIFICATION-TYPE
        OBJECTS        {        neName,
                                neType,
                                eventGroupName,                        -- 22: SNMP
                                eventName,                             -- 001: SnmpReconfigError
                                correlationId,
                                severity,
                                eventTime,
                                nodes,
                                faultyObject,
                                monitoredValue,
                                thresholdValues,
                                info   }
        STATUS                current
        DESCRIPTION        "Spontaneous Alarm from the managed network element:
                            SnmpV3 Users not created successfully
                            Check if all necessary credentials for SnmpV3 Users are defined in Network.xml.If not update file."
        ::= { eventGroupC22 1 }


        --********************************************************************
        -- Alarm Trap Definitions for alarm eventC 23: Syslog
        --********************************************************************

        alarmC23001 NOTIFICATION-TYPE
        OBJECTS        {        neName,
                                neType,
                                eventGroupName,                        -- 23: Syslog
                                eventName,                             -- 001: Emerg
                                correlationId,
                                severity,
                                eventTime,
                                nodes,
                                faultyObject,
                                monitoredValue,
                                thresholdValues,
                                info   }
        STATUS                current
        DESCRIPTION        "Spontaneous Alarm from the managed network element:
                            Emgergency syslog failure.
                            Look at syslog entries and correct problem."
        ::= { eventGroupC23 1 }

        alarmC23002 NOTIFICATION-TYPE
        OBJECTS        {        neName,
                                neType,
                                eventGroupName,                        -- 23: Syslog
                                eventName,                             -- 002: Alert
                                correlationId,
                                severity,
                                eventTime,
                                nodes,
                                faultyObject,
                                monitoredValue,
                                thresholdValues,
                                info   }
        STATUS                current
        DESCRIPTION        "Spontaneous Alarm from the managed network element:
                            Alert syslog failure.
                            Look at syslog entries and correct problem."
        ::= { eventGroupC23 2 }

        alarmC23003 NOTIFICATION-TYPE
        OBJECTS        {        neName,
                                neType,
                                eventGroupName,                        -- 23: Syslog
                                eventName,                             -- 003: Crit
                                correlationId,
                                severity,
                                eventTime,
                                nodes,
                                faultyObject,
                                monitoredValue,
                                thresholdValues,
                                info   }
        STATUS                current
        DESCRIPTION        "Spontaneous Alarm from the managed network element:
                            Critical syslog failure.
                            Look at syslog entries and correct problem."
        ::= { eventGroupC23 3 }

        alarmC23004 NOTIFICATION-TYPE
        OBJECTS        {        neName,
                                neType,
                                eventGroupName,                        -- 23: Syslog
                                eventName,                             -- 004: Error
                                correlationId,
                                severity,
                                eventTime,
                                nodes,
                                faultyObject,
                                monitoredValue,
                                thresholdValues,
                                info   }
        STATUS                current
        DESCRIPTION        "Spontaneous Alarm from the managed network element:
                            Error syslog failure.
                            Look at syslog entries and correct problem."
        ::= { eventGroupC23 4 }


        --********************************************************************
        -- Alarm Trap Definitions for alarm eventC 50: Connectivity
        --********************************************************************

        alarmC50001 NOTIFICATION-TYPE
        OBJECTS        {        neName,
                                neType,
                                eventGroupName,                        -- 50: Connectivity
                                eventName,                             -- 001: SmartCloudConnectionFailure
                                correlationId,
                                severity,
                                eventTime,
                                nodes,
                                faultyObject,
                                monitoredValue,
                                thresholdValues,
                                info   }
        STATUS                current
        DESCRIPTION        "Spontaneous Alarm from the managed network element:
                            Smart Cloud Connection failure.
                            Check if the Access node has internet connection and can reach the Cloud server."
        ::= { eventGroupC50 1 }

        alarmC50002 NOTIFICATION-TYPE
        OBJECTS        {        neName,
                                neType,
                                eventGroupName,                        -- 50: Connectivity
                                eventName,                             -- 002: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC50 2 }

        alarmC50003 NOTIFICATION-TYPE
        OBJECTS        {        neName,
                                neType,
                                eventGroupName,                        -- 50: Connectivity
                                eventName,                             -- 003: FileApiSocketsUsage
                                correlationId,
                                severity,
                                eventTime,
                                nodes,
                                faultyObject,
                                monitoredValue,
                                thresholdValues,
                                info   }
        STATUS                current
        DESCRIPTION        "Spontaneous Alarm from the managed network element:
                            The percentage of used concurrent sockets in fileApi between Access Server and IBM crossed the defined threshold.
                            Check if it is necessary to increase the number of concurrent sockets in fileApi."
        ::= { eventGroupC50 3 }

        alarmC50005 NOTIFICATION-TYPE
        OBJECTS        {        neName,
                                neType,
                                eventGroupName,                        -- 50: Connectivity
                                eventName,                             -- 005: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC50 5 }

        alarmC50006 NOTIFICATION-TYPE
        OBJECTS        {        neName,
                                neType,
                                eventGroupName,                        -- 50: Connectivity
                                eventName,                             -- 006: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC50 6 }

        alarmC50007 NOTIFICATION-TYPE
        OBJECTS        {        neName,
                                neType,
                                eventGroupName,                        -- 50: Connectivity
                                eventName,                             -- 007: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC50 7 }

        alarmC50011 NOTIFICATION-TYPE
        OBJECTS        {        neName,
                                neType,
                                eventGroupName,                        -- 50: Connectivity
                                eventName,                             -- 011: ConnectionsResponseTime
                                correlationId,
                                severity,
                                eventTime,
                                nodes,
                                faultyObject,
                                monitoredValue,
                                thresholdValues,
                                info   }
        STATUS                current
        DESCRIPTION        "Spontaneous Alarm from the managed network element:
                            Smart Cloud Connection response time too high.
                            Check whether the high response time is justified. If not check the network and processed traffic. Are additional nodes needed? Is Smart Cloud overloaded?"
        ::= { eventGroupC50 11 }

        alarmC50015 NOTIFICATION-TYPE
        OBJECTS        {        neName,
                                neType,
                                eventGroupName,                        -- 50: Connectivity
                                eventName,                             -- 015: ConnectionsActivityServiceFailure
                                correlationId,
                                severity,
                                eventTime,
                                nodes,
                                faultyObject,
                                monitoredValue,
                                thresholdValues,
                                info   }
        STATUS                current
        DESCRIPTION        "Spontaneous Alarm from the managed network element:
                            Connectivity could not be established with the IBM Connections Activity Service.
                            Check if the node has internet connection and can reach the Cloud server."
        ::= { eventGroupC50 15 }

        alarmC50016 NOTIFICATION-TYPE
        OBJECTS        {        neName,
                                neType,
                                eventGroupName,                        -- 50: Connectivity
                                eventName,                             -- 016: ConnectionsFileServiceFailure
                                correlationId,
                                severity,
                                eventTime,
                                nodes,
                                faultyObject,
                                monitoredValue,
                                thresholdValues,
                                info   }
        STATUS                current
        DESCRIPTION        "Spontaneous Alarm from the managed network element:
                            Connectivity could not be established with the IBM Connections File Service.
                            Check if the node has internet connection and can reach the Cloud server."
        ::= { eventGroupC50 16 }

        alarmC50017 NOTIFICATION-TYPE
        OBJECTS        {        neName,
                                neType,
                                eventGroupName,                        -- 50: Connectivity
                                eventName,                             -- 017: ConnectionsBSSServiceFailure
                                correlationId,
                                severity,
                                eventTime,
                                nodes,
                                faultyObject,
                                monitoredValue,
                                thresholdValues,
                                info   }
        STATUS                current
        DESCRIPTION        "Spontaneous Alarm from the managed network element:
                            Connectivity could not be established with the IBM Connections BSS Service.
                            Check if the node has internet connection and can reach the Cloud server."
        ::= { eventGroupC50 17 }

        alarmC50018 NOTIFICATION-TYPE
        OBJECTS        {        neName,
                                neType,
                                eventGroupName,                        -- 50: Connectivity
                                eventName,                             -- 018: ConnectionsSearchServiceFailure
                                correlationId,
                                severity,
                                eventTime,
                                nodes,
                                faultyObject,
                                monitoredValue,
                                thresholdValues,
                                info   }
        STATUS                current
        DESCRIPTION        "Spontaneous Alarm from the managed network element:
                            Connectivity could not be established with the IBM Connections Search Service.
                            Check if the node has internet connection and can reach the Cloud server."
        ::= { eventGroupC50 18 }

        alarmC50021 NOTIFICATION-TYPE
        OBJECTS        {        neName,
                                neType,
                                eventGroupName,                        -- 50: Connectivity
                                eventName,                             -- 021: LossOfComSMTP
                                correlationId,
                                severity,
                                eventTime,
                                nodes,
                                faultyObject,
                                monitoredValue,
                                thresholdValues,
                                info   }
        STATUS                current
        DESCRIPTION        "Spontaneous Alarm from the managed network element:
                            The IMP application node has lost connectivity with the SMTP server identified in the faultyObject parameter.
                            Check the network (router, firewall, LAN). Check whether the SMTP server is out of service."
        ::= { eventGroupC50 21 }

        alarmC50022 NOTIFICATION-TYPE
        OBJECTS        {        neName,
                                neType,
                                eventGroupName,                        -- 50: Connectivity
                                eventName,                             -- 022: LossOfComActex
                                correlationId,
                                severity,
                                eventTime,
                                nodes,
                                faultyObject,
                                monitoredValue,
                                thresholdValues,
                                info   }
        STATUS                current
        DESCRIPTION        "Spontaneous Alarm from the managed network element:
                            The IMP application node has lost connectivity with the Actex server identified in the faultyObject parameter.
                            Check the network (router, firewall, LAN). Check whether the Actex server is out of service."
        ::= { eventGroupC50 22 }

        alarmC50051 NOTIFICATION-TYPE
        OBJECTS        {        neName,
                                neType,
                                eventGroupName,                        -- 50: Connectivity
                                eventName,                             -- 051: LossOfComApp
                                correlationId,
                                severity,
                                eventTime,
                                nodes,
                                faultyObject,
                                monitoredValue,
                                thresholdValues,
                                info   }
        STATUS                current
        DESCRIPTION        "Spontaneous Alarm from the managed network element:
                            Access server lost communication with Application node.
                            The Application node maybe down, check the network setup. Also check the node configuration files and logs."
        ::= { eventGroupC50 51 }

        alarmC50052 NOTIFICATION-TYPE
        OBJECTS        {        neName,
                                neType,
                                eventGroupName,                        -- 50: Connectivity
                                eventName,                             -- 052: LossOfComSto
                                correlationId,
                                severity,
                                eventTime,
                                nodes,
                                faultyObject,
                                monitoredValue,
                                thresholdValues,
                                info   }
        STATUS                current
        DESCRIPTION        "Spontaneous Alarm from the managed network element:
                            Access server lost communication with Storage node.
                            The Storage node maybe down, check the network setup. Also check the node configuration files and logs."
        ::= { eventGroupC50 52 }

        alarmC50061 NOTIFICATION-TYPE
        OBJECTS        {        neName,
                                neType,
                                eventGroupName,                        -- 50: Connectivity
                                eventName,                             -- 061: LossOfComAccClient
                                correlationId,
                                severity,
                                eventTime,
                                nodes,
                                faultyObject,
                                monitoredValue,
                                thresholdValues,
                                info   }
        STATUS                current
        DESCRIPTION        "Spontaneous Alarm from the managed network element:
                            Access server lost communication with Access Client node.
                            Check that all nodes of the solution are active."
        ::= { eventGroupC50 61 }

        alarmC50062 NOTIFICATION-TYPE
        OBJECTS        {        neName,
                                neType,
                                eventGroupName,                        -- 50: Connectivity
                                eventName,                             -- 062: LossOfComAccServer
                                correlationId,
                                severity,
                                eventTime,
                                nodes,
                                faultyObject,
                                monitoredValue,
                                thresholdValues,
                                info   }
        STATUS                current
        DESCRIPTION        "Spontaneous Alarm from the managed network element:
                            Access server lost communication with Access Server node.
                            Check that all nodes of the solution are active."
        ::= { eventGroupC50 62 }

        alarmC50071 NOTIFICATION-TYPE
        OBJECTS        {        neName,
                                neType,
                                eventGroupName,                        -- 50: Connectivity
                                eventName,                             -- 071: LossOfComAcc
                                correlationId,
                                severity,
                                eventTime,
                                nodes,
                                faultyObject,
                                monitoredValue,
                                thresholdValues,
                                info   }
        STATUS                current
        DESCRIPTION        "Spontaneous Alarm from the managed network element:
                            Server lost communication with Access node.
                            The Access node maybe down, check the network setup. Also check the node configuration files and logs."
        ::= { eventGroupC50 71 }

        alarmC50072 NOTIFICATION-TYPE
        OBJECTS        {        neName,
                                neType,
                                eventGroupName,                        -- 50: Connectivity
                                eventName,                             -- 072: LossOfComHazelcast
                                correlationId,
                                severity,
                                eventTime,
                                nodes,
                                faultyObject,
                                monitoredValue,
                                thresholdValues,
                                info   }
        STATUS                current
        DESCRIPTION        "Spontaneous Alarm from the managed network element:
                            The IMP application node has lost connectivity with the Hazelcast service.
                            Check the status of the Hazelcast service."
        ::= { eventGroupC50 72 }

        alarmC50073 NOTIFICATION-TYPE
        OBJECTS        {        neName,
                                neType,
                                eventGroupName,                        -- 50: Connectivity
                                eventName,                             -- 073: LossOfComKMS
                                correlationId,
                                severity,
                                eventTime,
                                nodes,
                                faultyObject,
                                monitoredValue,
                                thresholdValues,
                                info   }
        STATUS                current
        DESCRIPTION        "Spontaneous Alarm from the managed network element:
                            The IMP application node has lost connectivity with one of the Key Management servers.
                            Review log file entries to determine source of problem"
        ::= { eventGroupC50 73 }


        --********************************************************************
        -- Alarm Trap Definitions for alarm eventC 53: Turn
        --********************************************************************

        alarmC53001 NOTIFICATION-TYPE
        OBJECTS        {        neName,
                                neType,
                                eventGroupName,                        -- 53: Turn
                                eventName,                             -- 001: LackOfUDPPorts
                                correlationId,
                                severity,
                                eventTime,
                                nodes,
                                faultyObject,
                                monitoredValue,
                                thresholdValues,
                                info   }
        STATUS                current
        DESCRIPTION        "Spontaneous Alarm from the managed network element:
                            Turn has used more UDP ports than one of the configured thresholds.
                            Escalate to next level of support to analyze the traffic."
        ::= { eventGroupC53 1 }


        --********************************************************************
        -- Alarm Trap Definitions for alarm eventC 54: LB
        --********************************************************************

        alarmC54001 NOTIFICATION-TYPE
        OBJECTS        {        neName,
                                neType,
                                eventGroupName,                        -- 54: LB
                                eventName,                             -- 001: LossOfRedundancy
                                correlationId,
                                severity,
                                eventTime,
                                nodes,
                                faultyObject,
                                monitoredValue,
                                thresholdValues,
                                info   }
        STATUS                current
        DESCRIPTION        "Spontaneous Alarm from the managed network element:
                            LB node lost its partner and now runs as master without backup.
                            Repair the LB partner node."
        ::= { eventGroupC54 1 }

        alarmC54002 NOTIFICATION-TYPE
        OBJECTS        {        neName,
                                neType,
                                eventGroupName,                        -- 54: LB
                                eventName,                             -- 002: FaultyConfiguration
                                correlationId,
                                severity,
                                eventTime,
                                nodes,
                                faultyObject,
                                monitoredValue,
                                thresholdValues,
                                info   }
        STATUS                current
        DESCRIPTION        "Spontaneous Alarm from the managed network element:
                            LB configuration file is faulty. LB functionality is restricted.
                            Review log file entries to determine source of problem."
        ::= { eventGroupC54 2 }


        --********************************************************************
        -- Alarm Trap Definitions for alarm eventC 56: MediaServer
        --********************************************************************

        alarmC56001 NOTIFICATION-TYPE
        OBJECTS        {        neName,
                                neType,
                                eventGroupName,                        -- 56: MediaServer
                                eventName,                             -- 001: SIPTrunkMissing
                                correlationId,
                                severity,
                                eventTime,
                                nodes,
                                faultyObject,
                                monitoredValue,
                                thresholdValues,
                                info   }
        STATUS                current
        DESCRIPTION        "Spontaneous Alarm from the managed network element:
                            Wrong SIP trunk configuration.
                            Escalate to next level of support."
        ::= { eventGroupC56 1 }

        alarmC56002 NOTIFICATION-TYPE
        OBJECTS        {        neName,
                                neType,
                                eventGroupName,                        -- 56: MediaServer
                                eventName,                             -- 002: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 2 }

        alarmC56003 NOTIFICATION-TYPE
        OBJECTS        {        neName,
                                neType,
                                eventGroupName,                        -- 56: MediaServer
                                eventName,                             -- 003: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 3 }

        alarmC56004 NOTIFICATION-TYPE
        OBJECTS        {        neName,
                                neType,
                                eventGroupName,                        -- 56: MediaServer
                                eventName,                             -- 004: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 4 }

        alarmC56005 NOTIFICATION-TYPE
        OBJECTS        {        neName,
                                neType,
                                eventGroupName,                        -- 56: MediaServer
                                eventName,                             -- 005: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 5 }

        alarmC56010 NOTIFICATION-TYPE
        OBJECTS        {        neName,
                                neType,
                                eventGroupName,                        -- 56: MediaServer
                                eventName,                             -- 010: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 10 }

        alarmC56011 NOTIFICATION-TYPE
        OBJECTS        {        neName,
                                neType,
                                eventGroupName,                        -- 56: MediaServer
                                eventName,                             -- 011: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 11 }

        alarmC56020 NOTIFICATION-TYPE
        OBJECTS        {        neName,
                                neType,
                                eventGroupName,                        -- 56: MediaServer
                                eventName,                             -- 020: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 20 }

        alarmC56021 NOTIFICATION-TYPE
        OBJECTS        {        neName,
                                neType,
                                eventGroupName,                        -- 56: MediaServer
                                eventName,                             -- 021: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 21 }

        alarmC56030 NOTIFICATION-TYPE
        OBJECTS        {        neName,
                                neType,
                                eventGroupName,                        -- 56: MediaServer
                                eventName,                             -- 030: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 30 }

        alarmC56031 NOTIFICATION-TYPE
        OBJECTS        {        neName,
                                neType,
                                eventGroupName,                        -- 56: MediaServer
                                eventName,                             -- 031: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 31 }

        alarmC56033 NOTIFICATION-TYPE
        OBJECTS        {        neName,
                                neType,
                                eventGroupName,                        -- 56: MediaServer
                                eventName,                             -- 033: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 33 }

        alarmC56040 NOTIFICATION-TYPE
        OBJECTS        {        neName,
                                neType,
                                eventGroupName,                        -- 56: MediaServer
                                eventName,                             -- 040: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 40 }

        alarmC56041 NOTIFICATION-TYPE
        OBJECTS        {        neName,
                                neType,
                                eventGroupName,                        -- 56: MediaServer
                                eventName,                             -- 041: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 41 }

        alarmC56042 NOTIFICATION-TYPE
        OBJECTS        {        neName,
                                neType,
                                eventGroupName,                        -- 56: MediaServer
                                eventName,                             -- 042: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 42 }

        alarmC56050 NOTIFICATION-TYPE
        OBJECTS        {        neName,
                                neType,
                                eventGroupName,                        -- 56: MediaServer
                                eventName,                             -- 050: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 50 }

        alarmC56100 NOTIFICATION-TYPE
        OBJECTS        {        neName,
                                neType,
                                eventGroupName,                        -- 56: MediaServer
                                eventName,                             -- 100: SipStackStartupProblem
                                correlationId,
                                severity,
                                eventTime,
                                nodes,
                                faultyObject,
                                monitoredValue,
                                thresholdValues,
                                info   }
        STATUS                current
        DESCRIPTION        "Spontaneous Alarm from the managed network element:
                            SIP stack startup problem
SIP Connectivity Provider,Failed to create a sip stack instance.
                            Please check the log for further information."
        ::= { eventGroupC56 100 }

        alarmC56101 NOTIFICATION-TYPE
        OBJECTS        {        neName,
                                neType,
                                eventGroupName,                        -- 56: MediaServer
                                eventName,                             -- 101: SipStackStartupProblemListening
                                correlationId,
                                severity,
                                eventTime,
                                nodes,
                                faultyObject,
                                monitoredValue,
                                thresholdValues,
                                info   }
        STATUS                current
        DESCRIPTION        "Spontaneous Alarm from the managed network element:
                            Startup problem with a SIP stack listening point

Failed to create a listening point. Maybe address or port is in use.
                            Please check listeningPoint settings in the management UI or in the sip-connectivity.xml file."
        ::= { eventGroupC56 101 }

        alarmC56102 NOTIFICATION-TYPE
        OBJECTS        {        neName,
                                neType,
                                eventGroupName,                        -- 56: MediaServer
                                eventName,                             -- 102: SipStackStartupProblemInternal
                                correlationId,
                                severity,
                                eventTime,
                                nodes,
                                faultyObject,
                                monitoredValue,
                                thresholdValues,
                                info   }
        STATUS                current
        DESCRIPTION        "Spontaneous Alarm from the managed network element:
                            Startup problem due to internal SIP stack error

Failed to create sip provider instance.
                            Please check the log for further information."
        ::= { eventGroupC56 102 }

        alarmC56103 NOTIFICATION-TYPE
        OBJECTS        {        neName,
                                neType,
                                eventGroupName,                        -- 56: MediaServer
                                eventName,                             -- 103: SipStackStartupProblemInternal2
                                correlationId,
                                severity,
                                eventTime,
                                nodes,
                                faultyObject,
                                monitoredValue,
                                thresholdValues,
                                info   }
        STATUS                current
        DESCRIPTION        "Spontaneous Alarm from the managed network element:
                            Startup problem due to internal SIP stack error

Failed to register SipManager as a SIP listener.
                            Please check the log for further information."
        ::= { eventGroupC56 103 }

        alarmC56104 NOTIFICATION-TYPE
        OBJECTS        {        neName,
                                neType,
                                eventGroupName,                        -- 56: MediaServer
                                eventName,                             -- 104: SipStackShutdownProblem
                                correlationId,
                                severity,
                                eventTime,
                                nodes,
                                faultyObject,
                                monitoredValue,
                                thresholdValues,
                                info   }
        STATUS                current
        DESCRIPTION        "Spontaneous Alarm from the managed network element:
                            SIP stack shutdown problem

Failed to delete a SipProvider instance from sip stack.
                            Please check the log for further information."
        ::= { eventGroupC56 104 }

        alarmC56105 NOTIFICATION-TYPE
        OBJECTS        {        neName,
                                neType,
                                eventGroupName,                        -- 56: MediaServer
                                eventName,                             -- 105: SipStackShutdownProblem2
                                correlationId,
                                severity,
                                eventTime,
                                nodes,
                                faultyObject,
                                monitoredValue,
                                thresholdValues,
                                info   }
        STATUS                current
        DESCRIPTION        "Spontaneous Alarm from the managed network element:
                            SIP stack shutdown problem

Failed to delete a listening point from sip stack.
                            Please check the log for further information."
        ::= { eventGroupC56 105 }

        alarmC56106 NOTIFICATION-TYPE
        OBJECTS        {        neName,
                                neType,
                                eventGroupName,                        -- 56: MediaServer
                                eventName,                             -- 106: SipProviderConfMissing
                                correlationId,
                                severity,
                                eventTime,
                                nodes,
                                faultyObject,
                                monitoredValue,
                                thresholdValues,
                                info   }
        STATUS                current
        DESCRIPTION        "Spontaneous Alarm from the managed network element:
                            SIP provider startup failed: configuration is missing

Failed to start SIP provider due to missing configuration.
                            Please check the log for further information."
        ::= { eventGroupC56 106 }

        alarmC56107 NOTIFICATION-TYPE
        OBJECTS        {        neName,
                                neType,
                                eventGroupName,                        -- 56: MediaServer
                                eventName,                             -- 107: SipProviderSdpParserMissing
                                correlationId,
                                severity,
                                eventTime,
                                nodes,
                                faultyObject,
                                monitoredValue,
                                thresholdValues,
                                info   }
        STATUS                current
        DESCRIPTION        "Spontaneous Alarm from the managed network element:
                            SIP provider startup failed: SDP parser missing

Failed to start SIP provider due to missing SDP parser component.
                            Please check the log for further information."
        ::= { eventGroupC56 107 }

        alarmC56108 NOTIFICATION-TYPE
        OBJECTS        {        neName,
                                neType,
                                eventGroupName,                        -- 56: MediaServer
                                eventName,                             -- 108: SipProviderAddrTransCompMissing
                                correlationId,
                                severity,
                                eventTime,
                                nodes,
                                faultyObject,
                                monitoredValue,
                                thresholdValues,
                                info   }
        STATUS                current
        DESCRIPTION        "Spontaneous Alarm from the managed network element:
                            SIP provider startup failed: Address Translation component missing.

Failed to start SIP provider due to missing Address Translation component.
                            Please check the log for further information."
        ::= { eventGroupC56 108 }

        alarmC56109 NOTIFICATION-TYPE
        OBJECTS        {        neName,
                                neType,
                                eventGroupName,                        -- 56: MediaServer
                                eventName,                             -- 109: SipProviderLocationDBCompMissing
                                correlationId,
                                severity,
                                eventTime,
                                nodes,
                                faultyObject,
                                monitoredValue,
                                thresholdValues,
                                info   }
        STATUS                current
        DESCRIPTION        "Spontaneous Alarm from the managed network element:
                            SIP provider startup failed: Location Database component missing

Failed to start SIP provider due to missing Location Database component.
                            Please check the log for further information."
        ::= { eventGroupC56 109 }

        alarmC56110 NOTIFICATION-TYPE
        OBJECTS        {        neName,
                                neType,
                                eventGroupName,                        -- 56: MediaServer
                                eventName,                             -- 110: SipProviderStartFailure
                                correlationId,
                                severity,
                                eventTime,
                                nodes,
                                faultyObject,
                                monitoredValue,
                                thresholdValues,
                                info   }
        STATUS                current
        DESCRIPTION        "Spontaneous Alarm from the managed network element:
                            Failed to start sip provider

Internal SIP manager startup problem.
                            Please check the log for further information."
        ::= { eventGroupC56 110 }

        alarmC56200 NOTIFICATION-TYPE
        OBJECTS        {        neName,
                                neType,
                                eventGroupName,                        -- 56: MediaServer
                                eventName,                             -- 200: MFWProviderMissing
                                correlationId,
                                severity,
                                eventTime,
                                nodes,
                                faultyObject,
                                monitoredValue,
                                thresholdValues,
                                info   }
        STATUS                current
        DESCRIPTION        "Spontaneous Alarm from the managed network element:
                            Missing MFW provider

Could not get MediaFramework (MFW) provider from Application Host. Processing of streaming data will not work.
                            Check log-output for more details."
        ::= { eventGroupC56 200 }

        alarmC56202 NOTIFICATION-TYPE
        OBJECTS        {        neName,
                                neType,
                                eventGroupName,                        -- 56: MediaServer
                                eventName,                             -- 202: MPSMediaProcessingProviderInitFailure
                                correlationId,
                                severity,
                                eventTime,
                                nodes,
                                faultyObject,
                                monitoredValue,
                                thresholdValues,
                                info   }
        STATUS                current
        DESCRIPTION        "Spontaneous Alarm from the managed network element:
                            Failed to initialize MPS Media Processing Provider

Failed to initialize the Media Processing (MPS) Provider. Processing of streaming data will not work.
                            Check log-output for more details."
        ::= { eventGroupC56 202 }

        alarmC56203 NOTIFICATION-TYPE
        OBJECTS        {        neName,
                                neType,
                                eventGroupName,                        -- 56: MediaServer
                                eventName,                             -- 203: NoMoreAvailableRTPChannel
                                correlationId,
                                severity,
                                eventTime,
                                nodes,
                                faultyObject,
                                monitoredValue,
                                thresholdValues,
                                info   }
        STATUS                current
        DESCRIPTION        "Spontaneous Alarm from the managed network element:
                            No more RTP channel available

Failed to allocate a RTP channel resource to handle call.
                            Please check the ResourceManagement configuration for this application."
        ::= { eventGroupC56 203 }

        alarmC56204 NOTIFICATION-TYPE
        OBJECTS        {        neName,
                                neType,
                                eventGroupName,                        -- 56: MediaServer
                                eventName,                             -- 204: NoMorAvailableTTSLicens
                                correlationId,
                                severity,
                                eventTime,
                                nodes,
                                faultyObject,
                                monitoredValue,
                                thresholdValues,
                                info   }
        STATUS                current
        DESCRIPTION        "Spontaneous Alarm from the managed network element:
                            No (more) TTS license available

Failed to allocate Text-To-Speech port license.
                            Please make sure that there are enough licenses installed and that the 'licensing service' is running."
        ::= { eventGroupC56 204 }

        alarmC56205 NOTIFICATION-TYPE
        OBJECTS        {        neName,
                                neType,
                                eventGroupName,                        -- 56: MediaServer
                                eventName,                             -- 205: NoMoreAvailableASRLicense
                                correlationId,
                                severity,
                                eventTime,
                                nodes,
                                faultyObject,
                                monitoredValue,
                                thresholdValues,
                                info   }
        STATUS                current
        DESCRIPTION        "Spontaneous Alarm from the managed network element:
                            No (more) ASR license available

Failed to allocate Speech-Recognition port license.
                            Please make sure that there are enough licenses installed and that the 'licensing service' is running."
        ::= { eventGroupC56 205 }

        alarmC56210 NOTIFICATION-TYPE
        OBJECTS        {        neName,
                                neType,
                                eventGroupName,                        -- 56: MediaServer
                                eventName,                             -- 210: NoDiscSpaceLeft
                                correlationId,
                                severity,
                                eventTime,
                                nodes,
                                faultyObject,
                                monitoredValue,
                                thresholdValues,
                                info   }
        STATUS                current
        DESCRIPTION        "Spontaneous Alarm from the managed network element:
                            No disc space left

Unable to write further samples for recording, since there is no more disc space available.
                            Run debug file collection and escalate to next level of support."
        ::= { eventGroupC56 210 }

        alarmC56211 NOTIFICATION-TYPE
        OBJECTS        {        neName,
                                neType,
                                eventGroupName,                        -- 56: MediaServer
                                eventName,                             -- 211: NoAvaiableResource
                                correlationId,
                                severity,
                                eventTime,
                                nodes,
                                faultyObject,
                                monitoredValue,
                                thresholdValues,
                                info   }
        STATUS                current
        DESCRIPTION        "Spontaneous Alarm from the managed network element:
                            Resource no longer available

Failed to write samples for recording, because the file path is not available or the file not writeable.
                            Run debug file collection and escalate to next level of support."
        ::= { eventGroupC56 211 }

        alarmC56300 NOTIFICATION-TYPE
        OBJECTS        {        neName,
                                neType,
                                eventGroupName,                        -- 56: MediaServer
                                eventName,                             -- 300: MediaGatewayProviderInitFailure
                                correlationId,
                                severity,
                                eventTime,
                                nodes,
                                faultyObject,
                                monitoredValue,
                                thresholdValues,
                                info   }
        STATUS                current
        DESCRIPTION        "Spontaneous Alarm from the managed network element:
                            Failed to initialize Media Gateway Provider

An error occurred while starting Media Gateway Provider.
                            Please verify Media Gateway Configuration and assure that the PromptDB provider is running."
        ::= { eventGroupC56 300 }

        alarmC56301 NOTIFICATION-TYPE
        OBJECTS        {        neName,
                                neType,
                                eventGroupName,                        -- 56: MediaServer
                                eventName,                             -- 301: ConfChangesActivationFailure
                                correlationId,
                                severity,
                                eventTime,
                                nodes,
                                faultyObject,
                                monitoredValue,
                                thresholdValues,
                                info   }
        STATUS                current
        DESCRIPTION        "Spontaneous Alarm from the managed network element:
                            Failed to activate configuration changes

An error occurred while activating configuration changes.
                            Please fix Media Gateway Configuration and restart provider."
        ::= { eventGroupC56 301 }

        alarmC56302 NOTIFICATION-TYPE
        OBJECTS        {        neName,
                                neType,
                                eventGroupName,                        -- 56: MediaServer
                                eventName,                             -- 302: MediaGatewayDeactivationFailure
                                correlationId,
                                severity,
                                eventTime,
                                nodes,
                                faultyObject,
                                monitoredValue,
                                thresholdValues,
                                info   }
        STATUS                current
        DESCRIPTION        "Spontaneous Alarm from the managed network element:
                            Failed to deactivate Media Gateway Provider

An unexpected error occurred while stopping Media Gateway Provider.
                            Run debug file collection and escalate to next level of support."
        ::= { eventGroupC56 302 }

        alarmC56303 NOTIFICATION-TYPE
        OBJECTS        {        neName,
                                neType,
                                eventGroupName,                        -- 56: MediaServer
                                eventName,                             -- 303: MediaGatewayActivationFailure
                                correlationId,
                                severity,
                                eventTime,
                                nodes,
                                faultyObject,
                                monitoredValue,
                                thresholdValues,
                                info   }
        STATUS                current
        DESCRIPTION        "Spontaneous Alarm from the managed network element:
                            Failed to activate media gateways

No listening point is defined in Media Gateway configuration.
                            Please add at least one listening point."
        ::= { eventGroupC56 303 }

        alarmC56304 NOTIFICATION-TYPE
        OBJECTS        {        neName,
                                neType,
                                eventGroupName,                        -- 56: MediaServer
                                eventName,                             -- 304: ConnectionCreationFailure
                                correlationId,
                                severity,
                                eventTime,
                                nodes,
                                faultyObject,
                                monitoredValue,
                                thresholdValues,
                                info   }
        STATUS                current
        DESCRIPTION        "Spontaneous Alarm from the managed network element:
                            Failed to create connection

Ignoring create connection command, since no incoming connection listener is registered.
                            Please assure that the terminal binder is running."
        ::= { eventGroupC56 304 }

        alarmC56310 NOTIFICATION-TYPE
        OBJECTS        {        neName,
                                neType,
                                eventGroupName,                        -- 56: MediaServer
                                eventName,                             -- 310: ConnectionCreationFailure2
                                correlationId,
                                severity,
                                eventTime,
                                nodes,
                                faultyObject,
                                monitoredValue,
                                thresholdValues,
                                info   }
        STATUS                current
        DESCRIPTION        "Spontaneous Alarm from the managed network element:
                            Failed to create connection

A new connection can not be created due to a non-recoverable problem.
                            Please check the log-output to get more detailed informations (logger: com.cycos.media)."
        ::= { eventGroupC56 310 }

        alarmC56311 NOTIFICATION-TYPE
        OBJECTS        {        neName,
                                neType,
                                eventGroupName,                        -- 56: MediaServer
                                eventName,                             -- 311: ConnectionModificationFailure
                                correlationId,
                                severity,
                                eventTime,
                                nodes,
                                faultyObject,
                                monitoredValue,
                                thresholdValues,
                                info   }
        STATUS                current
        DESCRIPTION        "Spontaneous Alarm from the managed network element:
                            Failed to modify connection

Existing connection can not be modified due to a non-recoverable problem.
                            Please check the log-output to get more detailed informations (logger: com.cycos.media)."
        ::= { eventGroupC56 311 }

        alarmC56312 NOTIFICATION-TYPE
        OBJECTS        {        neName,
                                neType,
                                eventGroupName,                        -- 56: MediaServer
                                eventName,                             -- 312: ConnectionDeletionFailure
                                correlationId,
                                severity,
                                eventTime,
                                nodes,
                                faultyObject,
                                monitoredValue,
                                thresholdValues,
                                info   }
        STATUS                current
        DESCRIPTION        "Spontaneous Alarm from the managed network element:
                            Failed to delete connection

Request to delete a connection can not be handled correctly due to a non-recoverable problem.
                            Please check the log-output to get more detailed informations (logger: com.cycos.media)."
        ::= { eventGroupC56 312 }

        alarmC56313 NOTIFICATION-TYPE
        OBJECTS        {        neName,
                                neType,
                                eventGroupName,                        -- 56: MediaServer
                                eventName,                             -- 313: NotificationRequestProcessingFailure
                                correlationId,
                                severity,
                                eventTime,
                                nodes,
                                faultyObject,
                                monitoredValue,
                                thresholdValues,
                                info   }
        STATUS                current
        DESCRIPTION        "Spontaneous Alarm from the managed network element:
                            Failed to process notification request

An internal problem occurred during the handling of a request for notification.
                            Escalate to next level of support."
        ::= { eventGroupC56 313 }

        alarmC56330 NOTIFICATION-TYPE
        OBJECTS        {        neName,
                                neType,
                                eventGroupName,                        -- 56: MediaServer
                                eventName,                             -- 330: ResourceAssociatedWithConnectionLost
                                correlationId,
                                severity,
                                eventTime,
                                nodes,
                                faultyObject,
                                monitoredValue,
                                thresholdValues,
                                info   }
        STATUS                current
        DESCRIPTION        "Spontaneous Alarm from the managed network element:
                            Lost the resource associated with the connection

An internal problem occurred and the gateway is terminating the connection.
                            Escalate to next level of support."
        ::= { eventGroupC56 330 }

        alarmC56400 NOTIFICATION-TYPE
        OBJECTS        {        neName,
                                neType,
                                eventGroupName,                        -- 56: MediaServer
                                eventName,                             -- 400: UnknownMFWFault
                                correlationId,
                                severity,
                                eventTime,
                                nodes,
                                faultyObject,
                                monitoredValue,
                                thresholdValues,
                                info   }
        STATUS                current
        DESCRIPTION        "Spontaneous Alarm from the managed network element:
                            Unknown MFW fault

Unspecified Media Framework Component fault.
                            Escalate to next level of support."
        ::= { eventGroupC56 400 }

        alarmC56401 NOTIFICATION-TYPE
        OBJECTS        {        neName,
                                neType,
                                eventGroupName,                        -- 56: MediaServer
                                eventName,                             -- 401: NativeMediaFrameworkStartupFailure
                                correlationId,
                                severity,
                                eventTime,
                                nodes,
                                faultyObject,
                                monitoredValue,
                                thresholdValues,
                                info   }
        STATUS                current
        DESCRIPTION        "Spontaneous Alarm from the managed network element:
                            Native Media Framework startup failed

Native part of Media Framework could not be started by Java.
                            Escalate to next level of support."
        ::= { eventGroupC56 401 }

        alarmC56402 NOTIFICATION-TYPE
        OBJECTS        {        neName,
                                neType,
                                eventGroupName,                        -- 56: MediaServer
                                eventName,                             -- 402: NativeMediaFrameworkNotResponding
                                correlationId,
                                severity,
                                eventTime,
                                nodes,
                                faultyObject,
                                monitoredValue,
                                thresholdValues,
                                info   }
        STATUS                current
        DESCRIPTION        "Spontaneous Alarm from the managed network element:
                            Native Media Framework not responding

Native part of Media Framework has crashed or is unable to respond.
                            Escalate to next level of support."
        ::= { eventGroupC56 402 }

        alarmC56403 NOTIFICATION-TYPE
        OBJECTS        {        neName,
                                neType,
                                eventGroupName,                        -- 56: MediaServer
                                eventName,                             -- 403: JavaMediaFrameworkReceiveSocketOverrun
                                correlationId,
                                severity,
                                eventTime,
                                nodes,
                                faultyObject,
                                monitoredValue,
                                thresholdValues,
                                info   }
        STATUS                current
        DESCRIPTION        "Spontaneous Alarm from the managed network element:
                            Java Media Framework receive socket overrun

Receive socket of java part of Media Framework is overloaded.
                            Escalate to next level of support."
        ::= { eventGroupC56 403 }

        alarmC56404 NOTIFICATION-TYPE
        OBJECTS        {        neName,
                                neType,
                                eventGroupName,                        -- 56: MediaServer
                                eventName,                             -- 404: NativeMediaFrameworkRecieveSocketOverrun
                                correlationId,
                                severity,
                                eventTime,
                                nodes,
                                faultyObject,
                                monitoredValue,
                                thresholdValues,
                                info   }
        STATUS                current
        DESCRIPTION        "Spontaneous Alarm from the managed network element:
                            Native Media Framework receive socket overrun

Receive socket of native part of Media Framework is overloaded.
                            Escalate to next level of support."
        ::= { eventGroupC56 404 }

        alarmC56405 NOTIFICATION-TYPE
        OBJECTS        {        neName,
                                neType,
                                eventGroupName,                        -- 56: MediaServer
                                eventName,                             -- 405: JavaMediaFrameworkReceiveSocketSequencError
                                correlationId,
                                severity,
                                eventTime,
                                nodes,
                                faultyObject,
                                monitoredValue,
                                thresholdValues,
                                info   }
        STATUS                current
        DESCRIPTION        "Spontaneous Alarm from the managed network element:
                            Java Media Framework receive socket sequence error

Messages lost on receive socket in java part of Media Framework.
                            Escalate to next level of support."
        ::= { eventGroupC56 405 }

        alarmC56406 NOTIFICATION-TYPE
        OBJECTS        {        neName,
                                neType,
                                eventGroupName,                        -- 56: MediaServer
                                eventName,                             -- 406: NativeMediaFrameworkReceiveSocketSequencError
                                correlationId,
                                severity,
                                eventTime,
                                nodes,
                                faultyObject,
                                monitoredValue,
                                thresholdValues,
                                info   }
        STATUS                current
        DESCRIPTION        "Spontaneous Alarm from the managed network element:
                            Native Media Framework receive socket sequence error

Messages lost on receive socket in native part of Media Framework.
                            Escalate to next level of support."
        ::= { eventGroupC56 406 }

        alarmC56407 NOTIFICATION-TYPE
        OBJECTS        {        neName,
                                neType,
                                eventGroupName,                        -- 56: MediaServer
                                eventName,                             -- 407: NativeMediaFrameworkSocketError
                                correlationId,
                                severity,
                                eventTime,
                                nodes,
                                faultyObject,
                                monitoredValue,
                                thresholdValues,
                                info   }
        STATUS                current
        DESCRIPTION        "Spontaneous Alarm from the managed network element:
                            Native Media Framework socket error

Bind of socket failed in native part of Media Framework.
                            Escalate to next level of support."
        ::= { eventGroupC56 407 }

        alarmC56408 NOTIFICATION-TYPE
        OBJECTS        {        neName,
                                neType,
                                eventGroupName,                        -- 56: MediaServer
                                eventName,                             -- 408: JavaMediaFrameworkUnrecoverableError
                                correlationId,
                                severity,
                                eventTime,
                                nodes,
                                faultyObject,
                                monitoredValue,
                                thresholdValues,
                                info   }
        STATUS                current
        DESCRIPTION        "Spontaneous Alarm from the managed network element:
                            Java Media Framework unrecoverable error

Unrecoverable error in java part of Media Framework leading to permanent service degradation. Any processing of streaming data won't work.
                            Escalate to next level of support."
        ::= { eventGroupC56 408 }

        alarmC56409 NOTIFICATION-TYPE
        OBJECTS        {        neName,
                                neType,
                                eventGroupName,                        -- 56: MediaServer
                                eventName,                             -- 409: NatvieMediaFrameworkUnrecoverableError
                                correlationId,
                                severity,
                                eventTime,
                                nodes,
                                faultyObject,
                                monitoredValue,
                                thresholdValues,
                                info   }
        STATUS                current
        DESCRIPTION        "Spontaneous Alarm from the managed network element:
                            Native Media Framework unrecoverable error

Unrecoverable error in native part of Media Framework leading to permanent service degradation. Any processing of streaming data won't work.
                            Escalate to next level of support."
        ::= { eventGroupC56 409 }

        alarmC56410 NOTIFICATION-TYPE
        OBJECTS        {        neName,
                                neType,
                                eventGroupName,                        -- 56: MediaServer
                                eventName,                             -- 410: NativeMediaFrameworkOutOfMemory
                                correlationId,
                                severity,
                                eventTime,
                                nodes,
                                faultyObject,
                                monitoredValue,
                                thresholdValues,
                                info   }
        STATUS                current
        DESCRIPTION        "Spontaneous Alarm from the managed network element:
                            Native Media Framework out of memory

Memory allocation failed in native part of Media Framework.
                            Escalate to next level of support."
        ::= { eventGroupC56 410 }

        alarmC56411 NOTIFICATION-TYPE
        OBJECTS        {        neName,
                                neType,
                                eventGroupName,                        -- 56: MediaServer
                                eventName,                             -- 411: NativeMediaFrameworkOutOfUDPPorts
                                correlationId,
                                severity,
                                eventTime,
                                nodes,
                                faultyObject,
                                monitoredValue,
                                thresholdValues,
                                info   }
        STATUS                current
        DESCRIPTION        "Spontaneous Alarm from the managed network element:
                            Native Media Framework out of UDP ports

Port allocation failed in native part of Media Framework.
                            Escalate to next level of support."
        ::= { eventGroupC56 411 }

        alarmC56412 NOTIFICATION-TYPE
        OBJECTS        {        neName,
                                neType,
                                eventGroupName,                        -- 56: MediaServer
                                eventName,                             -- 412: NativeMediaFrameworkCryptoSessionNotFound
                                correlationId,
                                severity,
                                eventTime,
                                nodes,
                                faultyObject,
                                monitoredValue,
                                thresholdValues,
                                info   }
        STATUS                current
        DESCRIPTION        "Spontaneous Alarm from the managed network element:
                            Native Media Framework crypto session not found

KeyManagement has no matching crypto session. Processing of encrypted streaming data will be affected.
                            Escalate to next level of support."
        ::= { eventGroupC56 412 }

        alarmC56413 NOTIFICATION-TYPE
        OBJECTS        {        neName,
                                neType,
                                eventGroupName,                        -- 56: MediaServer
                                eventName,                             -- 413: NativeMediaFrameworkSRTPError
                                correlationId,
                                severity,
                                eventTime,
                                nodes,
                                faultyObject,
                                monitoredValue,
                                thresholdValues,
                                info   }
        STATUS                current
        DESCRIPTION        "Spontaneous Alarm from the managed network element:
                            Native Media Framework srtp error

Srtp stack returned error. Processing of encrypted streaming data will be affected.
                            Escalate to next level of support."
        ::= { eventGroupC56 413 }

        alarmC56414 NOTIFICATION-TYPE
        OBJECTS        {        neName,
                                neType,
                                eventGroupName,                        -- 56: MediaServer
                                eventName,                             -- 414: NativeMediaFrameworkJeyManagementFatalErro
                                correlationId,
                                severity,
                                eventTime,
                                nodes,
                                faultyObject,
                                monitoredValue,
                                thresholdValues,
                                info   }
        STATUS                current
        DESCRIPTION        "Spontaneous Alarm from the managed network element:
                            Native Media Framework keyManagement fatal error

KeyManagement in unrecoverable error state. Processing of encrypted streaming data will be affected.
                            Escalate to next level of support."
        ::= { eventGroupC56 414 }

        alarmC56415 NOTIFICATION-TYPE
        OBJECTS        {        neName,
                                neType,
                                eventGroupName,                        -- 56: MediaServer
                                eventName,                             -- 415: NativeMediaFrameworkControlPortBindError
                                correlationId,
                                severity,
                                eventTime,
                                nodes,
                                faultyObject,
                                monitoredValue,
                                thresholdValues,
                                info   }
        STATUS                current
        DESCRIPTION        "Spontaneous Alarm from the managed network element:
                            Media Framework control port bind error

Control port for Java-native communication could not be opened - check port configuration or other processes using conflicting ports.
                            Escalate to next level of support."
        ::= { eventGroupC56 415 }

        alarmC56416 NOTIFICATION-TYPE
        OBJECTS        {        neName,
                                neType,
                                eventGroupName,                        -- 56: MediaServer
                                eventName,                             -- 416: NativeMediaFrameworkRealtimeError
                                correlationId,
                                severity,
                                eventTime,
                                nodes,
                                faultyObject,
                                monitoredValue,
                                thresholdValues,
                                info   }
        STATUS                current
        DESCRIPTION        "Spontaneous Alarm from the managed network element:
                            Native Media Framework realtime error

Native MFW process could not be started in realtime mode: this may lead to bad voice quality.
                            Check access rights for native image."
        ::= { eventGroupC56 416 }

        alarmC56417 NOTIFICATION-TYPE
        OBJECTS        {        neName,
                                neType,
                                eventGroupName,                        -- 56: MediaServer
                                eventName,                             -- 417: NativeMediaFrameworksRTCError
                                correlationId,
                                severity,
                                eventTime,
                                nodes,
                                faultyObject,
                                monitoredValue,
                                thresholdValues,
                                info   }
        STATUS                current
        DESCRIPTION        "Spontaneous Alarm from the managed network element:
                            Native Media Framework RTC error

Realtime clock could not be initialized: this may degrade voice quality.
                            Check for configuration or conflicting usage of RTC by another process."
        ::= { eventGroupC56 417 }

        alarmC56418 NOTIFICATION-TYPE
        OBJECTS        {        neName,
                                neType,
                                eventGroupName,                        -- 56: MediaServer
                                eventName,                             -- 418: UDPPortBindError
                                correlationId,
                                severity,
                                eventTime,
                                nodes,
                                faultyObject,
                                monitoredValue,
                                thresholdValues,
                                info   }
        STATUS                current
        DESCRIPTION        "Spontaneous Alarm from the managed network element:
                            UDP port bind error

Bind of a UDP port failed.
                            If this error persists check port range configuration."
        ::= { eventGroupC56 418 }

        alarmC56419 NOTIFICATION-TYPE
        OBJECTS        {        neName,
                                neType,
                                eventGroupName,                        -- 56: MediaServer
                                eventName,                             -- 419: IllegalCommandOption
                                correlationId,
                                severity,
                                eventTime,
                                nodes,
                                faultyObject,
                                monitoredValue,
                                thresholdValues,
                                info   }
        STATUS                current
        DESCRIPTION        "Spontaneous Alarm from the managed network element:
                            Illegal command option

Media Framework was started with an illegal command option.
                            Check configuration in Media Framework configuration file 'mfw.component.xml'."
        ::= { eventGroupC56 419 }

        alarmC56420 NOTIFICATION-TYPE
        OBJECTS        {        neName,
                                neType,
                                eventGroupName,                        -- 56: MediaServer
                                eventName,                             -- 420: NoMoreAvailableUDPPorts
                                correlationId,
                                severity,
                                eventTime,
                                nodes,
                                faultyObject,
                                monitoredValue,
                                thresholdValues,
                                info   }
        STATUS                current
        DESCRIPTION        "Spontaneous Alarm from the managed network element:
                            No more free UDP ports available

The media framework (MFW) has run out of free UDP ports.
                            Please make sure that the media servers configured port range is sufficient."
        ::= { eventGroupC56 420 }

        alarmC56422 NOTIFICATION-TYPE
        OBJECTS        {        neName,
                                neType,
                                eventGroupName,                        -- 56: MediaServer
                                eventName,                             -- 422: NoMoreAvailableNetworkPorts
                                correlationId,
                                severity,
                                eventTime,
                                nodes,
                                faultyObject,
                                monitoredValue,
                                thresholdValues,
                                info   }
        STATUS                current
        DESCRIPTION        "Spontaneous Alarm from the managed network element:
                            stream ports (nearly) exhausted

At least 1 stream route is (nearly) out of free network ports. Probably no more connections could be established. Check log-output for more details.
                            The alarm is cleared automatically as soon as enough network ports are available again."
        ::= { eventGroupC56 422 }

        alarmC56423 NOTIFICATION-TYPE
        OBJECTS        {        neName,
                                neType,
                                eventGroupName,                        -- 56: MediaServer
                                eventName,                             -- 423: TurnServiceConfigurationError
                                correlationId,
                                severity,
                                eventTime,
                                nodes,
                                faultyObject,
                                monitoredValue,
                                thresholdValues,
                                info   }
        STATUS                current
        DESCRIPTION        "Spontaneous Alarm from the managed network element:
                            TURN service configuration error

TURN service will not work. Check log-output for more details.
                            Check the TURN service configuration and try to fix it."
        ::= { eventGroupC56 423 }

        alarmC56424 NOTIFICATION-TYPE
        OBJECTS        {        neName,
                                neType,
                                eventGroupName,                        -- 56: MediaServer
                                eventName,                             -- 424: TurnServiceResourceError
                                correlationId,
                                severity,
                                eventTime,
                                nodes,
                                faultyObject,
                                monitoredValue,
                                thresholdValues,
                                info   }
        STATUS                current
        DESCRIPTION        "Spontaneous Alarm from the managed network element:
                            TURN service resource error

One or more (possibly all) TURN service ports couldn't be bound. Check log-output for more details.
                            There could be many causes that the configured ports couldn't be used, e. g. access restrictions, port already in use etc."
        ::= { eventGroupC56 424 }

        alarmC56425 NOTIFICATION-TYPE
        OBJECTS        {        neName,
                                neType,
                                eventGroupName,                        -- 56: MediaServer
                                eventName,                             -- 425: NoMoreAvailableTurnRelayPorts
                                correlationId,
                                severity,
                                eventTime,
                                nodes,
                                faultyObject,
                                monitoredValue,
                                thresholdValues,
                                info   }
        STATUS                current
        DESCRIPTION        "Spontaneous Alarm from the managed network element:
                            TURN relay ports (nearly) exhausted

At least 1 TURN relay address type is (nearly) out of free network ports. Probably no more TURN connections could be established. Check log-output for more details.
                            The alarm is cleared automatically as soon as enough network ports are available again."
        ::= { eventGroupC56 425 }

        alarmC56500 NOTIFICATION-TYPE
        OBJECTS        {        neName,
                                neType,
                                eventGroupName,                        -- 56: MediaServer
                                eventName,                             -- 500: MRCPServerConnectionSetupError
                                correlationId,
                                severity,
                                eventTime,
                                nodes,
                                faultyObject,
                                monitoredValue,
                                thresholdValues,
                                info   }
        STATUS                current
        DESCRIPTION        "Spontaneous Alarm from the managed network element:
                            Unable to setup a connection with MRCP server

Unable to setup a connection with MRCP server. No TTS or ASR services may be used within the media server's applications.
                            Escalate to next level of support."
        ::= { eventGroupC56 500 }

        alarmC56510 NOTIFICATION-TYPE
        OBJECTS        {        neName,
                                neType,
                                eventGroupName,                        -- 56: MediaServer
                                eventName,                             -- 510: AMQPWebkitConnector
                                correlationId,
                                severity,
                                eventTime,
                                nodes,
                                faultyObject,
                                monitoredValue,
                                thresholdValues,
                                info   }
        STATUS                current
        DESCRIPTION        "Spontaneous Alarm from the managed network element:
                            AMQP channel shutdown

MediaServer webkit connectivity over AMQP is temporaly broken. It should autorecover as soon as the AMQP cluster is accessible again.
                            Check network connectivity to the AMQP cluster. Escalate to next level of support."
        ::= { eventGroupC56 510 }

        alarmC56511 NOTIFICATION-TYPE
        OBJECTS        {        neName,
                                neType,
                                eventGroupName,                        -- 56: MediaServer
                                eventName,                             -- 511: AMQPWebkitConnector
                                correlationId,
                                severity,
                                eventTime,
                                nodes,
                                faultyObject,
                                monitoredValue,
                                thresholdValues,
                                info   }
        STATUS                current
        DESCRIPTION        "Spontaneous Alarm from the managed network element:
                            An AMQP WebKit resource has been released

MediaServer might have to be restarted.
                            Check network connectivity to AMQP cluster. Escalate to next level of support."
        ::= { eventGroupC56 511 }

        alarmC56520 NOTIFICATION-TYPE
        OBJECTS        {        neName,
                                neType,
                                eventGroupName,                        -- 56: MediaServer
                                eventName,                             -- 520: AMQPWebkitTransport
                                correlationId,
                                severity,
                                eventTime,
                                nodes,
                                faultyObject,
                                monitoredValue,
                                thresholdValues,
                                info   }
        STATUS                current
        DESCRIPTION        "Spontaneous Alarm from the managed network element:
                            AMQP channel shutdown

MediaServer webkit connectivity over AMQP is temporaly broken. It should autorecover as soon as the AMQP cluster is accessible again.
                            Check network connectivity to tha AMQP cluster. Escalate to next level of support."
        ::= { eventGroupC56 520 }

        alarmC56521 NOTIFICATION-TYPE
        OBJECTS        {        neName,
                                neType,
                                eventGroupName,                        -- 56: MediaServer
                                eventName,                             -- 521: AMQPWebkitTransport
                                correlationId,
                                severity,
                                eventTime,
                                nodes,
                                faultyObject,
                                monitoredValue,
                                thresholdValues,
                                info   }
        STATUS                current
        DESCRIPTION        "Spontaneous Alarm from the managed network element:
                            MediaServer paas replies are timing out. Check AMQP messaging in MS Webkit (async-proxy).
                            Check Network Connectivity to the AMQP cluster. Escalate to next level of support."
        ::= { eventGroupC56 521 }

        alarmC56990 NOTIFICATION-TYPE
        OBJECTS        {        neName,
                                neType,
                                eventGroupName,                        -- 56: MediaServer
                                eventName,                             -- 990: TooManyRTCParticipants
                                correlationId,
                                severity,
                                eventTime,
                                nodes,
                                faultyObject,
                                monitoredValue,
                                thresholdValues,
                                info   }
        STATUS                current
        DESCRIPTION        "Spontaneous Alarm from the managed network element:
                            A new RTC participant tried to enter an RTC conference and the limit is reached. The new participant is removed.
                            The alarm is not cleared manually."
        ::= { eventGroupC56 990 }

        alarmC56991 NOTIFICATION-TYPE
        OBJECTS        {        neName,
                                neType,
                                eventGroupName,                        -- 56: MediaServer
                                eventName,                             -- 991: TooManyPSTNParticipants
                                correlationId,
                                severity,
                                eventTime,
                                nodes,
                                faultyObject,
                                monitoredValue,
                                thresholdValues,
                                info   }
        STATUS                current
        DESCRIPTION        "Spontaneous Alarm from the managed network element:
                            A new PSTN participant tried to enter an RTC conference and the limit is reached. The new participant is removed.
                            The alarm is not cleared manually."
        ::= { eventGroupC56 991 }

        alarmC56992 NOTIFICATION-TYPE
        OBJECTS        {        neName,
                                neType,
                                eventGroupName,                        -- 56: MediaServer
                                eventName,                             -- 992: Overload
                                correlationId,
                                severity,
                                eventTime,
                                nodes,
                                faultyObject,
                                monitoredValue,
                                thresholdValues,
                                info   }
        STATUS                current
        DESCRIPTION        "Spontaneous Alarm from the managed network element:
                            The media server has too much load. If possible new conference calls are assigned to other media servers, if not they are rejected.
                            If the alarm condition remains over a longer period of time review installation sizing. If the installation is sized properly escalate to development to check for SW problems."
        ::= { eventGroupC56 992 }

        alarmC56993 NOTIFICATION-TYPE
        OBJECTS        {        neName,
                                neType,
                                eventGroupName,                        -- 56: MediaServer
                                eventName,                             -- 993: AttachmentUploadFailed
                                correlationId,
                                severity,
                                eventTime,
                                nodes,
                                faultyObject,
                                monitoredValue,
                                thresholdValues,
                                info   }
        STATUS                current
        DESCRIPTION        "Spontaneous Alarm from the managed network element:
                            The mediaserver was not able to upload an attachment in several tries. The attachment is going to be lost on next Circuit update. The operations team has to rescue the attachment from mediaserver and wait if the customer requests this lost attachment.
                            The alarm is not cleared automatically. It must be cleared by operations team. Please save the attachment before clearing the alarm ! If the attachment is not saved externally, it is erased during next Circuit update !"
        ::= { eventGroupC56 993 }

        alarmC56994 NOTIFICATION-TYPE
        OBJECTS        {        neName,
                                neType,
                                eventGroupName,                        -- 56: MediaServer
                                eventName,                             -- 994: ConnectionLost
                                correlationId,
                                severity,
                                eventTime,
                                nodes,
                                faultyObject,
                                monitoredValue,
                                thresholdValues,
                                info   }
        STATUS                current
        DESCRIPTION        "Spontaneous Alarm from the managed network element:
                            RTC Controller cannot connect to selected Media Server.
                            If the alarm condition remains check if the Media Server specified in the faulty object is running."
        ::= { eventGroupC56 994 }

        alarmC56995 NOTIFICATION-TYPE
        OBJECTS        {        neName,
                                neType,
                                eventGroupName,                        -- 56: MediaServer
                                eventName,                             -- 995: NotAvailable
                                correlationId,
                                severity,
                                eventTime,
                                nodes,
                                faultyObject,
                                monitoredValue,
                                thresholdValues,
                                info   }
        STATUS                current
        DESCRIPTION        "Spontaneous Alarm from the managed network element:
                            No Media Server is reachable by the RTC Controller.
                            If the alarm condition remains check if there is a media node running and registered to zookeeper. Also check the connectivity from application node to zookeeper nodes."
        ::= { eventGroupC56 995 }

        alarmC56996 NOTIFICATION-TYPE
        OBJECTS        {        neName,
                                neType,
                                eventGroupName,                        -- 56: MediaServer
                                eventName,                             -- 996: MediaserverRediscoveryFailed
                                correlationId,
                                severity,
                                eventTime,
                                nodes,
                                faultyObject,
                                monitoredValue,
                                thresholdValues,
                                info   }
        STATUS                current
        DESCRIPTION        "Spontaneous Alarm from the managed network element:
                            There are some configured Media Servers not available for use by the RTC Controller.
                            If the alarm condition remains check if all mediaservers are running and the zookeeper configuration is correct. Check the tracelogs on the application node."
        ::= { eventGroupC56 996 }

        alarmC56997 NOTIFICATION-TYPE
        OBJECTS        {        neName,
                                neType,
                                eventGroupName,                        -- 56: MediaServer
                                eventName,                             -- 997: NoMonitoringRtcNode
                                correlationId,
                                severity,
                                eventTime,
                                nodes,
                                faultyObject,
                                monitoredValue,
                                thresholdValues,
                                info   }
        STATUS                current
        DESCRIPTION        "Spontaneous Alarm from the managed network element:
                            The monitoring RTC node is down.
                            If the alarm condition remains check if there is an application node with RTC Controller running on it and the zookeeper configuration is correct. Check the tracelogs on the application node."
        ::= { eventGroupC56 997 }

        alarmC56998 NOTIFICATION-TYPE
        OBJECTS        {        neName,
                                neType,
                                eventGroupName,                        -- 56: MediaServer
                                eventName,                             -- 998: NoNodesInRegion
                                correlationId,
                                severity,
                                eventTime,
                                nodes,
                                faultyObject,
                                monitoredValue,
                                thresholdValues,
                                info   }
        STATUS                current
        DESCRIPTION        "Spontaneous Alarm from the managed network element:
                            No Media Server found in region.
                            There are either no nodes configured for this region or all nodes are busy. This is just informational as there will be a fallback to default region."
        ::= { eventGroupC56 998 }

        alarmC56999 NOTIFICATION-TYPE
        OBJECTS        {        neName,
                                neType,
                                eventGroupName,                        -- 56: MediaServer
                                eventName,                             -- 999: JoinFailures
                                correlationId,
                                severity,
                                eventTime,
                                nodes,
                                faultyObject,
                                monitoredValue,
                                thresholdValues,
                                info   }
        STATUS                current
        DESCRIPTION        "Spontaneous Alarm from the managed network element:
                            More than 10 users failed to join for the last minute.
                            If the alarm condition remains check if there is a need to restart Virgo container. Check the tracelogs on the application node and look for unexpected exception cause the join failure."
        ::= { eventGroupC56 999 }


        --********************************************************************
        -- Alarm Trap Definitions for alarm eventC 57: IMPApplication
        --********************************************************************

        alarmC57001 NOTIFICATION-TYPE
        OBJECTS        {        neName,
                                neType,
                                eventGroupName,                        -- 57: IMPApplication
                                eventName,                             -- 001: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC57 1 }

        alarmC57003 NOTIFICATION-TYPE
        OBJECTS        {        neName,
                                neType,
                                eventGroupName,                        -- 57: IMPApplication
                                eventName,                             -- 003: ClientAPITimeHigh
                                correlationId,
                                severity,
                                eventTime,
                                nodes,
                                faultyObject,
                                monitoredValue,
                                thresholdValues,
                                info   }
        STATUS                current
        DESCRIPTION        "Spontaneous Alarm from the managed network element:
                            Client API average response time.
                            Escalate to next level of support."
        ::= { eventGroupC57 3 }

        alarmC57004 NOTIFICATION-TYPE
        OBJECTS        {        neName,
                                neType,
                                eventGroupName,                        -- 57: IMPApplication
                                eventName,                             -- 004: ClientAPIFailure
                                correlationId,
                                severity,
                                eventTime,
                                nodes,
                                faultyObject,
                                monitoredValue,
                                thresholdValues,
                                info   }
        STATUS                current
        DESCRIPTION        "Spontaneous Alarm from the managed network element:
                            Client API times out, no response.
                            Escalate to next level of support."
        ::= { eventGroupC57 4 }

        alarmC57005 NOTIFICATION-TYPE
        OBJECTS        {        neName,
                                neType,
                                eventGroupName,                        -- 57: IMPApplication
                                eventName,                             -- 005: ClientAPIZpoolFull
                                correlationId,
                                severity,
                                eventTime,
                                nodes,
                                faultyObject,
                                monitoredValue,
                                thresholdValues,
                                info   }
        STATUS                current
        DESCRIPTION        "Spontaneous Alarm from the managed network element:
                            The zpool contains data.

A high fill level may cause issues and failed conversions once 100% reached.
                            If the alarm condition remains over a longer period of time review installation sizing. If the installation is sized properly escalate to development to check for SW problems."
        ::= { eventGroupC57 5 }

        alarmC57006 NOTIFICATION-TYPE
        OBJECTS        {        neName,
                                neType,
                                eventGroupName,                        -- 57: IMPApplication
                                eventName,                             -- 006: ClientAPIOverload
                                correlationId,
                                severity,
                                eventTime,
                                nodes,
                                faultyObject,
                                monitoredValue,
                                thresholdValues,
                                info   }
        STATUS                current
        DESCRIPTION        "Spontaneous Alarm from the managed network element:
                            Client API overload condition.
                            Check the application node usage and escalate to next level of support. A node addition could be considered."
        ::= { eventGroupC57 6 }

        alarmC57007 NOTIFICATION-TYPE
        OBJECTS        {        neName,
                                neType,
                                eventGroupName,                        -- 57: IMPApplication
                                eventName,                             -- 007: ClientAPIRestApiSDKUsage
                                correlationId,
                                severity,
                                eventTime,
                                nodes,
                                faultyObject,
                                monitoredValue,
                                thresholdValues,
                                info   }
        STATUS                current
        DESCRIPTION        "Spontaneous Alarm from the managed network element:
                            RestAPI or JS SDK Usage Violation detection.
                            Check the RestAPI and JS SDK usage and escalate to next level of support."
        ::= { eventGroupC57 7 }

        alarmC57013 NOTIFICATION-TYPE
        OBJECTS        {        neName,
                                neType,
                                eventGroupName,                        -- 57: IMPApplication
                                eventName,                             -- 013: UnknownAlarmId
                                correlationId,
                                severity,
                                eventTime,
                                nodes,
                                faultyObject,
                                monitoredValue,
                                thresholdValues,
                                info   }
        STATUS                current
        DESCRIPTION        "Spontaneous Alarm from the managed network element:
                            The platform alarm configuration file could not be found.
                            Check installation. If correct, check permissions on alarm configuration file."
        ::= { eventGroupC57 13 }

        alarmC57014 NOTIFICATION-TYPE
        OBJECTS        {        neName,
                                neType,
                                eventGroupName,                        -- 57: IMPApplication
                                eventName,                             -- 014: InvalidMonitoredValue
                                correlationId,
                                severity,
                                eventTime,
                                nodes,
                                faultyObject,
                                monitoredValue,
                                thresholdValues,
                                info   }
        STATUS                current
        DESCRIPTION        "Spontaneous Alarm from the managed network element:
                            An alarm has been raised or used with an invalid monitored attribute value.
                            Correct code raising the alarm."
        ::= { eventGroupC57 14 }

        alarmC57015 NOTIFICATION-TYPE
        OBJECTS        {        neName,
                                neType,
                                eventGroupName,                        -- 57: IMPApplication
                                eventName,                             -- 015: FaultyObjectTooLong
                                correlationId,
                                severity,
                                eventTime,
                                nodes,
                                faultyObject,
                                monitoredValue,
                                thresholdValues,
                                info   }
        STATUS                current
        DESCRIPTION        "Spontaneous Alarm from the managed network element:
                            An alarm has been raised with a FaultyObject string that is longer than 255. It has been truncated.
                            Correct code raising the alarm."
        ::= { eventGroupC57 15 }

        alarmC57016 NOTIFICATION-TYPE
        OBJECTS        {        neName,
                                neType,
                                eventGroupName,                        -- 57: IMPApplication
                                eventName,                             -- 016: AddlInfoTooLong
                                correlationId,
                                severity,
                                eventTime,
                                nodes,
                                faultyObject,
                                monitoredValue,
                                thresholdValues,
                                info   }
        STATUS                current
        DESCRIPTION        "Spontaneous Alarm from the managed network element:
                            An alarm has been raised with an Addl Info string that is longer than 255. It has been truncated.
                            Correct code raising the alarm."
        ::= { eventGroupC57 16 }

        alarmC57017 NOTIFICATION-TYPE
        OBJECTS        {        neName,
                                neType,
                                eventGroupName,                        -- 57: IMPApplication
                                eventName,                             -- 017: UnknownAlarmId
                                correlationId,
                                severity,
                                eventTime,
                                nodes,
                                faultyObject,
                                monitoredValue,
                                thresholdValues,
                                info   }
        STATUS                current
        DESCRIPTION        "Spontaneous Alarm from the managed network element:
                            An alarm has been raised or used with an unknown group ID and/or event ID.
                            Check if the alarm should be raised/used. If correct, add alarm to alarm configuration."
        ::= { eventGroupC57 17 }

        alarmC57021 NOTIFICATION-TYPE
        OBJECTS        {        neName,
                                neType,
                                eventGroupName,                        -- 57: IMPApplication
                                eventName,                             -- 021: UnexpectedRMQPartitions
                                correlationId,
                                severity,
                                eventTime,
                                nodes,
                                faultyObject,
                                monitoredValue,
                                thresholdValues,
                                info   }
        STATUS                current
        DESCRIPTION        "Spontaneous Alarm from the managed network element:
                            RabbitMQ Partitions have been detected. Application Nodes may be operating independently of others.
                            Manual action is required in order to recover. Please bring all nodes down, clean up mnesia database and start all nodes again."
        ::= { eventGroupC57 21 }

        alarmC57022 NOTIFICATION-TYPE
        OBJECTS        {        neName,
                                neType,
                                eventGroupName,                        -- 57: IMPApplication
                                eventName,                             -- 022: UnexpectedRMQClusterError
                                correlationId,
                                severity,
                                eventTime,
                                nodes,
                                faultyObject,
                                monitoredValue,
                                thresholdValues,
                                info   }
        STATUS                current
        DESCRIPTION        "Spontaneous Alarm from the managed network element:
                            RabbitMQ join_cluster command has failed, application node(s) may be operating independently of others.
                            Manual action is required in order to recover. Please restart virgo application server process."
        ::= { eventGroupC57 22 }

        alarmC57023 NOTIFICATION-TYPE
        OBJECTS        {        neName,
                                neType,
                                eventGroupName,                        -- 57: IMPApplication
                                eventName,                             -- 023: UnexpectedRMQConnectivityLost
                                correlationId,
                                severity,
                                eventTime,
                                nodes,
                                faultyObject,
                                monitoredValue,
                                thresholdValues,
                                info   }
        STATUS                current
        DESCRIPTION        "Spontaneous Alarm from the managed network element:
                            Messaging controller has lost connectivity to RabbitMQ broker.
                            Manually action is required in order to recover. Check Virgo/RabbitMQ processes."
        ::= { eventGroupC57 23 }

        alarmC57024 NOTIFICATION-TYPE
        OBJECTS        {        neName,
                                neType,
                                eventGroupName,                        -- 57: IMPApplication
                                eventName,                             -- 024: HazelcastPartitionMigrationIssue
                                correlationId,
                                severity,
                                eventTime,
                                nodes,
                                faultyObject,
                                monitoredValue,
                                thresholdValues,
                                info   }
        STATUS                current
        DESCRIPTION        "Spontaneous Alarm from the managed network element:
                            Hazelcast partition migration reported an error.
                            Manual action is required for checking Hazelcast cluster status. Please check the logs and if needed, restart Hazelcast process (pmc restart ansible-hazelcast)."
        ::= { eventGroupC57 24 }

        alarmC57025 NOTIFICATION-TYPE
        OBJECTS        {        neName,
                                neType,
                                eventGroupName,                        -- 57: IMPApplication
                                eventName,                             -- 025: VirgoHeapIssue
                                correlationId,
                                severity,
                                eventTime,
                                nodes,
                                faultyObject,
                                monitoredValue,
                                thresholdValues,
                                info   }
        STATUS                current
        DESCRIPTION        "Spontaneous Alarm from the managed network element:
                            Virgo heap usage is high. The root cause of this incident may be a slow memory leak. The user impact effect is that some of these Virgo containers will be unresponsive (but not down) for several minutes.
                            Manually action maybe required in order to recover. Check the process and the heap memory usage of Virgo."
        ::= { eventGroupC57 25 }

        alarmC57026 NOTIFICATION-TYPE
        OBJECTS        {        neName,
                                neType,
                                eventGroupName,                        -- 57: IMPApplication
                                eventName,                             -- 026: ApplicationNodeStateChanged
                                correlationId,
                                severity,
                                eventTime,
                                nodes,
                                faultyObject,
                                monitoredValue,
                                thresholdValues,
                                info   }
        STATUS                current
        DESCRIPTION        "Spontaneous Alarm from the managed network element:
                            Application node state changed to BUSY or BLOCKED due to high resource usage.
                            Manual action may be required in order to recover."
        ::= { eventGroupC57 26 }

        alarmC57027 NOTIFICATION-TYPE
        OBJECTS        {        neName,
                                neType,
                                eventGroupName,                        -- 57: IMPApplication
                                eventName,                             -- 027: HazelcastHeapIssue
                                correlationId,
                                severity,
                                eventTime,
                                nodes,
                                faultyObject,
                                monitoredValue,
                                thresholdValues,
                                info   }
        STATUS                current
        DESCRIPTION        "Spontaneous Alarm from the managed network element:
                            Hazelcast heap usage is high. The root cause of this incident may be a slow memory leak.
                            Manually action maybe required in order to recover. Check the process and the heap memory usage of Hazelcast."
        ::= { eventGroupC57 27 }

        alarmC57028 NOTIFICATION-TYPE
        OBJECTS        {        neName,
                                neType,
                                eventGroupName,                        -- 57: IMPApplication
                                eventName,                             -- 028: ZookeeperHeapIssue
                                correlationId,
                                severity,
                                eventTime,
                                nodes,
                                faultyObject,
                                monitoredValue,
                                thresholdValues,
                                info   }
        STATUS                current
        DESCRIPTION        "Spontaneous Alarm from the managed network element:
                            Zookeeper heap usage is high. The root cause of this incident may be a slow memory leak.
                            Manually action maybe required in order to recover. Check the process and the heap memory usage of Zookeeper."
        ::= { eventGroupC57 28 }

        alarmC57029 NOTIFICATION-TYPE
        OBJECTS        {        neName,
                                neType,
                                eventGroupName,                        -- 57: IMPApplication
                                eventName,                             -- 029: RMQBlockedConnection
                                correlationId,
                                severity,
                                eventTime,
                                nodes,
                                faultyObject,
                                monitoredValue,
                                thresholdValues,
                                info   }
        STATUS                current
        DESCRIPTION        "Spontaneous Alarm from the managed network element:
                            The connection is blocked due to the broker running low on resources (memory or disk).
                            Manual action may be required in order to recover. Check RabbitMQ processes."
        ::= { eventGroupC57 29 }

        alarmC57030 NOTIFICATION-TYPE
        OBJECTS        {        neName,
                                neType,
                                eventGroupName,                        -- 57: IMPApplication
                                eventName,                             -- 030: RMQClusterStatusUnknown
                                correlationId,
                                severity,
                                eventTime,
                                nodes,
                                faultyObject,
                                monitoredValue,
                                thresholdValues,
                                info   }
        STATUS                current
        DESCRIPTION        "Spontaneous Alarm from the managed network element:
                            Rabbitmq management plugin is down. Broker status is unknown, partition check cannot be completed.
                            Please check manually the broker's status and the cluster's health."
        ::= { eventGroupC57 30 }

        alarmC57031 NOTIFICATION-TYPE
        OBJECTS        {        neName,
                                neType,
                                eventGroupName,                        -- 57: IMPApplication
                                eventName,                             -- 031: UserSessionTokens
                                correlationId,
                                severity,
                                eventTime,
                                nodes,
                                faultyObject,
                                monitoredValue,
                                thresholdValues,
                                info   }
        STATUS                current
        DESCRIPTION        "Spontaneous Alarm from the managed network element:
                            A user is creating too many session tokens caused by too many login requests.
                            Check the user id in the fault object and suspend the user if needed."
        ::= { eventGroupC57 31 }

        alarmC57032 NOTIFICATION-TYPE
        OBJECTS        {        neName,
                                neType,
                                eventGroupName,                        -- 57: IMPApplication
                                eventName,                             -- 032: SecurityKeyEventing
                                correlationId,
                                severity,
                                eventTime,
                                nodes,
                                faultyObject,
                                monitoredValue,
                                thresholdValues,
                                info   }
        STATUS                current
        DESCRIPTION        "Spontaneous Alarm from the managed network element:
                            New security keys are not distributed across the APP-nodes caused by an error with the eventing system.
                            Check the RabbitMQ status, the type of the key in the fault object and the error description in the additional information."
        ::= { eventGroupC57 32 }

        alarmC57033 NOTIFICATION-TYPE
        OBJECTS        {        neName,
                                neType,
                                eventGroupName,                        -- 57: IMPApplication
                                eventName,                             -- 033: HazelcastClusterZooInconsistency
                                correlationId,
                                severity,
                                eventTime,
                                nodes,
                                faultyObject,
                                monitoredValue,
                                thresholdValues,
                                info   }
        STATUS                current
        DESCRIPTION        "Spontaneous Alarm from the managed network element:
                            Hazelcast cluster inconsistency with Zookeeper entries.
                            Hazelcast cluster status failed. Please check the connection between hazelcast members and zookeeper ephemeral services entries and if needed, restart Hazelcast process (pmc restart ansible-hazelcast)."
        ::= { eventGroupC57 33 }

        alarmC57034 NOTIFICATION-TYPE
        OBJECTS        {        neName,
                                neType,
                                eventGroupName,                        -- 57: IMPApplication
                                eventName,                             -- 034: HazelcastClusterMembersError
                                correlationId,
                                severity,
                                eventTime,
                                nodes,
                                faultyObject,
                                monitoredValue,
                                thresholdValues,
                                info   }
        STATUS                current
        DESCRIPTION        "Spontaneous Alarm from the managed network element:
                            Hazelcast cluster members error.
                            Hazelcast cluster status failed. Please check the logs for hazelcast members multiple removal operations and if needed, restart Hazelcast process (pmc restart ansible-hazelcast)."
        ::= { eventGroupC57 34 }

        alarmC57035 NOTIFICATION-TYPE
        OBJECTS        {        neName,
                                neType,
                                eventGroupName,                        -- 57: IMPApplication
                                eventName,                             -- 035: NettyOutOfDirectMemory
                                correlationId,
                                severity,
                                eventTime,
                                nodes,
                                faultyObject,
                                monitoredValue,
                                thresholdValues,
                                info   }
        STATUS                current
        DESCRIPTION        "Spontaneous Alarm from the managed network element:
                            The Netty network communication framework is out of memory.
                            NONE"
        ::= { eventGroupC57 35 }

        alarmC57036 NOTIFICATION-TYPE
        OBJECTS        {        neName,
                                neType,
                                eventGroupName,                        -- 57: IMPApplication
                                eventName,                             -- 036: NettyError
                                correlationId,
                                severity,
                                eventTime,
                                nodes,
                                faultyObject,
                                monitoredValue,
                                thresholdValues,
                                info   }
        STATUS                current
        DESCRIPTION        "Spontaneous Alarm from the managed network element:
                            The Netty network communication framework has a problem.
                            The Netty network communication framework has a problem. Check the error description in the additional information to find out what caused the error. Probably you have to restart the Virgo container on the APP node (pmc restart ansible-virgo)."
        ::= { eventGroupC57 36 }

        alarmC57050 NOTIFICATION-TYPE
        OBJECTS        {        neName,
                                neType,
                                eventGroupName,                        -- 57: IMPApplication
                                eventName,                             -- 050: UCaaSCreateITSPFailed
                                correlationId,
                                severity,
                                eventTime,
                                nodes,
                                faultyObject,
                                monitoredValue,
                                thresholdValues,
                                info   }
        STATUS                current
        DESCRIPTION        "Spontaneous Alarm from the managed network element:
                            Create Openscape Telephony Provider failed.
                            Create Openscape Telephony Provider failed. Please check the faulty object for the tenantId and ITSP information. Cleanup of SBC/OSV resources may be needed."
        ::= { eventGroupC57 50 }


        --********************************************************************
        -- Alarm Trap Definitions for alarm eventC 58: Redis
        --********************************************************************

        alarmC58001 NOTIFICATION-TYPE
        OBJECTS        {        neName,
                                neType,
                                eventGroupName,                        -- 58: Redis
                                eventName,                             -- 001: RedisClusterFail
                                correlationId,
                                severity,
                                eventTime,
                                nodes,
                                faultyObject,
                                monitoredValue,
                                thresholdValues,
                                info   }
        STATUS                current
        DESCRIPTION        "Spontaneous Alarm from the managed network element:
                            Redis cluster is in fail state and can not recover by itself. As a result all requests to the data center is not being processed. Human intervention is needed immediately.
                            This alarm can occur during system startup and cluster formation. If this is not the case, check if all nodes are running. Check also if redis-cluster and redis-audit are running. If everything looks good then probably the cluster will not recover by itself. To recover the system lock all nodes (pmc state locked) then run '/etc/init.d/redis-audit clean' in all nodes, afterwards unlock the nodes (pmc state locked) - this way a fresh redis-cluster will start."
        ::= { eventGroupC58 1 }

        alarmC58002 NOTIFICATION-TYPE
        OBJECTS        {        neName,
                                neType,
                                eventGroupName,                        -- 58: Redis
                                eventName,                             -- 002: RedisClusterFailOver
                                correlationId,
                                severity,
                                eventTime,
                                nodes,
                                faultyObject,
                                monitoredValue,
                                thresholdValues,
                                info   }
        STATUS                current
        DESCRIPTION        "Spontaneous Alarm from the managed network element:
                            One of the redis node is down so a failover just happened.
                            This alarm can happen temporarily if some other Access node is restarting. Please check if all nodes are running or if there are network issues. The redis audit will try to rebalance the cluster once the Access node is available again (then the alarm will be automatically cleared). The process of rebalancing can take about 5 to 15 minutes to complete."
        ::= { eventGroupC58 2 }

        alarmC58003 NOTIFICATION-TYPE
        OBJECTS        {        neName,
                                neType,
                                eventGroupName,                        -- 58: Redis
                                eventName,                             -- 003: RedisClusterRebalancing
                                correlationId,
                                severity,
                                eventTime,
                                nodes,
                                faultyObject,
                                monitoredValue,
                                thresholdValues,
                                info   }
        STATUS                current
        DESCRIPTION        "Spontaneous Alarm from the managed network element:
                            A resharding is started, do not stop the nodes participating in the resharding until the alarm is cleared.
                            The redis audit is moving hash slots (resharding). This happens if nodes are added or removed, the alarm will be automatically cleared once the resharding process is complete. The process of resharding can take about 5 to 15 minutes to complete."
        ::= { eventGroupC58 3 }

        alarmC58004 NOTIFICATION-TYPE
        OBJECTS        {        neName,
                                neType,
                                eventGroupName,                        -- 58: Redis
                                eventName,                             -- 004: RedisClusterInit
                                correlationId,
                                severity,
                                eventTime,
                                nodes,
                                faultyObject,
                                monitoredValue,
                                thresholdValues,
                                info   }
        STATUS                current
        DESCRIPTION        "Spontaneous Alarm from the managed network element:
                            Redis Cluster is in the process of reinitializing, all data will be erased and a new cluster will be formed.
                            The redis audit is in process of creating a new cluster, allocating hash slots for each node and defining the Master/Slave roles. This alarm can also happen temporarily after resharding and rebalancing. The alarm will be automatically cleared once the cluster formation process is complete, this process can take about 5 minutes to complete."
        ::= { eventGroupC58 4 }


        --********************************************************************
        -- Alarm Trap Definitions for alarm eventC 59: LogManager
        --********************************************************************

        alarmC59001 NOTIFICATION-TYPE
        OBJECTS        {        neName,
                                neType,
                                eventGroupName,                        -- 59: LogManager
                                eventName,                             -- 001: PostAlarmFailure
                                correlationId,
                                severity,
                                eventTime,
                                nodes,
                                faultyObject,
                                monitoredValue,
                                thresholdValues,
                                info   }
        STATUS                current
        DESCRIPTION        "Spontaneous Alarm from the managed network element:
                            The log manger could not store an alarm record in the alarm database. The alarm is not reported as SNMP trap and not displayed in the active alarm database.
                            Run debug file collection of the operations node and escalate to SW development."
        ::= { eventGroupC59 1 }

        alarmC59002 NOTIFICATION-TYPE
        OBJECTS        {        neName,
                                neType,
                                eventGroupName,                        -- 59: LogManager
                                eventName,                             -- 002: PostSolrFailure
                                correlationId,
                                severity,
                                eventTime,
                                nodes,
                                faultyObject,
                                monitoredValue,
                                thresholdValues,
                                info   }
        STATUS                current
        DESCRIPTION        "Spontaneous Alarm from the managed network element:
                            The log manger could not store a log record in Solr. The log is not shown in the log manager GUI and it is not archived in hadoop.
                            Check the partition fill level and accessibility of the /db/logmg directory. Run debug file collection of the operations node and escalate to SW development."
        ::= { eventGroupC59 2 }

        alarmC59004 NOTIFICATION-TYPE
        OBJECTS        {        neName,
                                neType,
                                eventGroupName,                        -- 59: LogManager
                                eventName,                             -- 004: CorruptedLogFile
                                correlationId,
                                severity,
                                eventTime,
                                nodes,
                                faultyObject,
                                monitoredValue,
                                thresholdValues,
                                info   }
        STATUS                current
        DESCRIPTION        "Spontaneous Alarm from the managed network element:
                            Log Manager has detected a corrupted log file and renamed it. The original file name is shown in the faulty object, while the new name is shown in the additional info field.
The content of the log file is not shown in log manager GUI and is not available for analytics.
                            Escalate to development to investigate the reason for file corruption.
Attach the corrupted log file to the fault report."
        ::= { eventGroupC59 4 }


        --********************************************************************
        -- Alarm Trap Definitions for alarm eventC 60: Access
        --********************************************************************

        alarmC60001 NOTIFICATION-TYPE
        OBJECTS        {        neName,
                                neType,
                                eventGroupName,                        -- 60: Access
                                eventName,                             -- 001: FaultyConfiguraton
                                correlationId,
                                severity,
                                eventTime,
                                nodes,
                                faultyObject,
                                monitoredValue,
                                thresholdValues,
                                info   }
        STATUS                current
        DESCRIPTION        "Spontaneous Alarm from the managed network element:
                            Access node configuration file is faulty. Access node functionality is restricted.
                            Review log file entries, especially /var/log/access.log, to determine source of problem."
        ::= { eventGroupC60 1 }

        alarmC60010 NOTIFICATION-TYPE
        OBJECTS        {        neName,
                                neType,
                                eventGroupName,                        -- 60: Access
                                eventName,                             -- 010: NodeJSHeapUsed
                                correlationId,
                                severity,
                                eventTime,
                                nodes,
                                faultyObject,
                                monitoredValue,
                                thresholdValues,
                                info   }
        STATUS                current
        DESCRIPTION        "Spontaneous Alarm from the managed network element:
                            Node.js process consumes high memory
                            Escalate to development for investigation (possible memory leak or we reached the user service limit)."
        ::= { eventGroupC60 10 }


        --********************************************************************
        -- Alarm Trap Definitions for alarm eventC 61: CLV
        --********************************************************************

        alarmC61100 NOTIFICATION-TYPE
        OBJECTS        {        neName,
                                neType,
                                eventGroupName,                        -- 61: CLV
                                eventName,                             -- 100: ClvLostConnToDB
                                correlationId,
                                severity,
                                eventTime,
                                nodes,
                                faultyObject,
                                monitoredValue,
                                thresholdValues,
                                info   }
        STATUS                current
        DESCRIPTION        "Spontaneous Alarm from the managed network element:
                            CLV lost connection to postgres DB
                            Ensure Postgres is running. When postgres is already running and CLV does not connect within 30 seconds, escalate to development with /var/log/clv/clvserver.log"
        ::= { eventGroupC61 100 }

        alarmC61101 NOTIFICATION-TYPE
        OBJECTS        {        neName,
                                neType,
                                eventGroupName,                        -- 61: CLV
                                eventName,                             -- 101: ClvLostConnToRabbitMQ
                                correlationId,
                                severity,
                                eventTime,
                                nodes,
                                faultyObject,
                                monitoredValue,
                                thresholdValues,
                                info   }
        STATUS                current
        DESCRIPTION        "Spontaneous Alarm from the managed network element:
                            CLV lost connection to RabbitMQ
                            Ensure RabbitMQ service is running on Zookeeper node and reachable. If CLV still cannot connect, escalate to development with /var/log/clv/clvserver.log"
        ::= { eventGroupC61 101 }

        alarmC61102 NOTIFICATION-TYPE
        OBJECTS        {        neName,
                                neType,
                                eventGroupName,                        -- 61: CLV
                                eventName,                             -- 102: ClvLostConnToZookeeper
                                correlationId,
                                severity,
                                eventTime,
                                nodes,
                                faultyObject,
                                monitoredValue,
                                thresholdValues,
                                info   }
        STATUS                current
        DESCRIPTION        "Spontaneous Alarm from the managed network element:
                            CLV lost connection to Zookeeper
                            Ensure Zookeeper service is running on Zookeeper node and reachable. If CLV still cannot connect, escalate to development with /var/log/clv/clvserver.log"
        ::= { eventGroupC61 102 }

        alarmC61103 NOTIFICATION-TYPE
        OBJECTS        {        neName,
                                neType,
                                eventGroupName,                        -- 61: CLV
                                eventName,                             -- 103: ClvLostConnToAdminAPI
                                correlationId,
                                severity,
                                eventTime,
                                nodes,
                                faultyObject,
                                monitoredValue,
                                thresholdValues,
                                info   }
        STATUS                current
        DESCRIPTION        "Spontaneous Alarm from the managed network element:
                            CLV lost connection to AdminAPI (REST)
                            Ensure virgo is running on App node and reachable. If CLV still cannot connect, escalate to development with /var/log/clv/clvserver.log"
        ::= { eventGroupC61 103 }


        --********************************************************************
        -- Alarm Trap Definitions for alarm eventC 62: XMPP
        --********************************************************************

        alarmC62001 NOTIFICATION-TYPE
        OBJECTS        {        neName,
                                neType,
                                eventGroupName,                        -- 62: XMPP
                                eventName,                             -- 001: NoMoreAvailableProvisionLicense
                                correlationId,
                                severity,
                                eventTime,
                                nodes,
                                faultyObject,
                                monitoredValue,
                                thresholdValues,
                                info   }
        STATUS                current
        DESCRIPTION        "Spontaneous Alarm from the managed network element:
                            Failed to provision user due to license limit
                            Please make sure that there are enough tenant licenses. If not add more licenses to the tenant."
        ::= { eventGroupC62 1 }


        --********************************************************************
        -- Alarm Trap Definitions for alarm eventC 80: NetworkCom
        --********************************************************************

        alarmC80001 NOTIFICATION-TYPE
        OBJECTS        {        neName,
                                neType,
                                eventGroupName,                        -- 80: NetworkCom
                                eventName,                             -- 001: NodesUnavailable
                                correlationId,
                                severity,
                                eventTime,
                                nodes,
                                faultyObject,
                                monitoredValue,
                                thresholdValues,
                                info   }
        STATUS                current
        DESCRIPTION        "Spontaneous Alarm from the managed network element:
                            The listed nodes are not reported as active in the zookeeper database.
                            Check the administrative and operational status. Try to access the node directly via ssh and run rapidstat."
        ::= { eventGroupC80 1 }

        alarmC80002 NOTIFICATION-TYPE
        OBJECTS        {        neName,
                                neType,
                                eventGroupName,                        -- 80: NetworkCom
                                eventName,                             -- 002: LocalResponseTime
                                correlationId,
                                severity,
                                eventTime,
                                nodes,
                                faultyObject,
                                monitoredValue,
                                thresholdValues,
                                info   }
        STATUS                current
        DESCRIPTION        "Spontaneous Alarm from the managed network element:
                            The node's response time to a test message sent by the operations node was too high.
                            If this alarm persists escalate to next level of support to determine whether is response time is justified. Ether the SW needs to be corrected or the threshold be changed."
        ::= { eventGroupC80 2 }

        alarmC80003 NOTIFICATION-TYPE
        OBJECTS        {        neName,
                                neType,
                                eventGroupName,                        -- 80: NetworkCom
                                eventName,                             -- 003: RemoteResponseTime
                                correlationId,
                                severity,
                                eventTime,
                                nodes,
                                faultyObject,
                                monitoredValue,
                                thresholdValues,
                                info   }
        STATUS                current
        DESCRIPTION        "Spontaneous Alarm from the managed network element:
                            Future.
                            Future."
        ::= { eventGroupC80 3 }

        alarmC80004 NOTIFICATION-TYPE
        OBJECTS        {        neName,
                                neType,
                                eventGroupName,                        -- 80: NetworkCom
                                eventName,                             -- 004: NodesNotStarted
                                correlationId,
                                severity,
                                eventTime,
                                nodes,
                                faultyObject,
                                monitoredValue,
                                thresholdValues,
                                info   }
        STATUS                current
        DESCRIPTION        "Spontaneous Alarm from the managed network element:
                            The listed nodes have been in an invalid admin - operational state combination for more than 15 minutes. The nodes did not startup to the requested level.
                            Collect log files and sequentially reboot the nodes."
        ::= { eventGroupC80 4 }

        alarmC80005 NOTIFICATION-TYPE
        OBJECTS        {        neName,
                                neType,
                                eventGroupName,                        -- 80: NetworkCom
                                eventName,                             -- 005: NodesNotStopped
                                correlationId,
                                severity,
                                eventTime,
                                nodes,
                                faultyObject,
                                monitoredValue,
                                thresholdValues,
                                info   }
        STATUS                current
        DESCRIPTION        "Spontaneous Alarm from the managed network element:
                            The listed nodes have been in an invalid admin - operational state combination for more than 15 minutes. The nodes did not stop/shutdown to the requested level.
                            Collect log files and sequentially reboot the nodes."
        ::= { eventGroupC80 5 }


        --********************************************************************
        -- Alarm Trap Definitions for alarm eventC 81: Eventing
        --********************************************************************

        alarmC81001 NOTIFICATION-TYPE
        OBJECTS        {        neName,
                                neType,
                                eventGroupName,                        -- 81: Eventing
                                eventName,                             -- 001: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC81 1 }


        --********************************************************************
        -- Alarm Trap Definitions for alarm eventC 82: InMemDatabase
        --********************************************************************

        alarmC82001 NOTIFICATION-TYPE
        OBJECTS        {        neName,
                                neType,
                                eventGroupName,                        -- 82: InMemDatabase
                                eventName,                             -- 001: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC82 1 }


        --********************************************************************
        -- Alarm Trap Definitions for alarm eventC 90: Storage
        --********************************************************************

        alarmC90001 NOTIFICATION-TYPE
        OBJECTS        {        neName,
                                neType,
                                eventGroupName,                        -- 90: Storage
                                eventName,                             -- 001: CassandraNodeFailure
                                correlationId,
                                severity,
                                eventTime,
                                nodes,
                                faultyObject,
                                monitoredValue,
                                thresholdValues,
                                info   }
        STATUS                current
        DESCRIPTION        "Spontaneous Alarm from the managed network element:
                            Cassandra node is down.
                            Collect log files and contact support."
        ::= { eventGroupC90 1 }

        alarmC90002 NOTIFICATION-TYPE
        OBJECTS        {        neName,
                                neType,
                                eventGroupName,                        -- 90: Storage
                                eventName,                             -- 002: CassandraClusterFailure
                                correlationId,
                                severity,
                                eventTime,
                                nodes,
                                faultyObject,
                                monitoredValue,
                                thresholdValues,
                                info   }
        STATUS                current
        DESCRIPTION        "Spontaneous Alarm from the managed network element:
                            Cassandra cluster is down.
                            Collect log files and contact support."
        ::= { eventGroupC90 2 }

        alarmC90003 NOTIFICATION-TYPE
        OBJECTS        {        neName,
                                neType,
                                eventGroupName,                        -- 90: Storage
                                eventName,                             -- 003: SchemaValidationFailure
                                correlationId,
                                severity,
                                eventTime,
                                nodes,
                                faultyObject,
                                monitoredValue,
                                thresholdValues,
                                info   }
        STATUS                current
        DESCRIPTION        "Spontaneous Alarm from the managed network element:
                            Some needed tables are missing from the schema
                            Collect log files and contact support."
        ::= { eventGroupC90 3 }

        alarmC90004 NOTIFICATION-TYPE
        OBJECTS        {        neName,
                                neType,
                                eventGroupName,                        -- 90: Storage
                                eventName,                             -- 004: ElasticSearchClusterFailure
                                correlationId,
                                severity,
                                eventTime,
                                nodes,
                                faultyObject,
                                monitoredValue,
                                thresholdValues,
                                info   }
        STATUS                current
        DESCRIPTION        "Spontaneous Alarm from the managed network element:
                            ElasticSearch cluster is down
                            No ElasticSearch data nodes are reachable. Check network/firewall and/or bring up ES nodes"
        ::= { eventGroupC90 4 }

        alarmC90005 NOTIFICATION-TYPE
        OBJECTS        {        neName,
                                neType,
                                eventGroupName,                        -- 90: Storage
                                eventName,                             -- 005: TooManyReadFailures
                                correlationId,
                                severity,
                                eventTime,
                                nodes,
                                faultyObject,
                                monitoredValue,
                                thresholdValues,
                                info   }
        STATUS                current
        DESCRIPTION        "Spontaneous Alarm from the managed network element:
                            Too many consecutive file read errors
                            Check that the file system (XTreemFS) where files are stored is functioning properly"
        ::= { eventGroupC90 5 }

        alarmC90006 NOTIFICATION-TYPE
        OBJECTS        {        neName,
                                neType,
                                eventGroupName,                        -- 90: Storage
                                eventName,                             -- 006: TooManyWriteFailures
                                correlationId,
                                severity,
                                eventTime,
                                nodes,
                                faultyObject,
                                monitoredValue,
                                thresholdValues,
                                info   }
        STATUS                current
        DESCRIPTION        "Spontaneous Alarm from the managed network element:
                            Too many consecutive file write errors
                            Check that the file system (XTreemFS) where files are stored is functioning properly"
        ::= { eventGroupC90 6 }

        alarmC90007 NOTIFICATION-TYPE
        OBJECTS        {        neName,
                                neType,
                                eventGroupName,                        -- 90: Storage
                                eventName,                             -- 007: ElasticSearchIndexInaccessibleFailure
                                correlationId,
                                severity,
                                eventTime,
                                nodes,
                                faultyObject,
                                monitoredValue,
                                thresholdValues,
                                info   }
        STATUS                current
        DESCRIPTION        "Spontaneous Alarm from the managed network element:
                            Some indices have missing shards
                            Too many ElasticSearch data nodes are down. Bring them back up"
        ::= { eventGroupC90 7 }

        alarmC90008 NOTIFICATION-TYPE
        OBJECTS        {        neName,
                                neType,
                                eventGroupName,                        -- 90: Storage
                                eventName,                             -- 008: StorageBackupFailure
                                correlationId,
                                severity,
                                eventTime,
                                nodes,
                                faultyObject,
                                monitoredValue,
                                thresholdValues,
                                info   }
        STATUS                current
        DESCRIPTION        "Spontaneous Alarm from the managed network element:
                            Backup of storage data services (Cassandra, ElasticSearch, XtreemFS) failed
                            Check backup status screen in management. Check backup log files on the shared storage to see reason of the failure. If there are no files present on shared storage, then most probably management was not able to connect to storage"
        ::= { eventGroupC90 8 }

        alarmC90009 NOTIFICATION-TYPE
        OBJECTS        {        neName,
                                neType,
                                eventGroupName,                        -- 90: Storage
                                eventName,                             -- 009: BackupVerificationFailure
                                correlationId,
                                severity,
                                eventTime,
                                nodes,
                                faultyObject,
                                monitoredValue,
                                thresholdValues,
                                info   }
        STATUS                current
        DESCRIPTION        "Spontaneous Alarm from the managed network element:
                            Backup verification failed. Backup could be corrupted
                            Check backup verification log file"
        ::= { eventGroupC90 9 }

        alarmC90010 NOTIFICATION-TYPE
        OBJECTS        {        neName,
                                neType,
                                eventGroupName,                        -- 90: Storage
                                eventName,                             -- 010: BackupSnapshotScheduleFailure
                                correlationId,
                                severity,
                                eventTime,
                                nodes,
                                faultyObject,
                                monitoredValue,
                                thresholdValues,
                                info   }
        STATUS                current
        DESCRIPTION        "Spontaneous Alarm from the managed network element:
                            Storage snapshot backup schedule set up on Management node failed
                            Check alarm message and contact support"
        ::= { eventGroupC90 10 }

        alarmC90011 NOTIFICATION-TYPE
        OBJECTS        {        neName,
                                neType,
                                eventGroupName,                        -- 90: Storage
                                eventName,                             -- 011: BackupIncrementScheduleFailure
                                correlationId,
                                severity,
                                eventTime,
                                nodes,
                                faultyObject,
                                monitoredValue,
                                thresholdValues,
                                info   }
        STATUS                current
        DESCRIPTION        "Spontaneous Alarm from the managed network element:
                            Storage increment backup schedule set up on Management node failed
                            Check alarm message and contact support"
        ::= { eventGroupC90 11 }

        alarmC90012 NOTIFICATION-TYPE
        OBJECTS        {        neName,
                                neType,
                                eventGroupName,                        -- 90: Storage
                                eventName,                             -- 012: StorageRestoreFailure
                                correlationId,
                                severity,
                                eventTime,
                                nodes,
                                faultyObject,
                                monitoredValue,
                                thresholdValues,
                                info   }
        STATUS                current
        DESCRIPTION        "Spontaneous Alarm from the managed network element:
                            Restore of storage data services (Cassandra, ElasticSearch, XtreemFS) failed
                            Check alarm message and storage restore status screen on management - then contact support"
        ::= { eventGroupC90 12 }

        alarmC90013 NOTIFICATION-TYPE
        OBJECTS        {        neName,
                                neType,
                                eventGroupName,                        -- 90: Storage
                                eventName,                             -- 013: VirusUpdateFailure
                                correlationId,
                                severity,
                                eventTime,
                                nodes,
                                faultyObject,
                                monitoredValue,
                                thresholdValues,
                                info   }
        STATUS                current
        DESCRIPTION        "Spontaneous Alarm from the managed network element:
                            Virus Update Failed
                            Check alarm message and contact support"
        ::= { eventGroupC90 13 }

        alarmC90014 NOTIFICATION-TYPE
        OBJECTS        {        neName,
                                neType,
                                eventGroupName,                        -- 90: Storage
                                eventName,                             -- 014: VirusUpdateDisabled
                                correlationId,
                                severity,
                                eventTime,
                                nodes,
                                faultyObject,
                                monitoredValue,
                                thresholdValues,
                                info   }
        STATUS                current
        DESCRIPTION        "Spontaneous Alarm from the managed network element:
                            Automatic Virus update is disabled in zookeeper: //Mappings/virusScan/enableAutoUpdate
                            Turn on automatic virus update in zookeeper: //Mappings/virusScan/enableAutoUpdate"
        ::= { eventGroupC90 14 }

        alarmC90015 NOTIFICATION-TYPE
        OBJECTS        {        neName,
                                neType,
                                eventGroupName,                        -- 90: Storage
                                eventName,                             -- 015: BackupServerDiskSpace
                                correlationId,
                                severity,
                                eventTime,
                                nodes,
                                faultyObject,
                                monitoredValue,
                                thresholdValues,
                                info   }
        STATUS                current
        DESCRIPTION        "Spontaneous Alarm from the managed network element:
                            Backup Server disk has crossed a level indicating a need for clean up of old backups
                            Check alarm message - tell support that the backup server is about to run out of space"
        ::= { eventGroupC90 15 }

        alarmC90016 NOTIFICATION-TYPE
        OBJECTS        {        neName,
                                neType,
                                eventGroupName,                        -- 90: Storage
                                eventName,                             -- 016: ConversationScheduledExportNotComplete
                                correlationId,
                                severity,
                                eventTime,
                                nodes,
                                faultyObject,
                                monitoredValue,
                                thresholdValues,
                                info   }
        STATUS                current
        DESCRIPTION        "Spontaneous Alarm from the managed network element:
                            Not all conversations were exported successfully in a scheduled export
                            Check logs for information on which conversations did not export properly"
        ::= { eventGroupC90 16 }

        alarmC90017 NOTIFICATION-TYPE
        OBJECTS        {        neName,
                                neType,
                                eventGroupName,                        -- 90: Storage
                                eventName,                             -- 017: ConversationScheduledExportFailure
                                correlationId,
                                severity,
                                eventTime,
                                nodes,
                                faultyObject,
                                monitoredValue,
                                thresholdValues,
                                info   }
        STATUS                current
        DESCRIPTION        "Spontaneous Alarm from the managed network element:
                            A scheduled export of conversations failed to complete
                            Check alarm message for details.  Verify zookeeper parameters in //serviceConfiguration/net.ansible.nosql.export-service"
        ::= { eventGroupC90 17 }

        alarmC90018 NOTIFICATION-TYPE
        OBJECTS        {        neName,
                                neType,
                                eventGroupName,                        -- 90: Storage
                                eventName,                             -- 018: StandbyElasticSearchClusterFailure
                                correlationId,
                                severity,
                                eventTime,
                                nodes,
                                faultyObject,
                                monitoredValue,
                                thresholdValues,
                                info   }
        STATUS                current
        DESCRIPTION        "Spontaneous Alarm from the managed network element:
                            Standby ElasticSearch cluster is down
                            No Standby ElasticSearch data nodes are reachable. Check network/firewall and/or bring up ES nodes"
        ::= { eventGroupC90 18 }

        alarmC90019 NOTIFICATION-TYPE
        OBJECTS        {        neName,
                                neType,
                                eventGroupName,                        -- 90: Storage
                                eventName,                             -- 019: StandbyElasticSearchIndexInaccessibleFailure
                                correlationId,
                                severity,
                                eventTime,
                                nodes,
                                faultyObject,
                                monitoredValue,
                                thresholdValues,
                                info   }
        STATUS                current
        DESCRIPTION        "Spontaneous Alarm from the managed network element:
                            Some indices in Standby have missing shards
                            Too many Standby ElasticSearch data nodes are down. Bring them back up"
        ::= { eventGroupC90 19 }

        alarmC90020 NOTIFICATION-TYPE
        OBJECTS        {        neName,
                                neType,
                                eventGroupName,                        -- 90: Storage
                                eventName,                             -- 020: DataRetentionStartFailure
                                correlationId,
                                severity,
                                eventTime,
                                nodes,
                                faultyObject,
                                monitoredValue,
                                thresholdValues,
                                info   }
        STATUS                current
        DESCRIPTION        "Spontaneous Alarm from the managed network element:
                            DATA RETENTION TOOL failed to start
                            check DATA RETENTION logfile to check what cause the startup failure"
        ::= { eventGroupC90 20 }

        alarmC90021 NOTIFICATION-TYPE
        OBJECTS        {        neName,
                                neType,
                                eventGroupName,                        -- 90: Storage
                                eventName,                             -- 021: DataRetentionRunFailure
                                correlationId,
                                severity,
                                eventTime,
                                nodes,
                                faultyObject,
                                monitoredValue,
                                thresholdValues,
                                info   }
        STATUS                current
        DESCRIPTION        "Spontaneous Alarm from the managed network element:
                            DATA RETENTION TOOL encountered an error during a run
                            check DATA RETENTION logfile to find out what caused the error"
        ::= { eventGroupC90 21 }

        alarmC90030 NOTIFICATION-TYPE
        OBJECTS        {        neName,
                                neType,
                                eventGroupName,                        -- 90: Storage
                                eventName,                             -- 030: LongTermStatsAggregationFailure
                                correlationId,
                                severity,
                                eventTime,
                                nodes,
                                faultyObject,
                                monitoredValue,
                                thresholdValues,
                                info   }
        STATUS                current
        DESCRIPTION        "Spontaneous Alarm from the managed network element:
                            Long term stats aggregation job did not generate some required metrics
                            check stats-server.log of the node the alarm was fired from to find out what caused the error"
        ::= { eventGroupC90 30 }

        alarmC90031 NOTIFICATION-TYPE
        OBJECTS        {        neName,
                                neType,
                                eventGroupName,                        -- 90: Storage
                                eventName,                             -- 031: SecurityKey
                                correlationId,
                                severity,
                                eventTime,
                                nodes,
                                faultyObject,
                                monitoredValue,
                                thresholdValues,
                                info   }
        STATUS                current
        DESCRIPTION        "Spontaneous Alarm from the managed network element:
                            Retrieving the master keys from the external master key server failed. The data on the server can not be encrypted or decrypted!
                            Check the error description in the additional information to find out what caused the error."
        ::= { eventGroupC90 31 }

        alarmC90032 NOTIFICATION-TYPE
        OBJECTS        {        neName,
                                neType,
                                eventGroupName,                        -- 90: Storage
                                eventName,                             -- 032: SecurityKey
                                correlationId,
                                severity,
                                eventTime,
                                nodes,
                                faultyObject,
                                monitoredValue,
                                thresholdValues,
                                info   }
        STATUS                current
        DESCRIPTION        "Spontaneous Alarm from the managed network element:
                            Retrieving the working keys for data encryption from storage failed. The data on the server can not be encrypted or decrypted!
                            Check the error description in the additional information to find out what caused the error."
        ::= { eventGroupC90 32 }

        alarmC90033 NOTIFICATION-TYPE
        OBJECTS        {        neName,
                                neType,
                                eventGroupName,                        -- 90: Storage
                                eventName,                             -- 033: SecurityKey
                                correlationId,
                                severity,
                                eventTime,
                                nodes,
                                faultyObject,
                                monitoredValue,
                                thresholdValues,
                                info   }
        STATUS                current
        DESCRIPTION        "Spontaneous Alarm from the managed network element:
                            Creating a working key for data encryption failed.
                            Check the error description in the additional information to find out what caused the error."
        ::= { eventGroupC90 33 }

        alarmC90034 NOTIFICATION-TYPE
        OBJECTS        {        neName,
                                neType,
                                eventGroupName,                        -- 90: Storage
                                eventName,                             -- 034: SecurityKey
                                correlationId,
                                severity,
                                eventTime,
                                nodes,
                                faultyObject,
                                monitoredValue,
                                thresholdValues,
                                info   }
        STATUS                current
        DESCRIPTION        "Spontaneous Alarm from the managed network element:
                            Adding a master key for data encryption failed.
                            Check the error description in the additional information to find out what caused the error."
        ::= { eventGroupC90 34 }

        alarmC90035 NOTIFICATION-TYPE
        OBJECTS        {        neName,
                                neType,
                                eventGroupName,                        -- 90: Storage
                                eventName,                             -- 035: SecurityKey
                                correlationId,
                                severity,
                                eventTime,
                                nodes,
                                faultyObject,
                                monitoredValue,
                                thresholdValues,
                                info   }
        STATUS                current
        DESCRIPTION        "Spontaneous Alarm from the managed network element:
                            Adding a working key for data encryption failed.
                            Check the error description in the additional information to find out what caused the error."
        ::= { eventGroupC90 35 }

        alarmC90036 NOTIFICATION-TYPE
        OBJECTS        {        neName,
                                neType,
                                eventGroupName,                        -- 90: Storage
                                eventName,                             -- 036: Encryption
                                correlationId,
                                severity,
                                eventTime,
                                nodes,
                                faultyObject,
                                monitoredValue,
                                thresholdValues,
                                info   }
        STATUS                current
        DESCRIPTION        "Spontaneous Alarm from the managed network element:
                            Encryption of data failed.
                            Check the error description in the additional information to find out what caused the error. Check the fault object to find out what element it is related to."
        ::= { eventGroupC90 36 }

        alarmC90037 NOTIFICATION-TYPE
        OBJECTS        {        neName,
                                neType,
                                eventGroupName,                        -- 90: Storage
                                eventName,                             -- 037: Encryption
                                correlationId,
                                severity,
                                eventTime,
                                nodes,
                                faultyObject,
                                monitoredValue,
                                thresholdValues,
                                info   }
        STATUS                current
        DESCRIPTION        "Spontaneous Alarm from the managed network element:
                            Decryption of data failed.
                            Check the error description in the additional information to find out what caused the error. Check the fault object to find out what element it is related to."
        ::= { eventGroupC90 37 }

        alarmC90038 NOTIFICATION-TYPE
        OBJECTS        {        neName,
                                neType,
                                eventGroupName,                        -- 90: Storage
                                eventName,                             -- 038: TooManyWriteFailuresIntoStandbyFileStore
                                correlationId,
                                severity,
                                eventTime,
                                nodes,
                                faultyObject,
                                monitoredValue,
                                thresholdValues,
                                info   }
        STATUS                current
        DESCRIPTION        "Spontaneous Alarm from the managed network element:
                            Replication to other DC's file storage has failed several times in a row
                            Check the status of the other DC's file storage and the connectivity from this DC to that DC"
        ::= { eventGroupC90 38 }

        alarmC90039 NOTIFICATION-TYPE
        OBJECTS        {        neName,
                                neType,
                                eventGroupName,                        -- 90: Storage
                                eventName,                             -- 039: SplunkTransferFailed
                                correlationId,
                                severity,
                                eventTime,
                                nodes,
                                faultyObject,
                                monitoredValue,
                                thresholdValues,
                                info   }
        STATUS                current
        DESCRIPTION        "Spontaneous Alarm from the managed network element:
                            Failed to do splunk transfer via cron.
                            Check the connectivity to remote endpoint for splunk."
        ::= { eventGroupC90 39 }

        alarmC90040 NOTIFICATION-TYPE
        OBJECTS        {        neName,
                                neType,
                                eventGroupName,                        -- 90: Storage
                                eventName,                             -- 040: HttpClientForSwiftRestarted
                                correlationId,
                                severity,
                                eventTime,
                                nodes,
                                faultyObject,
                                monitoredValue,
                                thresholdValues,
                                info   }
        STATUS                current
        DESCRIPTION        "Spontaneous Alarm from the managed network element:
                            Http client used to communicate with Swift Object Storage is not releasing its connections and has been restarted.
                            Collect virgo trace logs in affected node. Report issue if it crosses the MAJOR threshold."
        ::= { eventGroupC90 40 }

END
