-- Avaya Aura Communication Manager MIB

-- Copyright (c) 2015 by Avaya Inc. All rights reserved.
-- Redistribution and use in source and binary forms of the software 
-- ( Software ), without modification, are
-- permitted provided that the following conditions are met:
-- (a) Redistributions of source code must retain the above copyright notice 
-- and the entire license.
-- (b) Redistributions in binary form must reproduce the above copyright notice
-- and this entire license in the
--      documentation and/or other materials provided with the distribution.
-- (c) Redistribution of the Software is solely for the purpose of managing 
--     and servicing Avaya products and solutions. 
-- (d) BY USING AND REDISTRIBUTING THE SOFTWARE, YOU, ON BEHALF OF YOURSELF AND
--      THE ENTITY FOR WHOM YOU USE THE SOFTWARE AGREE TO ALL THE TERMS AND 
--      CONDITIONS OF THIS LICENSE AND CREATE A BINDING CONTRACT BETWEEN YOU 
--      AND AVAYA INC.
--      THIS SOFTWARE IS PROVIDED BY AVAYA INC. "AS IS" AND ANY EXPRESS OR 
--	IMPLIED WARRANTIES, INCLUDING, BUT NOT LIMITED TO, THE IMPLIED 
--      WARRANTIES OF MERCHANTABILITY AND FITNESS FOR A PARTICULAR PURPOSE ARE 
--      DISCLAIMED. IN NO EVENT SHALL AVAYA INC. BE LIABLE FOR ANY DIRECT, 
--      INDIRECT, INCIDENTAL, SPECIAL, EXEMPLARY, OR CONSEQUENTIAL DAMAGES 
--	(INCLUDING, BUT NOT LIMITED TO, PROCUREMENT OF
--      SUBSTITUTE GOODS OR SERVICES; LOSS OF USE, DATA, OR PROFITS; OR BUSINESS
--      INTERRUPTION) HOWEVER CAUSED AND ON ANY THEORY OF LIABILITY, WHETHER IN 
--      CONTRACT,
--      STRICT LIABILITY, OR TORT (INCLUDING NEGLIGENCE OR OTHERWISE) ARISING 
--	IN ANY WAY OUT OF THE USE OF THIS SOFTWARE, EVEN IF ADVISED OF THE 
--	POSSIBILITY OF SUCH DAMAGE. 

-- MIB version 1.0.0

AVAYA-AURA-CM-MIB DEFINITIONS ::= BEGIN

IMPORTS
	OBJECT-TYPE, Integer32, enterprises, MODULE-IDENTITY
		FROM SNMPv2-SMI
	MODULE-COMPLIANCE, OBJECT-GROUP
		FROM SNMPv2-CONF
	SnmpAdminString
		FROM SNMP-FRAMEWORK-MIB;

avCmMib MODULE-IDENTITY
    LAST-UPDATED "201505050000Z"		-- 05 May 2015, midnight
    ORGANIZATION "Avaya Inc"
    CONTACT-INFO "	Avaya Customer Services
			postal:	Avaya, Inc
				211 Mt Airy Rd.
				Basking Ridge, NJ 07920
				USA
		 "
    DESCRIPTION	 "Avaya Aura Communication Manager MIB."

    REVISION	 "201505050000Z"
    DESCRIPTION	 "No revisions"

    ::= { avCommMgrMibs 8 }

avaya			OBJECT IDENTIFIER ::= { enterprises 6889 }
products		OBJECT IDENTIFIER ::= { avaya 1 }
mibs			OBJECT IDENTIFIER ::= { avaya 2 }
avCommMgrProd		OBJECT IDENTIFIER ::= { products 73 }
avCommMgrMibs		OBJECT IDENTIFIER ::= { mibs 73 }

avCmNotification	OBJECT IDENTIFIER ::= { avCmMib 0 }
avCmObjects		OBJECT IDENTIFIER ::= { avCmMib 1 }
avCmConformance		OBJECT IDENTIFIER ::= { avCmMib 2 }

-- Notifications are not supported in this MIB. Notifications
-- are defined in the AVAYA-AURA-CMALARM-MIB

-- DOCUMENT REFERENCE SECTION

--	REF_DOC_1:	Maintenance Commands for Avaya Aura
--			Communication Manager, Media Gateways and Servers.

--	REF_DOC_2:	Avaya Aura Communication Manager Server Alarms.

--	REF_DOC_3:	Maintenance Commands for Avaya Aura Communication
--			Manager, Branch Gateways and Servers.

--	REF_DOC_4:	Avaya Aura Communication Manager Reports.

--	REF_DOC_5:	Administering Avaya Aura Communication Manager.

--  The above reference documents can be downloaded from:

--	http://support.avaya.com/documents/

-- Each Mib Group has documentation about it embedded as comments.

-- Types of fields.

--	Single   	Field corresponds to 1 FID.
--	Multiple   	Field corresponds to multiple FIDs.

-- Types of polling:

--	Configuration
--	Fault
--	Inventory
--	Performance/Utilization
--	Security

------------------------------------------------------------------------------
-- Product Identifiers
------------------------------------------------------------------------------

avayaAuraCmSp           OBJECT IDENTIFIER ::= { avCommMgrProd 1 }
avayaAuraCmVe		OBJECT IDENTIFIER ::= { avCommMgrProd 2 }

------------------------------------------------------------------------------
-- Objects Information
------------------------------------------------------------------------------

-- *************************** avCmVersion Group ***********************

-- MIB GROUP DESCRIPTION

-- MIB Group Name:
--		avCmVersion
-- OID:
--		enterprises.6889.2.73.8.1.1
-- Description:
--		The avCmVersion MIB Group displays the output of the "swversion"
--		command. The "swversion" command displays the Servers Software
--		Version information
-- Releases Supported:
--		CM6.3.100 and greater
-- Polling Type:
--		Configuration
-- Polling Interval:
--		No more than once a day.
-- Default Caching Interval
-- 		60 seconds
-- Timeout Interval:
--		Initial Timeout should be set to 15 seconds.
-- Retry Interval:
--		Initial Retry should be set to 3.
-- Limitations:
--              Green/Low - The data collected by this MIB Group
--              is minimal and therefore has a low impact on the system.
-- Command Type:
--		1. BASH
-- Command:
--		1. swversion
-- Form/Report Name:
--		1. CM Software Version
-- Reference Document:
--		1. A detailed description of the command and form can be
--		   found in document referenced by REF_DOC_1 in the
--		   DOCUMENT REFERENCE SECTION.
-- Command Permission/User-profile:
--		1. No special permissions needed.

avCmVersion		OBJECT IDENTIFIER ::= { avCmObjects 1 }

avCmVersionOperSystem	OBJECT-TYPE
    SYNTAX	SnmpAdminString (SIZE (0..50))
    MAX-ACCESS	read-only
    STATUS	current
    DESCRIPTION
	"
	Fld OID Name:	avCmVersionOperSystem
	Fld OID:	enterprises.6889.2.73.8.1.1.1
	Fld Form/Rpt:	CM Software Version
	Fld Format:	Single Field
	Fld(s) Name:	Operating System
	Fld Descr:	An object that contains the operating system
			running on the Server.
	"
    ::= { avCmVersion 1 }

avCmVersionBuildDate	OBJECT-TYPE
    SYNTAX	SnmpAdminString (SIZE (0..25))
    MAX-ACCESS	read-only
    STATUS	current
    DESCRIPTION
	"
	Fld OID Name:	avCmVersionBuildDate
	Fld OID:	enterprises.6889.2.73.8.1.1.2
	Fld Form/Rpt:	CM Software Version
	Fld Format:	Single Field
	Fld(s) Name:	Built:
	Fld Descr:	An object containing the build date.
	"
    ::= { avCmVersion 2 }

avCmVersionLoadNumber	OBJECT-TYPE
    SYNTAX	SnmpAdminString (SIZE (0..15))
    MAX-ACCESS	read-only
    STATUS	current
    DESCRIPTION
	"
	Fld OID Name:	avCmVersionLoadNumber
	Fld  OID:	enterprises.6889.2.73.8.1.1.3
	Fld Form/Rpt:	CM Software Version
	Fld Format:	Single Field
	Fld(s) Name:	Contains:
	Fld Descr:	An object containing the current CM load number
			running on the server.
	"
    ::= { avCmVersion 3 }

avCmVersionRlsNumber	OBJECT-TYPE
    SYNTAX	SnmpAdminString (SIZE (0..25))
    MAX-ACCESS	read-only
    STATUS	current
    DESCRIPTION
	"
	Fld OID Name:	avCmVersionRlsNumber
	Fld OID:	enterprises.6889.2.73.8.1.1.4
	Fld Form/Rpt:	CM Software Version
	Fld Format:	Single Field
	Fld(s) Name:	CM Reports as:
	Fld Descr:	An object containing the current CM Release number
			running on the server.
	"
    ::= { avCmVersion 4 }

avCmVersionRlsString	OBJECT-TYPE
    SYNTAX	SnmpAdminString (SIZE (0..25))
    MAX-ACCESS	read-only
    STATUS	current
    DESCRIPTION
	"
	Fld OID Name:	avCmVersionRlsString
	Fld OID:	enterprises.6889.2.73.8.1.1.5
	Fld Form/Rpt:	CM Software Version
	Fld Format:	Single Field
	Fld(s) Name:	CM Release String:
	Fld Descr:	An object containing the CM Release string.
	"
    ::= { avCmVersion 5 }

avCmVersionVMToolsVers	OBJECT-TYPE
    SYNTAX	SnmpAdminString (SIZE (0..28))
    MAX-ACCESS	read-only
    STATUS	current
    DESCRIPTION
	"
	Fld OID Name:	avCmVersionVMToolsVers
	Fld OID:	enterprises.6889.2.73.8.1.1.6
	Fld Form/Rpt:	CM Software Version
	Fld Format:	Single Field
	Fld(s) Name:	VMwaretools version
	Fld Descr:	An object containing the VMwaretools version string
			(Only displayed on VMware platform).
	"
    ::= { avCmVersion 6 }

avCmVersionTransSaved	OBJECT-TYPE
    SYNTAX	SnmpAdminString (SIZE (0..20))
    MAX-ACCESS	read-only
    STATUS	current
    DESCRIPTION
	"
	Fld OID Name:	avCmVersionTransSaved
	Fld OID:	enterprises.6889.2.73.8.1.1.7
	Fld Form/Rpt:	CM Software Version
	Fld Format:	Single Field
	Fld(s) Name:	CM Translation Saved:
	Fld Descr:	An object containing the date and time that
			translations were last saved on the CM server.
	"
    ::= { avCmVersion 7 }

avCmVersionLicInstalled	OBJECT-TYPE
    SYNTAX	SnmpAdminString (SIZE (0..20))
    MAX-ACCESS	read-only
    STATUS	current
    DESCRIPTION
	"
	Fld OID Name:	avCmVersionLicInstalled
	Fld OID:	enterprises.6889.2.73.8.1.1.8
	Fld Form/Rpt:	CM Software Version
	Fld Format:	Single Field
	Fld(s) Name:	CM License Installed:
	Fld Descr:	An object containing the date and time that the
			license was installed on the CM server.
	"
    ::= { avCmVersion 8 }

avCmVersionMemConfig OBJECT-TYPE
    SYNTAX      SnmpAdminString (SIZE (0..20))
    MAX-ACCESS  read-only
    STATUS      current
    DESCRIPTION
        "
        Fld OID Name:   avCmVersionMemConfig
        Fld OID:        enterprises.6889.2.73.8.1.1.9
        Fld Form/Rpt:   CM Software Version
        Fld Format:     Single Field
        Fld(s) Name:    CM Memory Config: 
        Fld Descr:      An object containing the memory configuration
                        on the CM server.
        "
    ::= { avCmVersion 9 }


--   ***********	 avCmServerAlarm Group       **************

-- MIB GROUP DESCRIPTION

-- MIB Group Name:
--		avCmServerAlarm
-- OID:
--		enterprises.6889.2.73.8.1.2
-- Description:
--		The avCmServerAlarm MIB Group displays the output of the
--		"almdisplay -serv -w" command.  The "almdisplay -serv -w"
--		displays all active server alarms.
-- Releases Supported:
--		CM6.3.100 and greater
-- Polling Type:
--		Fault
-- Polling Interval:
--		No more than every 20 minutes.
-- Default Caching Interval
-- 		90 seconds
-- Timeout Interval:
--		Initial Timeout should be set to 15 seconds.
-- Retry Interval:
--		Initial Retry should be set to 3.
-- Limitations:
--		Yellow/Medium - The data collected by this MIB Group
--		may have some impact on the system.
-- Command Type:
--		1. BASH
-- Command:
--		1. almdisplay -serv -w
-- Form/Report Name:
--		1. Server Alarms
-- Reference Document:
--		1. A detailed description of the command and form can be
--		   found in REF_DOC_1 in the DOCUMENT REFERENCE SECTION.
-- Command Permission/User-profile:
--		1. No special permissions needed.

avCmServerAlarm		OBJECT IDENTIFIER ::= { avCmObjects 2 }

avCmServerAlarmTable	OBJECT-TYPE
    SYNTAX	SEQUENCE OF AvCmServerAlarmEntry
    MAX-ACCESS	not-accessible
    STATUS	current
    DESCRIPTION
	"
	Fld OID Name:	avCmServerAlarmEntry
	Fld OID:	enterprises.6889.2.73.8.1.2.1
	Fld Form/Rpt:	NA
	Fld Format:	NA
	Fld(s) Name:	NA
	Fld Descr:	A list of the avCmServerAlarms entries
	"
    ::= { avCmServerAlarm 1 }

avCmServerAlarmEntry	OBJECT-TYPE
    SYNTAX	AvCmServerAlarmEntry
    MAX-ACCESS	not-accessible
    STATUS	current
    DESCRIPTION
	"
	Fld OID Name:	avCmServerAlarmEntry
	Fld OID:	enterprises.6889.2.73.8.1.2.1.1
	Fld Form/Rpt:	NA
	Fld Format:	NA
	Fld(s) Name:	NA
	Fld Descr:	A avCmServerAlarm entry containing objects of the
			avCmServerAlarm information sent by the switch.
	"
    INDEX    { avCmServerAlarmIdx }
    ::= { avCmServerAlarmTable 1 }

AvCmServerAlarmEntry ::= SEQUENCE {
		avCmServerAlarmIdx
		    Integer32,
		avCmServerAlarmID
		    Integer32,
		avCmServerAlarmSource
		    SnmpAdminString,
		avCmServerAlarmEventID
		    SnmpAdminString,
		avCmServerAlarmLevel
		    SnmpAdminString,
		avCmServerAlarmAck
		    SnmpAdminString,
		avCmServerAlarmDate
		    SnmpAdminString,
		avCmServerAlarmDescription
		    SnmpAdminString
		}
avCmServerAlarmIdx	OBJECT-TYPE
    SYNTAX	Integer32 (0..400)
    MAX-ACCESS	not-accessible
    STATUS	current
    DESCRIPTION
	"
	Fld OID Name:	avCmServerAlarmIdx
	Fld OID:	enterprises.6889.2.73.8.1.2.1.1.1
	Fld Format:	NA
	Fld(s) Name:	NA
	Fld Descr:	An object that uniquely identifies each Server Alarm.
	"
    ::= { avCmServerAlarmEntry 1 }

avCmServerAlarmID	OBJECT-TYPE
    SYNTAX	Integer32 (0..400)
    MAX-ACCESS	read-only
    STATUS	current
    DESCRIPTION
	"
	Fld OID Name:	avCmServerAlarmID
	Fld OID:	enterprises.6889.2.73.8.1.2.1.1.2
	Fld Form/Rpt:	Server Alarms
	Fld Format:	Single
	Fld(s) Name:	ID
	Fld Descr:	An object that uniquely identifies each Server Alarm.
	"
    ::= { avCmServerAlarmEntry 2 }

avCmServerAlarmSource	OBJECT-TYPE
    SYNTAX	SnmpAdminString (SIZE (0..7))
    MAX-ACCESS	read-only
    STATUS	current
    DESCRIPTION
	"
	Fld OID Name:	avCmServerAlarmSource
	Fld OID:	enterprises.6889.2.73.8.1.2.1.1.3
	Fld Form/Rpt:	Server Alarms
	Fld Format:	Single
	Fld(s) Name:	Source
	Fld Descr:	An object that displays the abbreviated name of
			the Source which generated the alarm.
	"
    ::= { avCmServerAlarmEntry 3 }

avCmServerAlarmEventID	OBJECT-TYPE
    SYNTAX	SnmpAdminString (SIZE (0..6))
    MAX-ACCESS	read-only
    STATUS	current
    DESCRIPTION
	"
	Fld OID Name:	avCmServerAlarmEventID
	Fld OID:	enterprises.6889.2.73.8.1.2.1.1.4
	Fld Form/Rpt:	Server Alarms
	Fld Format:	Single
	Fld(s) Name:	EvtID
	Fld Descr:	An object that displays the Event ID of the alarm.
			The Event ID is a unique number that identifies an
			alarm event on a per Source basis.
	"
    ::= { avCmServerAlarmEntry 4 }

avCmServerAlarmLevel	OBJECT-TYPE
    SYNTAX	SnmpAdminString (SIZE (0..4))
    MAX-ACCESS	read-only
    STATUS	current
    DESCRIPTION
	"
	Fld OID Name:	avCmServerAlarmLevel
	Fld OID:	enterprises.6889.2.73.8.1.2.1.1.5
	Fld Form/Rpt:	Server Alarms
	Fld Format:	Single
	Fld(s) Name:	Lvl
	Fld Descr:	An object that contains the severity level of the alarm:
			Warning (WRN), Minor (MIN), or Major (MAJ).
	"
    ::= { avCmServerAlarmEntry 5 }

avCmServerAlarmAck	OBJECT-TYPE
    SYNTAX	SnmpAdminString (SIZE (0..4))
    MAX-ACCESS	read-only
    STATUS	current
    DESCRIPTION
	"
	Fld OID Name:	avCmServerAlarmAck
	Fld OID:	enterprises.6889.2.73.8.1.2.1.1.6
	Fld Form/Rpt:	Server Alarms
	Fld Format:	Single
	Fld(s) Name:	Ack
	Fld Descr:	An object that displays Y or N, indicating whether or
			not the alarm has been acknowledged by INADS.
	"
    ::= { avCmServerAlarmEntry 6 }

avCmServerAlarmDate	OBJECT-TYPE
    SYNTAX	SnmpAdminString (SIZE (0..35))
    MAX-ACCESS	read-only
    STATUS	current
    DESCRIPTION
	"
	Fld OID Name:	avCmServerAlarmDate
	Fld OID:	enterprises.6889.2.73.8.1.2.1.1.7
	Fld Form/Rpt:	Server Alarms
	Fld Format:	Single
	Fld(s) Name:	Date
	Fld Descr:	An object that contains the date the Server Alarm
			was generated.
	"
    ::= { avCmServerAlarmEntry 7 }

avCmServerAlarmDescription	OBJECT-TYPE
    SYNTAX	SnmpAdminString (SIZE (0..120))
    MAX-ACCESS	read-only
    STATUS	current
    DESCRIPTION
	"
	Fld OID Name:	avCmServerAlarmDescription
	Fld OID:	enterprises.6889.2.73.8.1.2.1.1.8
	Fld Form/Rpt:	Server Alarms
	Fld Format:	Single
	Fld(s) Name:	Description
	Fld Descr:	An object that contains a description of the
			Server Alarm.
	"
    ::= { avCmServerAlarmEntry 8 }

--   ***********	 avCmConfiguration Group       **************

-- MIB GROUP DESCRIPTION

-- MIB Group Name:
--		avCmConfiguration
-- OID:
--		enterprises.6889.2.73.8.1.3
-- Description:
--		The avCmConfiguration MIB group displays the output from the
--		"list configuration all" command. The "list configuration all"
--		generates a System Configuration report which includes
--		the type, code, suffix, and vintage of the circuit packs
--		installed in the system.
-- Releases Supported:
--		CM6.3.100 and greater
-- Polling Type:
--		Inventory and Configuration
-- Polling Interval:
--		No more than once a day or after configuration changes.
-- Default Caching Interval
-- 		60 seconds
-- Timeout Interval:
--		Initial Timeout should be set to 15 seconds.
-- Retry Interval:
--		Initial Retry should be set to 3.
-- Limitations:
--		Red/High - The data collected by this MIB Group will
--		increase as the number of boards in the system increase.
--		Consequently the data collected by this MIB Group could be
--		very large and therefore may take a very long time to collect
--		and could impact system performance.
-- Command Type:
--		1. SAT
-- Command:
--		1. list configuration all
-- Form/Report Name:
--		1. SYSTEM CONFIGURATION
-- Reference Document:
--		1. A detailed description of the command and form can be
--		   found in REF_DOC_1 in the DOCUMENT REFERENCE SECTION.
-- Command Permission/User-profile:
--		1. No special permissions needed. Default customer super-user
--		   profile can access this command.

avCmConfiguration	OBJECT IDENTIFIER ::= { avCmObjects 3 }

avCmConfigurationTable	OBJECT-TYPE
    SYNTAX	SEQUENCE OF AvCmConfigurationEntry
    MAX-ACCESS	not-accessible
    STATUS	current
    DESCRIPTION
	"
	Fld OID Name:	avCmConfigurationTable
	Fld OID:	enterprises.6889.2.73.8.1.3.1
	Fld Form/Rpt:	NA
	Fld Format:	NA
	Fld(s) Name:	NA
	Fld Descr:	A list of the avCmConfiguration entries.
	"
    ::= { avCmConfiguration 1 }

avCmConfigurationEntry	OBJECT-TYPE
    SYNTAX	AvCmConfigurationEntry
    MAX-ACCESS	not-accessible
    STATUS	current
    DESCRIPTION
	"
	Fld OID Name:	avCmConfigurationEntry
	Fld OID:	enterprises.6889.2.73.8.1.3.1.1
	Fld Form/Rpt:	NA
	Fld Format:	NA
	Fld(s) Name:	NA
	Fld Descr:	A avCmConfiguration entry containing objects of the
			avCmConfiguration information sent by the switch.
	"
    INDEX    { avCmConfigurationBoardIdx }
    ::= { avCmConfigurationTable 1 }

AvCmConfigurationEntry ::= SEQUENCE {
		avCmConfigurationBoardIdx
		    SnmpAdminString,
		avCmConfigurationBoardNumber
		    SnmpAdminString,
		avCmConfigurationBoardType
		    SnmpAdminString,
		avCmConfigurationCode
		    SnmpAdminString,
		avCmConfigurationVintage
		    SnmpAdminString,
		avCmConfigurationAssignedPorts
		    SnmpAdminString
		}

avCmConfigurationBoardIdx	OBJECT-TYPE
    SYNTAX	SnmpAdminString (SIZE (0..10))
    MAX-ACCESS	not-accessible
    STATUS	current
    DESCRIPTION
	"
	Fld OID Name:	avCmConfigurationBoardIdx
	Fld OID:	enterprises.6889.2.73.8.1.3.1.1.1
	Fld Form/Rpt:	NA
	Fld Format:	NA
	Fld(s) Name:	NA
	Fld Descr:	An object that contains that uniquely identifies
			a board based on its location in the system.  The
			syntax for the Board Number is as follows:
			cabinet(01-64):carrier(A-E):slot(01-20).
	"
    ::= { avCmConfigurationEntry 1 }

avCmConfigurationBoardNumber	OBJECT-TYPE
    SYNTAX	SnmpAdminString (SIZE (0..8))
    MAX-ACCESS	read-only
    STATUS	current
    DESCRIPTION
	"
	Fld OID Name:	avCmConfigurationBoardNumber
	Fld OID:	enterprises.6889.2.73.8.1.3.1.1.2
	Fld Form/Rpt:	SYSTEM CONFIGURATION
	Fld Format:	Single Field
	Fld(s) Name:	Board Number
	Fld Descr:	An object that contains that uniquely identifies
			a board based on its location in the system.  The
			syntax for the Board Number is as follows:
			cabinet(01-64):carrier(A-E):slot(01-20).
	"
    ::= { avCmConfigurationEntry 2 }

avCmConfigurationBoardType	OBJECT-TYPE
    SYNTAX	SnmpAdminString (SIZE (0..20))
    MAX-ACCESS	read-only
    STATUS	current
    DESCRIPTION
	"
	Fld OID Name:	avCmConfigurationBoardType
	Fld OID:	enterprises.6889.2.73.8.1.3.1.1.3
	Fld Form/Rpt:	SYSTEM CONFIGURATION
	Fld Format:	Single Field
	Fld(s) Name:	Board Type
	Fld Descr:	An object containing the type of board.
	"
    ::= { avCmConfigurationEntry 3 }

avCmConfigurationCode	OBJECT-TYPE
    SYNTAX	SnmpAdminString (SIZE (0..11))
    MAX-ACCESS	read-only
    STATUS	current
    DESCRIPTION
	"
	Fld OID Name:	avCmConfigurationCode
	Fld  OID:	enterprises.6889.2.73.8.1.3.1.1.4
	Fld Form/Rpt:	SYSTEM CONFIGURATION
	Fld Format:	Multiple Field: Board Code and Board Suffix
	Fld(s) Name:	Code
	Fld Descr:	An object that contains a the board code and suffix
			of the board.
	"
    ::= { avCmConfigurationEntry 4 }

avCmConfigurationVintage	OBJECT-TYPE
    SYNTAX	SnmpAdminString (SIZE (0..11))
    MAX-ACCESS	read-only
    STATUS	current
    DESCRIPTION
	"
	Fld OID Name:	avCmConfigurationVintage
	Fld OID:	enterprises.6889.2.73.8.1.3.1.1.5
	Fld Form/Rpt:	SYSTEM CONFIGURATION
	Fld Format:	Single Field
	Fld(s) Name:	Vintage
	Fld Descr:	An object that contains vintage of the board.
	"
    ::= { avCmConfigurationEntry 5 }

avCmConfigurationAssignedPorts	OBJECT-TYPE
    SYNTAX	SnmpAdminString (SIZE (0..193))
    MAX-ACCESS	read-only
    STATUS	current
    DESCRIPTION
	"
	Fld OID Name:	avCmConfigurationPorts
	Fld OID:	enterprises.6889.2.73.8.1.3.1.1.6
	Fld Form/Rpt:	SYSTEM CONFIGURATION
	Fld Format:	Multiple - List of ports administered on the board.
	Fld(s) Name:	Assigned Ports
	Fld Descr:	An object that specifies the assignment of the port.
			A string representing integers identical to the port
			numbers that are assigned.
			The char (u) indicates that the port is unassigned.
			The char (t) indicates that the port is assigned
			via the TTI feature.
			The char (p) indicates that the port is assigned via
			the PSA feature.
			A NULL char or string indicates that the port(s) does
			not exist or is not administered on that board.
	"
    ::= { avCmConfigurationEntry 6 }

--   ***********	 avCmServerInfo Group       **************

-- MIB GROUP DESCRIPTION

-- MIB Group Name:
--		avCmServerInfo
-- OID:
--		enterprises.6889.2.73.8.1.4
-- Description:
--		The avCmServerInfo MIB group displays the general information
--		about the system such as Server Names, Server IP Address,
--		Server State.
-- Releases Supported:
--		CM6.3.100 and greater
-- Polling Type:
--		Configuration
-- Polling Interval:
--		No more than every fifteen minutes.
-- Default Caching Interval
-- 		30 seconds
-- Timeout Interval:
--		Initial Timeout should be set to 15 seconds.
-- Retry Interval:
--		Initial Retry should be set to 3.
-- Limitations:
--		Green/Low - The data collected by this MIB Group
--		is minimal and therefore has a low impact on the system.
-- Command Type:
--		1. BASH
--		2. BASH
-- Command:
--		1. productid
--		2. server
-- Form/Report Name:
--		1. Product ID
--		2. SERVER STATUS
-- Reference Document:
--		1. A detailed description of the command and form can be
--		   found in document referenced by REF_DOC_1 in the
--		   DOCUMENT REFERENCE SECTION.
--		2. A detailed description of the command and form can be
--		   found in document referenced by REF_DOC_1 in the
--		   DOCUMENT REFERENCE SECTION.
-- Command Permission/User-profile:
--		1. No special permissions needed. Default customer super-user
--		   profile can access this command.
--		2. No special permissions needed. Default customer super-user
--		   profile can access this command.

avCmServerInfo		OBJECT IDENTIFIER ::= { avCmObjects 4 }

avCmServerInfoProductID	OBJECT-TYPE
    SYNTAX	SnmpAdminString (SIZE (0..11))
    MAX-ACCESS	read-only
    STATUS	current
    DESCRIPTION
	"
	Fld OID Name:	avCmServerInfoProductID
	Fld OID:	enterprises.6889.2.73.8.1.4.1
	Fld Form/Rpt:	Product ID
	Fld Format:	Single Field
	Fld(s) Name:	Product ID:
	Fld Descr:	An object that contains the Product ID of the server
			Command Type: BASH. Command: productid. Form/Report
			Name: Product ID.
	"
    ::= { avCmServerInfo 1 }

avCmServerInfoActiveName	OBJECT-TYPE
    SYNTAX	SnmpAdminString (SIZE (0..30))
    MAX-ACCESS	read-only
    STATUS	current
    DESCRIPTION
	"
	Fld OID Name:	avCmServerInfoActiveName
	Fld OID:	enterprises.6889.2.73.8.1.4.2
	Fld Form/Rpt:	NA
	Fld Format:	NA
	Fld(s) Name:	NA
	Fld Descr:	An object containing the name of the aliased active
			Server.
	"
    ::= { avCmServerInfo 2 }

avCmServerInfoActiveIPAddr	OBJECT-TYPE
    SYNTAX	SnmpAdminString (SIZE (0..50))
    MAX-ACCESS	read-only
    STATUS	current
    DESCRIPTION
	"
	Fld OID Name:	avCmServerInfoActiveIPAddr
	Fld OID:	enterprises.6889.2.73.8.1.4.3
	Fld Form/Rpt:	NA
	Fld Format:	NA
	Fld(s) Name:	NA
	Fld Descr:	An object containing the IP address of the aliased
			active Server.
	"
    ::= { avCmServerInfo 3 }

avCmServerInfoServer1Name	OBJECT-TYPE
    SYNTAX	SnmpAdminString (SIZE (0..30))
    MAX-ACCESS	read-only
    STATUS	current
    DESCRIPTION
	"
	Fld OID Name:	avCmServerInfoServer1Name
	Fld OID:	enterprises.6889.2.73.8.1.4.4
	Fld Form/Rpt:	NA
	Fld Format:	NA
	Fld(s) Name:	NA
	Fld Descr:	An object containing the name of Server 1.
	"
    ::= { avCmServerInfo 4 }

avCmServerInfoServer1IPAddr	OBJECT-TYPE
    SYNTAX	SnmpAdminString (SIZE (0..50))
    MAX-ACCESS	read-only
    STATUS	current
    DESCRIPTION
	"
	Fld OID Name:	avCmServerInfoServer1IPAddr
	Fld OID:	enterprises.6889.2.73.8.1.4.5
	Fld Form/Rpt:	NA
	Fld Format:	NA
	Fld(s) Name:	NA
	Fld Descr:	An object containing the IP address of Server 1.
	"
    ::= { avCmServerInfo 5 }

avCmServerInfoServer1State	OBJECT-TYPE
    SYNTAX	SnmpAdminString (SIZE (0..20))
    MAX-ACCESS	read-only
    STATUS	current
    DESCRIPTION
	"
	Fld OID Name:	avCmServerInfoServer1State
	Fld OID:	enterprises.6889.2.73.8.1.4.6
	Fld Form/Rpt:	SERVER STATUS
	Fld Format:	Single Field
	Fld(s) Name:	Mode
	Fld Descr:	An object containing the current state of Server 1.
			Valid responses are 'active', 'standby', 'dormant',
			and 'busyout'.
	"
    ::= { avCmServerInfo 6 }

avCmServerInfoServer2Name	OBJECT-TYPE
    SYNTAX	SnmpAdminString (SIZE (0..30))
    MAX-ACCESS	read-only
    STATUS	current
    DESCRIPTION
	"
	Fld OID Name:	avCmServerInfoServer2Name
	Fld OID:	enterprises.6889.2.73.8.1.4.7
	Fld Form/Rpt:	NA
	Fld Format:	NA
	Fld(s) Name:	NA
	Fld Descr:	An object containing the name of Server 2.
	"
    ::= { avCmServerInfo 7 }

avCmServerInfoServer2IPAddr	OBJECT-TYPE
    SYNTAX	SnmpAdminString (SIZE (0..50))
    MAX-ACCESS	read-only
    STATUS	current
    DESCRIPTION
	"
	Fld OID Name:	avCmServerInfoServer2IPAddr
	Fld OID:	enterprises.6889.2.73.8.1.4.8
	Fld Form/Rpt:	NA
	Fld Format:	NA
	Fld(s) Name:	NA
	Fld Descr:	An object containing the IP address of Server 2.
	"
    ::= { avCmServerInfo 8 }

avCmServerInfoServer2State	OBJECT-TYPE
    SYNTAX	SnmpAdminString (SIZE (0..20))
    MAX-ACCESS	read-only
    STATUS	current
    DESCRIPTION
	"
	Fld OID Name:	avCmServerInfoServer2State
	Fld OID:	enterprises.6889.2.73.8.1.4.9
	Fld Form/Rpt:	SERVER STATUS
	Fld Format:	Single Field
	Fld(s) Name:	Mode
	Fld Descr:	An object containing the current state of Server 2.
			Valid responses are 'active', 'standby', 'dormant',
			and 'busyout'.
	"
    ::= { avCmServerInfo 9 }

avCmServerInfoServerType	OBJECT-TYPE
    SYNTAX	SnmpAdminString (SIZE (0..20))
    MAX-ACCESS	read-only
    STATUS	current
    DESCRIPTION
	"
	Fld OID Name:	avCmServerInfoServerType
	Fld OID:	enterprises.6889.2.73.8.1.4.10
	Fld Form/Rpt:	ecs.conf
	Fld Format:	Single Field
	Fld(s) Name:	ServerType
	Fld Descr:	An object containing the hardware server type.
	"
    ::= { avCmServerInfo 10 }

avCmServerInfoSurvRemoteConfig	OBJECT-TYPE
    SYNTAX	SnmpAdminString (SIZE (0..20))
    MAX-ACCESS	read-only
    STATUS	current
    DESCRIPTION
	"
	Fld OID Name:	avCmServerInfoSurvRemoteConfig
	Fld OID:	enterprises.6889.2.73.8.1.4.11
	Fld Form/Rpt:	ecs.conf
	Fld Format:	Single Field
	Fld(s) Name:	lspconfig
	Fld Descr:	An object indicating whether the switch is configured
			as a survivable remote server/LSP. Possible values are
			'icc', 'lsp' and 'unset'.
	"
    ::= { avCmServerInfo 11 }

avCmServerInfoSurvCoreConfig	OBJECT-TYPE
    SYNTAX	SnmpAdminString (SIZE (0..20))
    MAX-ACCESS	read-only
    STATUS	current
    DESCRIPTION
	"
	Fld OID Name:	avCmServerInfoSurvCoreConfig
	Fld OID:	enterprises.6889.2.73.8.1.4.12
	Fld Form/Rpt:	ecs.conf
	Fld Format:	Single Field
	Fld(s) Name:	essconfig
	Fld Descr:	An object indicating whether the switch is configured
			as a survivable core server/ESS. Possible values are
			'ess', 'main' and 'unset'.
	"
    ::= { avCmServerInfo 12 }

avCmServerInfoStdbyRefresh	OBJECT-TYPE
    SYNTAX	SnmpAdminString (SIZE (0..10))
    MAX-ACCESS	read-only
    STATUS	current
    DESCRIPTION
	"
	Fld OID Name:	avCmServerInfoStdbyRefresh
	Fld OID:	enterprises.6889.2.73.8.1.4.13
	Fld Form/Rpt:	STATUS SERVER
	Fld Format:	Single Field
	Fld(s) Name:	Mode
	Fld Descr:	An object displaying whether the Standby Server is
			refreshed or not and is it ready to go for an
			interchange. Possible values are 'yes' and 'no'.
	"
    ::= { avCmServerInfo 13 }

--   ***********	 avCmAlarms Group       **************

-- MIB GROUP DESCRIPTION

-- MIB Group Name:
--		avCmAlarms
-- OID:
--		enterprises.6889.2.73.8.1.5
-- Description:
--		The avCmAlarms MIB group displays the output of CMs Active
--		Alarm Report.
-- Releases Supported:
--		CM6.3.100 and greater
-- Polling Type:
--		Fault
-- Polling Interval:
--		No more than every 1 hour.
-- Default Caching Interval
-- 		300 seconds
-- Timeout Interval:
--		Initial Timeout should be set to 15 seconds.
-- Retry Interval:
--		Initial Retry should be set to 3.
-- Limitations:
--		Red/High - The data collected by this MIB Group will
--		increase as the number of alarms on the system increase.
--		Consequently the data collected by this MIB Group could be
--		very large and therefore may take a very long time to collect
--		and could impact system performance.
-- Command Type:
--		1. SAT
-- Command:
--		1. display alarms
-- Form/Report Name:
--		1. ALARM REPORT
-- Reference Document:
--		1. A detailed description of the command and form can be
--		   found in REF_DOC_1 in the DOCUMENT REFERENCE SECTION.
-- Command Permission/User-profile:
--		1. No special permissions needed. Default customer super-user
--		   profile can access this command.

avCmAlarms		OBJECT IDENTIFIER ::= { avCmObjects 5 }

avCmAlarmsTable		OBJECT-TYPE
    SYNTAX	SEQUENCE OF AvCmAlarmsEntry
    MAX-ACCESS	not-accessible
    STATUS	current
    DESCRIPTION
	"
	Fld OID Name:	avCmAlarmsTable
	Fld OID:	enterprises.6889.2.73.8.1.5.1
	Fld Form/Rpt:	NA
	Fld Format:	NA
	Fld(s) Name:	NA
	Fld Descr:	A list of the avCmAlarms entries
	"
    ::= { avCmAlarms 1 }

avCmAlarmsEntry		OBJECT-TYPE
    SYNTAX	AvCmAlarmsEntry
    MAX-ACCESS	not-accessible
    STATUS	current
    DESCRIPTION
	"
	Fld OID Name:	avCmAlarmsEntry
	Fld OID:	enterprises.6889.2.73.8.1.5.1.1
	Fld Form/Rpt:	NA
	Fld Format:	NA
	Fld(s) Name:	NA
	Fld Descr:	An avCmAlarms entry containing objects of the
			avCmAlarms information sent by the switch
	"
    INDEX    { avCmAlarmsPortIdx, avCmAlarmsMtceNameIdx, avCmAlarmsIndex }
    ::= { avCmAlarmsTable 1 }

AvCmAlarmsEntry ::= SEQUENCE {
		avCmAlarmsPortIdx
		    SnmpAdminString,
		avCmAlarmsMtceNameIdx
		    SnmpAdminString,
		avCmAlarmsIndex
		    Integer32,
		avCmAlarmsPort
		    SnmpAdminString,
		avCmAlarmsMtceName
		    SnmpAdminString,
		avCmAlarmsOnBrd
		    SnmpAdminString,
		avCmAlarmsAltName
		    SnmpAdminString,
		avCmAlarmsAlarmType
		    SnmpAdminString,
		avCmAlarmsSvcState
		    SnmpAdminString,
		avCmAlarmsAck
		    SnmpAdminString,
		avCmAlarmsDateAlarmed
		    SnmpAdminString,
		avCmAlarmsDateResolved
		    SnmpAdminString
		}

avCmAlarmsPortIdx	OBJECT-TYPE
    SYNTAX	SnmpAdminString (SIZE (0..10))
    MAX-ACCESS	not-accessible
    STATUS	current
    DESCRIPTION
	"
	Fld OID Name:	avCmAlarmsPortIdx
	Fld OID:	enterprises.6889.2.73.8.1.5.1.1.1
	Fld Form/Rpt:	NA
	Fld Format:	NA
	Fld(s) Name:	NA
	Fld Descr:	An object containing an index that uniquely
			identifies a port based on its location in the
			system.  The syntax for the Port Number is as
			follows:  cabinet(01-64):
			carrier(A-E):slot(01-20):port(01-64).
	"
    ::= { avCmAlarmsEntry 1 }

avCmAlarmsMtceNameIdx	OBJECT-TYPE
    SYNTAX	SnmpAdminString (SIZE (0..9))
    MAX-ACCESS	not-accessible
    STATUS	current
    DESCRIPTION
	"
	Fld OID Name:	avCmAlarmsMtceNameIdx
	Fld OID:	enterprises.6889.2.73.8.1.5.1.1.2
	Fld Form/Rpt:	NA
	Fld Format:	NA
	Fld(s) Name:	NA
	Fld Descr:	An object containing an index that uniquely
			identifies a Maintenance Object Name.
	"
    ::= { avCmAlarmsEntry 2 }

avCmAlarmsIndex		OBJECT-TYPE
    SYNTAX	Integer32 (0..6500)
    MAX-ACCESS	not-accessible
    STATUS	current
    DESCRIPTION
	"
	Fld OID Name:	avCmAlarmsIndex
	Fld OID:	enterprises.6889.2.73.8.1.5.1.1.3
	Fld Form/Rpt:	NA
	Fld Format:	NA
	Fld(s) Name:	NA
	Fld Descr:	An Integer32 object containing an index that numbers
			the alarm entry for the avCmAlarmsPortIdx.  This
			object along with avCmAlarmsPortIdx serves as the
			instance identifier for avCmAlarmsEntry.
	"
    ::= { avCmAlarmsEntry 3 }

avCmAlarmsPort		OBJECT-TYPE
    SYNTAX	SnmpAdminString (SIZE (0..10))
    MAX-ACCESS	read-only
    STATUS	current
    DESCRIPTION
	"
	Fld OID Name:	avCmAlarmsPort
	Fld OID:	enterprises.6889.2.73.8.1.5.1.1.4
	Fld Form/Rpt:	ALARM REPORT
	Fld Format:	Single Field
	Fld(s) Name:	Port
	Fld Descr:	An object that uniquely identifies a port based
			on its location in the system.  The syntax for the
			Port Number is as follows:  cabinet(01-64):
			carrier(A-E):slot(01-20):port(01-64).
	 "
    ::= { avCmAlarmsEntry 4}

avCmAlarmsMtceName	OBJECT-TYPE
    SYNTAX	SnmpAdminString (SIZE (0..9))
    MAX-ACCESS	read-only
    STATUS	current
    DESCRIPTION
	"
	Fld OID Name:	avCmAlarmsMtceName
	Fld OID:	enterprises.6889.2.73.8.1.5.1.1.5
	Fld Form/Rpt:	ALARM REPORT
	Fld Format:	Single Field
	Fld(s) Name:	Mtce Name
	Fld Descr:	An object that contains the Maintenance Object Name.
	"
    ::= { avCmAlarmsEntry 5 }

avCmAlarmsOnBrd		OBJECT-TYPE
    SYNTAX	SnmpAdminString (SIZE (0..2))
    MAX-ACCESS	read-only
    STATUS	current
    DESCRIPTION
	"
	Fld OID Name:	avCmAlarmsOnBrd
	Fld OID:	enterprises.6889.2.73.8.1.5.1.1.6
	Fld Form/Rpt:	ALARM REPORT
	Fld Format:	Single Field
	Fld(s) Name:	On Brd?
	Fld Descr:	An object that contains the whether or not the alarm
			is on or off board.
	"
    ::= { avCmAlarmsEntry 6 }

avCmAlarmsAltName	OBJECT-TYPE
    SYNTAX	SnmpAdminString (SIZE (0..14))
    MAX-ACCESS	read-only
    STATUS	current
    DESCRIPTION
	"
	Fld OID Name:	avCmAlarmsAltName
	Fld OID:	enterprises.6889.2.73.8.1.5.1.1.7
	Fld Form/Rpt:	ALARM REPORT
	Fld Format:	Single Field
	Fld(s) Name:	Alt Name
	Fld Descr:	An object that contains the alternate name of
			the alarmed object.  Alternate names can consist of
			extension numbers, trunk group numbers or other
			identifying data.
	"
    ::= { avCmAlarmsEntry 7 }

avCmAlarmsAlarmType	OBJECT-TYPE
    SYNTAX	SnmpAdminString (SIZE (0..8))
    MAX-ACCESS	read-only
    STATUS	current
    DESCRIPTION
	"
	Fld OID Name:	avCmAlarmsAlarmType
	Fld OID:	enterprises.6889.2.73.8.1.5.1.1.8
	Fld Form/Rpt:	ALARM REPORT
	Fld Format:	Single Field
	Fld(s) Name:	Alarm Type
	Fld Descr:	An object that contains the alarm severity
	"
    ::= { avCmAlarmsEntry 8 }

avCmAlarmsSvcState	OBJECT-TYPE
    SYNTAX	SnmpAdminString (SIZE (0..4))
    MAX-ACCESS	read-only
    STATUS	current
    DESCRIPTION
	"
	Fld OID Name:	avCmAlarmsSvcState
	Fld OID:	enterprises.6889.2.73.8.1.5.1.1.9
	Fld Form/Rpt:	ALARM REPORT
	Fld Format:	Single Field
	Fld(s) Name:	Svc State
	Fld Descr:	An object that contains the service state of the
			alarmed object.
	"
    ::= { avCmAlarmsEntry 9 }

avCmAlarmsAck		OBJECT-TYPE
    SYNTAX	SnmpAdminString (SIZE (0..18))
    MAX-ACCESS	read-only
    STATUS	current
    DESCRIPTION
	"
	Fld OID Name:	avCmAlarmsAck
	Fld OID:	enterprises.6889.2.73.8.1.5.1.1.10
	Fld Form/Rpt:	ALARM REPORT
	Fld Format:	Multiple - Ack 1: y/n Ack 2: y/n/blank
	Fld(s) Name:	Ack 1 2
	Fld Descr:	An object that contains whether or not the alarm
			has been acknowledged by the alarm receiver.
	"
    ::= { avCmAlarmsEntry 10 }

avCmAlarmsDateAlarmed	OBJECT-TYPE
    SYNTAX	SnmpAdminString (SIZE (0..12))
    MAX-ACCESS	read-only
    STATUS	current
    DESCRIPTION
	"
	Fld OID Name:	avCmAlarmsDateAlarmed
	Fld OID:	enterprises.6889.2.73.8.1.5.1.1.11
	Fld Form/Rpt:	ALARM REPORT
	Fld Format:	Single Field
	Fld(s) Name:	Date Alarmed
	Fld Descr:	An object that contains the month/day/hour:minute
			the alarm was generated.
	"
    ::= { avCmAlarmsEntry 11 }

avCmAlarmsDateResolved	OBJECT-TYPE
    SYNTAX	SnmpAdminString (SIZE (0..12))
    MAX-ACCESS	read-only
    STATUS	current
    DESCRIPTION
	"
	Fld OID Name:	avCmAlarmsDateResolved
	Fld OID:	enterprises.6889.2.73.8.1.5.1.1.12
	Fld Form/Rpt:	ALARM REPORT
	Fld Format:	Single Field
	Fld(s) Name:	Date Resolved
	Fld Descr:	An object that contains the month/day/hour:minute
			the alarm was Resolved.
	"
    ::= { avCmAlarmsEntry 12 }

--   ***********	     avCmErrors Group       **************

-- MIB Group Name:
--		avCmErrors
-- OID:
--		enterprises.6889.2.73.8.1.6
-- Description:
--		The avCmErrors MIB group displays the output of CMs error log.
-- Releases Supported:
--		CM6.3.100 and greater
-- Polling Type:
--		Fault
-- Polling Interval:
--		No more than every 1 hour.
-- Default Caching Interval
-- 		300 seconds
-- Timeout Interval:
--		Initial Timeout should be set to 15 seconds.
-- Retry Interval:
--		Initial Retry should be set to 3.
-- Limitations:
--		Red/High - The data collected by this MIB Group will
--		increase as the number of alarms on the system increase.
--		Consequently the data collected by this MIB Group could be
--		very large and therefore may take a very long time to collect
--		and could impact system performance.
-- Command Type:
--		1. SAT
-- Command:
--		1. display errors
-- Form/Report Name:
--		1. ERROR REPORT
-- Reference Document:
--		1. A detailed description of the command and form can be
--		   found in REF_DOC_1 in the DOCUMENT REFERENCE SECTION.
-- Command Permission/User-profile:
--		1. No special permissions needed. Default customer super-user
--		   profile can access this command.

avCmErrors		OBJECT IDENTIFIER ::= { avCmObjects 6 }

avCmErrorsTable		OBJECT-TYPE
    SYNTAX	SEQUENCE OF AvCmErrorsEntry
    MAX-ACCESS	not-accessible
    STATUS	current
    DESCRIPTION
	"
	Fld OID Name:	avCmErrorsTable
	Fld OID:	enterprises.6889.2.73.8.1.6.1
	Fld Form/Rpt:	NA
	Fld Format:	NA
	Fld(s) Name:	NA
	Fld Descr:	A list of the avCmErrors entries.
	"
    ::= { avCmErrors 1 }

avCmErrorsEntry		OBJECT-TYPE
    SYNTAX	AvCmErrorsEntry
    MAX-ACCESS	not-accessible
    STATUS	current
    DESCRIPTION
	"
	Fld OID Name:	avCmErrorsEntry
	Fld OID:	enterprises.6889.2.73.8.1.6.1.1
	Fld Form/Rpt:	NA
	Fld Format:	NA
	Fld(s) Name:	NA
	Fld Descr:	a avCmErrors entry containing objects of the
			avCmErrors information sent by the switch.
	"
    INDEX    { avCmErrorsPortIdx, avCmErrorsMtceNameIdx, avCmErrorsIndex }
    ::= { avCmErrorsTable 1 }

AvCmErrorsEntry ::= SEQUENCE {
		avCmErrorsPortIdx
		    SnmpAdminString,
		avCmErrorsMtceNameIdx
		    SnmpAdminString,
		avCmErrorsIndex
		    Integer32,
		avCmErrorsPort
		    SnmpAdminString,
		avCmErrorsMtceName
		    SnmpAdminString,
		avCmErrorsAltName
		    SnmpAdminString,
		avCmErrorsErrType
		    SnmpAdminString,
		avCmErrorsAuxData
		    SnmpAdminString,
		avCmErrorsFirstLastOccurrence
		    SnmpAdminString,
		avCmErrorsErrCnt
		    SnmpAdminString,
		avCmErrorsErrRt
		    SnmpAdminString,
		avCmErrorsRtHr
		    SnmpAdminString,
		avCmErrorsAlSt
		    SnmpAdminString,
		avCmErrorsAc
		    SnmpAdminString
		}

avCmErrorsPortIdx	OBJECT-TYPE
    SYNTAX	SnmpAdminString (SIZE (0..10))
    MAX-ACCESS	not-accessible
    STATUS	current
    DESCRIPTION
	"
	Fld OID Name:	avCmErrorsPortIdx
	Fld OID:	enterprises.6889.2.73.8.1.6.1.1.1
	Fld Form/Rpt:	NA
	Fld Format:	NA
	Fld(s) Name:	NA
	Fld Descr:	An object that is an index that uniquely identifies
			a port based on its location in the system.  The
			syntax for the Port Number is as follows:
			cabinet(01-64):carrier(A-E):slot(01-20):port(01-64).
	"
    ::= { avCmErrorsEntry 1 }

avCmErrorsMtceNameIdx	OBJECT-TYPE
    SYNTAX	SnmpAdminString (SIZE (0..9))
    MAX-ACCESS	not-accessible
    STATUS	current
    DESCRIPTION
	"
	Fld OID Name:	avCmErrorsMtceNameIdx
	Fld OID:	enterprises.6889.2.73.8.1.6.1.1.2
	Fld Form/Rpt:	NA
	Fld Format:	NA
	Fld(s) Name:	NA
	Fld Descr:	An object containing an index that uniquely
			identifies a Maintenance Object Name.
	"
    ::= { avCmErrorsEntry 2 }

avCmErrorsIndex		OBJECT-TYPE
    SYNTAX	Integer32 (0..6500)
    MAX-ACCESS	not-accessible
    STATUS	current
    DESCRIPTION
	"
	Fld OID Name:	avCmErrorsIndex
	Fld OID:	enterprises.6889.2.73.8.1.6.1.1.3
	Fld Format:	NA
	Fld(s) Name:	NA
	Fld Form/Rpt:	NA
	Fld Descr:	An object containing an index numbering into the error
			table for the board specified in avCmErrorsPortIdx.
			This object along with avCmErrorsPortIdx will serve
			as the instance identifier for the port entry.
	"
    ::= { avCmErrorsEntry 3 }

avCmErrorsPort		OBJECT-TYPE
    SYNTAX	SnmpAdminString (SIZE (0..10))
    MAX-ACCESS	read-only
    STATUS	current
    DESCRIPTION
	"
	Fld OID Name:	avCmErrorsPort
	Fld OID:	enterprises.6889.2.73.8.1.6.1.1.4
	Fld Form/Rpt:	ERROR REPORT
	Fld Format:	Single
	Fld(s) Name:	Port
	Fld Descr:	An object that uniquely identifies a port based
			on its location in the system.  The syntax for the
			Port Number is as follows:  cabinet(01-64):
			carrier(A-E):slot(01-20):port(01-64).
	"
    ::= { avCmErrorsEntry 4 }

avCmErrorsMtceName	OBJECT-TYPE
    SYNTAX	SnmpAdminString (SIZE (0..9))
    MAX-ACCESS	read-only
    STATUS	current
    DESCRIPTION
	"
	Fld OID Name:	avCmErrorsMtceName
	Fld OID:	enterprises.6889.2.73.8.1.6.1.1.5
	Fld Form/Rpt:	ERROR REPORT
	Fld Format:	Single
	Fld(s) Name:	Mtce Name
	Fld Descr:	An object that contains the Maintenance Object Name.
	"
    ::= { avCmErrorsEntry 5 }

avCmErrorsAltName	OBJECT-TYPE
    SYNTAX	SnmpAdminString (SIZE (0..14))
    MAX-ACCESS	read-only
    STATUS	current
    DESCRIPTION
	"
	Fld OID Name:	avCmErrorsAltName
	Fld OID:	enterprises.6889.2.73.8.1.6.1.1.6
	Fld Form/Rpt:	ERROR REPORT
	Fld Format:	Single
	Fld(s) Name:	Alt Name
	Fld Descr:	An object that contains the alternate name of
			the object with an error. Alternate names can consist of
			extension numbers, trunk group numbers or other
			identifying data.
	"
    ::= { avCmErrorsEntry 6 }

avCmErrorsErrType	OBJECT-TYPE
    SYNTAX	SnmpAdminString (SIZE (0..6))
    MAX-ACCESS	read-only
    STATUS	current
    DESCRIPTION
	"
	Fld OID Name:	avCmErrorsErrType
	Fld OID:	enterprises.6889.2.73.8.1.6.1.1.7
	Fld Form/Rpt:	ERROR REPORT
	Fld Format:	Single
	Fld(s) Name:	Err Type
	Fld Descr:	An object that contains the specific error type
			in numeric code used to determine the type of error.
	"
    ::= { avCmErrorsEntry 7 }

avCmErrorsAuxData	OBJECT-TYPE
    SYNTAX	SnmpAdminString (SIZE (0..6))
    MAX-ACCESS	read-only
    STATUS	current
    DESCRIPTION
	"
	Fld OID Name:	avCmErrorsAuxData
	Fld OID:	enterprises.6889.2.73.8.1.6.1.1.8
	Fld Form/Rpt:	ERROR REPORT
	Fld Format:	Single
	Fld(s) Name:	Aux Data
	Fld Descr:	An object that contains the numeric auxiliary code
			used with the errType to troubleshoot a problem.
	"
    ::= { avCmErrorsEntry 8 }

avCmErrorsFirstLastOccurrence	OBJECT-TYPE
    SYNTAX	SnmpAdminString (SIZE (0..37))
    MAX-ACCESS	read-only
    STATUS	current
    DESCRIPTION
	"
	Fld OID Name:	avCmErrorsMtceName
	Fld OID:	enterprises.6889.2.73.8.1.6.1.1.9
	Fld Form/Rpt:	ERROR REPORT
	Fld Format:	Multiple - in the format:
			  'First: month/day/hour:min Last: month/day/hour:min'
	Fld(s) Name:	First/Last Occurrence
	Fld Descr:	An object that contains the mon/day/hour:min the alarm
			first last occurred.
	"
    ::= { avCmErrorsEntry 9 }

avCmErrorsErrCnt	OBJECT-TYPE
    SYNTAX	SnmpAdminString (SIZE (0..4))
    MAX-ACCESS	read-only
    STATUS	current
    DESCRIPTION
	"
	Fld OID Name:	avCmErrorsErrCnt
	Fld OID:	enterprises.6889.2.73.8.1.6.1.1.10
	Fld Form/Rpt:	ERROR REPORT
	Fld Format:	Single
	Fld(s) Name:	Err Cnt
	Fld Descr:	An object that contains a numeric count of the
			occurrence of error.
	"
    ::= { avCmErrorsEntry 10 }

avCmErrorsErrRt		OBJECT-TYPE
    SYNTAX	SnmpAdminString (SIZE (0..4))
    MAX-ACCESS	read-only
    STATUS	current
    DESCRIPTION
	"
	Fld OID Name:	avCmErrorsErrRt
	Fld OID:	enterprises.6889.2.73.8.1.6.1.1.11
	Fld Form/Rpt:	ERROR REPORT
	Fld Format:	Single
	Fld(s) Name:	Err Rt
	Fld Descr:	An object that contains the error rate occurrences
			of the error hour.
	"
	::= { avCmErrorsEntry 11 }

avCmErrorsRtHr		OBJECT-TYPE
    SYNTAX	SnmpAdminString (SIZE (0..4))
    MAX-ACCESS	read-only
    STATUS	current
    DESCRIPTION
	"
	Fld OID Name:	avCmErrorsRtHr
	Fld OID:	enterprises.6889.2.73.8.1.6.1.1.12
	Fld Form/Rpt:	ERROR REPORT
	Fld Format:	Single
	Fld(s) Name:	Rt Hr
	Fld Descr:	A DisplayString Object containing the error rate
			per hour.
	"
	::= { avCmErrorsEntry 12 }

avCmErrorsAlSt		OBJECT-TYPE
    SYNTAX	SnmpAdminString (SIZE (0..2))
    MAX-ACCESS	read-only
    STATUS	current
    DESCRIPTION
	"
	Fld OID Name:	avCmErrorsAlSt
	Fld OID:	enterprises.6889.2.73.8.1.6.1.1.13
	Fld Form/Rpt:	ERROR REPORT
	Fld Format:	Single
	Fld(s) Name:	Alm St
	Fld Descr:	An object that contains the alarm state of the error.
	"
    ::= { avCmErrorsEntry 13 }

avCmErrorsAc		OBJECT-TYPE
    SYNTAX	SnmpAdminString (SIZE (0..2))
    MAX-ACCESS	read-only
    STATUS	current
    DESCRIPTION
	"
	Fld OID Name:	avCmErrorsMtceName
	Fld OID:	enterprises.6889.2.73.8.1.6.1.1.14
	Fld Form/Rpt:	ERROR REPORT
	Fld Format:	Single
	Fld(s) Name:	Ac
	Fld Descr:	An object that contains ...
	"
    ::= { avCmErrorsEntry 14 }

--   ***********	  avCmListStation Group       **************

-- MIB Group Name:
--		avCmListStation
-- OID:
--		enterprises.6889.2.73.8.1.7
-- Description:
--		The avCmListStation MIB group displays the output of the
--		list station command.
-- Releases Supported:
--		CM6.3.100 and greater
-- Polling Type:
--		Inventory and Performance/Utilization 
-- Polling Interval:
--		No more than once a day or when stations are added.
-- Default Caching Interval
-- 		300 seconds
-- Timeout Interval:
--		Initial Timeout should be set to 15 seconds.
-- Retry Interval:
--		Initial Retry should be set to 3.
-- Limitations:
--		Red/High - The data collected by this MIB Group will
--		increase as the number of stations on the system increase.
--		Consequently the data collected by this MIB Group could be
--		very large and therefore may take a very long time to collect
--		and could impact system performance.
-- Command Type:
--		1. SAT
-- Command:
--		1. list station
-- Form/Report Name:
--		1. STATIONS
-- Reference Document:
--		1. A detailed description of the command and form can be
--		   found in REF_DOC_3 in the DOCUMENT REFERENCE SECTION.
-- Command Permission/User-profile:
--		1. No special permissions needed. Default customer super-user
--		   profile can access this command.

avCmListStation		OBJECT IDENTIFIER ::= { avCmObjects 7 }

avCmListStationTable	OBJECT-TYPE
    SYNTAX	SEQUENCE OF AvCmListStationEntry
    MAX-ACCESS	not-accessible
    STATUS	current
    DESCRIPTION
	"
	Fld OID Name:	avCmListStationEntry
	Fld OID:	enterprises.6889.2.73.8.1.7.1
	Fld Form/Rpt:	NA
	Fld Format:	NA
	Fld(s) Name:	NA
	Fld Descr:	A list of the avCmServerAlarms entries
	"
    ::= { avCmListStation 1 }

avCmListStationEntry	OBJECT-TYPE
    SYNTAX	AvCmListStationEntry
    MAX-ACCESS	not-accessible
    STATUS	current
    DESCRIPTION
	"
	Fld OID Name:	avCmListStationEntry
	Fld OID:	enterprises.6889.2.73.8.1.7.1.1
	Fld Format:	NA
	Fld Form/Rpt:	NA
	Fld(s) Name:	NA
	Fld Descr:	A avCmServerAlarm entry containing objects of the
			avCmServerAlarm information sent by the switch.
	"
    INDEX    { avCmListStationIdx }
    ::= { avCmListStationTable 1 }

AvCmListStationEntry ::= SEQUENCE {
		avCmListStationIdx
		    SnmpAdminString,
		avCmListStationExtension
		    SnmpAdminString,
		avCmListStationType
		    SnmpAdminString,
		avCmListStationName
		    SnmpAdminString,
		avCmListStationPort
		    SnmpAdminString
		}

avCmListStationIdx	OBJECT-TYPE
    SYNTAX	SnmpAdminString (SIZE (0..17))
    MAX-ACCESS	not-accessible
    STATUS	current
    DESCRIPTION
	"
	Fld OID Name:	avCmServerStationIdx
	Fld OID:	enterprises.6889.2.73.8.1.7.1.1.1
	Fld Form/Rpt:	NA
	Fld Format:	NA
	Fld(s) Name:	NA
	Fld Descr:	An object containing an index that uniquely identifies
			an administered station.
	"
    ::= { avCmListStationEntry 1 }

avCmListStationExtension	OBJECT-TYPE
    SYNTAX	SnmpAdminString (SIZE (0..17))
    MAX-ACCESS	read-only
    STATUS	current
    DESCRIPTION
	"
	Fld OID Name:	avCmServerExtension
	Fld OID:	enterprises.6889.2.73.8.1.7.1.1.2
	Fld Form/Rpt:	STATIONS
	Fld Format:	Single
	Fld(s) Name:	Ext
	Fld Descr:	An object containing the stations extension.
	"
    ::= { avCmListStationEntry 2 }

avCmListStationType	OBJECT-TYPE
    SYNTAX	SnmpAdminString (SIZE (0..10))
    MAX-ACCESS	read-only
    STATUS	current
    DESCRIPTION
	"
	Fld OID Name:	avCmStationType
	Fld OID:	enterprises.6889.2.73.8.1.7.1.1.3
	Fld Form/Rpt:	STATIONS
	Fld Format:	Single
	Fld(s) Name:	Type
	Fld Descr:	An object containing the station type.
	"
    ::= { avCmListStationEntry 3 }

avCmListStationName	OBJECT-TYPE
    SYNTAX	SnmpAdminString (SIZE (0..28))
    MAX-ACCESS	read-only
    STATUS	current
    DESCRIPTION
	"
	Fld OID Name:	avCmStationName
	Fld OID:	enterprises.6889.2.73.8.1.7.1.1.4
	Fld Form/Rpt:	STATIONS
	Fld Format:	Single
	Fld(s) Name:	ID
	Fld Descr:	An object containing the name assigned to the station.
	"
    ::= { avCmListStationEntry 4 }

avCmListStationPort	OBJECT-TYPE
    SYNTAX	SnmpAdminString (SIZE (0..8))
    MAX-ACCESS	read-only
    STATUS	current
    DESCRIPTION
	"
	Fld OID Name:	avCmStationPort
	Fld OID:	enterprises.6889.2.73.8.1.7.1.1.5
	Fld Form/Rpt:	STATIONS
	Fld Format:	Single
	Fld(s) Name:	Port
	Fld Descr:	An object containing the stations port assignment.
	"
    ::= { avCmListStationEntry 5 }

--   ***********	  avCmListStationRange Group       **************

-- MIB Group Name:
--		avCmListStationRange
-- OID:
--		enterprises.6889.2.73.8.1.8
-- Description:
--		The avCmListStationRange MIB group displays the output of the
--		list station xxxx count xx command. This MIB Group  should be
--		used instead of the avCmListStations MIB Group on systems
--		with over 100 stations.
-- Releases Supported:
--		CM6.3.100 and greater
-- Polling Type:
--		Inventory and Performance/Utilization
-- Polling Interval:
--		No more than once a day or when stations are added.
-- Default Caching Interval
-- 		300 seconds
-- Timeout Interval:
--		Initial Timeout should be set to 15 seconds.
-- Retry Interval:
--		Initial Retry should be set to 3.
-- Limitations:
--		Yellow/Medium - The data collected by this MIB Group
--		may have some impact on the system.
-- Command Type:
--		1. SAT
--		2. SAT
-- Command:
--		1. list station xxxxx count x
--		2. display station xxxxx
-- Form/Report Name:
--		1. STATIONS
-- Reference Document:
--		1. A detailed description of the command and form can be
--		   found in REF_DOC_3 in the DOCUMENT REFERENCE SECTION.
-- Command Permission/User-profile:
--		1. No special permissions needed. Default customer super-user
--		   profile can access this command.

avCmListStationRange	OBJECT IDENTIFIER ::= { avCmObjects 8 }

avCmListStationRangeStartExt	OBJECT-TYPE
    SYNTAX	SnmpAdminString (SIZE (0..17))
    MAX-ACCESS	read-write
    STATUS	current
    DESCRIPTION
	"
	Fld OID Name:	avCmSationRangeStartExt
	Fld OID:	enterprises.6889.2.73.8.1.8.1
	Fld Form/Rpt:	NA
	Fld Format:	NA
	Fld(s) Name:	NA
	Fld Descr:	An object containing the starting Extension location
	"
    ::= { avCmListStationRange 1 }

avCmListStationRangeCount	OBJECT-TYPE
    SYNTAX	Integer32 (1..100)
    MAX-ACCESS	read-write
    STATUS	current
    DESCRIPTION
	"
	Fld OID Name:	avCmStationRangeCount
	Fld OID:	enterprises.6889.2.73.8.1.8.2
	Fld Form/Rpt:	NA
	Fld Format:	NA
	Fld(s) Name:	NA
	Fld Descr:	An object containing the number of stations to list.
	"
    DEFVAL	{ 10 }
    ::= { avCmListStationRange 2 }

avCmListStationRangeTable	OBJECT-TYPE
    SYNTAX	SEQUENCE OF AvCmListStationRangeEntry
    MAX-ACCESS	not-accessible
    STATUS	current
    DESCRIPTION
	"
	Fld OID Name:	avCmListStationRangeTable
	Fld OID:	enterprises.6889.2.73.8.1.8.3
	Fld Form/Rpt:	NA
	Fld Format:	NA
	Fld(s) Name:	NA
	Fld Descr:	A list of the avCmStationRange entries.
	"
    ::= { avCmListStationRange 3 }

avCmListStationRangeEntry	OBJECT-TYPE
    SYNTAX	AvCmListStationRangeEntry
    MAX-ACCESS	not-accessible
    STATUS	current
    DESCRIPTION
	"
	Fld OID Name:	avCmListStationRangeEntry
	Fld OID:	enterprises.6889.2.73.8.1.8.3.1
	Fld Form/Rpt:	NA
	Fld Format:	NA
	Fld(s) Name:	NA
	Fld Descr:	A avCmListStationRange entry containing objects of the
			avCmListStationRange information sent by the switch.
	"
    INDEX    { avCmListStationRangeIdx }
    ::= { avCmListStationRangeTable 1 }

AvCmListStationRangeEntry ::= SEQUENCE {
		avCmListStationRangeIdx
		    SnmpAdminString,
		avCmListStationRangeExtension
		    SnmpAdminString,
		avCmListStationRangeType
		    SnmpAdminString,
		avCmListStationRangeName
		    SnmpAdminString,
		avCmListStationRangePort
		    SnmpAdminString,
		avCmListStationRangeBuilding
		    SnmpAdminString,
		avCmListStationRangeFloor
		    SnmpAdminString,
		avCmListStationRangeRoom
		    SnmpAdminString,
		avCmListStationRangeCable
		    SnmpAdminString,
		avCmListStationRangeJack
		    SnmpAdminString
		}

avCmListStationRangeIdx	OBJECT-TYPE
    SYNTAX	SnmpAdminString (SIZE (0..17))
    MAX-ACCESS	not-accessible
    STATUS	current
    DESCRIPTION
	"
	Fld OID Name:	avCmListStationRangeIdx
	Fld OID:	enterprises.6889.2.73.8.1.8.3.1.1
	Fld Form/Rpt:	NA
	Fld Format:	NA
	Fld(s) Name:	NA
	Fld Descr:	An object that uniquely identifies each Server Alarm.
	"
    ::= { avCmListStationRangeEntry 1 }

avCmListStationRangeExtension	OBJECT-TYPE
    SYNTAX	SnmpAdminString (SIZE (0..17))
    MAX-ACCESS	read-only
    STATUS	current
    DESCRIPTION
	"
	Fld OID Name:	avCmStationRangeExtension
	Fld OID:	enterprises.6889.2.73.8.1.8.3.1.2
	Fld Form/Rpt:	STATIONS
	Fld Format:	Single
	Fld(s) Name:	Ext
	Fld Descr:	An object that contains the station extension.
	"
    ::= { avCmListStationRangeEntry 2 }

avCmListStationRangeType	OBJECT-TYPE
    SYNTAX	SnmpAdminString (SIZE (0..10))
    MAX-ACCESS	read-only
    STATUS	current
    DESCRIPTION
	"
	Fld OID Name:	avCmStationRangeType
	Fld OID:	enterprises.6889.2.73.8.1.8.3.1.3
	Fld Form/Rpt:	STATIONS
	Fld Format:	Single
	Fld(s) Name:	Type
	Fld Descr:	An object containing the station type.
	"
    ::= { avCmListStationRangeEntry 3 }

avCmListStationRangeName	OBJECT-TYPE
    SYNTAX	SnmpAdminString (SIZE (0..28))
    MAX-ACCESS	read-only
    STATUS	current
    DESCRIPTION
	"
	Fld OID Name:	avCmStationRangeName
	Fld OID:	enterprises.6889.2.73.8.1.8.3.1.4
	Fld Form/Rpt:	STATIONS
	Fld Format:	Single
	Fld(s) Name:	Name
	Fld Descr:	An object containing the name assigned to the station.
	"
    ::= { avCmListStationRangeEntry 4 }

avCmListStationRangePort	OBJECT-TYPE
    SYNTAX	SnmpAdminString (SIZE (0..8))
    MAX-ACCESS	read-only
    STATUS	current
    DESCRIPTION
	"
	Fld OID Name:	avCmListStationRangePort
	Fld OID:	enterprises.6889.2.73.8.1.8.3.1.5
	Fld Form/Rpt:	STATIONS
	Fld Format:	Single
	Fld(s) Name:	Port
	Fld Descr:	An object containing the stations port assignment.
	"
    ::= { avCmListStationRangeEntry 5 }

avCmListStationRangeBuilding	OBJECT-TYPE
    SYNTAX	SnmpAdminString (SIZE (0..11))
    MAX-ACCESS	read-only
    STATUS	current
    DESCRIPTION
	"
	Fld OID Name:	avCmListStationRangeBuilding
	Fld OID:	enterprises.6889.2.73.8.1.8.3.1.6
	Fld Form/Rpt:	STATION
	Fld Format:	Single
	Fld(s) Name:	ID
	Fld Descr:	An object containing the building location of the
			station.
	"
    ::= { avCmListStationRangeEntry 6 }

avCmListStationRangeFloor	OBJECT-TYPE
    SYNTAX	SnmpAdminString (SIZE (0..11))
    MAX-ACCESS	read-only
    STATUS	current
    DESCRIPTION
	"
	Fld OID Name:	avCmServerAlarmID
	Fld OID:	enterprises.6889.2.73.8.1.8.3.1.7
	Fld Form/Rpt:	STATION
	Fld Format:	Single
	Fld(s) Name:	ID
	Fld Descr:	An object containing the floor location of the
			station.
	"
    ::= { avCmListStationRangeEntry 7 }

avCmListStationRangeRoom	OBJECT-TYPE
    SYNTAX	SnmpAdminString (SIZE (0..11))
    MAX-ACCESS	read-only
    STATUS	current
    DESCRIPTION
	"
	Fld OID Name:	avCmListStationRangeRoom
	Fld OID:	enterprises.6889.2.73.8.1.8.3.1.8
	Fld Form/Rpt:	STATIONS
	Fld Format:	Single
	Fld(s) Name:	ID
	Fld Descr:	An object containing the room location of the
			station.
	"
    ::= { avCmListStationRangeEntry 8 }

avCmListStationRangeCable	OBJECT-TYPE
    SYNTAX	SnmpAdminString (SIZE (0..6))
    MAX-ACCESS	read-only
    STATUS	current
    DESCRIPTION
	"
	Fld OID Name:	avCmListStationRangeCable
	Fld OID:	enterprises.6889.2.73.8.1.8.3.1.9
	Fld Form/Rpt:	STATIONS
	Fld Format:	Single
	Fld(s) Name:	ID
	Fld Descr:	An object containing the cable used by the station.
	"
    ::= { avCmListStationRangeEntry 9 }

avCmListStationRangeJack	OBJECT-TYPE
    SYNTAX	SnmpAdminString (SIZE (0..6))
    MAX-ACCESS	read-only
    STATUS	current
    DESCRIPTION
	"
	Fld OID Name:	avCmListStationRangeJack
	Fld OID:	enterprises.6889.2.73.8.1.8.3.1.10
	Fld Form/Rpt:	STATIONS
	Fld Format:	Single
	Fld(s) Name:	ID
	Fld Descr:	An object containing the jack used by the station.
	"
    ::= { avCmListStationRangeEntry 10 }

-- ******************** avCmUpdateShow Group *************************

-- MIB GROUP DESCRIPTION

-- MIB Group Name:
--		avCmUpdateShow
-- OID:
--		enterprises.6889.2.73.8.1.9
-- Description:
--		The avCmUpdateShow MIB Group uses the "update_show"
-- 		command to retrieve the Servers Patch information. 
--		
-- Releases Supported:
--		CM6.3.100 and greater
-- Polling Type:
--		Configuration
-- Polling Interval:
--		No more than once a day.
-- Default Caching Interval
-- 		60 seconds
-- Timeout Interval:
--		Initial Timeout should be set to 15 seconds.
-- Retry Interval:
--		Initial Retry should be set to 3.
-- Limitations:
--		Green/Low - The data collected by this MIB Group
--		is minimal and therefore has a low impact on the system.
-- Command Type:
--		1. BASH
-- Command:
--		1. update_show
-- Form/Report Name:
--		1. NA
-- Reference Document:
--		1. A detailed description of the command and form can be
--		   found in document referenced by REF_DOC_1 in the
--		   DOCUMENT REFERENCE SECTION.
-- Command Permission/User-profile:
--		1. No special permissions needed.

avCmUpdateShow	OBJECT IDENTIFIER ::= { avCmObjects 9 }

avCmUpdateShowTable	OBJECT-TYPE
    SYNTAX	SEQUENCE OF AvCmUpdateShowEntry
    MAX-ACCESS	not-accessible
    STATUS	current
    DESCRIPTION
	"
	Fld OID Name:	avCmUpdateShowTable
	Fld OID:	enterprises.6889.2.73.8.1.9.1
	Fld Form/Rpt:	NA
	Fld Format:	NA
	Fld(s) Name:	NA
	Fld Descr:	A list of the avCmUpdateShow entries
	"
    ::= { avCmUpdateShow 1 }

avCmUpdateShowEntry	OBJECT-TYPE
    SYNTAX	AvCmUpdateShowEntry
    MAX-ACCESS	not-accessible
    STATUS	current
    DESCRIPTION
	"
	Fld OID Name:	avCmUpdateShowEntry
	Fld OID:	enterprises.6889.2.73.8.1.9.1.1
	Fld Form/Rpt:	NA
	Fld Format:	NA
	Fld(s) Name:	NA
	Fld Descr:	A avCmUpdateShow entry containing objects of the
			avCmUpdateShow information sent by the switch.
	"
    INDEX    { avCmUpdateShowIdx }
    ::= { avCmUpdateShowTable 1 }

AvCmUpdateShowEntry ::= SEQUENCE {
		avCmUpdateShowIdx
		    SnmpAdminString,
		avCmUpdateShowID
		    SnmpAdminString,
		avCmUpdateShowStatus
		    SnmpAdminString,
		avCmUpdateShowType
		    SnmpAdminString,
		avCmUpdateShowDescription
		    SnmpAdminString
		}

avCmUpdateShowIdx	OBJECT-TYPE
    SYNTAX	SnmpAdminString (SIZE (0..33))
    MAX-ACCESS	not-accessible
    STATUS	current
    DESCRIPTION
	"
	Fld OID Name:	avCmUpdateShowIdx
	Fld OID:	enterprises.6889.2.73.8.1.9.1.1.1
	Fld Format:	NA
	Fld(s) Name:	NA
	Fld Descr:	An object that uniquely identifies each Update.
	"
    ::= { avCmUpdateShowEntry 1 }

avCmUpdateShowID	OBJECT-TYPE
    SYNTAX	SnmpAdminString (SIZE (0..33))
    MAX-ACCESS	read-only
    STATUS	current
    DESCRIPTION
	"
	Fld OID Name:	avCmUpdateShowID
	Fld OID:	enterprises.6889.2.73.8.1.9.1.1.2
	Fld Form/Rpt:	NA
	Fld Format:	Single Field
	Fld(s) Name:	Update ID
	Fld Descr:	An object that contains the Patch ID.
	"
    ::= { avCmUpdateShowEntry 2 }

avCmUpdateShowStatus	OBJECT-TYPE
    SYNTAX	SnmpAdminString (SIZE (0..15))
    MAX-ACCESS	read-only
    STATUS	current
    DESCRIPTION
	"
	Fld OID Name:	avCmUpdateShowStatus
	Fld OID:	enterprises.6889.2.73.8.1.9.1.1.3
	Fld Form/Rpt:	NA
	Fld Format:	Single Field
	Fld(s) Name:	Status
	Fld Descr:	An object that contains the Status of the Patch.
	"
    ::= { avCmUpdateShowEntry 3 }

avCmUpdateShowType	OBJECT-TYPE
    SYNTAX	SnmpAdminString (SIZE (0..10))
    MAX-ACCESS	read-only
    STATUS	current
    DESCRIPTION
	"
	Fld OID Name:	avCmUpdateShowType
	Fld OID:	enterprises.6889.2.73.8.1.9.1.1.4
	Fld Form/Rpt:	NA
	Fld Format:	Single Field
	Fld(s) Name:	Type
	Fld Descr:	An object that contains the Type of the Patch.
	"
    ::= { avCmUpdateShowEntry 4 }

avCmUpdateShowDescription	OBJECT-TYPE
    SYNTAX	SnmpAdminString (SIZE (0..80))
    MAX-ACCESS	read-only
    STATUS	current
    DESCRIPTION
	"
	Fld OID Name:	avCmUpdateShowDescription
	Fld OID:	enterprises.6889.2.73.8.1.9.1.1.5
	Fld Form/Rpt:	NA
	Fld Format:	Single Field
	Fld(s) Name:	Type
	Fld Descr:	An object that contains the Description of the Patch.
	"
    ::= { avCmUpdateShowEntry 5 }


-- ******************** avCmListTrunk Group *************************


-- MIB GROUP DESCRIPTION

-- MIB Group Name:
--		avCmListTrunk Group
-- OID:
--		enterprises.6889.2.73.8.1.10
-- Description:
--		The avCmListTrunk MIB Group uses the "list trunk-group"
-- 		command to retrieve the systems administered trunk group 
--		information.   In addition to list trunk information, some
--		fields from the "display trunk-group" form are displayed.
--		
-- Releases Supported:
--		CM6.3.100 and greater
-- Polling Type:
--		Configuration and Inventory
-- Polling Interval:
--		No more than once a day or when trunk administration is 
--		changed.
-- Default Caching Interval
-- 		600 seconds
-- Timeout Interval:
--		Initial Timeout should be set to 20 seconds.
-- Retry Interval:
--		Initial Retry should be set to 3.
-- Limitations:
--		Red/High - The data collected by this MIB Group will
--		increase as the number of administered trunks increase.
--		Consequently the data collected by this MIB Group could be
--		very large and therefore may take a very long time to collect
--		and could impact system performance.
-- Command Type:
--		1. SAT
--		2. SAT
-- Command:
--		1. list trunk-group
--		2. display trunk-group
-- Form/Report Name:
--		1. TRUNK GROUPS 
--		2. TRUNK_GROUP 
-- Reference Document:
--		1. Information about trunk-groups can be
--		   found in document referenced by REF_DOC_5 
--		   in the DOCUMENT REFERENCE SECTION.
--		2. Information about trunk-groups can be
--		   found in document referenced by REF_DOC_5 
--		   in the DOCUMENT REFERENCE SECTION.
-- Command Permission/User-profile:
--		1. No special permissions needed.
--		2. No special permissions needed.

avCmListTrunk	OBJECT IDENTIFIER ::= { avCmObjects 10 }

avCmListTrunkTable	OBJECT-TYPE
    SYNTAX	SEQUENCE OF AvCmListTrunkEntry
    MAX-ACCESS	not-accessible
    STATUS	current
    DESCRIPTION
	"
	Fld OID Name:	avCmListTrunkEntry
	Fld OID:	enterprises.6889.2.73.8.1.10.1
	Fld Form/Rpt:	NA
	Fld Format:	NA
	Fld(s) Name:	NA
	Fld Descr:	A list of the avCmListTrunk entries
	"
    ::= { avCmListTrunk 1 }

avCmListTrunkEntry	OBJECT-TYPE
    SYNTAX	AvCmListTrunkEntry
    MAX-ACCESS	not-accessible
    STATUS	current
    DESCRIPTION
	"
	Fld OID Name:	avCmListTrunkEntry
	Fld OID:	enterprises.6889.2.73.8.1.10.1.1
	Fld Form/Rpt:	NA
	Fld Format:	NA
	Fld(s) Name:	NA
	Fld Descr:	A avCmListTrunk entry containing objects of the
			avCmListTrunk information sent by the switch.
	"
    INDEX    { avCmListTrunkIdx }
    ::= { avCmListTrunkTable 1 }

AvCmListTrunkEntry ::= SEQUENCE {
		avCmListTrunkIdx
		    Integer32,
		avCmListTrunkGrpNumber
		    Integer32,
		avCmListTrunkGrpType
		    SnmpAdminString,
		avCmListTrunkGrpName
		    SnmpAdminString,
		avCmListTrunkTAC
		    SnmpAdminString,
		avCmListTrunkDirection
		    SnmpAdminString,
		avCmListTrunkServiceType
		    SnmpAdminString,
		avCmListTrunkCommType
		    SnmpAdminString,
		avCmListTrunkTrunkType
		    SnmpAdminString
		}

avCmListTrunkIdx	OBJECT-TYPE
    SYNTAX	Integer32 (0..2000)
    MAX-ACCESS	not-accessible
    STATUS	current
    DESCRIPTION
	"
	Fld OID Name:	avCmListTrunkIdx
	Fld OID:	enterprises.6889.2.73.8.1.10.1.1.1
	Fld Format:	NA
	Fld(s) Name:	NA
	Fld Descr:	An object that uniquely identifies each Trunk Group.
	"
    ::= { avCmListTrunkEntry 1 }

avCmListTrunkGrpNumber	OBJECT-TYPE
    SYNTAX	Integer32 (0..2000)
    MAX-ACCESS	read-only
    STATUS	current
    DESCRIPTION
	"
	Fld OID Name:	avCmListTrunkGrpNumber
	Fld OID:	enterprises.6889.2.73.8.1.10.1.1.2
	Fld Form/Rpt:	TRUNK GROUPS
	Fld Format:	Single Field
	Fld(s) Name:	List Command: Grp No 
			Display Command: Group Number
	Fld Descr:	An object that uniquely identifies each Trunk Group.
	"
    ::= { avCmListTrunkEntry 2 }

avCmListTrunkGrpType	OBJECT-TYPE
    SYNTAX	SnmpAdminString (SIZE (0..14))
    MAX-ACCESS	read-only
    STATUS	current
    DESCRIPTION
	"
	Fld OID Name:	avCmListTrunkGrpType
	Fld OID:	enterprises.6889.2.73.8.1.10.1.1.3
	Fld Form/Rpt:	TRUNK GROUPS
	Fld Format:	Single Field
	Fld(s) Name:	List Command: Group Type
			Display Command: Group Type
	Fld Descr:	An object that contains the trunk group type.
	"
    ::= { avCmListTrunkEntry 3 }

avCmListTrunkGrpName	OBJECT-TYPE
    SYNTAX	SnmpAdminString (SIZE (0..28))
    MAX-ACCESS	read-only
    STATUS	current
    DESCRIPTION
	"
	Fld OID Name:	avCmListGrpName
	Fld OID:	enterprises.6889.2.73.8.1.10.1.1.4
	Fld Form/Rpt:	TRUNK GROUPS
	Fld Format:	Single Field
	Fld(s) Name:	List Command: Group Name
			Display Command: Group Name
	Fld Descr:	An object that contains the name assigned to the 
			trunk group.
	"
    ::= { avCmListTrunkEntry 4 }

avCmListTrunkTAC	OBJECT-TYPE
    SYNTAX	SnmpAdminString (SIZE (0..5))
    MAX-ACCESS	read-only
    STATUS	current
    DESCRIPTION
	"
	Fld OID Name:	avCmListTrunkTAC
	Fld OID:	enterprises.6889.2.73.8.1.10.1.1.5
	Fld Form/Rpt:	TRUNK GROUPS
	Fld Format:	Single Field
	Fld(s) Name:	List Command: TAC
			Display Command: TAC
	Fld Descr:	An object that contains the Access Code for the 
			Trunk Group.
	"
    ::= { avCmListTrunkEntry 5 }

avCmListTrunkDirection	OBJECT-TYPE
    SYNTAX	SnmpAdminString (SIZE (0..9))
    MAX-ACCESS	read-only
    STATUS	current
    DESCRIPTION
	"
	Fld OID Name:	avCmListTrunkDirection
	Fld OID:	enterprises.6889.2.73.8.1.10.1.1.6
	Fld Form/Rpt:	TRUNK GROUPS
	Fld Format:	Single Field
	Fld(s) Name:	List Command: Does not display this field
			Display Command: Direction
	Fld Descr:	An object that contains the trunk group direction.
	"
    ::= { avCmListTrunkEntry 6 }

avCmListTrunkServiceType	OBJECT-TYPE
    SYNTAX	SnmpAdminString (SIZE (0..16))
    MAX-ACCESS	read-only
    STATUS	current
    DESCRIPTION
	"
	Fld OID Name:	avCmListTrunkServiceType
	Fld OID:	enterprises.6889.2.73.8.1.10.1.1.7
	Fld Form/Rpt:	TRUNK GROUPS
	Fld Format:	Single Field
	Fld(s) Name:	List Command: Does not display this field
			Display Command: Service Type
	Fld Descr:	An object that contains the Service Type of the 
			Trunk Group.
	"
    ::= { avCmListTrunkEntry 7 }

avCmListTrunkCommType	OBJECT-TYPE
    SYNTAX	SnmpAdminString (SIZE (0..6))
    MAX-ACCESS	read-only
    STATUS	current
    DESCRIPTION
	"
	Fld OID Name:	avCmListTrunkCommType
	Fld OID:	enterprises.6889.2.73.8.1.10.1.1.8
	Fld Form/Rpt:	TRUNK GROUPS
	Fld Format:	Single Field
	Fld(s) Name:	List Command: Does not display this field
			Display Command: Comm Type
	Fld Descr:	An object that contains the Comm Type of the 
			Trunk Group.
	"
    ::= { avCmListTrunkEntry 8 }

avCmListTrunkTrunkType	OBJECT-TYPE
    SYNTAX	SnmpAdminString (SIZE (0..13))
    MAX-ACCESS	read-only
    STATUS	current
    DESCRIPTION
	"
	Fld OID Name:	avCmListTrunkTrunkType
	Fld OID:	enterprises.6889.2.73.8.1.10.1.1.9
	Fld Form/Rpt:	TRUNK GROUPS
	Fld Format:	Single Field
	Fld(s) Name:	List Command: Does not display this field
			Display Command: Trunk Type
	Fld Descr:	An object that contains the Trunk Type of the 
			Trunk Group.
	"
    ::= { avCmListTrunkEntry 9 }

--   *********** avCmListTrunkRange Group **************

-- MIB Group Name:
--		avCmListTrunkRange
-- OID:
--		enterprises.6889.2.73.8.1.11
-- Description:
--		The avCmListTrunkRange MIB group displays the output of the
--		list trunk xxxx count xx command. This MIB Group  should be
--		used instead of the avCmListTrunk MIB Group on systems
--		with over 100 trunks.
-- Releases Supported:
--		CM6.3.100 and greater
-- Polling Type:
--		Inventory and Performance/Utilization
-- Polling Interval:
--		No more than once a day or when stations are added.
-- Default Caching Interval
-- 		600 seconds
-- Timeout Interval:
--		Initial Timeout should be set to 15 seconds.
-- Retry Interval:
--		Initial Retry should be set to 3.
-- Limitations:
--		Yellow/Medium - The data collected by this MIB Group
--		may have some impact on the system.
-- Command Type:
--		1. SAT
--		2. SAT
-- Command:
--		1. list trunk xxxxx count x
--		2. display trunk xxxxx
-- Form/Report Name:
--		1. TRUNK GROUPS
--		2. TRUNK GROUP
-- Reference Document:
--		1. Information about trunk-groups can be
--		   found in REF_DOC_5 in the DOCUMENT REFERENCE SECTION.
--		2. Information about trunk-groups can be
--		   found in REF_DOC_5 in the DOCUMENT REFERENCE SECTION.
-- Command Permission/User-profile:
--		1. No special permissions needed. Default customer super-user
--		   profile can access this command.
--		2. No special permissions needed. Default customer super-user
--		   profile can access this command.

avCmListTrunkRange	OBJECT IDENTIFIER ::= { avCmObjects 11 }

avCmListTrunkRangeStartGrp	OBJECT-TYPE
    SYNTAX	Integer32 (0..2000)
    MAX-ACCESS	read-write
    STATUS	current
    DESCRIPTION
	"
	Fld OID Name:	avCmListTrunkRangeStartGrp
	Fld OID:	enterprises.6889.2.73.8.1.11.1
	Fld Form/Rpt:	NA
	Fld Format:	NA
	Fld(s) Name:	NA
	Fld Descr:	An object containing the starting trunk group
	"
    ::= { avCmListTrunkRange 1 }

avCmListTrunkRangeCount	OBJECT-TYPE
    SYNTAX	Integer32 (1..100)
    MAX-ACCESS	read-write
    STATUS	current
    DESCRIPTION
	"
	Fld OID Name:	avCmListTrunkRangeCount
	Fld OID:	enterprises.6889.2.73.8.1.11.2
	Fld Form/Rpt:	NA
	Fld Format:	NA
	Fld(s) Name:	NA
	Fld Descr:	An object containing the number of trunks to list.
	"
    DEFVAL	{ 10 }
    ::= { avCmListTrunkRange 2 }

avCmListTrunkRangeTable	OBJECT-TYPE
    SYNTAX	SEQUENCE OF AvCmListTrunkRangeEntry
    MAX-ACCESS	not-accessible
    STATUS	current
    DESCRIPTION
	"
	Fld OID Name:	avCmListTrunkRangeTable
	Fld OID:	enterprises.6889.2.73.8.1.11.3
	Fld Form/Rpt:	NA
	Fld Format:	NA
	Fld(s) Name:	NA
	Fld Descr:	A list of the avCmTrunkRange entries.
	"
    ::= { avCmListTrunkRange 3 }

avCmListTrunkRangeEntry	OBJECT-TYPE
    SYNTAX	AvCmListTrunkRangeEntry
    MAX-ACCESS	not-accessible
    STATUS	current
    DESCRIPTION
	"
	Fld OID Name:	avCmListTrunkRangeEntry
	Fld OID:	enterprises.6889.2.73.8.1.11.3.1
	Fld Form/Rpt:	NA
	Fld Format:	NA
	Fld(s) Name:	NA
	Fld Descr:	A avCmListTrunkRange entry containing objects of the
			avCmListTrunkRange information sent by the switch.
	"
    INDEX    { avCmListTrunkRangeIdx }
    ::= { avCmListTrunkRangeTable 1 }

AvCmListTrunkRangeEntry ::= SEQUENCE {
		avCmListTrunkRangeIdx
		    Integer32,
                avCmListTrunkRangeGrpNumber
                    Integer32,
                avCmListTrunkRangeTAC
                    SnmpAdminString,
                avCmListTrunkRangeGrpType
                    SnmpAdminString,
                avCmListTrunkRangeGrpName
                    SnmpAdminString,
                avCmListTrunkRangeGrpNoMem
                    Integer32,
                avCmListTrunkRangeSigGrp
                    Integer32,
                avCmListTrunkRangeGrpSigType
                    SnmpAdminString,
                avCmListTrunkRangeDirection
                    SnmpAdminString,
                avCmListTrunkRangeServiceType
                    SnmpAdminString,
                avCmListTrunkRangeCommType
                    SnmpAdminString,
                avCmListTrunkRangeTrunkType
                    SnmpAdminString,
                avCmListTrunkRangeMemAssignMeth
                    SnmpAdminString,
                avCmListTrunkRangeCarMedium
                    SnmpAdminString
		}

avCmListTrunkRangeIdx	OBJECT-TYPE
    SYNTAX	Integer32 (0..2000)
    MAX-ACCESS	not-accessible
    STATUS	current
    DESCRIPTION
	"
	Fld OID Name:	avCmListTrunkRangeIdx
	Fld OID:	enterprises.6889.2.73.8.1.11.3.1.1
	Fld Form/Rpt:	NA
	Fld Format:	NA
	Fld(s) Name:	NA
	Fld Descr:	An object that uniquely identifies each Server Alarm.
	"
    ::= { avCmListTrunkRangeEntry 1 }

avCmListTrunkRangeGrpNumber  OBJECT-TYPE
    SYNTAX      Integer32 (0..2000)
    MAX-ACCESS  read-only
    STATUS      current
    DESCRIPTION
        "
        Fld OID Name:   avCmListTrunkRangeGrpNumber
        Fld OID:        enterprises.6889.2.73.8.1.11.3.1.2
        Fld Form/Rpt:   TRUNK GROUPS
        Fld Format:     Single Field
        Fld(s) Name:    List Command: Grp No
                        Display Command: Group Number
        Fld Descr:      An object that uniquely identifies each Trunk Group.
        "
    ::= { avCmListTrunkRangeEntry 2 }

avCmListTrunkRangeTAC        OBJECT-TYPE
    SYNTAX      SnmpAdminString (SIZE (0..5))
    MAX-ACCESS  read-only
    STATUS      current
    DESCRIPTION
        "
        Fld OID Name:   avCmListTrunkRangeTAC
        Fld OID:        enterprises.6889.2.73.8.1.11.3.1.3
        Fld Form/Rpt:   TRUNK GROUPS
        Fld Format:     Single Field
        Fld(s) Name:    List Command: TAC
                        Display Command: TAC
        Fld Descr:      An object that contains the Access Code for the
                        Trunk Group.
        "
    ::= { avCmListTrunkRangeEntry 3 }

avCmListTrunkRangeGrpType	OBJECT-TYPE
    SYNTAX	SnmpAdminString (SIZE (0..14))
    MAX-ACCESS	read-only
    STATUS	current
    DESCRIPTION
	"
	Fld OID Name:	avCmListTrunkRangeGrpType
	Fld OID:	enterprises.6889.2.73.8.1.11.3.1.4
	Fld Form/Rpt:	TRUNK GROUP
	Fld Format:	Single
	Fld(s) Name:	Type
	Fld Descr:	An object containing the trunk group type.
	"
    ::= { avCmListTrunkRangeEntry 4 }

avCmListTrunkRangeGrpName	OBJECT-TYPE
    SYNTAX	SnmpAdminString (SIZE (0..28))
    MAX-ACCESS	read-only
    STATUS	current
    DESCRIPTION
	"
	Fld OID Name:	avCmListTrunkRangeGrpName
	Fld OID:	enterprises.6889.2.73.8.1.11.3.1.5
	Fld Form/Rpt:	TRUNK GROUP
	Fld Format:	Single
	Fld(s) Name:	Name
	Fld Descr:	An object containing the name assigned to the trunk.
	"
    ::= { avCmListTrunkRangeEntry 5 }

avCmListTrunkRangeGrpNoMem	OBJECT-TYPE
    SYNTAX	Integer32 (0..255)
    MAX-ACCESS	read-only
    STATUS	current
    DESCRIPTION
	"
	Fld OID Name:	avCmListTrunkRangeGrpNoMem
	Fld OID:	enterprises.6889.2.73.8.1.11.3.1.6
	Fld Form/Rpt:	TRUNK GROUP
	Fld Format:	Single
	Fld(s) Name:	No. Mem
	Fld Descr:	An object containing the trunk group  number of ports
			assigned.
	"
    ::= { avCmListTrunkRangeEntry 6 }

avCmListTrunkRangeSigGrp	OBJECT-TYPE
    SYNTAX	Integer32 (0..999)
    MAX-ACCESS	read-only
    STATUS	current
    DESCRIPTION
	"
	Fld OID Name:	avCmListTrunkRangeSigGrp
	Fld OID:	enterprises.6889.2.73.8.1.11.3.1.7
	Fld Form/Rpt:	TRUNK GROUP
	Fld Format:	Single
	Fld(s) Name:	Signaling Group
	Fld Descr:	An object containing the signaling group of the sip
			trunk group.
	"
    ::= { avCmListTrunkRangeEntry 7 }

avCmListTrunkRangeGrpSigType	OBJECT-TYPE
    SYNTAX	SnmpAdminString (SIZE (0..8))
    MAX-ACCESS	read-only
    STATUS	current
    DESCRIPTION
	"
	Fld OID Name:	avCmListTrunkRangeGrpSigType
	Fld OID:	enterprises.6889.2.73.8.1.11.3.1.8
	Fld Form/Rpt:	TRUNK GROUP
	Fld Format:	Single
	Fld(s) Name:	Trunk Signaling Type
	Fld Descr:	An object containing the Trunk Signaling Type of the
			trunk group.
	"
    ::= { avCmListTrunkRangeEntry 8 }

avCmListTrunkRangeDirection	OBJECT-TYPE
    SYNTAX	SnmpAdminString (SIZE (0..9))
    MAX-ACCESS	read-only
    STATUS	current
    DESCRIPTION
	"
	Fld OID Name:	avCmListTrunkRangeDirection
	Fld OID:	enterprises.6889.2.73.8.1.11.3.1.9
	Fld Form/Rpt:	TRUNK GROUP
	Fld Format:	Single
	Fld(s) Name:	Direction
	Fld Descr:	An object containing the Direction of the
			trunk group.
	"
    ::= { avCmListTrunkRangeEntry 9 }

avCmListTrunkRangeServiceType        OBJECT-TYPE
    SYNTAX      SnmpAdminString (SIZE (0..17))
    MAX-ACCESS  read-only
    STATUS      current
    DESCRIPTION
        "
        Fld OID Name:   avCmListTrunkRangeServiceType
        Fld OID:        enterprises.6889.2.73.8.1.11.3.1.10
        Fld Form/Rpt:   TRUNK GROUPS
        Fld Format:     Single Field
        Fld(s) Name:    List Command: Does not display this field
                        Display Command: Service Type
        Fld Descr:      An object that contains the Service Type of the
                        Trunk Group.
        "
    ::= { avCmListTrunkRangeEntry 10 }

avCmListTrunkRangeCommType   OBJECT-TYPE
    SYNTAX      SnmpAdminString (SIZE (0..6))
    MAX-ACCESS  read-only
    STATUS      current
    DESCRIPTION
        "
        Fld OID Name:   avCmListTrunkRangeCommType
        Fld OID:        enterprises.6889.2.73.8.1.11.3.1.11
        Fld Form/Rpt:   TRUNK GROUPS
        Fld Format:     Single Field
        Fld(s) Name:    List Command: Does not display this field
                        Display Command: Comm Type
        Fld Descr:      An object that contains the Comm Type of the
                        Trunk Group.
        "
    ::= { avCmListTrunkRangeEntry 11 }


avCmListTrunkRangeTrunkType  OBJECT-TYPE
    SYNTAX      SnmpAdminString (SIZE (0..14))
    MAX-ACCESS  read-only
    STATUS      current
    DESCRIPTION
        "
        Fld OID Name:   avCmListTrunkRangeTrunkType
        Fld OID:        enterprises.6889.2.73.8.1.11.3.1.12
        Fld Form/Rpt:   TRUNK GROUPS
        Fld Format:     Single Field
        Fld(s) Name:    List Command: Does not display this field
                        Display Command: Trunk Type
        Fld Descr:      An object that contains the Trunk Type of the
                        Trunk Group.
        "
    ::= { avCmListTrunkRangeEntry 12 }


avCmListTrunkRangeMemAssignMeth  OBJECT-TYPE
    SYNTAX      SnmpAdminString (SIZE (0..7))
    MAX-ACCESS  read-only
    STATUS      current
    DESCRIPTION
        "
        Fld OID Name:   avCmListTrunkRangeMemAssignMeth
        Fld OID:        enterprises.6889.2.73.8.1.11.3.1.13
        Fld Form/Rpt:   TRUNK GROUPS
        Fld Format:     Single Field
        Fld(s) Name:    List Command: Does not display this field
                        Display Command: Member Assignment Method
        Fld Descr:      An object that contains the Member Assignment Method 
			of the Trunk Group.
        "
    ::= { avCmListTrunkRangeEntry 13 }

avCmListTrunkRangeCarMedium  OBJECT-TYPE
    SYNTAX      SnmpAdminString (SIZE (0..8))
    MAX-ACCESS  read-only
    STATUS      current
    DESCRIPTION
        "
        Fld OID Name:   avCmListTrunkRangeCarMedium
        Fld OID:        enterprises.6889.2.73.8.1.11.3.1.14
        Fld Form/Rpt:   TRUNK GROUPS
        Fld Format:     Single Field
        Fld(s) Name:    List Command: Does not display this field
                        Display Command: Carrier Medium
        Fld Descr:      An object that contains the Carrier Medium
			of the Trunk Group.
        "
    ::= { avCmListTrunkRangeEntry 14 }


-- ******************** avCmCapacityAsai Group *************************

-- MIB GROUP DESCRIPTION

-- MIB Group Name:
--		avCmCapacityAsai
-- OID:
--		enterprises.6889.2.73.8.1.12
-- Description:
--		The avCmCapacityAsai MIB Group uses the "display capacity"
-- 		command to retrieve the ASAI capacity information
-- 		under the ADJUNCT SWITCH APPLICATION INTERFACE (ASAI) section
-- 		of the SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityAsai	OBJECT IDENTIFIER ::= { avCmObjects 12 }

avCmCapacityAsaiActCtrlAsscUsed	OBJECT-TYPE
    SYNTAX	Integer32 (0..99999)
    MAX-ACCESS	read-only
    STATUS	current
    DESCRIPTION
	"
	Fld OID Name:	avCmCapacityAsaiActCtrlAsscUsed
	Fld OID:	enterprises.6889.2.73.8.1.12.1
	Fld Form/Rpt:	System Capacity
	Fld Format:	Single Field
	Fld(s) Name:	Active Controlling Associations
	Fld Descr:	An object that contains the number of Used Active 
			Controlling Associations.
	"
    ::= { avCmCapacityAsai 1 }

avCmCapacityAsaiActCtrlAsscAvail	OBJECT-TYPE
    SYNTAX	Integer32 (0..99999)
    MAX-ACCESS	read-only
    STATUS	current
    DESCRIPTION
	"
	Fld OID Name:	avCmCapacityAsaiActCtrlAsscAvail
	Fld OID:	enterprises.6889.2.73.8.1.12.2
	Fld Form/Rpt:	System Capacity
	Fld Format:	Single Field
	Fld(s) Name:	Active Controlling Associations
	Fld Descr:	An object that contains the number of Available Active 
			Controlling Associations.
	"
    ::= { avCmCapacityAsai 2 }

avCmCapacityAsaiActCtrlAsscSysLim	OBJECT-TYPE
    SYNTAX	Integer32 (0..99999)
    MAX-ACCESS	read-only
    STATUS	current
    DESCRIPTION
	"
	Fld OID Name:	avCmCapacityAsaiActCtrlAsscSysLim
	Fld OID:	enterprises.6889.2.73.8.1.12.3
	Fld Form/Rpt:	System Capacity
	Fld Format:	Single Field
	Fld(s) Name:	Active Controlling Associations
	Fld Descr:	An object that contains the System Limit of Active 
			Controlling Associations.
	"
    ::= { avCmCapacityAsai 3 }


avCmCapacityAsaiNotifReqUsed	OBJECT-TYPE
    SYNTAX      Integer32 (0..99999)
    MAX-ACCESS	read-only
    STATUS	current
    DESCRIPTION
	"
	Fld OID Name:	avCmCapacityAsaiNotifReqUsed
	Fld OID:	enterprises.6889.2.73.8.1.12.4
	Fld Form/Rpt:	System Capacity
	Fld Format:	Single Field
	Fld(s) Name:	Notification Requests Used
	Fld Descr:	An object that contains the number of Used Notification 
			Requests.
	"
    ::= { avCmCapacityAsai 4 }

avCmCapacityAsaiNotifReqAvail	OBJECT-TYPE
    SYNTAX      Integer32 (0..99999)
    MAX-ACCESS	read-only
    STATUS	current
    DESCRIPTION
	"
	Fld OID Name:	avCmCapacityAsaiNotifReqAvail
	Fld OID:	enterprises.6889.2.73.8.1.12.5
	Fld Form/Rpt:	System Capacity
	Fld Format:	Single Field
	Fld(s) Name:	Notification Requests
	Fld Descr:	An object that contains the number of Available
			Notification Requests.
	"
    ::= { avCmCapacityAsai 5 }

avCmCapacityAsaiNotifReqSysLim	OBJECT-TYPE
    SYNTAX      Integer32 (0..99999)
    MAX-ACCESS	read-only
    STATUS	current
    DESCRIPTION
	"
	Fld OID Name:	avCmCapacityAsaiNotifReqSysLim
	Fld OID:	enterprises.6889.2.73.8.1.12.6
	Fld Form/Rpt:	System Capacity
	Fld Format:	Single Field
	Fld(s) Name:	Notification Requests
	Fld Descr:	An object that contains the System Limit of Notification
			Requests.
	"
    ::= { avCmCapacityAsai 6 }


avCmCapacityAsaiSimActAdjCtrlCallUsed	OBJECT-TYPE
    SYNTAX	Integer32 (0..99999)
    MAX-ACCESS	read-only
    STATUS	current
    DESCRIPTION
	"
	Fld OID Name:	avCmCapacityAsaiSimActAdjCtrlCallUsed
	Fld OID:	enterprises.6889.2.73.8.1.12.7
	Fld Form/Rpt:	System Capacity
	Fld Format:	Single Field
	Fld(s) Name:	Simultaneous Active Adjunct Controlled Calls
	Fld Descr:	An object that contains the number of Used Simultaneous 
			Active Adjunct Controlled Calls.
	"
    ::= { avCmCapacityAsai 7 }

avCmCapacityAsaiSimActAdjCtrlCallAvail	OBJECT-TYPE
    SYNTAX      Integer32 (0..99999)
    MAX-ACCESS	read-only
    STATUS	current
    DESCRIPTION
	"
	Fld OID Name:	avCmCapacityAsaiSimActAdjCtrlCallAvail
	Fld OID:	enterprises.6889.2.73.8.1.12.8
	Fld Form/Rpt:	System Capacity
	Fld Format:	Single Field
	Fld(s) Name:	Simultaneous Active Adjunct Controlled Calls
	Fld Descr:	An object that contains the number of Available
			Simultaneous Active Adjunct Controlled Calls.
	"
    ::= { avCmCapacityAsai 8 }

avCmCapacityAsaiSimActAdjCtrlCallSysLim	OBJECT-TYPE
    SYNTAX	Integer32 (0..99999)
    MAX-ACCESS	read-only
    STATUS	current
    DESCRIPTION
	"
	Fld OID Name:	avCmCapacityAsaiSimActAdjCtrlCallSysLim
	Fld OID:	enterprises.6889.2.73.8.1.12.9
	Fld Form/Rpt:	System Capacity
	Fld Format:	Single Field
	Fld(s) Name:	Notification Requests
	Fld Descr:	An object that contains the System Limit of
			Simultaneous Active Adjunct Controlled Calls.
	"
    ::= { avCmCapacityAsai 9 }

-- ******************** avCmCapacityBcms Group *************************

-- MIB GROUP DESCRIPTION

-- MIB Group Name:
--		avCmCapacityBcms
-- OID:
--		enterprises.6889.2.73.8.1.13
-- Description:
--		The avCmCapacityBcms MIB Group uses the "display capacity"
-- 		command to retrieve the Bcms capacity information
-- 		under the BASIC CALL MANAGEMENT SYSTEM (BCMS) section
-- 		of the SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityBcms	OBJECT IDENTIFIER ::= { avCmObjects 13 }

avCmCapacityBcmsMeasAgentsUsed	OBJECT-TYPE
    SYNTAX	Integer32 (0..99999)
    MAX-ACCESS	read-only
    STATUS	current
    DESCRIPTION
	"
	Fld OID Name:	avCmCapacityBcmsMeasAgentsUsed
	Fld OID:	enterprises.6889.2.73.8.1.13.1
	Fld Form/Rpt:	System Capacity
	Fld Format:	Single Field
	Fld(s) Name:	BCMS Measured Agents 
	Fld Descr:	An object that contains the number of Used BCMS 
			Measured Agents.
	"
    ::= { avCmCapacityBcms 1 }

avCmCapacityBcmsMeasAgentsAvail	OBJECT-TYPE
    SYNTAX	Integer32 (0..99999)
    MAX-ACCESS	read-only
    STATUS	current
    DESCRIPTION
	"
	Fld OID Name:	avCmCapacityBcmsMeasAgentsAvail
	Fld OID:	enterprises.6889.2.73.8.1.13.2
	Fld Form/Rpt:	System Capacity
	Fld Format:	Single Field
	Fld(s) Name:	BCMS Measured Agents 
	Fld Descr:	An object that contains the number of Available BCMS 
			Measured Agents.
	"
    ::= { avCmCapacityBcms 2 }

avCmCapacityBcmsMeasAgentsSysLim	OBJECT-TYPE
    SYNTAX	Integer32 (0..99999)
    MAX-ACCESS	read-only
    STATUS	current
    DESCRIPTION
	"
	Fld OID Name:	avCmCapacityBcmsMeasAgentsSysLim
	Fld OID:	enterprises.6889.2.73.8.1.13.3
	Fld Form/Rpt:	System Capacity
	Fld Format:	Single Field
	Fld(s) Name:	BCMS Measured Agents 
	Fld Descr:	An object that contains the System Limit of BCMS 
			Measured Agents.
	"
    ::= { avCmCapacityBcms 3 }


avCmCapacityBcmsMeasAcdMemUsed	OBJECT-TYPE
    SYNTAX	Integer32 (0..99999)
    MAX-ACCESS	read-only
    STATUS	current
    DESCRIPTION
	"
	Fld OID Name:	avCmCapacityBcmsMeasAcdMemUsed
	Fld OID:	enterprises.6889.2.73.8.1.13.4
	Fld Form/Rpt:	System Capacity
	Fld Format:	Single Field
	Fld(s) Name:	BCMS Measured ACD Members
	Fld Descr:	An object that contains the number of Used BCMS 
			Measured ACD Members.
	"
    ::= { avCmCapacityBcms 4 }

avCmCapacityBcmsMeasAcdMemAvail	OBJECT-TYPE
    SYNTAX	Integer32 (0..99999)
    MAX-ACCESS	read-only
    STATUS	current
    DESCRIPTION
	"
	Fld OID Name:	avCmCapacityBcmsMeasAcdMemAvail
	Fld OID:	enterprises.6889.2.73.8.1.13.5
	Fld Form/Rpt:	System Capacity
	Fld Format:	Single Field
	Fld(s) Name:	BCMS Measured ACD Members
	Fld Descr:	An object that contains the number of Available
			BCMS Measured ACD Members.
	"
    ::= { avCmCapacityBcms 5 }

avCmCapacityBcmsMeasAcdMemSysLim	OBJECT-TYPE
    SYNTAX	Integer32 (0..99999)
    MAX-ACCESS	read-only
    STATUS	current
    DESCRIPTION
	"
	Fld OID Name:	avCmCapacityBcmsMeasAcdMemSysLim
	Fld OID:	enterprises.6889.2.73.8.1.13.6
	Fld Form/Rpt:	System Capacity
	Fld Format:	Single Field
	Fld(s) Name:	BCMS Measured ACD Members
	Fld Descr:	An object that contains the System Limit of BCMS 
			Measured ACD Members.
	"
    ::= { avCmCapacityBcms 6 }


avCmCapacityBcmsMeasSpliSkilUsed	OBJECT-TYPE
    SYNTAX	Integer32 (0..99999)
    MAX-ACCESS	read-only
    STATUS	current
    DESCRIPTION
	"
	Fld OID Name:	avCmCapacityBcmsMeasSpliSkilUsed
	Fld OID:	enterprises.6889.2.73.8.1.13.7
	Fld Form/Rpt:	System Capacity
	Fld Format:	Single Field
	Fld(s) Name:	BCMS Measured Splits/Skills
	Fld Descr:	An object that contains the number of Used BCMS 
			Measured Splits/Skills.
	"
    ::= { avCmCapacityBcms 7 }

avCmCapacityBcmsMeasSpliSkilAvail	OBJECT-TYPE
    SYNTAX	Integer32 (0..99999)
    MAX-ACCESS	read-only
    STATUS	current
    DESCRIPTION
	"
	Fld OID Name:	avCmCapacityBcmsMeasSpliSkilAvail
	Fld OID:	enterprises.6889.2.73.8.1.13.8
	Fld Form/Rpt:	System Capacity
	Fld Format:	Single Field
	Fld(s) Name:	BCMS Measured Splits/Skills
	Fld Descr:	An object that contains the number of Available
			BCMS Measured Splits/Skills.
	"
    ::= { avCmCapacityBcms 8 }

avCmCapacityBcmsMeasSpliSkilSysLim	OBJECT-TYPE
    SYNTAX	Integer32 (0..99999)
    MAX-ACCESS	read-only
    STATUS	current
    DESCRIPTION
	"
	Fld OID Name:	avCmCapacityBcmsMeasSpliSkilSysLim
	Fld OID:	enterprises.6889.2.73.8.1.13.9
	Fld Form/Rpt:	System Capacity
	Fld Format:	Single Field
	Fld(s) Name:	CMS Measured Splits/Skills
	Fld Descr:	An object that contains the System Limit of
			CMS Measured Splits/Skills
	"
    ::= { avCmCapacityBcms 9 }


avCmCapacityBcmsMeasVdnUsed	OBJECT-TYPE
    SYNTAX	Integer32 (0..99999)
    MAX-ACCESS	read-only
    STATUS	current
    DESCRIPTION
	"
	Fld OID Name:	avCmCapacityBcmsMeasVdnUsed
	Fld OID:	enterprises.6889.2.73.8.1.13.10
	Fld Form/Rpt:	System Capacity
	Fld Format:	Single Field
	Fld(s) Name:	BCMS Measured VDNs
	Fld Descr:	An object that contains the number of Used BCMS 
			Measured VDNs.
	"
    ::= { avCmCapacityBcms 10 }

avCmCapacityBcmsMeasVdnAvail	OBJECT-TYPE
    SYNTAX	Integer32 (0..99999)
    MAX-ACCESS	read-only
    STATUS	current
    DESCRIPTION
	"
	Fld OID Name:	avCmCapacityBcmsMeasVdnAvail
	Fld OID:	enterprises.6889.2.73.8.1.13.11
	Fld Form/Rpt:	System Capacity
	Fld Format:	Single Field
	Fld(s) Name:	BCMS Measured VDNs
	Fld Descr:	An object that contains the number of Available
			BCMS Measured VDNs
	"
    ::= { avCmCapacityBcms 11 }

avCmCapacityBcmsMeasVdnSysLim	OBJECT-TYPE
    SYNTAX	Integer32 (0..99999)
    MAX-ACCESS	read-only
    STATUS	current
    DESCRIPTION
	"
	Fld OID Name:	avCmCapacityBcmsMeasVdnSysLim
	Fld OID:	enterprises.6889.2.73.8.1.13.12
	Fld Form/Rpt:	System Capacity
	Fld Format:	Single Field
	Fld(s) Name:	BCMS Measured VDNs
	Fld Descr:	An object that contains the System Limit of
			BCMS Measured VDNs.
	"
    ::= { avCmCapacityBcms 12 }

-- ******************** avCmCapacityCallVec Group *************************

-- MIB GROUP DESCRIPTION

-- MIB Group Name:
--		avCmCapacityCallVec
-- OID:
--		enterprises.6889.2.73.8.1.14
-- Description:
--		The avCmCapacityCallVec MIB Group uses the "display capacity"
-- 		command to retrieve the  CALL VECTORING capacity information
-- 		under the CALL VECTORING/CALL PROMPTING section
-- 		of the SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityCallVec	OBJECT IDENTIFIER ::= { avCmObjects 14 }

avCmCapacityCallVecTotalVdnUsed	OBJECT-TYPE
    SYNTAX	Integer32 (0..99999)
    MAX-ACCESS	read-only
    STATUS	current
    DESCRIPTION
	"
	Fld OID Name:	avCmCapacityCallVecTotalVdnUsed
	Fld OID:	enterprises.6889.2.73.8.1.14.1
	Fld Form/Rpt:	System Capacity
	Fld Format:	Single Field
	Fld(s) Name:	Total Vector Directory Numbers
	Fld Descr:	An object that contains the number of Used Total Vector
			Directory Numbers.
	"
    ::= { avCmCapacityCallVec 1 }

avCmCapacityCallVecTotalVdnAvail	OBJECT-TYPE
    SYNTAX	Integer32 (0..99999)
    MAX-ACCESS	read-only
    STATUS	current
    DESCRIPTION
	"
	Fld OID Name:	avCmCapacityCallVecTotalVdnAvail
	Fld OID:	enterprises.6889.2.73.8.1.14.2
	Fld Form/Rpt:	System Capacity
	Fld Format:	Single Field
	Fld(s) Name:	Total Vector Directory Numbers
	Fld Descr:	An object that contains the number of Available Total 
			Vector Directory Numbers.
	"
    ::= { avCmCapacityCallVec 2 }

avCmCapacityCallVecTotalVdnSysLim	OBJECT-TYPE
    SYNTAX	Integer32 (0..99999)
    MAX-ACCESS	read-only
    STATUS	current
    DESCRIPTION
	"
	Fld OID Name:	avCmCapacityCallVecTotalVdnSysLim
	Fld OID:	enterprises.6889.2.73.8.1.14.3
	Fld Form/Rpt:	System Capacity
	Fld Format:	Single Field
	Fld(s) Name:	Total Vector Directory Numbers
	Fld Descr:	An object that contains the System Limit of Total 
			Vector Directory Numbers.
	"
    ::= { avCmCapacityCallVec 3 }


avCmCapacityCallVecMeetMeVdnUsed	OBJECT-TYPE
    SYNTAX	Integer32 (0..99999)
    MAX-ACCESS	read-only
    STATUS	current
    DESCRIPTION
	"
	Fld OID Name:	avCmCapacityCallVecMeetMeVdnUsed
	Fld OID:	enterprises.6889.2.73.8.1.14.4
	Fld Form/Rpt:	System Capacity
	Fld Format:	Single Field
	Fld(s) Name:	Meet-me Conference VDNs per system
	Fld Descr:	An object that contains the number of Used Meet-me 
			Conference VDNs per system.
	"
    ::= { avCmCapacityCallVec 4 }

avCmCapacityCallVecMeetMeVdnAvail	OBJECT-TYPE
    SYNTAX	Integer32 (0..99999)
    MAX-ACCESS	read-only
    STATUS	current
    DESCRIPTION
	"
	Fld OID Name:	avCmCapacityCallVecMeetMeVdnAvail
	Fld OID:	enterprises.6889.2.73.8.1.14.5
	Fld Form/Rpt:	System Capacity
	Fld Format:	Single Field
	Fld(s) Name:	Meet-me Conference VDNs per system
	Fld Descr:	An object that contains the number of Available
			Meet-me Conference VDNs per system.
	"
    ::= { avCmCapacityCallVec 5 }

avCmCapacityCallVecMeetMeVdnSysLim	OBJECT-TYPE
    SYNTAX	Integer32 (0..99999)
    MAX-ACCESS	read-only
    STATUS	current
    DESCRIPTION
	"
	Fld OID Name:	avCmCapacityCallVecMeetMeVdnSysLim
	Fld OID:	enterprises.6889.2.73.8.1.14.6
	Fld Form/Rpt:	System Capacity
	Fld Format:	Single Field
	Fld(s) Name:	Meet-me Conference VDNs per system
	Fld Descr:	An object that contains the System Limit of Meet-me 
			Conference VDNs per system.
	"
    ::= { avCmCapacityCallVec 6 }

avCmCapacityCallVecMaxExpMeetMePtsUsed	OBJECT-TYPE
    SYNTAX	Integer32 (0..99999)
    MAX-ACCESS	read-only
    STATUS	current
    DESCRIPTION
	"
	Fld OID Name:	avCmCapacityCallVecMaxExpMeetMePtsUsed
	Fld OID:	enterprises.6889.2.73.8.1.14.7
	Fld Form/Rpt:	System Capacity
	Fld Format:	Single Field
	Fld(s) Name:	Maximum Number of Expanded Meet-me Conf. Ports
	Fld Descr:	An object that contains the number of Used Maximum 
			Number of Expanded Meet-me Conf. Ports.
	"
    ::= { avCmCapacityCallVec 7 }

avCmCapacityCallVecMaxExpMeetMePtsAvail	OBJECT-TYPE
    SYNTAX	Integer32 (0..99999)
    MAX-ACCESS	read-only
    STATUS	current
    DESCRIPTION
	"
	Fld OID Name:	avCmCapacityCallVecMaxExpMeetMePtsAvail
	Fld OID:	enterprises.6889.2.73.8.1.14.8
	Fld Form/Rpt:	System Capacity
	Fld Format:	Single Field
	Fld(s) Name:	Maximum Number of Expanded Meet-me Conf. Ports
	Fld Descr:	An object that contains the number of Available
			Maximum Number of Expanded Meet-me Conf. Ports
	"
    ::= { avCmCapacityCallVec 8 }

avCmCapacityCallVecMaxExpMeetMePtsSysLim	OBJECT-TYPE
    SYNTAX	Integer32 (0..99999)
    MAX-ACCESS	read-only
    STATUS	current
    DESCRIPTION
	"
	Fld OID Name:	avCmCapacityCallVecMaxExpMeetMePtsSysLim
	Fld OID:	enterprises.6889.2.73.8.1.14.9
	Fld Form/Rpt:	System Capacity
	Fld Format:	Single Field
	Fld(s) Name:	Maximum Number of Expanded Meet-me Conf. Ports
	Fld Descr:	An object that contains the System Limit of
			Maximum Number of Expanded Meet-me Conf. Ports.
	"
    ::= { avCmCapacityCallVec 9 }

avCmCapacityCallVecTotalVectorsUsed	OBJECT-TYPE
    SYNTAX	Integer32 (0..99999)
    MAX-ACCESS	read-only
    STATUS	current
    DESCRIPTION
	"
	Fld OID Name:	avCmCapacityCallVecTotalVectorsUsed
	Fld OID:	enterprises.6889.2.73.8.1.14.10
	Fld Form/Rpt:	System Capacity
	Fld Format:	Single Field
	Fld(s) Name:	Total Vectors Per System
	Fld Descr:	An object that contains the number of Used Total 
			Vectors Per System.
	"
    ::= { avCmCapacityCallVec 10 }

avCmCapacityCallVecTotalVectorsAvail	OBJECT-TYPE
    SYNTAX	Integer32 (0..99999)
    MAX-ACCESS	read-only
    STATUS	current
    DESCRIPTION
	"
	Fld OID Name:	avCmCapacityCallVecTotalVectorsAvail
	Fld OID:	enterprises.6889.2.73.8.1.14.11
	Fld Form/Rpt:	System Capacity
	Fld Format:	Single Field
	Fld(s) Name:	Total Vectors Per System
	Fld Descr:	An object that contains the number of Available
			Total Vectors Per System.
	"
    ::= { avCmCapacityCallVec 11 }

avCmCapacityCallVecTotalVectorsSysLim	OBJECT-TYPE
    SYNTAX	Integer32 (0..99999)
    MAX-ACCESS	read-only
    STATUS	current
    DESCRIPTION
	"
	Fld OID Name:	avCmCapacityCallVecTotalVectorsSysLim
	Fld OID:	enterprises.6889.2.73.8.1.14.12
	Fld Form/Rpt:	System Capacity
	Fld Format:	Single Field
	Fld(s) Name:	Total Vectors Per System
	Fld Descr:	An object that contains the System Limit of
			Total Vectors Per System
	"
    ::= { avCmCapacityCallVec 12 }

avCmCapacityCallVecMeetMeVectorsUsed	OBJECT-TYPE
    SYNTAX	Integer32 (0..99999)
    MAX-ACCESS	read-only
    STATUS	current
    DESCRIPTION
	"
	Fld OID Name:	avCmCapacityCallVecMeetMeVectorsUsed
	Fld OID:	enterprises.6889.2.73.8.1.14.13
	Fld Form/Rpt:	System Capacity
	Fld Format:	Single Field
	Fld(s) Name:	Meet-me Conference vectors per system
	Fld Descr:	An object that contains the number of Used
			Meet-me Conference vectors per system.
	"
    ::= { avCmCapacityCallVec 13 }

avCmCapacityCallVecMeetMeVectorsAvail	OBJECT-TYPE
    SYNTAX	Integer32 (0..99999)
    MAX-ACCESS	read-only
    STATUS	current
    DESCRIPTION
	"
	Fld OID Name:	avCmCapacityCallVecMeetMeVectorsAvail
	Fld OID:	enterprises.6889.2.73.8.1.14.14
	Fld Form/Rpt:	System Capacity
	Fld Format:	Single Field
	Fld(s) Name:	Meet-me Conference vectors per system
	Fld Descr:	An object that contains the number of Available
			Meet-me Conference vectors per system.
	"
    ::= { avCmCapacityCallVec 14 }

avCmCapacityCallVecMeetMeVectorsSysLim	OBJECT-TYPE
    SYNTAX	Integer32 (0..99999)
    MAX-ACCESS	read-only
    STATUS	current
    DESCRIPTION
	"
	Fld OID Name:	avCmCapacityCallVecMeetMeVectorsSysLim
	Fld OID:	enterprises.6889.2.73.8.1.14.15
	Fld Form/Rpt:	System Capacity
	Fld Format:	Single Field
	Fld(s) Name:	Meet-me Conference vectors per system
	Fld Descr:	An object that contains the System Limit of
			Meet-me Conference vectors per system.
	"
    ::= { avCmCapacityCallVec 15 }

avCmCapacityCallVecBsrAppLocPairsUsed	OBJECT-TYPE
    SYNTAX	Integer32 (0..99999)
    MAX-ACCESS	read-only
    STATUS	current
    DESCRIPTION
	"
	Fld OID Name:	avCmCapacityCallVecBsrAppLocPairsUsed
	Fld OID:	enterprises.6889.2.73.8.1.14.16
	Fld Form/Rpt:	System Capacity
	Fld Format:	Single Field
	Fld(s) Name:	BSR Application-Location Pairs Per System
	Fld Descr:	An object that contains the number of Used Maximum 
			BSR Application-Location Pairs Per System.
	"
    ::= { avCmCapacityCallVec 16 }

avCmCapacityCallVecBsrAppLocPairsAvail	OBJECT-TYPE
    SYNTAX	Integer32 (0..99999)
    MAX-ACCESS	read-only
    STATUS	current
    DESCRIPTION
	"
	Fld OID Name:	avCmCapacityCallVecBsrAppLocPairsAvail
	Fld OID:	enterprises.6889.2.73.8.1.14.17
	Fld Form/Rpt:	System Capacity
	Fld Format:	Single Field
	Fld(s) Name:	BSR Application-Location Pairs Per System
	Fld Descr:	An object that contains the number of Available
			BSR Application-Location Pairs Per System.
	"
    ::= { avCmCapacityCallVec  17}

avCmCapacityCallVecBsrAppLocPairsSysLim	OBJECT-TYPE
    SYNTAX	Integer32 (0..99999)
    MAX-ACCESS	read-only
    STATUS	current
    DESCRIPTION
	"
	Fld OID Name:	avCmCapacityCallVecBsrAppLocPairsSysLim
	Fld OID:	enterprises.6889.2.73.8.1.14.18
	Fld Form/Rpt:	System Capacity
	Fld Format:	Single Field
	Fld(s) Name:	BSR Application-Location Pairs Per System
	Fld Descr:	An object that contains the System Limit of
			BSR Application-Location Pairs Per System.
	"
    ::= { avCmCapacityCallVec 18 }

avCmCapacityCallVecBkgrdBsrPollVdnUsed	OBJECT-TYPE
    SYNTAX	Integer32 (0..99999)
    MAX-ACCESS	read-only
    STATUS	current
    DESCRIPTION
	"
	Fld OID Name:	avCmCapacityCallVecBkgrdBsrPollVdnUsed
	Fld OID:	enterprises.6889.2.73.8.1.14.19
	Fld Form/Rpt:	System Capacity
	Fld Format:	Single Field
	Fld(s) Name:	Background BSR Poll VDNs
	Fld Descr:	An object that contains the number of Used
			Background BSR Poll VDNs.
			
	"
    ::= { avCmCapacityCallVec 19 }

avCmCapacityCallVecBkgrdBsrPollVdnAvail	OBJECT-TYPE
    SYNTAX	Integer32 (0..99999)
    MAX-ACCESS	read-only
    STATUS	current
    DESCRIPTION
	"
	Fld OID Name:	avCmCapacityCallVecBkgrdBsrPollVdnAvail
	Fld OID:	enterprises.6889.2.73.8.1.14.20
	Fld Form/Rpt:	System Capacity
	Fld Format:	Single Field
	Fld(s) Name:	Background BSR Poll VDNs
	Fld Descr:	An object that contains the number of Available
			Background BSR Poll VDNs.
	"
    ::= { avCmCapacityCallVec 20 }

avCmCapacityCallVecBkgrdBsrPollVdnSysLim	OBJECT-TYPE
    SYNTAX	Integer32 (0..99999)
    MAX-ACCESS	read-only
    STATUS	current
    DESCRIPTION
	"
	Fld OID Name:	avCmCapacityCallVecBsrAppLocPairsSysLim
	Fld OID:	enterprises.6889.2.73.8.1.14.21
	Fld Form/Rpt:	System Capacity
	Fld Format:	Single Field
	Fld(s) Name:	Background BSR Poll VDNs
	Fld Descr:	An object that contains the System Limit of
			Background BSR Poll VDNs
	"
    ::= { avCmCapacityCallVec 21 }

avCmCapacityCallVecVecComStepsUsed	OBJECT-TYPE
    SYNTAX	Integer32 (0..99999)
    MAX-ACCESS	read-only
    STATUS	current
    DESCRIPTION
	"
	Fld OID Name:	avCmCapacityCallVecVecComStepsUsed
	Fld OID:	enterprises.6889.2.73.8.1.14.22
	Fld Form/Rpt:	System Capacity
	Fld Format:	Single Field
	Fld(s) Name:	Vector Comment Steps (non-blank)
	Fld Descr:	An object that contains the number of Used
			Vector Comment Steps (non-blank).
	"
    ::= { avCmCapacityCallVec 22 }

avCmCapacityCallVecVecComStepsAvail	OBJECT-TYPE
    SYNTAX	Integer32 (0..99999)
    MAX-ACCESS	read-only
    STATUS	current
    DESCRIPTION
	"
	Fld OID Name:	avCmCapacityCallVecVecComStepsAvail
	Fld OID:	enterprises.6889.2.73.8.1.14.23
	Fld Form/Rpt:	System Capacity
	Fld Format:	Single Field
	Fld(s) Name:	Vector Comment Steps (non-blank)
	Fld Descr:	An object that contains the number of Available
			Vector Comment Steps (non-blank).
	"
    ::= { avCmCapacityCallVec 23 }

avCmCapacityCallVecVecComStepsSysLim	OBJECT-TYPE
    SYNTAX	Integer32 (0..99999)
    MAX-ACCESS	read-only
    STATUS	current
    DESCRIPTION
	"
	Fld OID Name:	avCmCapacityCallVecVecComStepsSysLim
	Fld OID:	enterprises.6889.2.73.8.1.14.24
	Fld Form/Rpt:	System Capacity
	Fld Format:	Single Field
	Fld(s) Name:	Vector Comment Steps (non-blank)
	Fld Descr:	An object that contains the System Limit of
			Vector Comment Steps (non-blank).
	"
    ::= { avCmCapacityCallVec 24 }

avCmCapacityCallVecPolicyRoutTblUsed	OBJECT-TYPE
    SYNTAX	Integer32 (0..99999)
    MAX-ACCESS	read-only
    STATUS	current
    DESCRIPTION
	"
	Fld OID Name:	avCmCapacityCallVecPolicyRoutTblUsed
	Fld OID:	enterprises.6889.2.73.8.1.14.25
	Fld Form/Rpt:	System Capacity
	Fld Format:	Single Field
	Fld(s) Name:	Policy Routing Tables
	Fld Descr:	An object that contains the number of Used 
			Policy Routing Tables.
	"
    ::= { avCmCapacityCallVec 25 }

avCmCapacityCallVecPolicyRoutTblAvail	OBJECT-TYPE
    SYNTAX	Integer32 (0..99999)
    MAX-ACCESS	read-only
    STATUS	current
    DESCRIPTION
	"
	Fld OID Name:	avCmCapacityCallVecPolicyRoutTblAvail
	Fld OID:	enterprises.6889.2.73.8.1.14.26
	Fld Form/Rpt:	System Capacity
	Fld Format:	Single Field
	Fld(s) Name:	Policy Routing Tables
	Fld Descr:	An object that contains the number of
			Policy Routing Tables.
	"
    ::= { avCmCapacityCallVec 26 }

avCmCapacityCallVecPolicyRoutTblSysLim	OBJECT-TYPE
    SYNTAX	Integer32 (0..99999)
    MAX-ACCESS	read-only
    STATUS	current
    DESCRIPTION
	"
	Fld OID Name:	avCmCapacityCallVecPolicyRoutTblSysLim
	Fld OID:	enterprises.6889.2.73.8.1.14.27
	Fld Form/Rpt:	System Capacity
	Fld Format:	Single Field
	Fld(s) Name:	Policy Routing Tables
	Fld Descr:	An object that contains the System Limit of
			Policy Routing Tables
	"
    ::= { avCmCapacityCallVec 27 }

avCmCapacityCallVecPolicyRoutPtslUsed	OBJECT-TYPE
    SYNTAX	Integer32 (0..99999)
    MAX-ACCESS	read-only
    STATUS	current
    DESCRIPTION
	"
	Fld OID Name:	avCmCapacityCallVecPolicyRoutPtslUsed
	Fld OID:	enterprises.6889.2.73.8.1.14.28
	Fld Form/Rpt:	System Capacity
	Fld Format:	Single Field
	Fld(s) Name:	Policy Routing Points
	Fld Descr:	An object that contains the number of Used 
			Policy Routing Points
	"
    ::= { avCmCapacityCallVec 28 }

avCmCapacityCallVecPolicyRoutPtsAvail	OBJECT-TYPE
    SYNTAX	Integer32 (0..99999)
    MAX-ACCESS	read-only
    STATUS	current
    DESCRIPTION
	"
	Fld OID Name:	avCmCapacityCallVecPolicyRoutPtsAvail
	Fld OID:	enterprises.6889.2.73.8.1.14.29
	Fld Form/Rpt:	System Capacity
	Fld Format:	Single Field
	Fld(s) Name:	Policy Routing Points
	Fld Descr:	An object that contains the number of Available
			Policy Routing Points
	"
    ::= { avCmCapacityCallVec 29 }

avCmCapacityCallVecPolicyRoutPtsSysLim	OBJECT-TYPE
    SYNTAX	Integer32 (0..99999)
    MAX-ACCESS	read-only
    STATUS	current
    DESCRIPTION
	"
	Fld OID Name:	avCmCapacityCallVecPolicyRoutPtsSysLim
	Fld OID:	enterprises.6889.2.73.8.1.14.30
	Fld Form/Rpt:	System Capacity
	Fld Format:	Single Field
	Fld(s) Name:	Policy Routing Points
	Fld Descr:	An object that contains the System Limit of
			Policy Routing Points
	"
    ::= { avCmCapacityCallVec 30 }

-- ******************** avCmCapacityDialPlan Group *************************

-- MIB GROUP DESCRIPTION

-- MIB Group Name:
--		avCmCapacityDialPlan
-- OID:
--		enterprises.6889.2.73.8.1.15
-- Description:
--		The avCmCapacityDialPlan MIB Group uses the "display capacity"
-- 		command to retrieve the DIAL PLAN capacity information
-- 		under the DIAL PLAN section of the SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityDialPlan	OBJECT IDENTIFIER ::= { avCmObjects 15 }

avCmCapacityDialPlanExtUsed	OBJECT-TYPE
    SYNTAX	Integer32 (0..99999)
    MAX-ACCESS	read-only
    STATUS	current
    DESCRIPTION
	"
	Fld OID Name:	avCmCapacityDialPlanExtUsed
	Fld OID:	enterprises.6889.2.73.8.1.15.1
	Fld Form/Rpt:	System Capacity
	Fld Format:	Single Field
	Fld(s) Name:	Extensions
	Fld Descr:	An object that contains the number of Used 
			Extensions.
	"
    ::= { avCmCapacityDialPlan 1 }

avCmCapacityDialPlanExtAvail	OBJECT-TYPE
    SYNTAX	Integer32 (0..99999)
    MAX-ACCESS	read-only
    STATUS	current
    DESCRIPTION
	"
	Fld OID Name:	avCmCapacityDialPlanExtAvail
	Fld OID:	enterprises.6889.2.73.8.1.15.2
	Fld Form/Rpt:	System Capacity
	Fld Format:	Single Field
	Fld(s) Name:	Extensions
	Fld Descr:	An object that contains the number of Available 
			Extensions.
	"
    ::= { avCmCapacityDialPlan 2 }

avCmCapacityDialPlanExtSysLim	OBJECT-TYPE
    SYNTAX	Integer32 (0..99999)
    MAX-ACCESS	read-only
    STATUS	current
    DESCRIPTION
	"
	Fld OID Name:	avCmCapacityDialPlanExtSysLim
	Fld OID:	enterprises.6889.2.73.8.1.15.3
	Fld Form/Rpt:	System Capacity
	Fld Format:	Single Field
	Fld(s) Name:	Extensions
	Fld Descr:	An object that contains the System Limit of 
			Extensions.
	"
    ::= { avCmCapacityDialPlan 3 }


avCmCapacityDialPlanMiscExtUsed	OBJECT-TYPE
    SYNTAX	Integer32 (0..99999)
    MAX-ACCESS	read-only
    STATUS	current
    DESCRIPTION
	"
	Fld OID Name:	avCmCapacityDialPlanMiscExtUsed
	Fld OID:	enterprises.6889.2.73.8.1.15.4
	Fld Form/Rpt:	System Capacity
	Fld Format:	Single Field
	Fld(s) Name:	Miscellaneous Extensions
	Fld Descr:	An object that contains the number of Used 
			Miscellaneous Extensions.
	"
    ::= { avCmCapacityDialPlan 4 }

avCmCapacityDialPlanMiscExtAvail	OBJECT-TYPE
    SYNTAX	Integer32 (0..99999)
    MAX-ACCESS	read-only
    STATUS	current
    DESCRIPTION
	"
	Fld OID Name:	avCmCapacityDialPlanMiscExtAvail
	Fld OID:	enterprises.6889.2.73.8.1.15.5
	Fld Form/Rpt:	System Capacity
	Fld Format:	Single Field
	Fld(s) Name:	Miscellaneous Extensions
	Fld Descr:	An object that contains the number of Available
			Miscellaneous Extensions.
	"
    ::= { avCmCapacityDialPlan 5 }

avCmCapacityDialPlanMiscExtSysLim	OBJECT-TYPE
    SYNTAX	Integer32 (0..99999)
    MAX-ACCESS	read-only
    STATUS	current
    DESCRIPTION
	"
	Fld OID Name:	avCmCapacityDialPlanMiscExtSysLim
	Fld OID:	enterprises.6889.2.73.8.1.15.6
	Fld Form/Rpt:	System Capacity
	Fld Format:	Single Field
	Fld(s) Name:	Miscellaneous Extensions
	Fld Descr:	An object that contains the System Limit of
			Miscellaneous Extensions.
	"
    ::= { avCmCapacityDialPlan 6 }

-- ******************** avCmCapacityHuntGrps Group *************************

-- MIB GROUP DESCRIPTION

-- MIB Group Name:
--		avCmCapacityHuntGrps
-- OID:
--		enterprises.6889.2.73.8.1.16
-- Description:
--		The avCmCapacityHuntGrps MIB Group uses the "display capacity"
-- 		command to retrieve the HUNT GROUPS capacity information
-- 		under the HUNT GROUPS, SPLITS, OR SKILLS section of the 
--		SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityHuntGrps	OBJECT IDENTIFIER ::= { avCmObjects 16 }

avCmCapacityHuntGrpsSpSkUsed	OBJECT-TYPE
    SYNTAX	Integer32 (0..99999)
    MAX-ACCESS	read-only
    STATUS	current
    DESCRIPTION
	"
	Fld OID Name:	avCmCapacityHuntGrpsSpSkUsed
	Fld OID:	enterprises.6889.2.73.8.1.16.1
	Fld Form/Rpt:	System Capacity
	Fld Format:	Single Field
	Fld(s) Name:	Groups/Splits/Skills
	Fld Descr:	An object that contains the number of Used 
			Groups/Splits/Skills.
	"
    ::= { avCmCapacityHuntGrps 1 }

avCmCapacityHuntGrpsSpSkAvail	OBJECT-TYPE
    SYNTAX	Integer32 (0..99999)
    MAX-ACCESS	read-only
    STATUS	current
    DESCRIPTION
	"
	Fld OID Name:	avCmCapacityHuntGrpsSpSkAvail
	Fld OID:	enterprises.6889.2.73.8.1.16.2
	Fld Form/Rpt:	System Capacity
	Fld Format:	Single Field
	Fld(s) Name:	Groups/Splits/Skills
	Fld Descr:	An object that contains the number of Available 
			Groups/Splits/Skills.
	"
    ::= { avCmCapacityHuntGrps 2 }

avCmCapacityHuntGrpsSpSkSysLim	OBJECT-TYPE
    SYNTAX	Integer32 (0..99999)
    MAX-ACCESS	read-only
    STATUS	current
    DESCRIPTION
	"
	Fld OID Name:	avCmCapacityHuntGrpsSpSkSysLim
	Fld OID:	enterprises.6889.2.73.8.1.16.3
	Fld Form/Rpt:	System Capacity
	Fld Format:	Single Field
	Fld(s) Name:	Groups/Splits/Skills
	Fld Descr:	An object that contains the System Limit of 
			Groups/Splits/Skills.
	"
    ::= { avCmCapacityHuntGrps 3 }


avCmCapacityHuntGrpsAdmLogAgtUsed	OBJECT-TYPE
    SYNTAX	Integer32 (0..99999)
    MAX-ACCESS	read-only
    STATUS	current
    DESCRIPTION
	"
	Fld OID Name:	avCmCapacityHuntGrpsAdmLogAgtUsed
	Fld OID:	enterprises.6889.2.73.8.1.16.4
	Fld Form/Rpt:	System Capacity
	Fld Format:	Single Field
	Fld(s) Name:	Administered Logical Agents
	Fld Descr:	An object that contains the number of Used 
			Administered Logical Agents.
	"
    ::= { avCmCapacityHuntGrps 4 }

avCmCapacityHuntGrpsAdmLogAgtAvail	OBJECT-TYPE
    SYNTAX	Integer32 (0..99999)
    MAX-ACCESS	read-only
    STATUS	current
    DESCRIPTION
	"
	Fld OID Name:	avCmCapacityHuntGrpsAdmLogAgtAvail
	Fld OID:	enterprises.6889.2.73.8.1.16.5
	Fld Form/Rpt:	System Capacity
	Fld Format:	Single Field
	Fld(s) Name:	Administered Logical Agents
	Fld Descr:	An object that contains the number of Available
			Administered Logical Agents.
	"
    ::= { avCmCapacityHuntGrps 5 }

avCmCapacityHuntGrpsAdmLogAgtSysLim	OBJECT-TYPE
    SYNTAX	Integer32 (0..99999)
    MAX-ACCESS	read-only
    STATUS	current
    DESCRIPTION
	"
	Fld OID Name:	avCmCapacityHuntGrpsAdmLogAgtSysLim
	Fld OID:	enterprises.6889.2.73.8.1.16.6
	Fld Form/Rpt:	System Capacity
	Fld Format:	Single Field
	Fld(s) Name:	Administered Logical Agents
	Fld Descr:	An object that contains the System Limit
			Administered Logical Agents
	"
    ::= { avCmCapacityHuntGrps 6 }

avCmCapacityHuntGrpsAdmLogAgtSkPrUsed	OBJECT-TYPE
    SYNTAX	Integer32 (0..99999)
    MAX-ACCESS	read-only
    STATUS	current
    DESCRIPTION
	"
	Fld OID Name:	avCmCapacityHuntGrpsAdmLogAgtSkPrUsed
	Fld OID:	enterprises.6889.2.73.8.1.16.7
	Fld Form/Rpt:	System Capacity
	Fld Format:	Single Field
	Fld(s) Name:	Administered Logical Agent-Skill Pairs
	Fld Descr:	An object that contains the number of Used 
			Administered Logical Agent-Skill Pairs.
	"
    ::= { avCmCapacityHuntGrps 7 }

avCmCapacityHuntGrpsAdmLogAgtSkPrAvail	OBJECT-TYPE
    SYNTAX	Integer32 (0..99999)
    MAX-ACCESS	read-only
    STATUS	current
    DESCRIPTION
	"
	Fld OID Name:	avCmCapacityHuntGrpsAdmLogAgtSkPrAvail
	Fld OID:	enterprises.6889.2.73.8.1.16.8
	Fld Form/Rpt:	System Capacity
	Fld Format:	Single Field
	Fld(s) Name:	Administered Logical Agent-Skill Pairs
	Fld Descr:	An object that contains the number of Available
			Administered Logical Agent-Skill Pairs.
	"
    ::= { avCmCapacityHuntGrps 8 }

avCmCapacityHuntGrpsAdmLogAgtSkPrSysLim	OBJECT-TYPE
    SYNTAX	Integer32 (0..99999)
    MAX-ACCESS	read-only
    STATUS	current
    DESCRIPTION
	"
	Fld OID Name:	avCmCapacityHuntGrpsAdmLogAgtSkPrSysLim
	Fld OID:	enterprises.6889.2.73.8.1.16.9
	Fld Form/Rpt:	System Capacity
	Fld Format:	Single Field
	Fld(s) Name:	Administered Logical Agent-Skill Pairs
	Fld Descr:	An object that contains the System Limit of
			Administered Logical Agent-Skill Pairs.
	"
    ::= { avCmCapacityHuntGrps 9 }

avCmCapacityHuntGrpsLogAcdAgtUsed	OBJECT-TYPE
    SYNTAX      Integer32 (0..99999)
    MAX-ACCESS	read-only
    STATUS	current
    DESCRIPTION
	"
	Fld OID Name:	avCmCapacityHuntGrpsLogAcdAgtUsed
	Fld OID:	enterprises.6889.2.73.8.1.16.10
	Fld Form/Rpt:	System Capacity
	Fld Format:	Single Field
	Fld(s) Name:	Logged-In ACD Agents
	Fld Descr:	An object that contains the number of Used 
			Logged-In ACD Agents.
	"
    ::= { avCmCapacityHuntGrps 10 }

avCmCapacityHuntGrpsLogAcdAgtAvail	OBJECT-TYPE
    SYNTAX      Integer32 (0..99999)
    MAX-ACCESS	read-only
    STATUS	current
    DESCRIPTION
	"
	Fld OID Name:	avCmCapacityHuntGrpsLogAcdAgtAvail
	Fld OID:	enterprises.6889.2.73.8.1.16.11
	Fld Form/Rpt:	System Capacity
	Fld Format:	Single Field
	Fld(s) Name:	Logged-In ACD Agents
	Fld Descr:	An object that contains the number of Available
			Logged-In ACD Agents.
	"
    ::= { avCmCapacityHuntGrps  11 }

avCmCapacityHuntGrpsLogAcdAgtSysLim	OBJECT-TYPE
    SYNTAX      Integer32 (0..99999)
    MAX-ACCESS	read-only
    STATUS	current
    DESCRIPTION
	"
	Fld OID Name:	avCmCapacityHuntGrpsLogAcdAgtSysLim
	Fld OID:	enterprises.6889.2.73.8.1.16.12
	Fld Form/Rpt:	System Capacity
	Fld Format:	Single Field
	Fld(s) Name:	Logged-In ACD Agents
	Fld Descr:	An object that contains the System Limit of
			Logged-In ACD Agents.
	"
    ::= { avCmCapacityHuntGrps 12 }

avCmCapacityHuntGrpsLogAdvocAgtUsed	OBJECT-TYPE
    SYNTAX      Integer32 (0..99999)
    MAX-ACCESS	read-only
    STATUS	current
    DESCRIPTION
	"
	Fld OID Name:	avCmCapacityHuntGrpsLogAdvocAgtUsed
	Fld OID:	enterprises.6889.2.73.8.1.16.13
	Fld Form/Rpt:	System Capacity
	Fld Format:	Single Field
	Fld(s) Name:	Logged-In Advocate Agents
	Fld Descr:	An object that contains the number of Used 
			Logged-In Advocate Agents.
	"
    ::= { avCmCapacityHuntGrps 13 }

avCmCapacityHuntGrpsLogAdvocAgtAvail	OBJECT-TYPE
    SYNTAX      Integer32 (0..99999)
    MAX-ACCESS	read-only
    STATUS	current
    DESCRIPTION
	"
	Fld OID Name:	avCmCapacityHuntGrpsLogAdvocAgtAvail
	Fld OID:	enterprises.6889.2.73.8.1.16.14
	Fld Form/Rpt:	System Capacity
	Fld Format:	Single Field
	Fld(s) Name:	Logged-In Advocate Agents
	Fld Descr:	An object that contains the number of Available
			Logged-In Advocate Agents.
	"
    ::= { avCmCapacityHuntGrps 14 }

avCmCapacityHuntGrpsLogAdvocAgtSysLim	OBJECT-TYPE
    SYNTAX      Integer32 (0..99999)
    MAX-ACCESS	read-only
    STATUS	current
    DESCRIPTION
	"
	Fld OID Name:	avCmCapacityHuntGrpsLogAdvocAgtSysLim
	Fld OID:	enterprises.6889.2.73.8.1.16.15
	Fld Form/Rpt:	System Capacity
	Fld Format:	Single Field
	Fld(s) Name:	Logged-In Advocate Agents
	Fld Descr:	An object that contains the System Limit of
			Logged-In Advocate Agents.
	"
    ::= { avCmCapacityHuntGrps 15 }

avCmCapacityHuntGrpsLogIPSoftAgtUsed	OBJECT-TYPE
    SYNTAX      Integer32 (0..99999)
    MAX-ACCESS	read-only
    STATUS	current
    DESCRIPTION
	"
	Fld OID Name:	avCmCapacityHuntGrpsLogIPSoftAgtUsed
	Fld OID:	enterprises.6889.2.73.8.1.16.16
	Fld Form/Rpt:	System Capacity
	Fld Format:	Single Field
	Fld(s) Name:	Logged-In IP Softphone Agents
	Fld Descr:	An object that contains the number of Used 
			Logged-In IP Softphone Agents.
	"
    ::= { avCmCapacityHuntGrps  16 }

avCmCapacityHuntGrpsLogIPSoftAgtAvail	OBJECT-TYPE
    SYNTAX      Integer32 (0..99999)
    MAX-ACCESS	read-only
    STATUS	current
    DESCRIPTION
	"
	Fld OID Name:	avCmCapacityHuntGrpsLogIPSoftAgtAvail
	Fld OID:	enterprises.6889.2.73.8.1.16.17
	Fld Form/Rpt:	System Capacity
	Fld Format:	Single Field
	Fld(s) Name:	Logged-In IP Softphone Agents
	Fld Descr:	An object that contains the number of Available
			Logged-In IP Softphone Agents.
	"
    ::= { avCmCapacityHuntGrps 17 }

avCmCapacityHuntGrpsLogIPSoftAgtSysLim	OBJECT-TYPE
    SYNTAX      Integer32 (0..99999)
    MAX-ACCESS	read-only
    STATUS	current
    DESCRIPTION
	"
	Fld OID Name:	avCmCapacityHuntGrpsLogIPSoftAgtSysLim
	Fld OID:	enterprises.6889.2.73.8.1.16.18
	Fld Form/Rpt:	System Capacity
	Fld Format:	Single Field
	Fld(s) Name:	Logged-In IP Softphone Agents
	Fld Descr:	An object that contains the System Limit of
			Logged-In IP Softphone Agents
	"
    ::= { avCmCapacityHuntGrps 18 }

avCmCapacityHuntGrpsLogSipEasAgtUsed	OBJECT-TYPE
    SYNTAX      Integer32 (0..99999)
    MAX-ACCESS	read-only
    STATUS	current
    DESCRIPTION
	"
	Fld OID Name:	avCmCapacityHuntGrpsLogSipEasAgtUsed
	Fld OID:	enterprises.6889.2.73.8.1.16.19
	Fld Form/Rpt:	System Capacity
	Fld Format:	Single Field
	Fld(s) Name:	Logged-In SIP EAS Agents
	Fld Descr:	An object that contains the number of Used 
			Logged-In SIP EAS Agents.
	"
    ::= { avCmCapacityHuntGrps 19 }

avCmCapacityHuntGrpsLogSipEasAgtAvail	OBJECT-TYPE
    SYNTAX      Integer32 (0..99999)
    MAX-ACCESS	read-only
    STATUS	current
    DESCRIPTION
	"
	Fld OID Name:	avCmCapacityHuntGrpsLogSipEasAgtAvail
	Fld OID:	enterprises.6889.2.73.8.1.16.20
	Fld Form/Rpt:	System Capacity
	Fld Format:	Single Field
	Fld(s) Name:	Logged-In SIP EAS Agents
	Fld Descr:	An object that contains the number of Available
			Logged-In SIP EAS Agents.
	"
    ::= { avCmCapacityHuntGrps 20 }

avCmCapacityHuntGrpsLogSipEasAgtSysLim	OBJECT-TYPE
    SYNTAX      Integer32 (0..99999)
    MAX-ACCESS	read-only
    STATUS	current
    DESCRIPTION
	"
	Fld OID Name:	avCmCapacityHuntGrpsLogSipEasAgtSysLim
	Fld OID:	enterprises.6889.2.73.8.1.16.21
	Fld Form/Rpt:	System Capacity
	Fld Format:	Single Field
	Fld(s) Name:	Logged-In SIP EAS Agents
	Fld Descr:	An object that contains the System Limit of
			Logged-In SIP EAS Agents.
	"
    ::= { avCmCapacityHuntGrps 21 }

avCmCapacityHuntGrpsGrpsMemPerSysUsed	OBJECT-TYPE
    SYNTAX      Integer32 (0..99999)
    MAX-ACCESS	read-only
    STATUS	current
    DESCRIPTION
	"
	Fld OID Name:	avCmCapacityHuntGrpsGrpsMemPerSysUsed
	Fld OID:	enterprises.6889.2.73.8.1.16.22
	Fld Form/Rpt:	System Capacity
	Fld Format:	Single Field
	Fld(s) Name:	Group Members Per System
	Fld Descr:	An object that contains the number of Used 
			Group Members Per System.
	"
    ::= { avCmCapacityHuntGrps 22 }

avCmCapacityHuntGrpsGrpsMemPerSysAvail	OBJECT-TYPE
    SYNTAX      Integer32 (0..99999)
    MAX-ACCESS	read-only
    STATUS	current
    DESCRIPTION
	"
	Fld OID Name:	avCmCapacityHuntGrpsGrpsMemPerSysAvail
	Fld OID:	enterprises.6889.2.73.8.1.16.23
	Fld Form/Rpt:	System Capacity
	Fld Format:	Single Field
	Fld(s) Name:	Group Members Per System
	Fld Descr:	An object that contains the number of Available
			Group Members Per System.
	"
    ::= { avCmCapacityHuntGrps 23 }

avCmCapacityHuntGrpsGrpsMemPerSysSysLim	OBJECT-TYPE
    SYNTAX      Integer32 (0..99999)
    MAX-ACCESS	read-only
    STATUS	current
    DESCRIPTION
	"
	Fld OID Name:	avCmCapacityHuntGrpsGrpsMemPerSysSysLim
	Fld OID:	enterprises.6889.2.73.8.1.16.24
	Fld Form/Rpt:	System Capacity
	Fld Format:	Single Field
	Fld(s) Name:	Group Members Per System
	Fld Descr:	An object that contains the System Limit of
			Group Members Per System.
	"
    ::= { avCmCapacityHuntGrps 24 }

avCmCapacityHuntGrpsCmsMeasAcdMemUsed	OBJECT-TYPE
    SYNTAX      Integer32 (0..99999)
    MAX-ACCESS	read-only
    STATUS	current
    DESCRIPTION
	"
	Fld OID Name:	avCmCapacityHuntGrpsCmsMeasAcdMemUsed
	Fld OID:	enterprises.6889.2.73.8.1.16.25
	Fld Form/Rpt:	System Capacity
	Fld Format:	Single Field
	Fld(s) Name:	CMS Measured ACD Members
	Fld Descr:	An object that contains the number of Used 
			CMS Measured ACD Members.
	"
    ::= { avCmCapacityHuntGrps 25 }

avCmCapacityHuntGrpsCmsMeasAcdMemAvail	OBJECT-TYPE
    SYNTAX      Integer32 (0..99999)
    MAX-ACCESS	read-only
    STATUS	current
    DESCRIPTION
	"
	Fld OID Name:	avCmCapacityHuntGrpsCmsMeasAcdMemAvail
	Fld OID:	enterprises.6889.2.73.8.1.16.26
	Fld Form/Rpt:	System Capacity
	Fld Format:	Single Field
	Fld(s) Name:	CMS Measured ACD Members
	Fld Descr:	An object that contains the number of Available
			CMS Measured ACD Members.
	"
    ::= { avCmCapacityHuntGrps 26 }

avCmCapacityHuntGrpsCmsMeasAcdMemSysLim	OBJECT-TYPE
    SYNTAX      Integer32 (0..99999)
    MAX-ACCESS	read-only
    STATUS	current
    DESCRIPTION
	"
	Fld OID Name:	avCmCapacityHuntGrpsCmsMeasAcdMemSysLim
	Fld OID:	enterprises.6889.2.73.8.1.16.27
	Fld Form/Rpt:	System Capacity
	Fld Format:	Single Field
	Fld(s) Name:	CMS Measured ACD Members
	Fld Descr:	An object that contains the System Limit of
			CMS Measured ACD Members.
	"
    ::= { avCmCapacityHuntGrps 27 }

-- ******************** avCmCapacityAnnounce Group *************************

-- MIB GROUP DESCRIPTION

-- MIB Group Name:
--		avCmCapacityAnnounce
-- OID:
--		enterprises.6889.2.73.8.1.17
-- Description:
--		The avCmCapacityAnnounce MIB Group uses the "display capacity"
-- 		command to retrieve the ANNOUNCEMENTS capacity information
-- 		under the RECORDED ANNOUNCEMENTS/MUSIC/AUDIO SOURCES section of
--		the SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityAnnounce	OBJECT IDENTIFIER ::= { avCmObjects 17 }

avCmCapacityAnnounceAdmAnnFileUsed	OBJECT-TYPE
    SYNTAX	Integer32 (0..99999)
    MAX-ACCESS	read-only
    STATUS	current
    DESCRIPTION
	"
	Fld OID Name:	avCmCapacityAnnounceAdmAnnFileUsed
	Fld OID:	enterprises.6889.2.73.8.1.17.1
	Fld Form/Rpt:	System Capacity
	Fld Format:	Single Field
	Fld(s) Name:	Administered Announcement Files
	Fld Descr:	An object that contains the number of Used 
			Administered Announcement Files.
	"
    ::= { avCmCapacityAnnounce 1 }

avCmCapacityAnnounceAdmAnnFileAvail	OBJECT-TYPE
    SYNTAX	Integer32 (0..99999)
    MAX-ACCESS	read-only
    STATUS	current
    DESCRIPTION
	"
	Fld OID Name:	avCmCapacityAnnounceAdmAnnFileAvail
	Fld OID:	enterprises.6889.2.73.8.1.17.2
	Fld Form/Rpt:	System Capacity
	Fld Format:	Single Field
	Fld(s) Name:	Administered Announcement Files
	Fld Descr:	An object that contains the number of Available 
			Administered Announcement Files.
	"
    ::= { avCmCapacityAnnounce 2 }

avCmCapacityAnnounceAdmAnnFileSysLim	OBJECT-TYPE
    SYNTAX	Integer32 (0..99999)
    MAX-ACCESS	read-only
    STATUS	current
    DESCRIPTION
	"
	Fld OID Name:	avCmCapacityAnnounceAdmAnnFileSysLim
	Fld OID:	enterprises.6889.2.73.8.1.17.3
	Fld Form/Rpt:	System Capacity
	Fld Format:	Single Field
	Fld(s) Name:	Administered Announcement Files
	Fld Descr:	An object that contains the System Limit of 
			Administered Announcement Files.
	"
    ::= { avCmCapacityAnnounce 3 }


avCmCapacityAnnounceTN2501ValBrdUsed	OBJECT-TYPE
    SYNTAX	Integer32 (0..99999)
    MAX-ACCESS	read-only
    STATUS	current
    DESCRIPTION
	"
	Fld OID Name:	avCmCapacityAnnounceTN2501ValBrdUsed
	Fld OID:	enterprises.6889.2.73.8.1.17.4
	Fld Form/Rpt:	System Capacity
	Fld Format:	Single Field
	Fld(s) Name:	TN2501 VAL Boards
	Fld Descr:	An object that contains the number of Used 
			TN2501 VAL Boards.
	"
    ::= { avCmCapacityAnnounce 4 }

avCmCapacityAnnounceTN2501ValBrdAvail	OBJECT-TYPE
    SYNTAX	Integer32 (0..99999)
    MAX-ACCESS	read-only
    STATUS	current
    DESCRIPTION
	"
	Fld OID Name:	avCmCapacityAnnounceTN2501ValBrdAvail
	Fld OID:	enterprises.6889.2.73.8.1.17.5
	Fld Form/Rpt:	System Capacity
	Fld Format:	Single Field
	Fld(s) Name:	TN2501 VAL Boards
	Fld Descr:	An object that contains the number of Available
			TN2501 VAL Boards.
	"
    ::= { avCmCapacityAnnounce 5 }

avCmCapacityAnnounceTN2501ValBrdSysLim	OBJECT-TYPE
    SYNTAX	Integer32 (0..99999)
    MAX-ACCESS	read-only
    STATUS	current
    DESCRIPTION
	"
	Fld OID Name:	avCmCapacityAnnounceTN2501ValBrdSysLim
	Fld OID:	enterprises.6889.2.73.8.1.17.6
	Fld Form/Rpt:	System Capacity
	Fld Format:	Single Field
	Fld(s) Name:	TN2501 VAL Boards
	Fld Descr:	An object that contains the System Limit
			TN2501 VAL Boards.
	"
    ::= { avCmCapacityAnnounce 6 }

avCmCapacityAnnounceMGValSrcUsed	OBJECT-TYPE
    SYNTAX	Integer32 (0..99999)
    MAX-ACCESS	read-only
    STATUS	current
    DESCRIPTION
	"
	Fld OID Name:	avCmCapacityAnnounceMGValSrcUsed
	Fld OID:	enterprises.6889.2.73.8.1.17.7
	Fld Form/Rpt:	System Capacity
	Fld Format:	Single Field
	Fld(s) Name:	Media Gateway vVAL Sources
	Fld Descr:	An object that contains the number of Used 
			Media Gateway vVAL Sources.
	"
    ::= { avCmCapacityAnnounce 7 }

avCmCapacityAnnounceMGValSrcAvail	OBJECT-TYPE
    SYNTAX	Integer32 (0..99999)
    MAX-ACCESS	read-only
    STATUS	current
    DESCRIPTION
	"
	Fld OID Name:	avCmCapacityAnnounceMGValSrcAvail
	Fld OID:	enterprises.6889.2.73.8.1.17.8
	Fld Form/Rpt:	System Capacity
	Fld Format:	Single Field
	Fld(s) Name:	Media Gateway vVAL Sources
	Fld Descr:	An object that contains the number of Available
			Media Gateway vVAL Sources.
	"
    ::= { avCmCapacityAnnounce 8 }

avCmCapacityAnnounceMGValSrcSysLim	OBJECT-TYPE
    SYNTAX	Integer32 (0..99999)
    MAX-ACCESS	read-only
    STATUS	current
    DESCRIPTION
	"
	Fld OID Name:	avCmCapacityAnnounceMGValSrcSysLim
	Fld OID:	enterprises.6889.2.73.8.1.17.9
	Fld Form/Rpt:	System Capacity
	Fld Format:	Single Field
	Fld(s) Name:	Media Gateway vVAL Sources
	Fld Descr:	An object that contains the System Limit of
			Media Gateway vVAL Sources.
	"
    ::= { avCmCapacityAnnounce 9 }

avCmCapacityAnnounceTN2602Brds80ChUsed	OBJECT-TYPE
    SYNTAX      Integer32 (0..99999)
    MAX-ACCESS	read-only
    STATUS	current
    DESCRIPTION
	"
	Fld OID Name:	avCmCapacityAnnounceTN2602Brds80ChUsed
	Fld OID:	enterprises.6889.2.73.8.1.17.10
	Fld Form/Rpt:	System Capacity
	Fld Format:	Single Field
	Fld(s) Name:	TN2602 Boards with 80 VoIP Channels
	Fld Descr:	An object that contains the number of Used 
			TN2602 Boards with 80 VoIP Channels.
	"
    ::= { avCmCapacityAnnounce 10 }

avCmCapacityAnnounceTN2602Brds80ChAvail	OBJECT-TYPE
    SYNTAX      Integer32 (0..99999)
    MAX-ACCESS	read-only
    STATUS	current
    DESCRIPTION
	"
	Fld OID Name:	avCmCapacityAnnounceTN2602Brds80ChAvail
	Fld OID:	enterprises.6889.2.73.8.1.17.11
	Fld Form/Rpt:	System Capacity
	Fld Format:	Single Field
	Fld(s) Name:	TN2602 Boards with 80 VoIP Channels
	Fld Descr:	An object that contains the number of Available
			TN2602 Boards with 80 VoIP Channels.
	"
    ::= { avCmCapacityAnnounce  11 }

avCmCapacityAnnounceTN2602Brds80ChSysLim	OBJECT-TYPE
    SYNTAX      Integer32 (0..99999)
    MAX-ACCESS	read-only
    STATUS	current
    DESCRIPTION
	"
	Fld OID Name:	avCmCapacityAnnounceTN2602Brds80ChSysLim
	Fld OID:	enterprises.6889.2.73.8.1.17.12
	Fld Form/Rpt:	System Capacity
	Fld Format:	Single Field
	Fld(s) Name:	TN2602 Boards with 80 VoIP Channels
	Fld Descr:	An object that contains the System Limit of
			TN2602 Boards with 80 VoIP Channels.
	"
    ::= { avCmCapacityAnnounce 12 }

avCmCapacityAnnounceTN2602Brds320Used	OBJECT-TYPE
    SYNTAX      Integer32 (0..99999)
    MAX-ACCESS	read-only
    STATUS	current
    DESCRIPTION
	"
	Fld OID Name:	avCmCapacityAnnounceTN2602Brds320Used
	Fld OID:	enterprises.6889.2.73.8.1.17.13
	Fld Form/Rpt:	System Capacity
	Fld Format:	Single Field
	Fld(s) Name:	TN2602 Boards with 320 VoIP Channels
	Fld Descr:	An object that contains the number of Used 
			TN2602 Boards with 320 VoIP Channels.
	"
    ::= { avCmCapacityAnnounce 13 }

avCmCapacityAnnounceTN2602Brds320Avail	OBJECT-TYPE
    SYNTAX      Integer32 (0..99999)
    MAX-ACCESS	read-only
    STATUS	current
    DESCRIPTION
	"
	Fld OID Name:	avCmCapacityAnnounceTN2602Brds320Avail
	Fld OID:	enterprises.6889.2.73.8.1.17.14
	Fld Form/Rpt:	System Capacity
	Fld Format:	Single Field
	Fld(s) Name:	TN2602 Boards with 320 VoIP Channels
	Fld Descr:	An object that contains the number of Available
			TN2602 Boards with 320 VoIP Channels.
	"
    ::= { avCmCapacityAnnounce 14 }

avCmCapacityAnnounceTN2602Brds320SysLim	OBJECT-TYPE
    SYNTAX      Integer32 (0..99999)
    MAX-ACCESS	read-only
    STATUS	current
    DESCRIPTION
	"
	Fld OID Name:	avCmCapacityAnnounceTN2602Brds320SysLim
	Fld OID:	enterprises.6889.2.73.8.1.17.15
	Fld Form/Rpt:	System Capacity
	Fld Format:	Single Field
	Fld(s) Name:	TN2602 Boards with 320 VoIP Channels
	Fld Descr:	An object that contains the System Limit of
			TN2602 Boards with 320 VoIP Channels.
	"
    ::= { avCmCapacityAnnounce 15 }

avCmCapacityAnnounceAvayaMedServUsed	OBJECT-TYPE
    SYNTAX      Integer32 (0..99999)
    MAX-ACCESS	read-only
    STATUS	current
    DESCRIPTION
	"
	Fld OID Name:	avCmCapacityAnnounceAvayaMedServUsed
	Fld OID:	enterprises.6889.2.73.8.1.17.16
	Fld Form/Rpt:	System Capacity
	Fld Format:	Single Field
	Fld(s) Name:	Avaya Media Servers
	Fld Descr:	An object that contains the number of Used 
			Avaya Media Servers.
	"
    ::= { avCmCapacityAnnounce  16 }

avCmCapacityAnnounceAvayaMedServAvail	OBJECT-TYPE
    SYNTAX      Integer32 (0..99999)
    MAX-ACCESS	read-only
    STATUS	current
    DESCRIPTION
	"
	Fld OID Name:	avCmCapacityAnnounceAvayaMedServAvail
	Fld OID:	enterprises.6889.2.73.8.1.17.17
	Fld Form/Rpt:	System Capacity
	Fld Format:	Single Field
	Fld(s) Name:	Avaya Media Servers
	Fld Descr:	An object that contains the number of Available
			Avaya Media Servers.
	"
    ::= { avCmCapacityAnnounce 17 }

avCmCapacityAnnounceAvayaMedServSysLim	OBJECT-TYPE
    SYNTAX      Integer32 (0..99999)
    MAX-ACCESS	read-only
    STATUS	current
    DESCRIPTION
	"
	Fld OID Name:	avCmCapacityAnnounceAvayaMedServSysLim
	Fld OID:	enterprises.6889.2.73.8.1.17.18
	Fld Form/Rpt:	System Capacity
	Fld Format:	Single Field
	Fld(s) Name:	Avaya Media Servers
	Fld Descr:	An object that contains the System Limit of
			Avaya Media Servers.
	"
    ::= { avCmCapacityAnnounce 18 }

-- ******************** avCmCapacityTrunks Group *************************

-- MIB GROUP DESCRIPTION

-- MIB Group Name:
--		avCmCapacityTrunks
-- OID:
--		enterprises.6889.2.73.8.1.18
-- Description:
--		The avCmCapacityTrunks MIB Group uses the "display capacity"
-- 		command to retrieve the TRUNKS capacity information
-- 		under the TRUNKS section of
--		the SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityTrunks	OBJECT IDENTIFIER ::= { avCmObjects 18 }

avCmCapacityTrunksDS1CirPksUsed	OBJECT-TYPE
    SYNTAX	Integer32 (0..99999)
    MAX-ACCESS	read-only
    STATUS	current
    DESCRIPTION
	"
	Fld OID Name:	avCmCapacityTrunksDS1CirPksUsed
	Fld OID:	enterprises.6889.2.73.8.1.18.1
	Fld Form/Rpt:	System Capacity
	Fld Format:	Single Field
	Fld(s) Name:	DS1 Circuit Packs
	Fld Descr:	An object that contains the number of Used 
			DS1 Circuit Packs.
	"
    ::= { avCmCapacityTrunks 1 }

avCmCapacityTrunksDS1CirPksAvail	OBJECT-TYPE
    SYNTAX	Integer32 (0..99999)
    MAX-ACCESS	read-only
    STATUS	current
    DESCRIPTION
	"
	Fld OID Name:	avCmCapacityTrunksDS1CirPksAvail
	Fld OID:	enterprises.6889.2.73.8.1.18.2
	Fld Form/Rpt:	System Capacity
	Fld Format:	Single Field
	Fld(s) Name:	DS1 Circuit Packs
	Fld Descr:	An object that contains the number of Available 
			DS1 Circuit Packs.
	"
    ::= { avCmCapacityTrunks 2 }

avCmCapacityTrunksDS1CirPksSysLim	OBJECT-TYPE
    SYNTAX	Integer32 (0..99999)
    MAX-ACCESS	read-only
    STATUS	current
    DESCRIPTION
	"
	Fld OID Name:	avCmCapacityTrunksDS1CirPksSysLim
	Fld OID:	enterprises.6889.2.73.8.1.18.3
	Fld Form/Rpt:	System Capacity
	Fld Format:	Single Field
	Fld(s) Name:	DS1 Circuit Packs
	Fld Descr:	An object that contains the System Limit of 
			DS1 Circuit Packs.
	"
    ::= { avCmCapacityTrunks 3 }


avCmCapacityTrunksDS1EchoCanUsed	OBJECT-TYPE
    SYNTAX	Integer32 (0..99999)
    MAX-ACCESS	read-only
    STATUS	current
    DESCRIPTION
	"
	Fld OID Name:	avCmCapacityTrunksDS1EchoCanUsed
	Fld OID:	enterprises.6889.2.73.8.1.18.4
	Fld Form/Rpt:	System Capacity
	Fld Format:	Single Field
	Fld(s) Name:	DS1 With Echo Cancellation
	Fld Descr:	An object that contains the number of Used 
			DS1 With Echo Cancellation.
	"
    ::= { avCmCapacityTrunks 4 }

avCmCapacityTrunksDS1EchoCanAvail	OBJECT-TYPE
    SYNTAX	Integer32 (0..99999)
    MAX-ACCESS	read-only
    STATUS	current
    DESCRIPTION
	"
	Fld OID Name:	avCmCapacityTrunksDS1EchoCanAvail
	Fld OID:	enterprises.6889.2.73.8.1.18.5
	Fld Form/Rpt:	System Capacity
	Fld Format:	Single Field
	Fld(s) Name:	DS1 With Echo Cancellation
	Fld Descr:	An object that contains the number of Available
			DS1 With Echo Cancellation.
	"
    ::= { avCmCapacityTrunks 5 }

avCmCapacityTrunksDS1EchoCanSysLim	OBJECT-TYPE
    SYNTAX	Integer32 (0..99999)
    MAX-ACCESS	read-only
    STATUS	current
    DESCRIPTION
	"
	Fld OID Name:	avCmCapacityTrunksDS1EchoCanSysLim
	Fld OID:	enterprises.6889.2.73.8.1.18.6
	Fld Form/Rpt:	System Capacity
	Fld Format:	Single Field
	Fld(s) Name:	DS1 With Echo Cancellation
	Fld Descr:	An object that contains the System Limit
			DS1 With Echo Cancellation.
	"
    ::= { avCmCapacityTrunks 6 }

avCmCapacityTrunksIchtIsdnSipTrkUsed	OBJECT-TYPE
    SYNTAX	Integer32 (0..99999)
    MAX-ACCESS	read-only
    STATUS	current
    DESCRIPTION
	"
	Fld OID Name:	avCmCapacityTrunksIchtIsdnSipTrkUsed
	Fld OID:	enterprises.6889.2.73.8.1.18.7
	Fld Form/Rpt:	System Capacity
	Fld Format:	Single Field
	Fld(s) Name:	ICHT For ISDN/SIP Trunks
	Fld Descr:	An object that contains the number of Used 
			ICHT For ISDN/SIP Trunks.
	"
    ::= { avCmCapacityTrunks 7 }

avCmCapacityTrunksIchtIsdnSipTrkAvail	OBJECT-TYPE
    SYNTAX	Integer32 (0..99999)
    MAX-ACCESS	read-only
    STATUS	current
    DESCRIPTION
	"
	Fld OID Name:	avCmCapacityTrunksIchtIsdnSipTrkAvail
	Fld OID:	enterprises.6889.2.73.8.1.18.8
	Fld Form/Rpt:	System Capacity
	Fld Format:	Single Field
	Fld(s) Name:	ICHT For ISDN/SIP Trunks
	Fld Descr:	An object that contains the number of Available
			ICHT For ISDN/SIP Trunks.
	"
    ::= { avCmCapacityTrunks 8 }

avCmCapacityTrunksIchtIsdnSipTrkSysLim	OBJECT-TYPE
    SYNTAX	Integer32 (0..99999)
    MAX-ACCESS	read-only
    STATUS	current
    DESCRIPTION
	"
	Fld OID Name:	avCmCapacityTrunksIchtIsdnSipTrkSysLim
	Fld OID:	enterprises.6889.2.73.8.1.18.9
	Fld Form/Rpt:	System Capacity
	Fld Format:	Single Field
	Fld(s) Name:	ICHT For ISDN/SIP Trunks
	Fld Descr:	An object that contains the System Limit of
			ICHT For ISDN/SIP Trunks.
	"
    ::= { avCmCapacityTrunks 9 }

avCmCapacityTrunksIsdnCbcTrkUsed	OBJECT-TYPE
    SYNTAX      Integer32 (0..99999)
    MAX-ACCESS	read-only
    STATUS	current
    DESCRIPTION
	"
	Fld OID Name:	avCmCapacityTrunksIsdnCbcTrkUsed
	Fld OID:	enterprises.6889.2.73.8.1.18.10
	Fld Form/Rpt:	System Capacity
	Fld Format:	Single Field
	Fld(s) Name:	ISDN CBC Service Selection Trunks
	Fld Descr:	An object that contains the number of Used 
			ISDN CBC Service Selection Trunks.
	"
    ::= { avCmCapacityTrunks 10 }

avCmCapacityTrunksIsdnCbcTrkAvail	OBJECT-TYPE
    SYNTAX      Integer32 (0..99999)
    MAX-ACCESS	read-only
    STATUS	current
    DESCRIPTION
	"
	Fld OID Name:	avCmCapacityTrunksIsdnCbcTrkAvail
	Fld OID:	enterprises.6889.2.73.8.1.18.11
	Fld Form/Rpt:	System Capacity
	Fld Format:	Single Field
	Fld(s) Name:	ISDN CBC Service Selection Trunks
	Fld Descr:	An object that contains the number of Available
			ISDN CBC Service Selection Trunks.
	"
    ::= { avCmCapacityTrunks  11 }

avCmCapacityTrunksIsdnCbcTrkSysLim	OBJECT-TYPE
    SYNTAX      Integer32 (0..99999)
    MAX-ACCESS	read-only
    STATUS	current
    DESCRIPTION
	"
	Fld OID Name:	avCmCapacityTrunksIsdnCbcTrkSysLim
	Fld OID:	enterprises.6889.2.73.8.1.18.12
	Fld Form/Rpt:	System Capacity
	Fld Format:	Single Field
	Fld(s) Name:	ISDN CBC Service Selection Trunks
	Fld Descr:	An object that contains the System Limit of
			ISDN CBC Service Selection Trunks.
	"
    ::= { avCmCapacityTrunks 12 }

avCmCapacityTrunksTrunkGrpsUsed	OBJECT-TYPE
    SYNTAX      Integer32 (0..99999)
    MAX-ACCESS	read-only
    STATUS	current
    DESCRIPTION
	"
	Fld OID Name:	avCmCapacityTrunksTrunkGrpsUsed
	Fld OID:	enterprises.6889.2.73.8.1.18.13
	Fld Form/Rpt:	System Capacity
	Fld Format:	Single Field
	Fld(s) Name:	Trunk Groups
	Fld Descr:	An object that contains the number of Used 
			Trunk Groups.
	"
    ::= { avCmCapacityTrunks 13 }

avCmCapacityTrunksTrunkGrpsAvail	OBJECT-TYPE
    SYNTAX      Integer32 (0..99999)
    MAX-ACCESS	read-only
    STATUS	current
    DESCRIPTION
	"
	Fld OID Name:	avCmCapacityTrunksTrunkGrpsAvail
	Fld OID:	enterprises.6889.2.73.8.1.18.14
	Fld Form/Rpt:	System Capacity
	Fld Format:	Single Field
	Fld(s) Name:	Trunk Groups
	Fld Descr:	An object that contains the number of Available
			Trunk Groups.
	"
    ::= { avCmCapacityTrunks 14 }

avCmCapacityTrunksTrunkGrpsSysLim	OBJECT-TYPE
    SYNTAX      Integer32 (0..99999)
    MAX-ACCESS	read-only
    STATUS	current
    DESCRIPTION
	"
	Fld OID Name:	avCmCapacityTrunksTrunkGrpsSysLim
	Fld OID:	enterprises.6889.2.73.8.1.18.15
	Fld Form/Rpt:	System Capacity
	Fld Format:	Single Field
	Fld(s) Name:	Trunk Groups
	Fld Descr:	An object that contains the System Limit of
			Trunk Groups.
	"
    ::= { avCmCapacityTrunks 15 }

avCmCapacityTrunksTrunkPtsUsed	OBJECT-TYPE
    SYNTAX      Integer32 (0..99999)
    MAX-ACCESS	read-only
    STATUS	current
    DESCRIPTION
	"
	Fld OID Name:	avCmCapacityTrunksTrunkPtsUsed
	Fld OID:	enterprises.6889.2.73.8.1.18.16
	Fld Form/Rpt:	System Capacity
	Fld Format:	Single Field
	Fld(s) Name:	Trunk Ports
	Fld Descr:	An object that contains the number of Used 
			Trunk Ports.
	"
    ::= { avCmCapacityTrunks  16 }

avCmCapacityTrunksTrunkPtsAvail	OBJECT-TYPE
    SYNTAX      Integer32 (0..99999)
    MAX-ACCESS	read-only
    STATUS	current
    DESCRIPTION
	"
	Fld OID Name:	avCmCapacityTrunksTrunkPtsAvail
	Fld OID:	enterprises.6889.2.73.8.1.18.17
	Fld Form/Rpt:	System Capacity
	Fld Format:	Single Field
	Fld(s) Name:	Trunk Ports
	Fld Descr:	An object that contains the number of Available
			Trunk Ports.
	"
    ::= { avCmCapacityTrunks 17 }

avCmCapacityTrunksTrunkPtsSysLim	OBJECT-TYPE
    SYNTAX      Integer32 (0..99999)
    MAX-ACCESS	read-only
    STATUS	current
    DESCRIPTION
	"
	Fld OID Name:	avCmCapacityTrunksTrunkPtsSysLim
	Fld OID:	enterprises.6889.2.73.8.1.18.18
	Fld Form/Rpt:	System Capacity
	Fld Format:	Single Field
	Fld(s) Name:	Trunk Ports
	Fld Descr:	An object that contains the System Limit of
			Trunk Ports.
	"
    ::= { avCmCapacityTrunks 18 }

avCmCapacityTrunksH323TrksUsed	OBJECT-TYPE
    SYNTAX      Integer32 (0..99999)
    MAX-ACCESS	read-only
    STATUS	current
    DESCRIPTION
	"
	Fld OID Name:	avCmCapacityTrunksH323TrksUsed
	Fld OID:	enterprises.6889.2.73.8.1.18.19
	Fld Form/Rpt:	System Capacity
	Fld Format:	Single Field
	Fld(s) Name:	H.323 Trunks (included in 'Trunk ports')
	Fld Descr:	An object that contains the number of Used 
			H.323 Trunks (included in 'Trunk ports').
	"
    ::= { avCmCapacityTrunks 19 }

avCmCapacityTrunksH323TrksAvail	OBJECT-TYPE
    SYNTAX      Integer32 (0..99999)
    MAX-ACCESS	read-only
    STATUS	current
    DESCRIPTION
	"
	Fld OID Name:	avCmCapacityTrunksH323TrksAvail
	Fld OID:	enterprises.6889.2.73.8.1.18.20
	Fld Form/Rpt:	System Capacity
	Fld Format:	Single Field
	Fld(s) Name:	H.323 Trunks (included in 'Trunk ports')
	Fld Descr:	An object that contains the number of Available
			H.323 Trunks (included in 'Trunk ports').
	"
    ::= { avCmCapacityTrunks 20 }

avCmCapacityTrunksH323TrksSysLim	OBJECT-TYPE
    SYNTAX      Integer32 (0..99999)
    MAX-ACCESS	read-only
    STATUS	current
    DESCRIPTION
	"
	Fld OID Name:	avCmCapacityTrunksH323TrksSysLim
	Fld OID:	enterprises.6889.2.73.8.1.18.21
	Fld Form/Rpt:	System Capacity
	Fld Format:	Single Field
	Fld(s) Name:	H.323 Trunks (included in 'Trunk ports')
	Fld Descr:	An object that contains the System Limit of
			H.323 Trunks (included in 'Trunk ports').
	"
    ::= { avCmCapacityTrunks 21 }

avCmCapacityTrunksRemOffTrksUsed	OBJECT-TYPE
    SYNTAX      Integer32 (0..99999)
    MAX-ACCESS	read-only
    STATUS	current
    DESCRIPTION
	"
	Fld OID Name:	avCmCapacityTrunksRemOffTrksUsed
	Fld OID:	enterprises.6889.2.73.8.1.18.22
	Fld Form/Rpt:	System Capacity
	Fld Format:	Single Field
	Fld(s) Name:	Remote Office Trunks (included in 'Trunk ports')
	Fld Descr:	An object that contains the number of Used 
			Remote Office Trunks (included in 'Trunk ports').
	"
    ::= { avCmCapacityTrunks 22 }

avCmCapacityTrunksRemOffTrksAvail	OBJECT-TYPE
    SYNTAX      Integer32 (0..99999)
    MAX-ACCESS	read-only
    STATUS	current
    DESCRIPTION
	"
	Fld OID Name:	avCmCapacityTrunksRemOffTrksAvail
	Fld OID:	enterprises.6889.2.73.8.1.18.23
	Fld Form/Rpt:	System Capacity
	Fld Format:	Single Field
	Fld(s) Name:	Remote Office Trunks (included in 'Trunk ports')
	Fld Descr:	An object that contains the number of Available
			Remote Office Trunks (included in 'Trunk ports').
	"
    ::= { avCmCapacityTrunks 23 }

avCmCapacityTrunksRemOffTrksSysLim	OBJECT-TYPE
    SYNTAX      Integer32 (0..99999)
    MAX-ACCESS	read-only
    STATUS	current
    DESCRIPTION
	"
	Fld OID Name:	avCmCapacityTrunksRemOffTrksSysLim
	Fld OID:	enterprises.6889.2.73.8.1.18.24
	Fld Form/Rpt:	System Capacity
	Fld Format:	Single Field
	Fld(s) Name:	Remote Office Trunks (included in 'Trunk ports')
	Fld Descr:	An object that contains the System Limit of
			Remote Office Trunks (included in 'Trunk ports').
	"
    ::= { avCmCapacityTrunks 24 }

avCmCapacityTrunksSbsTrksUsed	OBJECT-TYPE
    SYNTAX      Integer32 (0..99999)
    MAX-ACCESS	read-only
    STATUS	current
    DESCRIPTION
	"
	Fld OID Name:	avCmCapacityTrunksSbsTrksUsed
	Fld OID:	enterprises.6889.2.73.8.1.18.25
	Fld Form/Rpt:	System Capacity
	Fld Format:	Single Field
	Fld(s) Name:	SBS Trunks (included in 'Trunk ports')
	Fld Descr:	An object that contains the number of Used 
			SBS Trunks (included in 'Trunk ports').
	"
    ::= { avCmCapacityTrunks 25 }

avCmCapacityTrunksSbsTrksAvail	OBJECT-TYPE
    SYNTAX      Integer32 (0..99999)
    MAX-ACCESS	read-only
    STATUS	current
    DESCRIPTION
	"
	Fld OID Name:	avCmCapacityTrunksSbsTrksAvail
	Fld OID:	enterprises.6889.2.73.8.1.18.26
	Fld Form/Rpt:	System Capacity
	Fld Format:	Single Field
	Fld(s) Name:	SBS Trunks (included in 'Trunk ports')
	Fld Descr:	An object that contains the number of Available
			SBS Trunks (included in 'Trunk ports').
	"
    ::= { avCmCapacityTrunks 26 }

avCmCapacityTrunksSbsTrksSysLim	OBJECT-TYPE
    SYNTAX      Integer32 (0..99999)
    MAX-ACCESS	read-only
    STATUS	current
    DESCRIPTION
	"
	Fld OID Name:	avCmCapacityTrunksSbsTrksSysLim
	Fld OID:	enterprises.6889.2.73.8.1.18.27
	Fld Form/Rpt:	System Capacity
	Fld Format:	Single Field
	Fld(s) Name:	SBS Trunks (included in 'Trunk ports')
	Fld Descr:	An object that contains the System Limit of
			SBS Trunks (included in 'Trunk ports').
	"
    ::= { avCmCapacityTrunks 27 }

avCmCapacityTrunksSipTrksUsed	OBJECT-TYPE
    SYNTAX      Integer32 (0..99999)
    MAX-ACCESS	read-only
    STATUS	current
    DESCRIPTION
	"
	Fld OID Name:	avCmCapacityTrunksSipTrksUsed
	Fld OID:	enterprises.6889.2.73.8.1.18.28
	Fld Form/Rpt:	System Capacity
	Fld Format:	Single Field
	Fld(s) Name:	SIP Trunks (included in 'Trunk ports')
	Fld Descr:	An object that contains the number of Used 
			SIP Trunks (included in 'Trunk ports').
	"
    ::= { avCmCapacityTrunks 28 }

avCmCapacityTrunksSipTrksAvail	OBJECT-TYPE
    SYNTAX      Integer32 (0..99999)
    MAX-ACCESS	read-only
    STATUS	current
    DESCRIPTION
	"
	Fld OID Name:	avCmCapacityTrunksSipTrksAvail
	Fld OID:	enterprises.6889.2.73.8.1.18.29
	Fld Form/Rpt:	System Capacity
	Fld Format:	Single Field
	Fld(s) Name:	SIP Trunks (included in 'Trunk ports')
	Fld Descr:	An object that contains the number of Available
			SIP Trunks (included in 'Trunk ports').
	"
    ::= { avCmCapacityTrunks 29 }

avCmCapacityTrunksSipTrksSysLim	OBJECT-TYPE
    SYNTAX      Integer32 (0..99999)
    MAX-ACCESS	read-only
    STATUS	current
    DESCRIPTION
	"
	Fld OID Name:	avCmCapacityTrunksSipTrksSysLim
	Fld OID:	enterprises.6889.2.73.8.1.18.30
	Fld Form/Rpt:	System Capacity
	Fld Format:	Single Field
	Fld(s) Name:	SIP Trunks (included in 'Trunk ports')
	Fld Descr:	An object that contains the System Limit of
			SIP Trunks (included in 'Trunk ports').
	"
    ::= { avCmCapacityTrunks 30 }

avCmCapacityTrunksAdVidConfPtsUsed	OBJECT-TYPE
    SYNTAX      Integer32 (0..99999)
    MAX-ACCESS	read-only
    STATUS	current
    DESCRIPTION
	"
	Fld OID Name:	avCmCapacityTrunksAdVidConfPtsUsed
	Fld OID:	enterprises.6889.2.73.8.1.18.31
	Fld Form/Rpt:	System Capacity
	Fld Format:	Single Field
	Fld(s) Name:	Ad-hoc Video Conferencing Ports
	Fld Descr:	An object that contains the number of Used 
			Ad-hoc Video Conferencing Ports.
	"
    ::= { avCmCapacityTrunks 31 }

avCmCapacityTrunksAdVidConfPtsAvail	OBJECT-TYPE
    SYNTAX      Integer32 (0..99999)
    MAX-ACCESS	read-only
    STATUS	current
    DESCRIPTION
	"
	Fld OID Name:	avCmCapacityTrunksAdVidConfPtsAvail
	Fld OID:	enterprises.6889.2.73.8.1.18.32
	Fld Form/Rpt:	System Capacity
	Fld Format:	Single Field
	Fld(s) Name:	Ad-hoc Video Conferencing Ports
	Fld Descr:	An object that contains the number of Available
			Ad-hoc Video Conferencing Ports.
	"
    ::= { avCmCapacityTrunks 32 }

avCmCapacityTrunksAdVidConfPtsSysLim	OBJECT-TYPE
    SYNTAX      Integer32 (0..99999)
    MAX-ACCESS	read-only
    STATUS	current
    DESCRIPTION
	"
	Fld OID Name:	avCmCapacityTrunksAdVidConfPtsSysLim
	Fld OID:	enterprises.6889.2.73.8.1.18.33
	Fld Form/Rpt:	System Capacity
	Fld Format:	Single Field
	Fld(s) Name:	Ad-hoc Video Conferencing Ports
	Fld Descr:	An object that contains the System Limit of
			Ad-hoc Video Conferencing Ports.
	"
    ::= { avCmCapacityTrunks 33 }

-- ******************** avCmCapacityVoiceTerm Group *************************

-- MIB GROUP DESCRIPTION

-- MIB Group Name:
--		avCmCapacityVoiceTerm
-- OID:
--		enterprises.6889.2.73.8.1.19
-- Description:
--		The avCmCapacityVoiceTerm MIB Group uses the "display capacity"
-- 		command to retrieve the STATION capacity information
-- 		under the VOICE TERMINALS section of the SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityVoiceTerm	OBJECT IDENTIFIER ::= { avCmObjects 19 }

avCmCapacityVoiceTermStatWithPtUsed	OBJECT-TYPE
    SYNTAX	Integer32 (0..99999)
    MAX-ACCESS	read-only
    STATUS	current
    DESCRIPTION
	"
	Fld OID Name:	avCmCapacityVoiceTermStatWithPtUsed
	Fld OID:	enterprises.6889.2.73.8.1.19.1
	Fld Form/Rpt:	System Capacity
	Fld Format:	Single Field
	Fld(s) Name:	Stations With Port
	Fld Descr:	An object that contains the number of Used 
			Stations With Port.
	"
    ::= { avCmCapacityVoiceTerm 1 }


avCmCapacityVoiceTermStatWithOutPtUsed	OBJECT-TYPE
    SYNTAX	Integer32 (0..99999)
    MAX-ACCESS	read-only
    STATUS	current
    DESCRIPTION
	"
	Fld OID Name:	avCmCapacityVoiceTermStatWithOutPtUsed
	Fld OID:	enterprises.6889.2.73.8.1.19.2
	Fld Form/Rpt:	System Capacity
	Fld Format:	Single Field
	Fld(s) Name:	Stations Without Port
	Fld Descr:	An object that contains the number of Used 
			Stations Without Port.
	"
    ::= { avCmCapacityVoiceTerm 2 }


avCmCapacityVoiceTermOtherStatUsed	OBJECT-TYPE
    SYNTAX	Integer32 (0..99999)
    MAX-ACCESS	read-only
    STATUS	current
    DESCRIPTION
	"
	Fld OID Name:	avCmCapacityVoiceTermOtherStatUsed
	Fld OID:	enterprises.6889.2.73.8.1.19.3
	Fld Form/Rpt:	System Capacity
	Fld Format:	Single Field
	Fld(s) Name:	Other Stations
	Fld Descr:	An object that contains the number of Used 
			Other Stations.
	"
    ::= { avCmCapacityVoiceTerm 3 }


avCmCapacityVoiceTermTTIportsUsed	OBJECT-TYPE
    SYNTAX      Integer32 (0..99999)
    MAX-ACCESS	read-only
    STATUS	current
    DESCRIPTION
	"
	Fld OID Name:	avCmCapacityVoiceTermTTIportsUsed
	Fld OID:	enterprises.6889.2.73.8.1.19.4
	Fld Form/Rpt:	System Capacity
	Fld Format:	Single Field
	Fld(s) Name:	TTI Ports
	Fld Descr:	An object that contains the number of Used 
			TTI Ports.
	"
    ::= { avCmCapacityVoiceTerm 4 }

avCmCapacityVoiceTermAdmIPSoftUsed	OBJECT-TYPE
    SYNTAX      Integer32 (0..99999)
    MAX-ACCESS	read-only
    STATUS	current
    DESCRIPTION
	"
	Fld OID Name:	avCmCapacityVoiceTermAdmIPSoftUsed
	Fld OID:	enterprises.6889.2.73.8.1.19.5
	Fld Form/Rpt:	System Capacity
	Fld Format:	Single Field
	Fld(s) Name:	Administered IP Softphones
	Fld Descr:	An object that contains the number of Used 
			Administered IP Softphones.
	"
    ::= { avCmCapacityVoiceTerm 5 }

avCmCapacityVoiceTermVidCapStatUsed	OBJECT-TYPE
    SYNTAX      Integer32 (0..99999)
    MAX-ACCESS	read-only
    STATUS	current
    DESCRIPTION
	"
	Fld OID Name:	avCmCapacityVoiceTermVidCapStatUsed
	Fld OID:	enterprises.6889.2.73.8.1.19.6
	Fld Form/Rpt:	System Capacity
	Fld Format:	Single Field
	Fld(s) Name:	Video Capable Stations
	Fld Descr:	An object that contains the number of Used 
			Video Capable Stations.
	"
    ::= { avCmCapacityVoiceTerm  6 }

avCmCapacityVoiceTermVidCapStatAvail	OBJECT-TYPE
    SYNTAX      Integer32 (0..99999)
    MAX-ACCESS	read-only
    STATUS	current
    DESCRIPTION
	"
	Fld OID Name:	avCmCapacityVoiceTermVidCapStatAvail
	Fld OID:	enterprises.6889.2.73.8.1.19.7
	Fld Form/Rpt:	System Capacity
	Fld Format:	Single Field
	Fld(s) Name:	Video Capable Stations
	Fld Descr:	An object that contains the number of Available
			Video Capable Stations.
	"
    ::= { avCmCapacityVoiceTerm 7 }

avCmCapacityVoiceTermVidCapStatSysLim	OBJECT-TYPE
    SYNTAX      Integer32 (0..99999)
    MAX-ACCESS	read-only
    STATUS	current
    DESCRIPTION
	"
	Fld OID Name:	avCmCapacityVoiceTermVidCapStatSysLim
	Fld OID:	enterprises.6889.2.73.8.1.19.8
	Fld Form/Rpt:	System Capacity
	Fld Format:	Single Field
	Fld(s) Name:	Video Capable Stations
	Fld Descr:	An object that contains the System Limit of
			Video Capable Stations.
	"
    ::= { avCmCapacityVoiceTerm 8 }

avCmCapacityVoiceTermVidCapSoftUsed	OBJECT-TYPE
    SYNTAX      Integer32 (0..99999)
    MAX-ACCESS	read-only
    STATUS	current
    DESCRIPTION
	"
	Fld OID Name:	avCmCapacityVoiceTermVidCapSoftUsed
	Fld OID:	enterprises.6889.2.73.8.1.19.9
	Fld Form/Rpt:	System Capacity
	Fld Format:	Single Field
	Fld(s) Name:	Video Capable IP Softphones
	Fld Descr:	An object that contains the number of Used 
			Video Capable IP Softphones.
	"
    ::= { avCmCapacityVoiceTerm 9 }

avCmCapacityVoiceTermVidCapSoftAvail	OBJECT-TYPE
    SYNTAX      Integer32 (0..99999)
    MAX-ACCESS	read-only
    STATUS	current
    DESCRIPTION
	"
	Fld OID Name:	avCmCapacityVoiceTermVidCapSoftAvail
	Fld OID:	enterprises.6889.2.73.8.1.19.10
	Fld Form/Rpt:	System Capacity
	Fld Format:	Single Field
	Fld(s) Name:	Video Capable IP Softphones
	Fld Descr:	An object that contains the number of Available
			Video Capable IP Softphones.
	"
    ::= { avCmCapacityVoiceTerm 10 }

avCmCapacityVoiceTermVidCapSoftSysLim	OBJECT-TYPE
    SYNTAX      Integer32 (0..99999)
    MAX-ACCESS	read-only
    STATUS	current
    DESCRIPTION
	"
	Fld OID Name:	avCmCapacityVoiceTermVidCapSoftSysLim
	Fld OID:	enterprises.6889.2.73.8.1.19.11
	Fld Form/Rpt:	System Capacity
	Fld Format:	Single Field
	Fld(s) Name:	Video Capable IP Softphones
	Fld Descr:	An object that contains the System Limit of
			Video Capable IP Softphones.
	"
    ::= { avCmCapacityVoiceTerm 11 }

avCmCapacityVoiceTermBRIEndTrkPtsUsed	OBJECT-TYPE
    SYNTAX      Integer32 (0..99999)
    MAX-ACCESS	read-only
    STATUS	current
    DESCRIPTION
	"
	Fld OID Name:	avCmCapacityVoiceTermBRIEndTrkPtsUsed
	Fld OID:	enterprises.6889.2.73.8.1.19.12
	Fld Form/Rpt:	System Capacity
	Fld Format:	Single Field
	Fld(s) Name:	ISDN BRI Endpoint And Trunk Ports
	Fld Descr:	An object that contains the number of Used 
			ISDN BRI Endpoint And Trunk Ports.
	"
    ::= { avCmCapacityVoiceTerm 12 }

avCmCapacityVoiceTermBRIEndTrkPtsAvail	OBJECT-TYPE
    SYNTAX      Integer32 (0..99999)
    MAX-ACCESS	read-only
    STATUS	current
    DESCRIPTION
	"
	Fld OID Name:	avCmCapacityVoiceTermBRIEndTrkPtsAvail
	Fld OID:	enterprises.6889.2.73.8.1.19.13
	Fld Form/Rpt:	System Capacity
	Fld Format:	Single Field
	Fld(s) Name:	ISDN BRI Endpoint And Trunk Ports
	Fld Descr:	An object that contains the number of Available
			ISDN BRI Endpoint And Trunk Ports.
	"
    ::= { avCmCapacityVoiceTerm 13 }

avCmCapacityVoiceTermBRIEndTrkPtsSysLim	OBJECT-TYPE
    SYNTAX      Integer32 (0..99999)
    MAX-ACCESS	read-only
    STATUS	current
    DESCRIPTION
	"
	Fld OID Name:	avCmCapacityVoiceTermBRIEndTrkPtsSysLim
	Fld OID:	enterprises.6889.2.73.8.1.19.14
	Fld Form/Rpt:	System Capacity
	Fld Format:	Single Field
	Fld(s) Name:	ISDN BRI Endpoint And Trunk Ports
	Fld Descr:	An object that contains the System Limit of
			ISDN BRI Endpoint And Trunk Ports.
	"
    ::= { avCmCapacityVoiceTerm 14 }

-- ******************** avCmCapacityLic Group *************************

-- MIB GROUP DESCRIPTION

-- MIB Group Name:
--		avCmCapacityLic
-- OID:
--		enterprises.6889.2.73.8.1.20
-- Description:
--		The avCmCapacityLic MIB Group uses the "display capacity"
-- 		command to retrieve the LICENSED capacity information
-- 		under the TOTAL LICENSED CAPACITY  section of the 
--		SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityLic	OBJECT IDENTIFIER ::= { avCmObjects 20 }

avCmCapacityLicStatTrkPtsUsed	OBJECT-TYPE
    SYNTAX	Integer32 (0..99999)
    MAX-ACCESS	read-only
    STATUS	current
    DESCRIPTION
	"
	Fld OID Name:	avCmCapacityLicStatTrkPtsUsed
	Fld OID:	enterprises.6889.2.73.8.1.20.1
	Fld Form/Rpt:	System Capacity
	Fld Format:	Single Field
	Fld(s) Name:	Station and Trunk Ports
	Fld Descr:	An object that contains the number of Used 
			Station and Trunk Ports.
	"
    ::= { avCmCapacityLic 1 }

avCmCapacityLicStatTrkPtsAvail	OBJECT-TYPE
    SYNTAX	Integer32 (0..99999)
    MAX-ACCESS	read-only
    STATUS	current
    DESCRIPTION
	"
	Fld OID Name:	avCmCapacityLicStatTrkPtsAvail
	Fld OID:	enterprises.6889.2.73.8.1.20.2
	Fld Form/Rpt:	System Capacity
	Fld Format:	Single Field
	Fld(s) Name:	Station and Trunk Ports
	Fld Descr:	An object that contains the number of Available 
			Station and Trunk Ports.
	"
    ::= { avCmCapacityLic 2 }

avCmCapacityLicStatTrkPtsLicLimit	OBJECT-TYPE
    SYNTAX	Integer32 (0..99999)
    MAX-ACCESS	read-only
    STATUS	current
    DESCRIPTION
	"
	Fld OID Name:	avCmCapacityLicStatTrkPtsLicLimit
	Fld OID:	enterprises.6889.2.73.8.1.20.3
	Fld Form/Rpt:	System Capacity
	Fld Format:	Single Field
	Fld(s) Name:	Station and Trunk Ports
	Fld Descr:	An object that contains the System Limit of 
			Station and Trunk Ports.
	"
    ::= { avCmCapacityLic 3 }


avCmCapacityLicStatCapUsed	OBJECT-TYPE
    SYNTAX	Integer32 (0..99999)
    MAX-ACCESS	read-only
    STATUS	current
    DESCRIPTION
	"
	Fld OID Name:	avCmCapacityLicStatCapUsed
	Fld OID:	enterprises.6889.2.73.8.1.20.4
	Fld Form/Rpt:	System Capacity
	Fld Format:	Single Field
	Fld(s) Name:	Station Capacity
	Fld Descr:	An object that contains the number of Used 
			Station Capacity.
	"
    ::= { avCmCapacityLic 4 }

avCmCapacityLicStatCapAvail	OBJECT-TYPE
    SYNTAX	Integer32 (0..99999)
    MAX-ACCESS	read-only
    STATUS	current
    DESCRIPTION
	"
	Fld OID Name:	avCmCapacityLicStatCapAvail
	Fld OID:	enterprises.6889.2.73.8.1.20.5
	Fld Form/Rpt:	System Capacity
	Fld Format:	Single Field
	Fld(s) Name:	Station Capacity
	Fld Descr:	An object that contains the number of Available
			Station Capacity.
	"
    ::= { avCmCapacityLic 5 }

avCmCapacityLicStatCapLicLimit	OBJECT-TYPE
    SYNTAX	Integer32 (0..99999)
    MAX-ACCESS	read-only
    STATUS	current
    DESCRIPTION
	"
	Fld OID Name:	avCmCapacityLicStatCapLicLimit
	Fld OID:	enterprises.6889.2.73.8.1.20.6
	Fld Form/Rpt:	System Capacity
	Fld Format:	Single Field
	Fld(s) Name:	Station Capacity
	Fld Descr:	An object that contains the System Limit
			Station Capacity.
	"
    ::= { avCmCapacityLic 6 }

avCmCapacityLicXmobileStatUsed	OBJECT-TYPE
    SYNTAX	Integer32 (0..99999)
    MAX-ACCESS	read-only
    STATUS	current
    DESCRIPTION
	"
	Fld OID Name:	avCmCapacityLicXmobileStatUsed
	Fld OID:	enterprises.6889.2.73.8.1.20.7
	Fld Form/Rpt:	System Capacity
	Fld Format:	Single Field
	Fld(s) Name:	XMOBILE Stations
	Fld Descr:	An object that contains the number of Used 
			XMOBILE Stations.
	"
    ::= { avCmCapacityLic 7 }

avCmCapacityLicXmobileStatAvail	OBJECT-TYPE
    SYNTAX	Integer32 (0..99999)
    MAX-ACCESS	read-only
    STATUS	current
    DESCRIPTION
	"
	Fld OID Name:	avCmCapacityLicXmobileStatAvail
	Fld OID:	enterprises.6889.2.73.8.1.20.8
	Fld Form/Rpt:	System Capacity
	Fld Format:	Single Field
	Fld(s) Name:	XMOBILE Stations
	Fld Descr:	An object that contains the number of Available
			XMOBILE Stations.
	"
    ::= { avCmCapacityLic 8 }

avCmCapacityLicXmobileStatLicLimit	OBJECT-TYPE
    SYNTAX	Integer32 (0..99999)
    MAX-ACCESS	read-only
    STATUS	current
    DESCRIPTION
	"
	Fld OID Name:	avCmCapacityLicXmobileStatLicLimit
	Fld OID:	enterprises.6889.2.73.8.1.20.9
	Fld Form/Rpt:	System Capacity
	Fld Format:	Single Field
	Fld(s) Name:	XMOBILE Stations
	Fld Descr:	An object that contains the System Limit of
			XMOBILE Stations.
	"
    ::= { avCmCapacityLic 9 }

avCmCapacityLicEC500Used	OBJECT-TYPE
    SYNTAX      Integer32 (0..99999)
    MAX-ACCESS	read-only
    STATUS	current
    DESCRIPTION
	"
	Fld OID Name:	avCmCapacityLicEC500Used
	Fld OID:	enterprises.6889.2.73.8.1.20.10
	Fld Form/Rpt:	System Capacity
	Fld Format:	Single Field
	Fld(s) Name:	EC500
	Fld Descr:	An object that contains the number of Used 
			EC500.
	"
    ::= { avCmCapacityLic 10 }

avCmCapacityLicIsdnDectUsed	OBJECT-TYPE
    SYNTAX      Integer32 (0..99999)
    MAX-ACCESS	read-only
    STATUS	current
    DESCRIPTION
	"
	Fld OID Name:	avCmCapacityLicIsdnDectUsed
	Fld OID:	enterprises.6889.2.73.8.1.20.11
	Fld Form/Rpt:	System Capacity
	Fld Format:	Single Field
	Fld(s) Name:	ISDN DECT
	Fld Descr:	An object that contains the number of Used 
			ISDN DECT.
	"
    ::= { avCmCapacityLic 11 }

avCmCapacityLicIpDectUsed	OBJECT-TYPE
    SYNTAX      Integer32 (0..99999)
    MAX-ACCESS	read-only
    STATUS	current
    DESCRIPTION
	"
	Fld OID Name:	avCmCapacityLicIpDectUsed
	Fld OID:	enterprises.6889.2.73.8.1.20.12
	Fld Form/Rpt:	System Capacity
	Fld Format:	Single Field
	Fld(s) Name:	IP DECT
	Fld Descr:	An object that contains the number of Used 
			IP DECT.
	"
    ::= { avCmCapacityLic  12 }

avCmCapacityLicPhsUsed	OBJECT-TYPE
    SYNTAX      Integer32 (0..99999)
    MAX-ACCESS	read-only
    STATUS	current
    DESCRIPTION
	"
	Fld OID Name:	avCmCapacityLicPhsUsed
	Fld OID:	enterprises.6889.2.73.8.1.20.13
	Fld Form/Rpt:	System Capacity
	Fld Format:	Single Field
	Fld(s) Name:	PHS
	Fld Descr:	An object that contains the number of Used 
			PHS.
	"
    ::= { avCmCapacityLic 13 }

avCmCapacityLicOffPbxTelEC500Used	OBJECT-TYPE
    SYNTAX      Integer32 (0..99999)
    MAX-ACCESS	read-only
    STATUS	current
    DESCRIPTION
	"
	Fld OID Name:	avCmCapacityLicOffPbxTelEC500Used
	Fld OID:	enterprises.6889.2.73.8.1.20.14
	Fld Form/Rpt:	System Capacity
	Fld Format:	Single Field
	Fld(s) Name:	Off-PBX Telephone - EC500
	Fld Descr:	An object that contains the number of Used 
			Off-PBX Telephone - EC500.
	"
    ::= { avCmCapacityLic 14 }

avCmCapacityLicOffPbxTelEC500Avail	OBJECT-TYPE
    SYNTAX      Integer32 (0..99999)
    MAX-ACCESS	read-only
    STATUS	current
    DESCRIPTION
	"
	Fld OID Name:	avCmCapacityLicOffPbxTelEC500Avail
	Fld OID:	enterprises.6889.2.73.8.1.20.15
	Fld Form/Rpt:	System Capacity
	Fld Format:	Single Field
	Fld(s) Name:	Off-PBX Telephone - EC500
	Fld Descr:	An object that contains the number of Available
			Off-PBX Telephone - EC500.
	"
    ::= { avCmCapacityLic 15 }

avCmCapacityLicOffPbxTelEC500LicLimit	OBJECT-TYPE
    SYNTAX      Integer32 (0..99999)
    MAX-ACCESS	read-only
    STATUS	current
    DESCRIPTION
	"
	Fld OID Name:	avCmCapacityLicOffPbxTelEC500LicLimit
	Fld OID:	enterprises.6889.2.73.8.1.20.16
	Fld Form/Rpt:	System Capacity
	Fld Format:	Single Field
	Fld(s) Name:	Off-PBX Telephone - EC500
	Fld Descr:	An object that contains the System Limit of
			Off-PBX Telephone - EC500.
	"
    ::= { avCmCapacityLic 16 }

avCmCapacityLicOffPbxTelOPSUsed	OBJECT-TYPE
    SYNTAX      Integer32 (0..99999)
    MAX-ACCESS	read-only
    STATUS	current
    DESCRIPTION
	"
	Fld OID Name:	avCmCapacityLicOffPbxTelOPSUsed
	Fld OID:	enterprises.6889.2.73.8.1.20.17
	Fld Form/Rpt:	System Capacity
	Fld Format:	Single Field
	Fld(s) Name:	Off-PBX Telephone -   OPS
	Fld Descr:	An object that contains the number of Used 
			Off-PBX Telephone -   OPS.
	"
    ::= { avCmCapacityLic 17 }

avCmCapacityLicOffPbxTelOPSAvail	OBJECT-TYPE
    SYNTAX      Integer32 (0..99999)
    MAX-ACCESS	read-only
    STATUS	current
    DESCRIPTION
	"
	Fld OID Name:	avCmCapacityLicOffPbxTelOPSAvail
	Fld OID:	enterprises.6889.2.73.8.1.20.18
	Fld Form/Rpt:	System Capacity
	Fld Format:	Single Field
	Fld(s) Name:	Off-PBX Telephone -   OPS
	Fld Descr:	An object that contains the number of Available
			Off-PBX Telephone -   OPS.
	"
    ::= { avCmCapacityLic 18 }

avCmCapacityLicOffPbxTelOPSLicLimit	OBJECT-TYPE
    SYNTAX      Integer32 (0..99999)
    MAX-ACCESS	read-only
    STATUS	current
    DESCRIPTION
	"
	Fld OID Name:	avCmCapacityLicOffPbxTelOPSLicLimit
	Fld OID:	enterprises.6889.2.73.8.1.20.19
	Fld Form/Rpt:	System Capacity
	Fld Format:	Single Field
	Fld(s) Name:	Off-PBX Telephone -   OPS
	Fld Descr:	An object that contains the System Limit of
			Off-PBX Telephone -   OPS.
	"
    ::= { avCmCapacityLic 19 }

avCmCapacityLicOffPbxTelPBFMCUsed	OBJECT-TYPE
    SYNTAX      Integer32 (0..99999)
    MAX-ACCESS	read-only
    STATUS	current
    DESCRIPTION
	"
	Fld OID Name:	avCmCapacityLicOffPbxTelPBFMCUsed
	Fld OID:	enterprises.6889.2.73.8.1.20.20
	Fld Form/Rpt:	System Capacity
	Fld Format:	Single Field
	Fld(s) Name:	Off-PBX Telephone - PBFMC
	Fld Descr:	An object that contains the number of Used 
			Off-PBX Telephone - PBFMC.
	"
    ::= { avCmCapacityLic 20 }

avCmCapacityLicOffPbxTelPBFMCAvail	OBJECT-TYPE
    SYNTAX      Integer32 (0..99999)
    MAX-ACCESS	read-only
    STATUS	current
    DESCRIPTION
	"
	Fld OID Name:	avCmCapacityLicOffPbxTelPBFMCAvail
	Fld OID:	enterprises.6889.2.73.8.1.20.21
	Fld Form/Rpt:	System Capacity
	Fld Format:	Single Field
	Fld(s) Name:	Off-PBX Telephone - PBFMC
	Fld Descr:	An object that contains the number of Available
			Off-PBX Telephone - PBFMC.
	"
    ::= { avCmCapacityLic 21 }

avCmCapacityLicOffPbxTelPBFMCLicLimit	OBJECT-TYPE
    SYNTAX      Integer32 (0..99999)
    MAX-ACCESS	read-only
    STATUS	current
    DESCRIPTION
	"
	Fld OID Name:	avCmCapacityLicOffPbxTelPBFMCLicLimit
	Fld OID:	enterprises.6889.2.73.8.1.20.22
	Fld Form/Rpt:	System Capacity
	Fld Format:	Single Field
	Fld(s) Name:	Off-PBX Telephone - PBFMC
	Fld Descr:	An object that contains the System Limit of
			Off-PBX Telephone - PBFMC.
	"
    ::= { avCmCapacityLic 22 }

avCmCapacityLicOffPbxTelPVFMCUsed	OBJECT-TYPE
    SYNTAX      Integer32 (0..99999)
    MAX-ACCESS	read-only
    STATUS	current
    DESCRIPTION
	"
	Fld OID Name:	avCmCapacityLicOffPbxTelPVFMCUsed
	Fld OID:	enterprises.6889.2.73.8.1.20.23
	Fld Form/Rpt:	System Capacity
	Fld Format:	Single Field
	Fld(s) Name:	Off-PBX Telephone - PVFMC
	Fld Descr:	An object that contains the number of Used 
			Off-PBX Telephone - PVFMC.
	"
    ::= { avCmCapacityLic 23 }

avCmCapacityLicOffPbxTelPVFMCAvail	OBJECT-TYPE
    SYNTAX      Integer32 (0..99999)
    MAX-ACCESS	read-only
    STATUS	current
    DESCRIPTION
	"
	Fld OID Name:	avCmCapacityLicOffPbxTelPVFMCAvail
	Fld OID:	enterprises.6889.2.73.8.1.20.24
	Fld Form/Rpt:	System Capacity
	Fld Format:	Single Field
	Fld(s) Name:	Off-PBX Telephone - PVFMC
	Fld Descr:	An object that contains the number of Available
			Off-PBX Telephone - PVFMC.
	"
    ::= { avCmCapacityLic 24 }

avCmCapacityLicOffPbxTelPVFMCLicLimit	OBJECT-TYPE
    SYNTAX      Integer32 (0..99999)
    MAX-ACCESS	read-only
    STATUS	current
    DESCRIPTION
	"
	Fld OID Name:	avCmCapacityLicOffPbxTelPVFMCLicLimit
	Fld OID:	enterprises.6889.2.73.8.1.20.25
	Fld Form/Rpt:	System Capacity
	Fld Format:	Single Field
	Fld(s) Name:	Off-PBX Telephone - PVFMC
	Fld Descr:	An object that contains the System Limit of
			Off-PBX Telephone - PVFMC.
	"
    ::= { avCmCapacityLic 25 }

avCmCapacityLicOffPbxTelSCCANUsed	OBJECT-TYPE
    SYNTAX      Integer32 (0..99999)
    MAX-ACCESS	read-only
    STATUS	current
    DESCRIPTION
	"
	Fld OID Name:	avCmCapacityLicOffPbxTelSCCANUsed
	Fld OID:	enterprises.6889.2.73.8.1.20.26
	Fld Form/Rpt:	System Capacity
	Fld Format:	Single Field
	Fld(s) Name:	Off-PBX Telephone - SCCAN
	Fld Descr:	An object that contains the number of Used 
			Off-PBX Telephone - SCCAN.
	"
    ::= { avCmCapacityLic 26 }

avCmCapacityLicOffPbxTelSCCANAvail	OBJECT-TYPE
    SYNTAX      Integer32 (0..99999)
    MAX-ACCESS	read-only
    STATUS	current
    DESCRIPTION
	"
	Fld OID Name:	avCmCapacityLicOffPbxTelSCCANAvail
	Fld OID:	enterprises.6889.2.73.8.1.20.27
	Fld Form/Rpt:	System Capacity
	Fld Format:	Single Field
	Fld(s) Name:	Off-PBX Telephone - SCCAN
	Fld Descr:	An object that contains the number of Available
			Off-PBX Telephone - SCCAN.
	"
    ::= { avCmCapacityLic 27 }

avCmCapacityLicOffPbxTelSCCANLicLimit	OBJECT-TYPE
    SYNTAX      Integer32 (0..99999)
    MAX-ACCESS	read-only
    STATUS	current
    DESCRIPTION
	"
	Fld OID Name:	avCmCapacityLicOffPbxTelSCCANLicLimit
	Fld OID:	enterprises.6889.2.73.8.1.20.28
	Fld Form/Rpt:	System Capacity
	Fld Format:	Single Field
	Fld(s) Name:	Off-PBX Telephone - SCCAN
	Fld Descr:	An object that contains the System Limit of
			Off-PBX Telephone - SCCAN.
	"
    ::= { avCmCapacityLic 28 }

avCmCapacityLicSurvProcUsed	OBJECT-TYPE
    SYNTAX      Integer32 (0..99999)
    MAX-ACCESS	read-only
    STATUS	current
    DESCRIPTION
	"
	Fld OID Name:	avCmCapacityLicSurvProcUsed
	Fld OID:	enterprises.6889.2.73.8.1.20.29
	Fld Form/Rpt:	System Capacity
	Fld Format:	Single Field
	Fld(s) Name:	Survivable Processor Capacity
	Fld Descr:	An object that contains the number of Used 
			Survivable Processor Capacity.
	"
    ::= { avCmCapacityLic 29 }

avCmCapacityLicSurvProcAvail	OBJECT-TYPE
    SYNTAX      Integer32 (0..99999)
    MAX-ACCESS	read-only
    STATUS	current
    DESCRIPTION
	"
	Fld OID Name:	avCmCapacityLicSurvProcAvail
	Fld OID:	enterprises.6889.2.73.8.1.20.30
	Fld Form/Rpt:	System Capacity
	Fld Format:	Single Field
	Fld(s) Name:	Survivable Processor Capacity
	Fld Descr:	An object that contains the number of Available
			Survivable Processor Capacity.
	"
    ::= { avCmCapacityLic 30 }

avCmCapacityLicSurvProcLicLimit	OBJECT-TYPE
    SYNTAX      Integer32 (0..99999)
    MAX-ACCESS	read-only
    STATUS	current
    DESCRIPTION
	"
	Fld OID Name:	avCmCapacityLicSurvProcLicLimit
	Fld OID:	enterprises.6889.2.73.8.1.20.31
	Fld Form/Rpt:	System Capacity
	Fld Format:	Single Field
	Fld(s) Name:	Survivable Processor Capacity
	Fld Descr:	An object that contains the System Limit of
			Survivable Processor Capacity.
	"
    ::= { avCmCapacityLic 31 }

avCmCapacityLicAvMedSerVoIPChUsed	OBJECT-TYPE
    SYNTAX      Integer32 (0..99999)
    MAX-ACCESS	read-only
    STATUS	current
    DESCRIPTION
	"
	Fld OID Name:	avCmCapacityLicAvMedSerVoIPChUsed
	Fld OID:	enterprises.6889.2.73.8.1.20.32
	Fld Form/Rpt:	System Capacity
	Fld Format:	Single Field
	Fld(s) Name:	Avaya Media Server VoIP Channels
	Fld Descr:	An object that contains the number of Used 
			Avaya Media Server VoIP Channels.
	"
    ::= { avCmCapacityLic 32 }

avCmCapacityLicAvMedSerVoIPChAvail	OBJECT-TYPE
    SYNTAX      Integer32 (0..99999)
    MAX-ACCESS	read-only
    STATUS	current
    DESCRIPTION
	"
	Fld OID Name:	avCmCapacityLicAvMedSerVoIPChAvail
	Fld OID:	enterprises.6889.2.73.8.1.20.33
	Fld Form/Rpt:	System Capacity
	Fld Format:	Single Field
	Fld(s) Name:	Avaya Media Server VoIP Channels
	Fld Descr:	An object that contains the number of Available
			Avaya Media Server VoIP Channels.
	"
    ::= { avCmCapacityLic 33 }

avCmCapacityLicAvMedSerVoIPChLicLimit	OBJECT-TYPE
    SYNTAX      Integer32 (0..99999)
    MAX-ACCESS	read-only
    STATUS	current
    DESCRIPTION
	"
	Fld OID Name:	avCmCapacityLicAvMedSerVoIPChLicLimit
	Fld OID:	enterprises.6889.2.73.8.1.20.34
	Fld Form/Rpt:	System Capacity
	Fld Format:	Single Field
	Fld(s) Name:	Avaya Media Server VoIP Channels
	Fld Descr:	An object that contains the System Limit of
			Avaya Media Server VoIP Channels.
	"
    ::= { avCmCapacityLic 34 }

-- ******************** avCmCapacityUsage Group *************************

-- MIB GROUP DESCRIPTION

-- MIB Group Name:
--		avCmCapacityUsage
-- OID:
--		enterprises.6889.2.73.8.1.21
-- Description:
--		The avCmCapacityUsage MIB Group uses the "display capacity"
-- 		command to retrieve the USAGE capacity information
-- 		under the CONCURRENT USAGE COUNTS section of the 
--		SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityUsage	OBJECT IDENTIFIER ::= { avCmObjects 21 }

avCmCapacityUsageIPStatUsed	OBJECT-TYPE
    SYNTAX	Integer32 (0..99999)
    MAX-ACCESS	read-only
    STATUS	current
    DESCRIPTION
	"
	Fld OID Name:	avCmCapacityUsageIPStatUsed
	Fld OID:	enterprises.6889.2.73.8.1.21.1
	Fld Form/Rpt:	System Capacity
	Fld Format:	Single Field
	Fld(s) Name:	IP Stations
	Fld Descr:	An object that contains the number of Used 
			IP Stations.
	"
    ::= { avCmCapacityUsage 1 }

avCmCapacityUsageIPStatAvail	OBJECT-TYPE
    SYNTAX	Integer32 (0..99999)
    MAX-ACCESS	read-only
    STATUS	current
    DESCRIPTION
	"
	Fld OID Name:	avCmCapacityUsageIPStatAvail
	Fld OID:	enterprises.6889.2.73.8.1.21.2
	Fld Form/Rpt:	System Capacity
	Fld Format:	Single Field
	Fld(s) Name:	IP Stations
	Fld Descr:	An object that contains the number of Available 
			IP Stations.
	"
    ::= { avCmCapacityUsage 2 }

avCmCapacityUsageIPStatSysLim	OBJECT-TYPE
    SYNTAX	Integer32 (0..99999)
    MAX-ACCESS	read-only
    STATUS	current
    DESCRIPTION
	"
	Fld OID Name:	avCmCapacityUsageIPStatSysLim
	Fld OID:	enterprises.6889.2.73.8.1.21.3
	Fld Form/Rpt:	System Capacity
	Fld Format:	Single Field
	Fld(s) Name:	IP Stations
	Fld Descr:	An object that contains the System Limit of 
			IP Stations.
	"
    ::= { avCmCapacityUsage 3 }


avCmCapacityUsageIPAttConUsed	OBJECT-TYPE
    SYNTAX	Integer32 (0..99999)
    MAX-ACCESS	read-only
    STATUS	current
    DESCRIPTION
	"
	Fld OID Name:	avCmCapacityUsageIPAttConUsed
	Fld OID:	enterprises.6889.2.73.8.1.21.4
	Fld Form/Rpt:	System Capacity
	Fld Format:	Single Field
	Fld(s) Name:	IP Attendant Consoles
	Fld Descr:	An object that contains the number of Used 
			IP Attendant Consoles.
	"
    ::= { avCmCapacityUsage 4 }

avCmCapacityUsageIPAttConAvail	OBJECT-TYPE
    SYNTAX	Integer32 (0..99999)
    MAX-ACCESS	read-only
    STATUS	current
    DESCRIPTION
	"
	Fld OID Name:	avCmCapacityUsageIPAttConAvail
	Fld OID:	enterprises.6889.2.73.8.1.21.5
	Fld Form/Rpt:	System Capacity
	Fld Format:	Single Field
	Fld(s) Name:	IP Attendant Consoles
	Fld Descr:	An object that contains the number of Available
			IP Attendant Consoles.
	"
    ::= { avCmCapacityUsage 5 }

avCmCapacityUsageIPAttConSysLim	OBJECT-TYPE
    SYNTAX	Integer32 (0..99999)
    MAX-ACCESS	read-only
    STATUS	current
    DESCRIPTION
	"
	Fld OID Name:	avCmCapacityUsageIPAttConSysLim
	Fld OID:	enterprises.6889.2.73.8.1.21.6
	Fld Form/Rpt:	System Capacity
	Fld Format:	Single Field
	Fld(s) Name:	IP Attendant Consoles
	Fld Descr:	An object that contains the System Limit
			IP Attendant Consoles.
	"
    ::= { avCmCapacityUsage 6 }

avCmCapacityUsageRemOffStatUsed	OBJECT-TYPE
    SYNTAX	Integer32 (0..99999)
    MAX-ACCESS	read-only
    STATUS	current
    DESCRIPTION
	"
	Fld OID Name:	avCmCapacityUsageRemOffStatUsed
	Fld OID:	enterprises.6889.2.73.8.1.21.7
	Fld Form/Rpt:	System Capacity
	Fld Format:	Single Field
	Fld(s) Name:	Remote Office Stations
	Fld Descr:	An object that contains the number of Used 
			Remote Office Stations.
	"
    ::= { avCmCapacityUsage 7 }

avCmCapacityUsageRemOffStatAvail	OBJECT-TYPE
    SYNTAX	Integer32 (0..99999)
    MAX-ACCESS	read-only
    STATUS	current
    DESCRIPTION
	"
	Fld OID Name:	avCmCapacityUsageRemOffStatAvail
	Fld OID:	enterprises.6889.2.73.8.1.21.8
	Fld Form/Rpt:	System Capacity
	Fld Format:	Single Field
	Fld(s) Name:	Remote Office Stations
	Fld Descr:	An object that contains the number of Available
			Remote Office Stations.
	"
    ::= { avCmCapacityUsage 8 }

avCmCapacityUsageRemOffStatSysLim	OBJECT-TYPE
    SYNTAX	Integer32 (0..99999)
    MAX-ACCESS	read-only
    STATUS	current
    DESCRIPTION
	"
	Fld OID Name:	avCmCapacityUsageRemOffStatSysLim
	Fld OID:	enterprises.6889.2.73.8.1.21.9
	Fld Form/Rpt:	System Capacity
	Fld Format:	Single Field
	Fld(s) Name:	Remote Office Stations
	Fld Descr:	An object that contains the System Limit of
			Remote Office Stations.
	"
    ::= { avCmCapacityUsage 9 }

avCmCapacityUsageUnauthH323StatUsed	OBJECT-TYPE
    SYNTAX      Integer32 (0..99999)
    MAX-ACCESS	read-only
    STATUS	current
    DESCRIPTION
	"
	Fld OID Name:	avCmCapacityUsageUnauthH323StatUsed
	Fld OID:	enterprises.6889.2.73.8.1.21.10
	Fld Form/Rpt:	System Capacity
	Fld Format:	Single Field
	Fld(s) Name:	Remote Office Stations
	Fld Descr:	An object that contains the number of Used 
			Remote Office Stations.
	"
    ::= { avCmCapacityUsage 10 }

avCmCapacityUsageUnauthH323StatAvail	OBJECT-TYPE
    SYNTAX      Integer32 (0..99999)
    MAX-ACCESS	read-only
    STATUS	current
    DESCRIPTION
	"
	Fld OID Name:	avCmCapacityUsageUnauthH323StatAvail
	Fld OID:	enterprises.6889.2.73.8.1.21.11
	Fld Form/Rpt:	System Capacity
	Fld Format:	Single Field
	Fld(s) Name:	Remote Office Stations
	Fld Descr:	An object that contains the number of Available
			Remote Office Stations.
	"
    ::= { avCmCapacityUsage  11 }

avCmCapacityUsageUnauthH323StatSysLim	OBJECT-TYPE
    SYNTAX      Integer32 (0..99999)
    MAX-ACCESS	read-only
    STATUS	current
    DESCRIPTION
	"
	Fld OID Name:	avCmCapacityUsageUnauthH323StatSysLim
	Fld OID:	enterprises.6889.2.73.8.1.21.12
	Fld Form/Rpt:	System Capacity
	Fld Format:	Single Field
	Fld(s) Name:	Remote Office Stations
	Fld Descr:	An object that contains the System Limit of
			Remote Office Stations.
	"
    ::= { avCmCapacityUsage 12 }

avCmCapacityUsageAESServLicUsed	OBJECT-TYPE
    SYNTAX      Integer32 (0..99999)
    MAX-ACCESS	read-only
    STATUS	current
    DESCRIPTION
	"
	Fld OID Name:	avCmCapacityUsageAESServLicUsed
	Fld OID:	enterprises.6889.2.73.8.1.21.13
	Fld Form/Rpt:	System Capacity
	Fld Format:	Single Field
	Fld(s) Name:	AES Server Licensed IP Stations
	Fld Descr:	An object that contains the number of Used 
			AES Server Licensed IP Stations.
	"
    ::= { avCmCapacityUsage  13 }

-- ******************** avCmCapacityIPUsage Group *************************

-- MIB GROUP DESCRIPTION

-- MIB Group Name:
--		avCmCapacityIPUsage
-- OID:
--		enterprises.6889.2.73.8.1.22
-- Description:
--		The avCmCapacityIPUsage MIB Group uses the "display capacity"
-- 		command to retrieve the  IP PORT USAGE capacity information
-- 		under the IP PORT USAGE COUNTS section of the 
--		SYSTEM CAPACITY form. 
--		
-- Releases Supported:
--		CM6.3.100 and greater
-- Polling Type:
--		Configuration, Inventory, and Performance/Utilization
-- Polling Interval:
--		No more than once every 20 minutes.
-- Default Caching Interval
-- 		600 seconds
-- Timeout Interval:
--		Initial Timeout should be set to 15 seconds.
-- Retry Interval:
--		Initial Retry should be set to 3.
-- Limitations:
--		Yellow/Medium - The data collected by this MIB Group
--		may have some impact the on the system.
-- Command Type:
--		1. SAT
-- Command:
--		1. display capacity
-- Form/Report Name:
--		1. System Capacity 
-- Reference Document:
--		1. A detailed description of the command and form can be
--		   found in document referenced by REF_DOC_1 in the
--		   DOCUMENT REFERENCE SECTION.
-- Command Permission/User-profile:
--		1. No special permissions needed.

avCmCapacityIPUsage	OBJECT IDENTIFIER ::= { avCmObjects 22 }

avCmCapacityIPUsageTotalIpStatPtsUsed	OBJECT-TYPE
    SYNTAX	Integer32 (0..99999)
    MAX-ACCESS	read-only
    STATUS	current
    DESCRIPTION
	"
	Fld OID Name:	avCmCapacityIPUsageTotalIpStatPtsUsed
	Fld OID:	enterprises.6889.2.73.8.1.22.1
	Fld Form/Rpt:	System Capacity
	Fld Format:	Single Field
	Fld(s) Name:	Total IP Station Ports
	Fld Descr:	An object that contains the number of Used 
			Total IP Station Ports.
	"
    ::= { avCmCapacityIPUsage 1 }

avCmCapacityIPUsageTotalIpStatPtsAvail	OBJECT-TYPE
    SYNTAX	Integer32 (0..99999)
    MAX-ACCESS	read-only
    STATUS	current
    DESCRIPTION
	"
	Fld OID Name:	avCmCapacityIPUsageTotalIpStatPtsAvail
	Fld OID:	enterprises.6889.2.73.8.1.22.2
	Fld Form/Rpt:	System Capacity
	Fld Format:	Single Field
	Fld(s) Name:	Total IP Station Ports
	Fld Descr:	An object that contains the number of Available 
			Total IP Station Ports.
	"
    ::= { avCmCapacityIPUsage 2 }

avCmCapacityIPUsageTotalIpStatPtsSysLim	OBJECT-TYPE
    SYNTAX	Integer32 (0..99999)
    MAX-ACCESS	read-only
    STATUS	current
    DESCRIPTION
	"
	Fld OID Name:	avCmCapacityIPUsageTotalIpStatPtsSysLim
	Fld OID:	enterprises.6889.2.73.8.1.22.3
	Fld Form/Rpt:	System Capacity
	Fld Format:	Single Field
	Fld(s) Name:	Total IP Station Ports
	Fld Descr:	An object that contains the System Limit of 
			Total IP Station Ports.
	"
    ::= { avCmCapacityIPUsage 3 }

--   *********** avCmCapacityCurrentUsage Group **************

-- MIB Group Name:
--		avCmCapacityCurrentUsage
-- OID:
--		enterprises.6889.2.73.8.1.23
-- Description:
--		The avCmCapacityCurrentUsage MIB group displays the output of 
--		the CURRENT USAGE COUNTS BY PRODUCT ID page of 
--		DISPLAY CAPACITY command.
-- Releases Supported:
--		CM6.3.100 and greater
-- Polling Type:
--              Configuration, Inventory, and Performance/Utilization
-- Polling Interval:
--              No more than once every 20 minutes.
-- Default Caching Interval
-- 		600 seconds
-- Timeout Interval:
--              Initial Timeout should be set to 15 seconds.
-- Retry Interval:
--              Initial Retry should be set to 3.
-- Limitations:
--              Yellow/Medium - The data collected by this MIB Group
--              may have some impact the on the system.
-- Command Type:
--              1. SAT
-- Command:
--              1. display capacity
-- Form/Report Name:
--              1. System Capacity
-- Reference Document:
--              1. A detailed description of the command and form can be
--                 found in document referenced by REF_DOC_1 in the
--                 DOCUMENT REFERENCE SECTION.
-- Command Permission/User-profile:
--              1. No special permissions needed.


avCmCapacityCurrentUsage		OBJECT IDENTIFIER ::= { avCmObjects 23 }

avCmCapacityCurrentUsageTable	OBJECT-TYPE
    SYNTAX	SEQUENCE OF AvCmCapacityCurrentUsageEntry
    MAX-ACCESS	not-accessible
    STATUS	current
    DESCRIPTION
	"
	Fld OID Name:	avCmCapacityCurrentUsageEntry
	Fld OID:	enterprises.6889.2.73.8.1.23.1
	Fld Form/Rpt:	NA
	Fld Format:	NA
	Fld(s) Name:	NA
	Fld Descr:	A list of the avCmCapacityCurrentUsage entries
	"
    ::= { avCmCapacityCurrentUsage 1 }

avCmCapacityCurrentUsageEntry	OBJECT-TYPE
    SYNTAX	AvCmCapacityCurrentUsageEntry
    MAX-ACCESS	not-accessible
    STATUS	current
    DESCRIPTION
	"
	Fld OID Name:	avCmCapacityCurrentUsageEntry
	Fld OID:	enterprises.6889.2.73.8.1.23.1.1
	Fld Format:	NA
	Fld Form/Rpt:	NA
	Fld(s) Name:	NA
	Fld Descr:	A avCmCapacityCurrentUsage  entry containing objects 
			of the avCmCapacityCurrentUsage information sent by 				the switch.
	"
    INDEX    { avCmCapacityCurrentUsageIdx }
    ::= { avCmCapacityCurrentUsageTable 1 }

AvCmCapacityCurrentUsageEntry ::= SEQUENCE {
		avCmCapacityCurrentUsageIdx
		    SnmpAdminString,
		avCmCapacityCurrentUsageID
		    SnmpAdminString,
		avCmCapacityCurrentUsageRel
		    SnmpAdminString,
		avCmCapacityCurrentUsageUsed
		    Integer32,
		avCmCapacityCurrentUsageAvail
		    Integer32,
		avCmCapacityCurrentUsageLicLim
		    Integer32
		}

avCmCapacityCurrentUsageIdx	OBJECT-TYPE
    SYNTAX	SnmpAdminString (SIZE (0..11))
    MAX-ACCESS	not-accessible
    STATUS	current
    DESCRIPTION
	"
	Fld OID Name:	avCmCapacityCurrentUsageIdx
	Fld OID:	enterprises.6889.2.73.8.1.23.1.1.1
	Fld Form/Rpt:	NA
	Fld Format:	NA
	Fld(s) Name:	NA
	Fld Descr:	An object containing an index that uniquely identifies
			an Product ID
	"
    ::= { avCmCapacityCurrentUsageEntry 1 }

avCmCapacityCurrentUsageID	OBJECT-TYPE
    SYNTAX	SnmpAdminString (SIZE (0..11))
    MAX-ACCESS	read-only
    STATUS	current
    DESCRIPTION
	"
	Fld OID Name:	avCmServerID
	Fld OID:	enterprises.6889.2.73.8.1.23.1.1.2
	Fld Form/Rpt:	System Capacity
	Fld Format:	Single
	Fld(s) Name:	ID
	Fld Descr:	An object containing the Product ID of the entry
	"
    ::= { avCmCapacityCurrentUsageEntry 2 }

avCmCapacityCurrentUsageRel	OBJECT-TYPE
    SYNTAX	SnmpAdminString (SIZE (0..3))
    MAX-ACCESS	read-only
    STATUS	current
    DESCRIPTION
	"
	Fld OID Name:	avCmCapacityCurrentUsageRel
	Fld OID:	enterprises.6889.2.73.8.1.23.1.1.3
	Fld Form/Rpt:	System Capacity
	Fld Format:	Single
	Fld(s) Name:	Rel
	Fld Descr:	An object containing the release of the product ID.
	"
    ::= { avCmCapacityCurrentUsageEntry 3 }

avCmCapacityCurrentUsageUsed	OBJECT-TYPE
    SYNTAX	Integer32 (0..99999)
    MAX-ACCESS	read-only
    STATUS	current
    DESCRIPTION
	"
	Fld OID Name:	avCmCapacityCurrentUsageUsed
	Fld OID:	enterprises.6889.2.73.8.1.23.1.1.4
	Fld Form/Rpt:	System Capacity
	Fld Format:	Single
	Fld(s) Name:	ID
	Fld Descr:	An object that contains the Used count	
			of a product ID.
	"
    ::= { avCmCapacityCurrentUsageEntry 4 }

avCmCapacityCurrentUsageAvail	OBJECT-TYPE
    SYNTAX	Integer32 (0..99999)
    MAX-ACCESS	read-only
    STATUS	current
    DESCRIPTION
	"
	Fld OID Name:	avCmCapacityCurrentUsageAvail
	Fld OID:	enterprises.6889.2.73.8.1.23.1.1.5
	Fld Form/Rpt:	System Capacity
	Fld Format:	Single
	Fld(s) Name:	Avail.
	Fld Descr:	An object that contains the Available count
			of a product ID.
	"
    ::= { avCmCapacityCurrentUsageEntry 5 }

avCmCapacityCurrentUsageLicLim	OBJECT-TYPE
    SYNTAX	Integer32 (0..99999)
    MAX-ACCESS	read-only
    STATUS	current
    DESCRIPTION
	"
	Fld OID Name:	avCmCapacityCurrentUsageLicLim
	Fld OID:	enterprises.6889.2.73.8.1.23.1.1.6
	Fld Form/Rpt:	System Capacity
	Fld Format:	Single
	Fld(s) Name:	Limit
	Fld Descr:	An object that contains the licensed limit
			of a product ID.
	"
    ::= { avCmCapacityCurrentUsageEntry 6 }

--   *********** avCmListMemTrunk Group **************

-- MIB Group Name:
--		avCmListMemTrunk
-- OID:
--		enterprises.6889.2.73.8.1.24
-- Description:
--		The avCmListMemTrunk MIB group displays the output of the
--		list member trunk command up to the first 500 members of
--              trunk groups.
--
-- Releases Supported:
--		CM6.3.100 and greater
-- Polling Type:
--		Configuration.
-- Polling Interval:
--		No more than once a day or when trunk members are added.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
--		2. SAT
-- Command:
--		1. list member trunk 
--		2. display trunk xxxxx
-- Form/Report Name:
--		1. TRUNK GROUP MEMBERS
--		2. TRUNK GROUP
-- Reference Document:
--		1. Information about trunk-groups can be
--		   found in REF_DOC_5 in the DOCUMENT REFERENCE SECTION.
--		2. Information about trunk-groups can be
--		   found in REF_DOC_5 in the DOCUMENT REFERENCE SECTION.
-- Command Permission/User-profile:
--		1. No special permissions needed. Default customer super-user
--		   profile can access this command.
--		2. No special permissions needed. Default customer super-user
--		   profile can access this command.

avCmListMemTrunk	OBJECT IDENTIFIER ::= { avCmObjects 24 }

avCmListMemTrunkGrp	OBJECT-TYPE
    SYNTAX	Integer32 (0..2000)
    MAX-ACCESS	read-write
    STATUS	current
    DESCRIPTION
	"
	Fld OID Name:	avCmListMemTrunkGrp
	Fld OID:	enterprises.6889.2.73.8.1.24.1
	Fld Form/Rpt:	NA
	Fld Format:	NA
	Fld(s) Name:	NA
	Fld Descr:	An object containing the trunk group
	"
    ::= { avCmListMemTrunk 1 }

avCmListMemTrunkTable	OBJECT-TYPE
    SYNTAX	SEQUENCE OF AvCmListMemTrunkEntry
    MAX-ACCESS	not-accessible
    STATUS	current
    DESCRIPTION
	"
	Fld OID Name:	avCmListMemTrunkTable
	Fld OID:	enterprises.6889.2.73.8.1.24.2
	Fld Form/Rpt:	NA
	Fld Format:	NA
	Fld(s) Name:	NA
	Fld Descr:	A list of the avCmMemTrunk entries.
	"
    ::= { avCmListMemTrunk 2 }

avCmListMemTrunkEntry	OBJECT-TYPE
    SYNTAX	AvCmListMemTrunkEntry
    MAX-ACCESS	not-accessible
    STATUS	current
    DESCRIPTION
	"
	Fld OID Name:	avCmListMemTrunkEntry
	Fld OID:	enterprises.6889.2.73.8.1.24.3.1
	Fld Form/Rpt:	NA
	Fld Format:	NA
	Fld(s) Name:	NA
	Fld Descr:	A avCmListMemTrunk entry containing objects of the
			avCmListMemTrunk information sent by the switch.
	"
    INDEX    { avCmListMemTrunkIdx, avCmListMemTrunkMemberIdx }
    ::= { avCmListMemTrunkTable 1 }

AvCmListMemTrunkEntry ::= SEQUENCE {
		avCmListMemTrunkIdx
		    Integer32,
                avCmListMemTrunkMemberIdx
                    Integer32,
                avCmListMemTrunkMemMember
                    Integer32,
                avCmListMemTrunkPort
                    SnmpAdminString,
                avCmListMemTrunkName
                    SnmpAdminString,
                avCmListMemTrunkType
                    SnmpAdminString,
                avCmListMemTrunkSigGrp
                    Integer32
		}

avCmListMemTrunkIdx	OBJECT-TYPE
    SYNTAX	Integer32 (1..2000)
    MAX-ACCESS	not-accessible
    STATUS	current
    DESCRIPTION
	"
	Fld OID Name:	avCmListMemTrunkIdx
	Fld OID:	enterprises.6889.2.73.8.1.24.3.1.1
	Fld Form/Rpt:	NA
	Fld Format:	NA
	Fld(s) Name:	NA
	Fld Descr:	An index into the Trunk Group.
	"
    ::= { avCmListMemTrunkEntry 1 }

avCmListMemTrunkMemberIdx        OBJECT-TYPE
    SYNTAX      Integer32 (0..255)
    MAX-ACCESS	not-accessible
    STATUS      current
    DESCRIPTION
        "
        Fld OID Name:   avCmListMemTrunkMemberIdx
        Fld OID:        enterprises.6889.2.73.8.1.24.3.1.2
        Fld Form/Rpt:   NA
        Fld Format:     NA
        Fld(s) Name:    NA
        Fld Descr:      An index that contains the Member No. for the
                        Trunk Group Port.
        "
    ::= { avCmListMemTrunkEntry 2 }

avCmListMemTrunkMemMember        OBJECT-TYPE
    SYNTAX      Integer32 (0..255)
    MAX-ACCESS  read-only
    STATUS      current
    DESCRIPTION
        "
        Fld OID Name:   avCmListMemTrunkMemMember
        Fld OID:        enterprises.6889.2.73.8.1.24.3.1.3
        Fld Form/Rpt:   TRUNK GROUP MEMBERS
        Fld Format:     Single Field
        Fld(s) Name:    List Command: Member No.
                        Display Command: Member No.
        Fld Descr:      An object that contains the Member No. for the
                        Trunk Group Port.
        "
    ::= { avCmListMemTrunkEntry 3 }

avCmListMemTrunkPort	OBJECT-TYPE
    SYNTAX	SnmpAdminString (SIZE (0..10))
    MAX-ACCESS	read-only
    STATUS	current
    DESCRIPTION
	"
	Fld OID Name:	avCmListMemTrunkPort
	Fld OID:	enterprises.6889.2.73.8.1.24.3.1.4
	Fld Form/Rpt:	TRUNK GROUP MEMBERS
	Fld Format:	Single
	Fld(s) Name:	Port
	Fld Descr:	An object containing the trunk member Port.
	"
    ::= { avCmListMemTrunkEntry 4 }

avCmListMemTrunkName	OBJECT-TYPE
    SYNTAX	SnmpAdminString (SIZE (0..11))
    MAX-ACCESS	read-only
    STATUS	current
    DESCRIPTION
	"
	Fld OID Name:	avCmListMemTrunkName
	Fld OID:	enterprises.6889.2.73.8.1.24.3.1.5
	Fld Form/Rpt:	TRUNK GROUP MEMBERS
	Fld Format:	Single
	Fld(s) Name:	Name
	Fld Descr:	An object containing the name assigned to the member.
	"
    ::= { avCmListMemTrunkEntry 5 }

avCmListMemTrunkType	OBJECT-TYPE
    SYNTAX	SnmpAdminString (SIZE (0..8))
    MAX-ACCESS	read-only
    STATUS	current
    DESCRIPTION
	"
	Fld OID Name:	avCmListMemTrunkType
	Fld OID:	enterprises.6889.2.73.8.1.24.3.1.6
	Fld Form/Rpt:	TRUNK GROUP
	Fld Format:	Single
	Fld(s) Name:	Type
	Fld Descr:	An object containing the trunk group  member type.
			assigned.
	"
    ::= { avCmListMemTrunkEntry 6 }

avCmListMemTrunkSigGrp	OBJECT-TYPE
    SYNTAX	Integer32 (0..999)
    MAX-ACCESS	read-only
    STATUS	current
    DESCRIPTION
	"
	Fld OID Name:	avCmListMemTrunkSigGrp
	Fld OID:	enterprises.6889.2.73.8.1.24.3.1.7
	Fld Form/Rpt:	TRUNK GROUP
	Fld Format:	Single
	Fld(s) Name:	Signaling Group
	Fld Descr:	An object containing the signaling group of the sip
			trunk group.
	"
    ::= { avCmListMemTrunkEntry 7 }

--   *********** avCmListMemTrunkRange Group **************

-- MIB Group Name:
--		avCmListMemTrunkRange
-- OID:
--		enterprises.6889.2.73.8.1.25
-- Description:
--		The avCmListMemTrunkRange MIB group displays the output of the
--		list member trunk xxxx count xxx command.
--
-- Releases Supported:
--		CM6.3.100 and greater
-- Polling Type:
--		Inventory and Performance/Utilization
-- Polling Interval:
--		No more than once a day or when trunk members are added.
-- Default Caching Interval
-- 		600 seconds
-- Timeout Interval:
--		Initial Timeout should be set to 15 seconds.
-- Retry Interval:
--		Initial Retry should be set to 3.
-- Limitations:
--		Yellow/Medium - The data collected by this MIB Group
--		may have some impact on the system.
-- Command Type:
--		1. SAT
--		2. SAT
-- Command:
--		1. list member trunk xxxx count xxx
--		2. display trunk xxxxx
-- Form/Report Name:
--		1. TRUNK GROUP MEMBERS
--		2. TRUNK GROUP
-- Reference Document:
--		1. Information about trunk-groups can be
--		   found in REF_DOC_5 in the DOCUMENT REFERENCE SECTION.
--		2. Information about trunk-groups can be
--		   found in REF_DOC_5 in the DOCUMENT REFERENCE SECTION.
-- Command Permission/User-profile:
--		1. No special permissions needed. Default customer super-user
--		   profile can access this command.
--		2. No special permissions needed. Default customer super-user
--		   profile can access this command.

avCmListMemTrunkRange	OBJECT IDENTIFIER ::= { avCmObjects 25 }

avCmListMemTrunkRangeGrp	OBJECT-TYPE
    SYNTAX	Integer32 (1..2000)
    MAX-ACCESS	read-write
    STATUS	current
    DESCRIPTION
	"
	Fld OID Name:	avCmListMemTrunkRangeGrp
	Fld OID:	enterprises.6889.2.73.8.1.25.1
	Fld Form/Rpt:	NA
	Fld Format:	NA
	Fld(s) Name:	NA
	Fld Descr:	An object containing the trunk group
	"
    ::= { avCmListMemTrunkRange 1 }

avCmListMemTrunkRangeStart        OBJECT-TYPE
    SYNTAX      Integer32 (1..255)
    MAX-ACCESS	read-write
    STATUS      current
    DESCRIPTION
        "
        Fld OID Name:   avCmListMemTrunkRangeStart
        Fld OID:        enterprises.6889.2.73.8.1.25.2
        Fld Form/Rpt:   NA
        Fld Format:     NA
        Fld(s) Name:    NA
        Fld Descr:      An index that contains the starting Member No. for the
                        Trunk Group Port.
        "
    ::= { avCmListMemTrunkRange 2 }

avCmListMemTrunkRangeCount	OBJECT-TYPE
    SYNTAX	Integer32 (1..255)
    MAX-ACCESS	read-write
    STATUS	current
    DESCRIPTION
	"
	Fld OID Name:	avCmListMemTrunkRangeCount
	Fld OID:	enterprises.6889.2.73.8.1.25.3
	Fld Form/Rpt:	NA
	Fld Format:	NA
	Fld(s) Name:	NA
	Fld Descr:	An object containing the trunk member count
	"
    ::= { avCmListMemTrunkRange 3 }

avCmListMemTrunkRangeTable	OBJECT-TYPE
    SYNTAX	SEQUENCE OF AvCmListMemTrunkRangeEntry
    MAX-ACCESS	not-accessible
    STATUS	current
    DESCRIPTION
	"
	Fld OID Name:	avCmListMemTrunkRangeTable
	Fld OID:	enterprises.6889.2.73.8.1.25.4
	Fld Form/Rpt:	NA
	Fld Format:	NA
	Fld(s) Name:	NA
	Fld Descr:	A list of the avCmMemTrunk entries.
	"
    ::= { avCmListMemTrunkRange 4 }

avCmListMemTrunkRangeEntry	OBJECT-TYPE
    SYNTAX	AvCmListMemTrunkRangeEntry
    MAX-ACCESS	not-accessible
    STATUS	current
    DESCRIPTION
	"
	Fld OID Name:	avCmListMemTrunkRangeEntry
	Fld OID:	enterprises.6889.2.73.8.1.25.4.1
	Fld Form/Rpt:	NA
	Fld Format:	NA
	Fld(s) Name:	NA
	Fld Descr:	A avCmListMemTrunkRange entry containing objects of the
			avCmListMemTrunkRange information sent by the switch.
	"
    INDEX    { avCmListMemTrunkRangeIdx, avCmListMemTrunkMemberIdx }
    ::= { avCmListMemTrunkRangeTable 1 }

AvCmListMemTrunkRangeEntry ::= SEQUENCE {
		avCmListMemTrunkRangeIdx
		    Integer32,
                avCmListMemTrunkRangeMemberIdx
                    Integer32,
                avCmListMemTrunkRangeMemMember
                    Integer32,
                avCmListMemTrunkRangePort
                    SnmpAdminString,
                avCmListMemTrunkRangeTnCode
                    SnmpAdminString,
                avCmListMemTrunkRangeSfx
                    SnmpAdminString,
                avCmListMemTrunkRangeName
                    SnmpAdminString,
                avCmListMemTrunkRangeNight
                    SnmpAdminString,
                avCmListMemTrunkRangeMode
                    SnmpAdminString,
                avCmListMemTrunkRangeType
                    SnmpAdminString,
                avCmListMemTrunkRangeAnsDelay
                    Integer32,
                avCmListMemTrunkRangeSigGrp
                    Integer32
		}

avCmListMemTrunkRangeIdx	OBJECT-TYPE
    SYNTAX	Integer32 (0..2000)
    MAX-ACCESS	not-accessible
    STATUS	current
    DESCRIPTION
	"
	Fld OID Name:	avCmListMemTrunkRangeIdx
	Fld OID:	enterprises.6889.2.73.8.1.25.4.1.1
	Fld Form/Rpt:	NA
	Fld Format:	NA
	Fld(s) Name:	NA
	Fld Descr:	An index into the Trunk Group.
	"
    ::= { avCmListMemTrunkRangeEntry 1 }

avCmListMemTrunkRangeMemberIdx        OBJECT-TYPE
    SYNTAX      Integer32 (0..255)
    MAX-ACCESS	not-accessible
    STATUS      current
    DESCRIPTION
        "
        Fld OID Name:   avCmListMemTrunkRangeMemberIdx
        Fld OID:        enterprises.6889.2.73.8.1.25.4.1.2
        Fld Form/Rpt:   NA
        Fld Format:     NA
        Fld(s) Name:    NA
        Fld Descr:      An index that contains the Member No. for the
                        Trunk Group Port.
        "
    ::= { avCmListMemTrunkRangeEntry 2 }

avCmListMemTrunkRangeMemMember        OBJECT-TYPE
    SYNTAX      Integer32 (0..255)
    MAX-ACCESS  read-only
    STATUS      current
    DESCRIPTION
        "
        Fld OID Name:   avCmListMemTrunkRangeMemMember
        Fld OID:        enterprises.6889.2.73.8.1.25.4.1.3
        Fld Form/Rpt:   NA
        Fld Format:     Single Field
        Fld(s) Name:    List Command: Member No.
                        Display Command: Member No.
        Fld Descr:      An object that contains the Member No. for the
                        Trunk Group Port.
        "
    ::= { avCmListMemTrunkRangeEntry 3 }

avCmListMemTrunkRangePort	OBJECT-TYPE
    SYNTAX	SnmpAdminString (SIZE (0..12))
    MAX-ACCESS	read-only
    STATUS	current
    DESCRIPTION
	"
	Fld OID Name:	avCmListMemTrunkRangePort
	Fld OID:	enterprises.6889.2.73.8.1.25.4.1.4
	Fld Form/Rpt:	TRUNK GROUP MEMBERS
	Fld Format:	Single
	Fld(s) Name:	Port
	Fld Descr:	An object containing the trunk member Port.
	"
    ::= { avCmListMemTrunkRangeEntry 4 }

avCmListMemTrunkRangeTnCode       OBJECT-TYPE
    SYNTAX      SnmpAdminString (SIZE (0..7))
    MAX-ACCESS  read-only
    STATUS      current
    DESCRIPTION
        "
        Fld OID Name:   avCmListMemTrunkRangeTnCode
        Fld OID:        enterprises.6889.2.73.8.1.25.4.1.5
        Fld Form/Rpt:   TRUNK GROUP MEMBERS
        Fld Format:     Single
        Fld(s) Name:    TN Code
        Fld Descr:      An object containing the trunk member TN code.
        "
    ::= { avCmListMemTrunkRangeEntry 5 }

avCmListMemTrunkRangeSfx       OBJECT-TYPE
    SYNTAX      SnmpAdminString (SIZE (0..2))
    MAX-ACCESS  read-only
    STATUS      current
    DESCRIPTION
        "
        Fld OID Name:   avCmListMemTrunkRangeSfx
        Fld OID:        enterprises.6889.2.73.8.1.25.4.1.6
        Fld Form/Rpt:   TRUNK GROUP MEMBERS
        Fld Format:     Single
        Fld(s) Name:    Sfx
        Fld Descr:      An object containing the trunk member TN code.
        "
    ::= { avCmListMemTrunkRangeEntry 6 }


avCmListMemTrunkRangeName	OBJECT-TYPE
    SYNTAX	SnmpAdminString (SIZE (0..13))
    MAX-ACCESS	read-only
    STATUS	current
    DESCRIPTION
	"
	Fld OID Name:	avCmListMemTrunkRangeName
	Fld OID:	enterprises.6889.2.73.8.1.25.4.1.7
	Fld Form/Rpt:	TRUNK GROUP MEMBERS
	Fld Format:	Single
	Fld(s) Name:	Name
	Fld Descr:	An object containing the name assigned to the member.
	"
    ::= { avCmListMemTrunkRangeEntry 7 }


avCmListMemTrunkRangeNight       OBJECT-TYPE
    SYNTAX      SnmpAdminString (SIZE (0..14))
    MAX-ACCESS  read-only
    STATUS      current
    DESCRIPTION
        "
        Fld OID Name:   avCmListMemTrunkRangeNight
        Fld OID:        enterprises.6889.2.73.8.1.25.4.1.8
        Fld Form/Rpt:   TRUNK GROUP MEMBERS
        Fld Format:     Single
        Fld(s) Name:    Night
        Fld Descr:      An object containing the night service extension.
        "
    ::= { avCmListMemTrunkRangeEntry 8 }

avCmListMemTrunkRangeMode       OBJECT-TYPE
    SYNTAX      SnmpAdminString (SIZE (0..10))
    MAX-ACCESS  read-only
    STATUS      current
    DESCRIPTION
        "
        Fld OID Name:   avCmListMemTrunkRangeMode
        Fld OID:        enterprises.6889.2.73.8.1.25.4.1.9
        Fld Form/Rpt:   TRUNK GROUP MEMBERS
        Fld Format:     Single
        Fld(s) Name:    Mode
        Fld Descr:      An object containing mode associated with the member.
        "
    ::= { avCmListMemTrunkRangeEntry 9 }


avCmListMemTrunkRangeType	OBJECT-TYPE
    SYNTAX	SnmpAdminString (SIZE (0..8))
    MAX-ACCESS	read-only
    STATUS	current
    DESCRIPTION
	"
	Fld OID Name:	avCmListMemTrunkRangeType
	Fld OID:	enterprises.6889.2.73.8.1.25.4.1.10
	Fld Form/Rpt:	TRUNK GROUP MEMBERS
	Fld Format:	Single
	Fld(s) Name:	Type
	Fld Descr:	An object containing the trunk group  member type.
			assigned.
	"
    ::= { avCmListMemTrunkRangeEntry 10 }

avCmListMemTrunkRangeAnsDelay	OBJECT-TYPE
    SYNTAX      Integer32 (0..5100)
    MAX-ACCESS	read-only
    STATUS	current
    DESCRIPTION
	"
	Fld OID Name:	avCmListMemTrunkRangeAnsDelay
	Fld OID:	enterprises.6889.2.73.8.1.25.4.1.11
	Fld Form/Rpt:	TRUNK GROUP MEMBERS
	Fld Format:	Single
	Fld(s) Name:	Ans. Delay
	Fld Descr:	An object containing the trunk group Answer Delay.
			assigned.
	"
    ::= { avCmListMemTrunkRangeEntry 11 }

avCmListMemTrunkRangeSigGrp	OBJECT-TYPE
    SYNTAX	Integer32 (0..999)
    MAX-ACCESS	read-only
    STATUS	current
    DESCRIPTION
	"
	Fld OID Name:	avCmListMemTrunkRangeSigGrp
	Fld OID:	enterprises.6889.2.73.8.1.25.4.1.12
	Fld Form/Rpt:	TRUNK GROUP MEMBERS
	Fld Format:	Single
	Fld(s) Name:	Signaling Group
	Fld Descr:	An object containing the signaling group of the sip
			trunk group.
	"
    ::= { avCmListMemTrunkRangeEntry 12 }


--   *********** avCmStatusTrunk Group **************

-- MIB Group Name:
--		avCmStatusTrunk
-- OID:
--		enterprises.6889.2.73.8.1.26
-- Description:
--		The avCmStatusTrunk MIB group displays the output of the
--		status trunk xxxx command.
--
-- Releases Supported:
--		CM6.3.100 and greater
-- Polling Type:
--		Performance/Utilization
-- Polling Interval:
--		The more Trunk Groups and Trunk Group Members, the less 
--		frequently this MIB Group should be queried.
-- Default Caching Interval
-- 		300 seconds
-- Timeout Interval:
--		Initial Timeout should be set to 15 seconds.
-- Retry Interval:
--		Initial Retry should be set to 3.
-- Limitations:
--              Red/High - The data collected by this MIB Group will
--              increase as the number of trunks on the system increase.
--              Consequently the data collected by this MIB Group could be
--              very large and therefore may take a very long time to collect
--              and could impact system performance.
-- Command Type:
--		1. SAT
-- Command:
--		1. status trunk xxxx
-- Form/Report Name:
--		1. TRUNK GROUP STATUS
-- Reference Document:
--		1. A detailed description of the command and form can be
--		   found in REF_DOC_1 in the DOCUMENT REFERENCE SECTION.
-- Command Permission/User-profile:
--		1. No special permissions needed. Default customer super-user
--		   profile can access this command.

avCmStatusTrunk	OBJECT IDENTIFIER ::= { avCmObjects 26 }

avCmStatusTrunkGrp	OBJECT-TYPE
    SYNTAX	Integer32 (0..2000)
    MAX-ACCESS	read-write
    STATUS	current
    DESCRIPTION
	"
	Fld OID Name:	avCmStatusTrunkGrp
	Fld OID:	enterprises.6889.2.73.8.1.26.1
	Fld Form/Rpt:	NA
	Fld Format:	NA
	Fld(s) Name:	NA
	Fld Descr:	An object containing the trunk group
	"
    ::= { avCmStatusTrunk 1 }

avCmStatusTrunkMember	OBJECT-TYPE
    SYNTAX	Integer32 (0..255)
    MAX-ACCESS	read-write
    STATUS	current
    DESCRIPTION
	"
	Fld OID Name:	avCmStatusTrunkGrp
	Fld OID:	enterprises.6889.2.73.8.1.26.2
	Fld Form/Rpt:	NA
	Fld Format:	NA
	Fld(s) Name:	NA
	Fld Descr:	An object containing the trunk group
	"
    ::= { avCmStatusTrunk 2 }

avCmStatusTrunkTable	OBJECT-TYPE
    SYNTAX	SEQUENCE OF AvCmStatusTrunkEntry
    MAX-ACCESS	not-accessible
    STATUS	current
    DESCRIPTION
	"
	Fld OID Name:	avCmStatusTrunkTable
	Fld OID:	enterprises.6889.2.73.8.1.26.3
	Fld Form/Rpt:	NA
	Fld Format:	NA
	Fld(s) Name:	NA
	Fld Descr:	An object containing the Trunk Member entry.
	"
    ::= { avCmStatusTrunk 3 }

avCmStatusTrunkEntry	OBJECT-TYPE
    SYNTAX	AvCmStatusTrunkEntry
    MAX-ACCESS	not-accessible
    STATUS	current
    DESCRIPTION
	"
	Fld OID Name:	avCmStatusTrunkEntry
	Fld OID:	enterprises.6889.2.73.8.1.26.4.1
	Fld Form/Rpt:	NA
	Fld Format:	NA
	Fld(s) Name:	NA
	Fld Descr:	A avCmStatusTrunk entry containing objects of the
			avCmStatusTrunk information sent by the switch.
	"
    INDEX    { avCmStatusTrunkIdx, avCmStatusTrunkMemberIdx }
    ::= { avCmStatusTrunkTable 1 }

AvCmStatusTrunkEntry ::= SEQUENCE {
		avCmStatusTrunkIdx
		    Integer32,
                avCmStatusTrunkMemberIdx
                    Integer32,
                avCmStatusTrunkMemMember
                    Integer32,
                avCmStatusTrunkPort
                    SnmpAdminString,
                avCmStatusTrunkServiceState
                    SnmpAdminString
		}

avCmStatusTrunkIdx	OBJECT-TYPE
    SYNTAX	Integer32 (1..2000)
    MAX-ACCESS	not-accessible
    STATUS	current
    DESCRIPTION
	"
	Fld OID Name:	avCmStatusTrunkIdx
	Fld OID:	enterprises.6889.2.73.8.1.26.3.1.1
	Fld Form/Rpt:	NA
	Fld Format:	NA
	Fld(s) Name:	NA
	Fld Descr:	An index into the Trunk Group.
	"
    ::= { avCmStatusTrunkEntry 1 }

avCmStatusTrunkMemberIdx        OBJECT-TYPE
    SYNTAX      Integer32 (0..255)
    MAX-ACCESS	not-accessible
    STATUS      current
    DESCRIPTION
        "
        Fld OID Name:   avCmStatusTrunkMemberIdx
        Fld OID:        enterprises.6889.2.73.8.1.26.3.1.2
        Fld Form/Rpt:   NA
        Fld Format:     NA
        Fld(s) Name:    NA
        Fld Descr:      An index that contains the Member No. for the
                        Trunk Group.
        "
    ::= { avCmStatusTrunkEntry 2 }

avCmStatusTrunkMemMember        OBJECT-TYPE
    SYNTAX      Integer32 (0..255)
    MAX-ACCESS  read-only
    STATUS      current
    DESCRIPTION
        "
        Fld OID Name:   avCmStatusTrunkMemMember
        Fld OID:        enterprises.6889.2.73.8.1.26.3.1.3
        Fld Form/Rpt:   TRUNK GROUP STATUS
        Fld Format:     Single Field
        Fld(s) Name:    Member
        Fld Descr:      An object that contains the Member No. for the
                        Trunk Group.
        "
    ::= { avCmStatusTrunkEntry 3 }

avCmStatusTrunkPort	OBJECT-TYPE
    SYNTAX	SnmpAdminString (SIZE (0..12))
    MAX-ACCESS	read-only
    STATUS	current
    DESCRIPTION
	"
	Fld OID Name:	avCmStatusTrunkPort
	Fld OID:	enterprises.6889.2.73.8.1.26.3.1.4
	Fld Form/Rpt:	TRUNK GROUP STATUS 
	Fld Format:	Single
	Fld(s) Name:	Port
	Fld Descr:	An object containing the trunk member Port.
	"
    ::= { avCmStatusTrunkEntry 4 }

avCmStatusTrunkServiceState	OBJECT-TYPE
    SYNTAX	SnmpAdminString (SIZE (0..19))
    MAX-ACCESS	read-only
    STATUS	current
    DESCRIPTION
	"
	Fld OID Name:	avCmStatusTrunkServiceState
	Fld OID:	enterprises.6889.2.73.8.1.26.3.1.5
	Fld Form/Rpt:	TRUNK GROUP STATUS
	Fld Format:	Single
	Fld(s) Name:	Service State
	Fld Descr:	An object containing the member service state.
	"
    ::= { avCmStatusTrunkEntry 5 }

--   *********** avCmStatusTrunkRange Group **************

-- MIB Group Name:
--		avCmStatusTrunkRange
-- OID:
--		enterprises.6889.2.73.8.1.27
-- Description:
--		The avCmStatusTrunkRange MIB group displays the output of the
--		status trunk xxxx command.
--
-- Releases Supported:
--		CM6.3.100 and greater
-- Polling Type:
--		Performance/Utilization
-- Polling Interval:
--		The more Trunk Groups and Trunk Group Members, the less 
--		frequently this MIB Group should be queried.
-- Timeout Interval:
--		Initial Timeout should be set to 15 seconds.
-- Retry Interval:
--		Initial Retry should be set to 3.
-- Limitations:
--              Red/High - The data collected by this MIB Group will
--              increase as the number of trunks on the system increase.
--              Consequently the data collected by this MIB Group could be
--              very large and therefore may take a very long time to collect
--              and could impact system performance.
-- Command Type:
--		1. SAT
-- Command:
--		1. status trunk xxxx
-- Form/Report Name:
--		1. TRUNK GROUPS
-- Reference Document:
--		1. A detailed description of the command and form can be
--		   found in REF_DOC_1 in the DOCUMENT REFERENCE SECTION.
-- Command Permission/User-profile:
--		1. No special permissions needed. Default customer super-user
--		   profile can access this command.

avCmStatusTrunkRange	OBJECT IDENTIFIER ::= { avCmObjects 27 }

avCmStatusTrunkRangeGrp	OBJECT-TYPE
    SYNTAX	Integer32 (0..2000)
    MAX-ACCESS	read-write
    STATUS	current
    DESCRIPTION
	"
	Fld OID Name:	avCmStatusTrunkRangeGrp
	Fld OID:	enterprises.6889.2.73.8.1.27.1
	Fld Form/Rpt:	NA
	Fld Format:	NA
	Fld(s) Name:	NA
	Fld Descr:	An object containing the trunk group
	"
    ::= { avCmStatusTrunkRange 1 }

avCmStatusTrunkRangeCount	OBJECT-TYPE
    SYNTAX	Integer32 (1..255)
    MAX-ACCESS	read-write
    STATUS	current
    DESCRIPTION
	"
	Fld OID Name:	avCmStatusTrunkRangeCount
	Fld OID:	enterprises.6889.2.73.8.1.27.2
	Fld Form/Rpt:	NA
	Fld Format:	NA
	Fld(s) Name:	NA
	Fld Descr:	An object containing the number of trunks to perform
			status trunk on.
	"
    DEFVAL	{ 10 }
    ::= { avCmStatusTrunkRange 2 }

avCmStatusTrunkRangeTable	OBJECT-TYPE
    SYNTAX	SEQUENCE OF AvCmStatusTrunkRangeEntry
    MAX-ACCESS	not-accessible
    STATUS	current
    DESCRIPTION
	"
	Fld OID Name:	avCmStatusTrunkRangeTable
	Fld OID:	enterprises.6889.2.73.8.1.27.3
	Fld Form/Rpt:	NA
	Fld Format:	NA
	Fld(s) Name:	NA
	Fld Descr:	An object containing the Trunk Member entry.
	"
    ::= { avCmStatusTrunkRange 3 }

avCmStatusTrunkRangeEntry	OBJECT-TYPE
    SYNTAX	AvCmStatusTrunkRangeEntry
    MAX-ACCESS	not-accessible
    STATUS	current
    DESCRIPTION
	"
	Fld OID Name:	avCmStatusTrunkRangeEntry
	Fld OID:	enterprises.6889.2.73.8.1.27.4.1
	Fld Form/Rpt:	NA
	Fld Format:	NA
	Fld(s) Name:	NA
	Fld Descr:	A avCmStatusTrunkRange entry containing objects of the
			avCmStatusTrunkRange information sent by the switch.
	"
    INDEX    { avCmStatusTrunkRangeIdx, avCmStatusTrunkRangeMemberIdx }
    ::= { avCmStatusTrunkRangeTable 1 }

AvCmStatusTrunkRangeEntry ::= SEQUENCE {
		avCmStatusTrunkRangeIdx
		    Integer32,
                avCmStatusTrunkRangeMemberIdx
                    Integer32,
                avCmStatusTrunkRangeMemMember
                    Integer32,
                avCmStatusTrunkRangePort
                    SnmpAdminString,
                avCmStatusTrunkRangeServiceState
                    SnmpAdminString,
		avCmStatusTrunkRangeMtceBusy
                    SnmpAdminString,
		avCmStatusTrunkRangeConnPorts1
                    SnmpAdminString,
		avCmStatusTrunkRangeConnPorts2
                    SnmpAdminString,
		avCmStatusTrunkRangeConnPorts3
                    SnmpAdminString,
		avCmStatusTrunkRangeConnPorts4
                    SnmpAdminString,
		avCmStatusTrunkRangeConnPorts5
                    SnmpAdminString,
		avCmStatusTrunkRangeConnPorts6
                    SnmpAdminString,
		avCmStatusTrunkRangeConnPorts7
                    SnmpAdminString,
		avCmStatusTrunkRangeConnPorts8
                    SnmpAdminString,
		avCmStatusTrunkRangeConnPorts9
                    SnmpAdminString
		}

avCmStatusTrunkRangeIdx	OBJECT-TYPE
    SYNTAX	Integer32 (1..2000)
    MAX-ACCESS	not-accessible
    STATUS	current
    DESCRIPTION
	"
	Fld OID Name:	avCmStatusTrunkRangeIdx
	Fld OID:	enterprises.6889.2.73.8.1.27.3.1.1
	Fld Form/Rpt:	NA
	Fld Format:	NA
	Fld(s) Name:	NA
	Fld Descr:	An index into the Trunk Group.
	"
    ::= { avCmStatusTrunkRangeEntry 1 }

avCmStatusTrunkRangeMemberIdx        OBJECT-TYPE
    SYNTAX      Integer32 (0..255)
    MAX-ACCESS	not-accessible
    STATUS      current
    DESCRIPTION
        "
        Fld OID Name:   avCmStatusTrunkRangeMemberIdx
        Fld OID:        enterprises.6889.2.73.8.1.27.3.1.2
        Fld Form/Rpt:   NA
        Fld Format:     NA
        Fld(s) Name:    NA
        Fld Descr:      An index that contains the Member No. for the
                        Trunk Group.
        "
    ::= { avCmStatusTrunkRangeEntry 2 }

avCmStatusTrunkRangeMemMember        OBJECT-TYPE
    SYNTAX      Integer32 (0..255)
    MAX-ACCESS  read-only
    STATUS      current
    DESCRIPTION
        "
        Fld OID Name:   avCmStatusTrunkRangeMemMember
        Fld OID:        enterprises.6889.2.73.8.1.27.3.1.3
        Fld Form/Rpt:   TRUNK GROUP STATUS
        Fld Format:     Single Field
        Fld(s) Name:    Member
        Fld Descr:      An object that contains the Member No. for the
                        Trunk Group.
        "
    ::= { avCmStatusTrunkRangeEntry 3 }

avCmStatusTrunkRangePort	OBJECT-TYPE
    SYNTAX	SnmpAdminString (SIZE (0..12))
    MAX-ACCESS	read-only
    STATUS	current
    DESCRIPTION
	"
	Fld OID Name:	avCmStatusTrunkRangePort
	Fld OID:	enterprises.6889.2.73.8.1.27.3.1.4
	Fld Form/Rpt:	TRUNK GROUP STATUS
	Fld Format:	Single
	Fld(s) Name:	Port
	Fld Descr:	An object containing the trunk member Port.
	"
    ::= { avCmStatusTrunkRangeEntry 4 }

avCmStatusTrunkRangeServiceState	OBJECT-TYPE
    SYNTAX	SnmpAdminString (SIZE (0..19))
    MAX-ACCESS	read-only
    STATUS	current
    DESCRIPTION
	"
	Fld OID Name:	avCmStatusTrunkRangeServiceState
	Fld OID:	enterprises.6889.2.73.8.1.27.3.1.5
	Fld Form/Rpt:	TRUNK GROUP STATUS
	Fld Format:	Single
	Fld(s) Name:	Service State
	Fld Descr:	An object containing the member service state.
	"
    ::= { avCmStatusTrunkRangeEntry 5 }

avCmStatusTrunkRangeMtceBusy        OBJECT-TYPE
    SYNTAX      SnmpAdminString (SIZE (0..5))
    MAX-ACCESS  read-only
    STATUS      current
    DESCRIPTION
        "
        Fld OID Name:   avCmStatusTrunkRangeMtceBusy
        Fld OID:        enterprises.6889.2.73.8.1.27.3.1.6
        Fld Form/Rpt:   TRUNK GROUP STATUS
        Fld Format:     Single
        Fld(s) Name:    Maintenance Busy
        Fld Descr:      An object containing whether the member is 
			maintenance busy.
        "
    ::= { avCmStatusTrunkRangeEntry 6 }

avCmStatusTrunkRangeConnPorts1        OBJECT-TYPE
    SYNTAX      SnmpAdminString (SIZE (0..12))
    MAX-ACCESS  read-only
    STATUS      current
    DESCRIPTION
        "
        Fld OID Name:   avCmStatusTrunkRangeConnPorts1
        Fld OID:        enterprises.6889.2.73.8.1.27.3.1.7
        Fld Form/Rpt:   TRUNK GROUP STATUS
        Fld Format:     Single
        Fld(s) Name:    Connected Ports
        Fld Descr:      An object containing ports connected to the member.
        "
    ::= { avCmStatusTrunkRangeEntry 7 }

avCmStatusTrunkRangeConnPorts2        OBJECT-TYPE
    SYNTAX      SnmpAdminString (SIZE (0..12))
    MAX-ACCESS  read-only
    STATUS      current
    DESCRIPTION
        "
        Fld OID Name:   avCmStatusTrunkRangeConnPorts2
        Fld OID:        enterprises.6889.2.73.8.1.27.3.1.8
        Fld Form/Rpt:   TRUNK GROUP STATUS
        Fld Format:     Single
        Fld(s) Name:    Connected Ports
        Fld Descr:      An object containing ports connected to the member.
        "
    ::= { avCmStatusTrunkRangeEntry 8 }

avCmStatusTrunkRangeConnPorts3        OBJECT-TYPE
    SYNTAX      SnmpAdminString (SIZE (0..12))
    MAX-ACCESS  read-only
    STATUS      current
    DESCRIPTION
        "
        Fld OID Name:   avCmStatusTrunkRangeConnPorts3
        Fld OID:        enterprises.6889.2.73.8.1.27.3.1.9
        Fld Form/Rpt:   TRUNK GROUP STATUS
        Fld Format:     Single
        Fld(s) Name:    Connected Ports
        Fld Descr:      An object containing ports connected to the member.
        "
    ::= { avCmStatusTrunkRangeEntry 9 }

avCmStatusTrunkRangeConnPorts4        OBJECT-TYPE
    SYNTAX      SnmpAdminString (SIZE (0..12))
    MAX-ACCESS  read-only
    STATUS      current
    DESCRIPTION
        "
        Fld OID Name:   avCmStatusTrunkRangeConnPorts4
        Fld OID:        enterprises.6889.2.73.8.1.27.3.1.10
        Fld Form/Rpt:   TRUNK GROUP STATUS
        Fld Format:     Single
        Fld(s) Name:    Connected Ports
        Fld Descr:      An object containing ports connected to the member.
        "
    ::= { avCmStatusTrunkRangeEntry 10 }


avCmStatusTrunkRangeConnPorts5        OBJECT-TYPE
    SYNTAX      SnmpAdminString (SIZE (0..12))
    MAX-ACCESS  read-only
    STATUS      current
    DESCRIPTION
        "
        Fld OID Name:   avCmStatusTrunkRangeConnPorts5
        Fld OID:        enterprises.6889.2.73.8.1.27.3.1.11
        Fld Form/Rpt:   TRUNK GROUP STATUS
        Fld Format:     Single
        Fld(s) Name:    Connected Ports
        Fld Descr:      An object containing ports connected to the member.
        "
    ::= { avCmStatusTrunkRangeEntry 11 }


avCmStatusTrunkRangeConnPorts6        OBJECT-TYPE
    SYNTAX      SnmpAdminString (SIZE (0..12))
    MAX-ACCESS  read-only
    STATUS      current
    DESCRIPTION
        "
        Fld OID Name:   avCmStatusTrunkRangeConnPorts6
        Fld OID:        enterprises.6889.2.73.8.1.27.3.1.12
        Fld Form/Rpt:   TRUNK GROUP STATUS
        Fld Format:     Single
        Fld(s) Name:    Connected Ports
        Fld Descr:      An object containing ports connected to the member.
        "
    ::= { avCmStatusTrunkRangeEntry 12 }


avCmStatusTrunkRangeConnPorts7        OBJECT-TYPE
    SYNTAX      SnmpAdminString (SIZE (0..12))
    MAX-ACCESS  read-only
    STATUS      current
    DESCRIPTION
        "
        Fld OID Name:   avCmStatusTrunkRangeConnPorts7
        Fld OID:        enterprises.6889.2.73.8.1.27.3.1.13
        Fld Form/Rpt:   TRUNK GROUP STATUS
        Fld Format:     Single
        Fld(s) Name:    Connected Ports
        Fld Descr:      An object containing ports connected to the member.
        "
    ::= { avCmStatusTrunkRangeEntry 13 }


avCmStatusTrunkRangeConnPorts8        OBJECT-TYPE
    SYNTAX      SnmpAdminString (SIZE (0..12))
    MAX-ACCESS  read-only
    STATUS      current
    DESCRIPTION
        "
        Fld OID Name:   avCmStatusTrunkRangeConnPorts8
        Fld OID:        enterprises.6889.2.73.8.1.27.3.1.14
        Fld Form/Rpt:   TRUNK GROUP STATUS
        Fld Format:     Single
        Fld(s) Name:    Connected Ports
        Fld Descr:      An object containing ports connected to the member.
        "
    ::= { avCmStatusTrunkRangeEntry 14 }


avCmStatusTrunkRangeConnPorts9        OBJECT-TYPE
    SYNTAX      SnmpAdminString (SIZE (0..12))
    MAX-ACCESS  read-only
    STATUS      current
    DESCRIPTION
        "
        Fld OID Name:   avCmStatusTrunkRangeConnPorts9
        Fld OID:        enterprises.6889.2.73.8.1.27.3.1.15
        Fld Form/Rpt:   TRUNK GROUP STATUS
        Fld Format:     Single
        Fld(s) Name:    Connected Ports
        Fld Descr:      An object containing ports connected to the member.
        "
    ::= { avCmStatusTrunkRangeEntry 15 }

--   *********** avCmStatusTrunkMem Group **************

-- MIB Group Name:
--		avCmStatusTrunkMem
-- OID:
--		enterprises.6889.2.73.8.1.28
-- Description:
--		The avCmStatusTrunkMem MIB group displays the output of the
--		status trunk xxxx/yyy (x=group 1-2000, y=member 1-255) command.
--		This MIB group only polls 1 trunk group/member at a time.
--
-- Releases Supported:
--		CM6.3.100 and greater
-- Polling Type:
--		Performance/Utilization
-- Polling Interval:
--              No more than once every 5 minutes.
-- Default Caching Interval
-- 		300 seconds
-- Timeout Interval:
--		Initial Timeout should be set to 15 seconds.
-- Retry Interval:
--		Initial Retry should be set to 3.
-- Limitations:
--		Yellow/Medium - The data collected by this MIB Group
--		may have some impact on the system.
-- Command Type:
--		1. SAT
-- Command:
--		1. status trunk xxxx/yyy
-- Form/Report Name:
--		1. TRUNK GROUP STATUS
-- Reference Document:
--		1. A detailed description of the command and form can be
--		   found in REF_DOC_1 in the DOCUMENT REFERENCE SECTION.
-- Command Permission/User-profile:
--		1. No special permissions needed. Default customer super-user
--		   profile can access this command.

avCmStatusTrunkMem	OBJECT IDENTIFIER ::= { avCmObjects 28 }

avCmStatusTrunkMemGrp	OBJECT-TYPE
    SYNTAX	Integer32 (0..2000)
    MAX-ACCESS	read-write
    STATUS	current
    DESCRIPTION
	"
	Fld OID Name:	avCmStatusTrunkMemGrp
	Fld OID:	enterprises.6889.2.73.8.1.28.1
	Fld Form/Rpt:	NA
	Fld Format:	NA
	Fld(s) Name:	NA
	Fld Descr:	An object containing the trunk group
	"
    ::= { avCmStatusTrunkMem 1 }

avCmStatusTrunkMemMem	OBJECT-TYPE
    SYNTAX	Integer32 (1..255)
    MAX-ACCESS	read-write
    STATUS	current
    DESCRIPTION
	"
	Fld OID Name:	avCmStatusTrunkMemMem
	Fld OID:	enterprises.6889.2.73.8.1.28.2
	Fld Form/Rpt:	NA
	Fld Format:	NA
	Fld(s) Name:	NA
	Fld Descr:	An object containing the member to perform
			status trunk on.
	"
    DEFVAL	{ 1 }
    ::= { avCmStatusTrunkMem 2 }

avCmStatusTrunkMemTable	OBJECT-TYPE
    SYNTAX	SEQUENCE OF AvCmStatusTrunkMemEntry
    MAX-ACCESS	not-accessible
    STATUS	current
    DESCRIPTION
	"
	Fld OID Name:	avCmStatusTrunkMemTable
	Fld OID:	enterprises.6889.2.73.8.1.28.3
	Fld Form/Rpt:	NA
	Fld Format:	NA
	Fld(s) Name:	NA
	Fld Descr:	An object containing the Trunk Mem entry.
	"
    ::= { avCmStatusTrunkMem 3 }

avCmStatusTrunkMemEntry	OBJECT-TYPE
    SYNTAX	AvCmStatusTrunkMemEntry
    MAX-ACCESS	not-accessible
    STATUS	current
    DESCRIPTION
	"
	Fld OID Name:	avCmStatusTrunkMemEntry
	Fld OID:	enterprises.6889.2.73.8.1.28.4.1
	Fld Form/Rpt:	NA
	Fld Format:	NA
	Fld(s) Name:	NA
	Fld Descr:	A avCmStatusTrunkMem entry containing objects of the
			avCmStatusTrunkMem information sent by the switch.
	"
    INDEX    { avCmStatusTrunkMemIdx, avCmStatusTrunkMemMemberIdx }
    ::= { avCmStatusTrunkMemTable 1 }

AvCmStatusTrunkMemEntry ::= SEQUENCE {
		avCmStatusTrunkMemIdx
		    Integer32,
                avCmStatusTrunkMemMemberIdx
                    Integer32,
                avCmStatusTrunkMemPort
                    SnmpAdminString,
                avCmStatusTrunkMemServiceState
                    SnmpAdminString,
		avCmStatusTrunkMemMtceBusy
                    SnmpAdminString,
		avCmStatusTrunkMemSigGrpId
                    SnmpAdminString,
		avCmStatusTrunkMemConnPorts1
                    SnmpAdminString,
		avCmStatusTrunkMemConnPorts2
                    SnmpAdminString,
		avCmStatusTrunkMemConnPorts3
                    SnmpAdminString,
		avCmStatusTrunkMemConnPorts4
                    SnmpAdminString,
		avCmStatusTrunkMemConnPorts5
                    SnmpAdminString,
		avCmStatusTrunkMemConnPorts6
                    SnmpAdminString,
		avCmStatusTrunkMemConnPorts7
                    SnmpAdminString,
		avCmStatusTrunkMemConnPorts8
                    SnmpAdminString,
		avCmStatusTrunkMemConnPorts9
                    SnmpAdminString
		}

avCmStatusTrunkMemIdx	OBJECT-TYPE
    SYNTAX	Integer32 (1..2000)
    MAX-ACCESS	not-accessible
    STATUS	current
    DESCRIPTION
	"
	Fld OID Name:	avCmStatusTrunkMemIdx
	Fld OID:	enterprises.6889.2.73.8.1.28.3.1.1
	Fld Form/Rpt:	NA
	Fld Format:	NA
	Fld(s) Name:	NA
	Fld Descr:	An index into the Trunk Group.
	"
    ::= { avCmStatusTrunkMemEntry 1 }

avCmStatusTrunkMemMemberIdx        OBJECT-TYPE
    SYNTAX      Integer32 (0..255)
    MAX-ACCESS	not-accessible
    STATUS      current
    DESCRIPTION
        "
        Fld OID Name:   avCmStatusTrunkMemMemberIdx
        Fld OID:        enterprises.6889.2.73.8.1.28.3.1.2
        Fld Form/Rpt:   NA
        Fld Format:     NA
        Fld(s) Name:    NA
        Fld Descr:      An index that contains the Member No. for the
                        Trunk Group.
        "
    ::= { avCmStatusTrunkMemEntry 2 }

avCmStatusTrunkMemPort	OBJECT-TYPE
    SYNTAX	SnmpAdminString (SIZE (0..12))
    MAX-ACCESS	read-only
    STATUS	current
    DESCRIPTION
	"
	Fld OID Name:	avCmStatusTrunkMemPort
	Fld OID:	enterprises.6889.2.73.8.1.28.3.1.3
	Fld Form/Rpt:	TRUNK GROUP STATUS
	Fld Format:	Single
	Fld(s) Name:	Port
	Fld Descr:	An object containing the trunk member Port.
	"
    ::= { avCmStatusTrunkMemEntry 3 }

avCmStatusTrunkMemServiceState	OBJECT-TYPE
    SYNTAX	SnmpAdminString (SIZE (0..19))
    MAX-ACCESS	read-only
    STATUS	current
    DESCRIPTION
	"
	Fld OID Name:	avCmStatusTrunkMemServiceState
	Fld OID:	enterprises.6889.2.73.8.1.28.3.1.4
	Fld Form/Rpt:	TRUNK GROUP STATUS
	Fld Format:	Single
	Fld(s) Name:	Service State
	Fld Descr:	An object containing the member service state.
	"
    ::= { avCmStatusTrunkMemEntry 4 }

avCmStatusTrunkMemMtceBusy        OBJECT-TYPE
    SYNTAX      SnmpAdminString (SIZE (0..5))
    MAX-ACCESS  read-only
    STATUS      current
    DESCRIPTION
        "
        Fld OID Name:   avCmStatusTrunkMemMtceBusy
        Fld OID:        enterprises.6889.2.73.8.1.28.3.1.5
        Fld Form/Rpt:   TRUNK GROUP STATUS
        Fld Format:     Single
        Fld(s) Name:    Maintenance Busy
        Fld Descr:      An object containing whether the member is 
			maintenance busy.
        "
    ::= { avCmStatusTrunkMemEntry 5 }

avCmStatusTrunkMemSigGrpId        OBJECT-TYPE
    SYNTAX      SnmpAdminString (SIZE (0..12))
    MAX-ACCESS  read-only
    STATUS      current
    DESCRIPTION
        "
        Fld OID Name:   avCmStatusTrunkMemSigGrpId
        Fld OID:        enterprises.6889.2.73.8.1.28.3.1.6
        Fld Form/Rpt:   TRUNK GROUP STATUS
        Fld Format:     Single
        Fld(s) Name:    Signaling Group ID
        Fld Descr:      An object containing the member
                        signaling group ID.
        "
    ::= { avCmStatusTrunkMemEntry 6 }

avCmStatusTrunkMemConnPorts1        OBJECT-TYPE
    SYNTAX      SnmpAdminString (SIZE (0..12))
    MAX-ACCESS  read-only
    STATUS      current
    DESCRIPTION
        "
        Fld OID Name:   avCmStatusTrunkMemConnPorts1
        Fld OID:        enterprises.6889.2.73.8.1.28.3.1.7
        Fld Form/Rpt:   TRUNK GROUP STATUS
        Fld Format:     Single
        Fld(s) Name:    Connected Ports
        Fld Descr:      An object containing ports connected to the member.
        "
    ::= { avCmStatusTrunkMemEntry 7 }

avCmStatusTrunkMemConnPorts2        OBJECT-TYPE
    SYNTAX      SnmpAdminString (SIZE (0..12))
    MAX-ACCESS  read-only
    STATUS      current
    DESCRIPTION
        "
        Fld OID Name:   avCmStatusTrunkMemConnPorts2
        Fld OID:        enterprises.6889.2.73.8.1.28.3.1.8
        Fld Form/Rpt:   TRUNK GROUP STATUS
        Fld Format:     Single
        Fld(s) Name:    Connected Ports
        Fld Descr:      An object containing ports connected to the member.
        "
    ::= { avCmStatusTrunkMemEntry 8 }

avCmStatusTrunkMemConnPorts3        OBJECT-TYPE
    SYNTAX      SnmpAdminString (SIZE (0..12))
    MAX-ACCESS  read-only
    STATUS      current
    DESCRIPTION
        "
        Fld OID Name:   avCmStatusTrunkMemConnPorts3
        Fld OID:        enterprises.6889.2.73.8.1.28.3.1.9
        Fld Form/Rpt:   TRUNK GROUP STATUS
        Fld Format:     Single
        Fld(s) Name:    Connected Ports
        Fld Descr:      An object containing ports connected to the member.
        "
    ::= { avCmStatusTrunkMemEntry 9 }

avCmStatusTrunkMemConnPorts4        OBJECT-TYPE
    SYNTAX      SnmpAdminString (SIZE (0..12))
    MAX-ACCESS  read-only
    STATUS      current
    DESCRIPTION
        "
        Fld OID Name:   avCmStatusTrunkMemConnPorts4
        Fld OID:        enterprises.6889.2.73.8.1.28.3.1.10
        Fld Form/Rpt:   TRUNK GROUP STATUS
        Fld Format:     Single
        Fld(s) Name:    Connected Ports
        Fld Descr:      An object containing ports connected to the member.
        "
    ::= { avCmStatusTrunkMemEntry 10 }


avCmStatusTrunkMemConnPorts5        OBJECT-TYPE
    SYNTAX      SnmpAdminString (SIZE (0..12))
    MAX-ACCESS  read-only
    STATUS      current
    DESCRIPTION
        "
        Fld OID Name:   avCmStatusTrunkMemConnPorts4
        Fld OID:        enterprises.6889.2.73.8.1.28.3.1.11
        Fld Form/Rpt:   TRUNK GROUP STATUS
        Fld Format:     Single
        Fld(s) Name:    Connected Ports
        Fld Descr:      An object containing ports connected to the member.
        "
    ::= { avCmStatusTrunkMemEntry 11 }


avCmStatusTrunkMemConnPorts6        OBJECT-TYPE
    SYNTAX      SnmpAdminString (SIZE (0..12))
    MAX-ACCESS  read-only
    STATUS      current
    DESCRIPTION
        "
        Fld OID Name:   avCmStatusTrunkMemConnPorts6
        Fld OID:        enterprises.6889.2.73.8.1.28.3.1.12
        Fld Form/Rpt:   TRUNK GROUP STATUS
        Fld Format:     Single
        Fld(s) Name:    Connected Ports
        Fld Descr:      An object containing ports connected to the member.
        "
    ::= { avCmStatusTrunkMemEntry 12 }


avCmStatusTrunkMemConnPorts7        OBJECT-TYPE
    SYNTAX      SnmpAdminString (SIZE (0..12))
    MAX-ACCESS  read-only
    STATUS      current
    DESCRIPTION
        "
        Fld OID Name:   avCmStatusTrunkMemConnPorts7
        Fld OID:        enterprises.6889.2.73.8.1.28.3.1.13
        Fld Form/Rpt:   TRUNK GROUP STATUS
        Fld Format:     Single
        Fld(s) Name:    Connected Ports
        Fld Descr:      An object containing ports connected to the member.
        "
    ::= { avCmStatusTrunkMemEntry 13 }


avCmStatusTrunkMemConnPorts8        OBJECT-TYPE
    SYNTAX      SnmpAdminString (SIZE (0..12))
    MAX-ACCESS  read-only
    STATUS      current
    DESCRIPTION
        "
        Fld OID Name:   avCmStatusTrunkMemConnPorts8
        Fld OID:        enterprises.6889.2.73.8.1.28.3.1.14
        Fld Form/Rpt:   TRUNK GROUP STATUS
        Fld Format:     Single
        Fld(s) Name:    Connected Ports
        Fld Descr:      An object containing ports connected to the member.
        "
    ::= { avCmStatusTrunkMemEntry 14 }


avCmStatusTrunkMemConnPorts9        OBJECT-TYPE
    SYNTAX      SnmpAdminString (SIZE (0..12))
    MAX-ACCESS  read-only
    STATUS      current
    DESCRIPTION
        "
        Fld OID Name:   avCmStatusTrunkMemConnPorts9
        Fld OID:        enterprises.6889.2.73.8.1.28.3.1.15
        Fld Form/Rpt:   TRUNK GROUP STATUS
        Fld Format:     Single
        Fld(s) Name:    Connected Ports
        Fld Descr:      An object containing ports connected to the member.
        "
    ::= { avCmStatusTrunkMemEntry 15 }

-- ******************** avCmStatusHealth Group *************************

-- MIB GROUP DESCRIPTION

-- MIB Group Name:
--		avCmStatusHealth
-- OID:
--		enterprises.6889.2.73.8.1.29
-- Description:
--		The avCmStatusHealth MIB Group uses the "status health"
-- 		command to retrieve the system health information.
--		
-- Releases Supported:
--		CM6.3.100 and greater
-- Polling Type:
--		Configuration, Inventory, and Performance/Utilization
-- Polling Interval:
--		No more than once every 5 minutes.
-- Default Caching Interval
-- 		300 seconds
-- Timeout Interval:
--		Initial Timeout should be set to 15 seconds.
-- Retry Interval:
--		Initial Retry should be set to 3.
-- Limitations:
--		Yellow/Medium - The data collected by this MIB Group
--		may have some impact on the system.
-- Command Type:
--		1. SAT
-- Command:
--		1. status health
-- Form/Report Name:
--		1. Status Health 
-- Reference Document:
--		1. A detailed description of the command and form can be
--		   found in document referenced by REF_DOC_1 in the
--		   DOCUMENT REFERENCE SECTION.
-- Command Permission/User-profile:
--		1. No special permissions needed.

avCmStatusHealth	OBJECT IDENTIFIER ::= { avCmObjects 29 }

avCmStatusHealthAlmMaj     OBJECT-TYPE
    SYNTAX	Integer32 (0..9999)
    MAX-ACCESS	read-only
    STATUS	current
    DESCRIPTION
	"
	Fld OID Name:	avCmStatusHealthAlmMaj
	Fld OID:	enterprises.6889.2.73.8.1.29.1
	Fld Form/Rpt:	Status Health
	Fld Format:	Single Field
	Fld(s) Name:	Alarms Major
	Fld Descr:	An object that contains the number of major alarms.
	"
    ::= { avCmStatusHealth 1 }

avCmStatusHealthAlmMin	OBJECT-TYPE
    SYNTAX	Integer32 (0..9999)
    MAX-ACCESS	read-only
    STATUS	current
    DESCRIPTION
	"
	Fld OID Name:	avCmStatusHealthAlmMin
	Fld OID:	enterprises.6889.2.73.8.1.29.2
	Fld Form/Rpt:	Status Health
	Fld Format:	Single Field
	Fld(s) Name:	Alarms Minor
	Fld Descr:	An object that contains the number of Minor Alarms.
	"
    ::= { avCmStatusHealth 2 }

avCmStatusHealthAlmWrn 	OBJECT-TYPE
    SYNTAX	Integer32 (0..9999)
    MAX-ACCESS	read-only
    STATUS	current
    DESCRIPTION
	"
	Fld OID Name:	avCmStatusHealthAlmWrn
	Fld OID:	enterprises.6889.2.73.8.1.29.3
	Fld Form/Rpt:	Status Health
	Fld Format:	Single Field
	Fld(s) Name:	Alarms Warning
	Fld Descr:	An object that contains the number of Warning Alarms.
	"
    ::= { avCmStatusHealth 3 }


avCmStatusHealthBusyOutTrk	OBJECT-TYPE
    SYNTAX      Integer32 (0..9999)
    MAX-ACCESS	read-only
    STATUS	current
    DESCRIPTION
	"
	Fld OID Name:	avCmStatusHealthBusyOutTrk
	Fld OID:	enterprises.6889.2.73.8.1.29.4
	Fld Form/Rpt:	Status Health
	Fld Format:	Single Field
	Fld(s) Name:	BUSYOUT Trunks
	Fld Descr:	An object that contains the number of Busied Out Trunks.
	"
    ::= { avCmStatusHealth 4 }

avCmStatusHealthBusyOutStn	OBJECT-TYPE
    SYNTAX      Integer32 (0..9999)
    MAX-ACCESS	read-only
    STATUS	current
    DESCRIPTION
	"
	Fld OID Name:	avCmStatusHealthBusyOutStn
	Fld OID:	enterprises.6889.2.73.8.1.29.5
	Fld Form/Rpt:	Status Health
	Fld Format:	Single Field
	Fld(s) Name:	BUSYOUT Stations
	Fld Descr:	An object that contains the number of Busied Out 
			Stations.
	"
    ::= { avCmStatusHealth 5 }

avCmStatusHealthBusyOutOth	OBJECT-TYPE
    SYNTAX      Integer32 (0..9999)
    MAX-ACCESS	read-only
    STATUS	current
    DESCRIPTION
	"
	Fld OID Name:	avCmStatusHealthBusyOutOth
	Fld OID:	enterprises.6889.2.73.8.1.29.6
	Fld Form/Rpt:	Status Health
	Fld Format:	Single Field
	Fld(s) Name:	BUSYOUT Other
	Fld Descr:	An object that contains the number of Busied Out Other
			objects.
	"
    ::= { avCmStatusHealth 6 }


avCmStatusHealthOccupancySt	OBJECT-TYPE
    SYNTAX	SnmpAdminString (SIZE (0..6))
    MAX-ACCESS	read-only
    STATUS	current
    DESCRIPTION
	"
	Fld OID Name:	avCmStatusHealthOccupancySt
	Fld OID:	enterprises.6889.2.73.8.1.29.7
	Fld Form/Rpt:	Status Health
	Fld Format:	Single Field
	Fld(s) Name:	OCC St
	Fld Descr:	An object that contains the static occupancy percentage.
	"
    ::= { avCmStatusHealth 7 }

avCmStatusHealthOccupancySm	OBJECT-TYPE
    SYNTAX      SnmpAdminString (SIZE (0..6))
    MAX-ACCESS	read-only
    STATUS	current
    DESCRIPTION
	"
	Fld OID Name:	avCmStatusHealthOccupancySm
	Fld OID:	enterprises.6889.2.73.8.1.29.8
	Fld Form/Rpt:	Status Health
	Fld Format:	Single Field
	Fld(s) Name:	OCC Sm
	Fld Descr:	An object that contains the system management occupancy
			percentage
	"
    ::= { avCmStatusHealth 8 }

avCmStatusHealthOccupancyCp	OBJECT-TYPE
    SYNTAX	SnmpAdminString (SIZE (0..6))
    MAX-ACCESS	read-only
    STATUS	current
    DESCRIPTION
	"
	Fld OID Name:	avCmStatusHealthOccupancyCp
	Fld OID:	enterprises.6889.2.73.8.1.29.9
	Fld Form/Rpt:	Status Health
	Fld Format:	Single Field
	Fld(s) Name:	OCC Cp
	Fld Descr:	An object that contains the call processing occupancy
			percentage.
	"
    ::= { avCmStatusHealth 9 }

avCmStatusHealthOccupancyIdl	OBJECT-TYPE
    SYNTAX	SnmpAdminString (SIZE (0..6))
    MAX-ACCESS	read-only
    STATUS	current
    DESCRIPTION
	"
	Fld OID Name:	avCmStatusHealthOccupancyIdl
	Fld OID:	enterprises.6889.2.73.8.1.29.10
	Fld Form/Rpt:	Status Health
	Fld Format:	Single Field
	Fld(s) Name:	OCC Idl
	Fld Descr:	An object that contains the idle occupancy
			percentage.
	"
    ::= { avCmStatusHealth 10 }

avCmStatusHealthEntryTmRecOvrLd    OBJECT-TYPE
    SYNTAX      SnmpAdminString (SIZE (0..20))
    MAX-ACCESS  read-only
    STATUS      current
    DESCRIPTION
        "
        Fld OID Name:   avCmStatusHealthEntryTmRecOvrLd
        Fld OID:        enterprises.6889.2.73.8.1.29.11
        Fld Form/Rpt:   Status Health
        Fld Format:     Single Field
        Fld(s) Name:    Entry Time of Most Recent Traffic Overload Interval
        Fld Descr:      An object that contains the Entry Time of Most Recent 
			Traffic Overload Interval.
        "
    ::= { avCmStatusHealth 11 }

avCmStatusHealthExitTmRecOvrLd    OBJECT-TYPE
    SYNTAX      SnmpAdminString (SIZE (0..20))
    MAX-ACCESS  read-only
    STATUS      current
    DESCRIPTION
        "
        Fld OID Name:   avCmStatusHealthExitTmRecOvrLd
        Fld OID:        enterprises.6889.2.73.8.1.29.12
        Fld Form/Rpt:   Status Health
        Fld Format:     Single Field
        Fld(s) Name:    Entry Time of Most Recent Traffic Overload Interval
        Fld Descr:      An object that contains the Exit Time of Most Recent 
                        Traffic Overload Interval.
        "
    ::= { avCmStatusHealth 12 }


avCmStatusHealthLogins    OBJECT-TYPE
    SYNTAX      Integer32 (0..99)
    MAX-ACCESS  read-only
    STATUS      current
    DESCRIPTION
        "
        Fld OID Name:   avCmStatusHealthLogins
        Fld OID:        enterprises.6889.2.73.8.1.29.13
        Fld Form/Rpt:   Status Health
        Fld Format:     Single Field
        Fld(s) Name:    Logins
        Fld Descr:      An object that contains the number of active Logins.
        "
    ::= { avCmStatusHealth 13 }

--   ***********	  avCmStatusStation Group       **************

-- MIB Group Name:
--		avCmStatusStation
-- OID:
--		enterprises.6889.2.73.8.1.30
-- Description:
--		The avCmStatusStation MIB group displays the output of the
--		status station command.
-- Releases Supported:
--		CM6.3.100 and greater
-- Polling Type:
--		Performance/Utilization 
-- Polling Interval:
--		No more than once a day or when stations are added.
-- Default Caching Interval
-- 		300 seconds
-- Timeout Interval:
--		Initial Timeout should be set to 15 seconds.
-- Retry Interval:
--		Initial Retry should be set to 3.
-- Limitations:
--		Red/High - The data collected by this MIB Group will
--		increase as the number of stations on the system increase.
--		Consequently the data collected by this MIB Group could be
--		very large and therefore may take a very long time to collect
--		and could impact system performance.
-- Command Type:
--		1. SAT
-- Command:
--		1. status station
-- Form/Report Name:
--		1. STATIONS
-- Reference Document:
--		1. A detailed description of the command and form can be
--		   found in REF_DOC_1 in the DOCUMENT REFERENCE SECTION.
-- Command Permission/User-profile:
--		1. No special permissions needed. Default customer super-user
--		   profile can access this command.

avCmStatusStation		OBJECT IDENTIFIER ::= { avCmObjects 30 }

avCmStatusStationTable	OBJECT-TYPE
    SYNTAX	SEQUENCE OF AvCmStatusStationEntry
    MAX-ACCESS	not-accessible
    STATUS	current
    DESCRIPTION
	"
	Fld OID Name:	avCmStatusStationEntry
	Fld OID:	enterprises.6889.2.73.8.1.30.1
	Fld Form/Rpt:	NA
	Fld Format:	NA
	Fld(s) Name:	NA
	Fld Descr:	A list of the avCmServerAlarms entries
	"
    ::= { avCmStatusStation 1 }

avCmStatusStationEntry	OBJECT-TYPE
    SYNTAX	AvCmStatusStationEntry
    MAX-ACCESS	not-accessible
    STATUS	current
    DESCRIPTION
	"
	Fld OID Name:	avCmStatusStationEntry
	Fld OID:	enterprises.6889.2.73.8.1.30.1.1
	Fld Format:	NA
	Fld Form/Rpt:	NA
	Fld(s) Name:	NA
	Fld Descr:	A avCmStatusStation entry containing objects of the
			avCmStatusStation information sent by the switch.
	"
    INDEX    { avCmStatusStationIdx }
    ::= { avCmStatusStationTable 1 }

AvCmStatusStationEntry ::= SEQUENCE {
		avCmStatusStationIdx
		    SnmpAdminString,
		avCmStatusStationExtension
		    SnmpAdminString,
		avCmStatusStationConnType
		    SnmpAdminString,
		avCmStatusStationServiceState
		    SnmpAdminString,
		avCmStatusStationPort
		    SnmpAdminString
		}

avCmStatusStationIdx	OBJECT-TYPE
    SYNTAX	SnmpAdminString (SIZE (0..17))
    MAX-ACCESS	not-accessible
    STATUS	current
    DESCRIPTION
	"
	Fld OID Name:	avCmServerStationIdx
	Fld OID:	enterprises.6889.2.73.8.1.30.1.1.1
	Fld Form/Rpt:	NA
	Fld Format:	NA
	Fld(s) Name:	NA
	Fld Descr:	An object containing an index that uniquely identifies
			an administered station.
	"
    ::= { avCmStatusStationEntry 1 }

avCmStatusStationExtension	OBJECT-TYPE
    SYNTAX	SnmpAdminString (SIZE (0..17))
    MAX-ACCESS	read-only
    STATUS	current
    DESCRIPTION
	"
	Fld OID Name:	avCmServerExtension
	Fld OID:	enterprises.6889.2.73.8.1.30.1.1.2
	Fld Form/Rpt:	STATIONS
	Fld Format:	Single
	Fld(s) Name:	Ext
	Fld Descr:	An object containing the stations extension.
	"
    ::= { avCmStatusStationEntry 2 }

avCmStatusStationConnType	OBJECT-TYPE
    SYNTAX	SnmpAdminString (SIZE (0..15))
    MAX-ACCESS	read-only
    STATUS	current
    DESCRIPTION
	"
	Fld OID Name:	avCmStatusStationConnType
	Fld OID:	enterprises.6889.2.73.8.1.30.1.1.3
	Fld Form/Rpt:	STATIONS
	Fld Format:	Single
	Fld(s) Name:	Connected Type
	Fld Descr:	An object containing the connected station type.
	"
    ::= { avCmStatusStationEntry 3 }

avCmStatusStationServiceState	OBJECT-TYPE
    SYNTAX	SnmpAdminString (SIZE (0..22))
    MAX-ACCESS	read-only
    STATUS	current
    DESCRIPTION
	"
	Fld OID Name:	avCmStatusStationServiceState
	Fld OID:	enterprises.6889.2.73.8.1.30.1.1.4
	Fld Form/Rpt:	STATIONS
	Fld Format:	Single
	Fld(s) Name:	Service State
	Fld Descr:	An object containing the service state of the station.
	"
    ::= { avCmStatusStationEntry 4 }

avCmStatusStationPort	OBJECT-TYPE
    SYNTAX	SnmpAdminString (SIZE (0..11))
    MAX-ACCESS	read-only
    STATUS	current
    DESCRIPTION
	"
	Fld OID Name:	avCmStatusStationPort
	Fld OID:	enterprises.6889.2.73.8.1.30.1.1.5
	Fld Form/Rpt:	STATIONS
	Fld Format:	Single
	Fld(s) Name:	Port
	Fld Descr:	An object containing the stations port assignment.
	"
    ::= { avCmStatusStationEntry 5 }

--   ***********	  avCmStatusStationRange Group       **************

-- MIB Group Name:
--		avCmStatusStationRange
-- OID:
--		enterprises.6889.2.73.8.1.31
-- Description:
--		The avCmStatusStationRange MIB group displays the output of the
--		status station command.
-- Releases Supported:
--		CM6.3.100 and greater
-- Polling Type:
--		Performance/Utilization 
-- Polling Interval:
--		No more than once a day or when stations are added.
-- Default Caching Interval
-- 		300 seconds
-- Timeout Interval:
--		Initial Timeout should be set to 15 seconds.
-- Retry Interval:
--		Initial Retry should be set to 3.
-- Limitations:
--		Red/High - The data collected by this MIB Group will
--		increase as the number of stations on the system increase.
--		Consequently the data collected by this MIB Group could be
--		very large and therefore may take a very long time to collect
--		and could impact system performance.
-- Command Type:
--		1. SAT
-- Command:
--		1. status station
-- Form/Report Name:
--		1. STATIONS
-- Reference Document:
--		1. A detailed description of the command and form can be
--		   found in REF_DOC_1 in the DOCUMENT REFERENCE SECTION.
-- Command Permission/User-profile:
--		1. No special permissions needed. Default customer super-user
--		   profile can access this command.

avCmStatusStationRange		OBJECT IDENTIFIER ::= { avCmObjects 31 }

avCmStatusStationRangeStartExt    OBJECT-TYPE
    SYNTAX      SnmpAdminString (SIZE (0..17))
    MAX-ACCESS  read-write
    STATUS      current
    DESCRIPTION
        "
        Fld OID Name:   avCmSationRangeStartExt
        Fld OID:        enterprises.6889.2.73.8.1.31.1
        Fld Form/Rpt:   NA
        Fld Format:     NA
        Fld(s) Name:    NA
        Fld Descr:      An object containing the starting Extension location
        "
    ::= { avCmStatusStationRange 1 }


avCmStatusStationRangeCount       OBJECT-TYPE
    SYNTAX      Integer32 (1..100)
    MAX-ACCESS  read-write
    STATUS      current
    DESCRIPTION
        "
        Fld OID Name:   avCmStatusStationRangeCount
        Fld OID:        enterprises.6889.2.73.8.1.31.2
        Fld Form/Rpt:   NA
        Fld Format:     NA
        Fld(s) Name:    NA
        Fld Descr:      An object containing the number of stations to list.
        "
    DEFVAL      { 10 }
    ::= { avCmStatusStationRange 2 }


avCmStatusStationRangeTable	OBJECT-TYPE
    SYNTAX	SEQUENCE OF AvCmStatusStationRangeEntry
    MAX-ACCESS	not-accessible
    STATUS	current
    DESCRIPTION
	"
	Fld OID Name:	avCmStatusStationRangeTable
	Fld OID:	enterprises.6889.2.73.8.1.31.3
	Fld Form/Rpt:	NA
	Fld Format:	NA
	Fld(s) Name:	NA
	Fld Descr:	A list of the avCmStatusStationRange entries
	"
    ::= { avCmStatusStationRange 3 }

avCmStatusStationRangeEntry       OBJECT-TYPE
    SYNTAX      AvCmStatusStationRangeEntry
    MAX-ACCESS  not-accessible
    STATUS      current
    DESCRIPTION
        "
        Fld OID Name:   avCmStatusStationRangeEntry
        Fld OID:        enterprises.6889.2.73.8.1.31.3.1
        Fld Form/Rpt:   NA
        Fld Format:     NA
        Fld(s) Name:    NA
        Fld Descr:      A avCmStatusStationRange entry containing objects of the
                        avCmStatusStationRange information sent by the switch.
        "
    INDEX    { avCmStatusStationRangeIdx }
    ::= { avCmStatusStationRangeTable 1 }

AvCmStatusStationRangeEntry ::= SEQUENCE {
		avCmStatusStationRangeIdx
		    SnmpAdminString,
		avCmStatusStationRangeExtension
		    SnmpAdminString,
		avCmStatusStationRangeConnType
		    SnmpAdminString,
		avCmStatusStationRangeServiceState
		    SnmpAdminString,
		avCmStatusStationRangePort
		    SnmpAdminString,
		avCmStatusStationRangeConnPort1
		    SnmpAdminString,
		avCmStatusStationRangeConnPort2
		    SnmpAdminString,
		avCmStatusStationRangeConnPort3
		    SnmpAdminString,
		avCmStatusStationRangeConnPort4
		    SnmpAdminString,
		avCmStatusStationRangeConnPort5
		    SnmpAdminString,
		avCmStatusStationRangeConnPort6
		    SnmpAdminString,
		avCmStatusStationRangeConnPort7
		    SnmpAdminString,
		avCmStatusStationRangeConnPort8
		    SnmpAdminString,
		avCmStatusStationRangeConnPort9
		    SnmpAdminString,
		avCmStatusStationRangeConnPort10
		    SnmpAdminString,
		avCmStatusStationRangeSACactive
		    SnmpAdminString,
		avCmStatusStationRangeCFdestExt
		    SnmpAdminString,
		avCmStatusStationRangeRingCutOff
		    SnmpAdminString,
		avCmStatusStationRangeSerialNbr
		    SnmpAdminString,
		avCmStatusStationRangePartID
		    SnmpAdminString,
		avCmStatusStationRangeSwitchPort
		    SnmpAdminString,
		avCmStatusStationRangeSwitchIPAddr
		    SnmpAdminString,
		avCmStatusStationRangeSwitchIPPort
		    SnmpAdminString,
		avCmStatusStationRangeSetIPAddr
		    SnmpAdminString,
		avCmStatusStationRangeSetIPPort
		    SnmpAdminString
		}

avCmStatusStationRangeIdx	OBJECT-TYPE
    SYNTAX	SnmpAdminString (SIZE (0..17))
    MAX-ACCESS	not-accessible
    STATUS	current
    DESCRIPTION
	"
	Fld OID Name:	avCmServerStationRangeIdx
	Fld OID:	enterprises.6889.2.73.8.1.31.3.1.1
	Fld Form/Rpt:	NA
	Fld Format:	NA
	Fld(s) Name:	NA
	Fld Descr:	An object containing an index that uniquely identifies
			an administered station.
	"
    ::= { avCmStatusStationRangeEntry 1 }

avCmStatusStationRangeExtension	OBJECT-TYPE
    SYNTAX	SnmpAdminString (SIZE (0..17))
    MAX-ACCESS	read-only
    STATUS	current
    DESCRIPTION
	"
	Fld OID Name:	avCmServerRangeExtension
	Fld OID:	enterprises.6889.2.73.8.1.31.3.1.2
	Fld Form/Rpt:	STATIONS
	Fld Format:	Single
	Fld(s) Name:	Ext
	Fld Descr:	An object containing the stations extension.
	"
    ::= { avCmStatusStationRangeEntry 2 }

avCmStatusStationRangeConnType	OBJECT-TYPE
    SYNTAX	SnmpAdminString (SIZE (0..15))
    MAX-ACCESS	read-only
    STATUS	current
    DESCRIPTION
	"
	Fld OID Name:	avCmStatusStationRangeConnType
	Fld OID:	enterprises.6889.2.73.8.1.31.3.1.3
	Fld Form/Rpt:	STATIONS
	Fld Format:	Single
	Fld(s) Name:	Connected Type
	Fld Descr:	An object containing the connected station type.
	"
    ::= { avCmStatusStationRangeEntry 3 }

avCmStatusStationRangeServiceState	OBJECT-TYPE
    SYNTAX	SnmpAdminString (SIZE (0..22))
    MAX-ACCESS	read-only
    STATUS	current
    DESCRIPTION
	"
	Fld OID Name:	avCmStatusStationRangeServiceState
	Fld OID:	enterprises.6889.2.73.8.1.31.3.1.4
	Fld Form/Rpt:	STATIONS
	Fld Format:	Single
	Fld(s) Name:	Service State
	Fld Descr:	An object containing the service state of the station.
	"
    ::= { avCmStatusStationRangeEntry 4 }

avCmStatusStationRangePort	OBJECT-TYPE
    SYNTAX	SnmpAdminString (SIZE (0..11))
    MAX-ACCESS	read-only
    STATUS	current
    DESCRIPTION
	"
	Fld OID Name:	avCmStatusStationRangePort
	Fld OID:	enterprises.6889.2.73.8.1.31.3.1.5
	Fld Form/Rpt:	STATIONS
	Fld Format:	Single
	Fld(s) Name:	Port
	Fld Descr:	An object containing the stations port assignment.
	"
    ::= { avCmStatusStationRangeEntry 5 }


avCmStatusStationRangeConnPort1	OBJECT-TYPE
    SYNTAX	SnmpAdminString (SIZE (0..11))
    MAX-ACCESS	read-only
    STATUS	current
    DESCRIPTION
	"
	Fld OID Name:	avCmStatusStationRangeConnPort1
	Fld OID:	enterprises.6889.2.73.8.1.31.3.1.6
	Fld Form/Rpt:	STATIONS
	Fld Format:	Single
	Fld(s) Name:	Connected Port
	Fld Descr:	A DisplayString Object that contains the first port 
			connected to the station.
	"
    ::= { avCmStatusStationRangeEntry 6 }


avCmStatusStationRangeConnPort2	OBJECT-TYPE
    SYNTAX	SnmpAdminString (SIZE (0..11))
    MAX-ACCESS	read-only
    STATUS	current
    DESCRIPTION
	"
	Fld OID Name:	avCmStatusStationRangeConnPort2
	Fld OID:	enterprises.6889.2.73.8.1.31.3.1.7
	Fld Form/Rpt:	STATIONS
	Fld Format:	Single
	Fld(s) Name:	Connected Port
	Fld Descr:	A DisplayString Object that contains the second port 
			connected to the station.
	"
    ::= { avCmStatusStationRangeEntry 7 }


avCmStatusStationRangeConnPort3	OBJECT-TYPE
    SYNTAX	SnmpAdminString (SIZE (0..11))
    MAX-ACCESS	read-only
    STATUS	current
    DESCRIPTION
	"
	Fld OID Name:	avCmStatusStationRangeConnPort3
	Fld OID:	enterprises.6889.2.73.8.1.31.3.1.8
	Fld Form/Rpt:	STATIONS
	Fld Format:	Single
	Fld(s) Name:	Connected Port
	Fld Descr:	A DisplayString Object that contains the third port 
			connected to the station.
	"
    ::= { avCmStatusStationRangeEntry 8 }

avCmStatusStationRangeConnPort4	OBJECT-TYPE
    SYNTAX	SnmpAdminString (SIZE (0..11))
    MAX-ACCESS	read-only
    STATUS	current
    DESCRIPTION
	"
	Fld OID Name:	avCmStatusStationRangeConnPort4
	Fld OID:	enterprises.6889.2.73.8.1.31.3.1.9
	Fld Form/Rpt:	STATIONS
	Fld Format:	Single
	Fld(s) Name:	Connected Port
	Fld Descr:	A DisplayString Object that contains the fourth port 
			connected to the station.
	"
    ::= { avCmStatusStationRangeEntry 9 }

avCmStatusStationRangeConnPort5	OBJECT-TYPE
    SYNTAX	SnmpAdminString (SIZE (0..11))
    MAX-ACCESS	read-only
    STATUS	current
    DESCRIPTION
	"
	Fld OID Name:	avCmStatusStationRangeConnPort5
	Fld OID:	enterprises.6889.2.73.8.1.31.1.1.10
	Fld Form/Rpt:	STATIONS
	Fld Format:	Single
	Fld(s) Name:	Connected Port
	Fld Descr:	A DisplayString Object that contains the fifth port 
			connected to the station.
	"
    ::= { avCmStatusStationRangeEntry 10 }

avCmStatusStationRangeConnPort6	OBJECT-TYPE
    SYNTAX	SnmpAdminString (SIZE (0..11))
    MAX-ACCESS	read-only
    STATUS	current
    DESCRIPTION
	"
	Fld OID Name:	avCmStatusStationRangeConnPort6
	Fld OID:	enterprises.6889.2.73.8.1.31.1.1.11
	Fld Form/Rpt:	STATIONS
	Fld Format:	Single
	Fld(s) Name:	Connected Port
	Fld Descr:	A DisplayString Object that contains the sixth port 
			connected to the station.
	"
    ::= { avCmStatusStationRangeEntry 11 }

avCmStatusStationRangeConnPort7	OBJECT-TYPE
    SYNTAX	SnmpAdminString (SIZE (0..11))
    MAX-ACCESS	read-only
    STATUS	current
    DESCRIPTION
	"
	Fld OID Name:	avCmStatusStationRangeConnPort7
	Fld OID:	enterprises.6889.2.73.8.1.31.1.1.12
	Fld Form/Rpt:	STATIONS
	Fld Format:	Single
	Fld(s) Name:	Connected Port
	Fld Descr:	A DisplayString Object that contains the seventh port 
			connected to the station.
	"
    ::= { avCmStatusStationRangeEntry 12 }

avCmStatusStationRangeConnPort8	OBJECT-TYPE
    SYNTAX	SnmpAdminString (SIZE (0..11))
    MAX-ACCESS	read-only
    STATUS	current
    DESCRIPTION
	"
	Fld OID Name:	avCmStatusStationRangeConnPort8
	Fld OID:	enterprises.6889.2.73.8.1.31.1.1.13
	Fld Form/Rpt:	STATIONS
	Fld Format:	Single
	Fld(s) Name:	Connected Port
	Fld Descr:	A DisplayString Object that contains the seventh port 
			connected to the station.
	"
    ::= { avCmStatusStationRangeEntry 13 }

avCmStatusStationRangeConnPort9	OBJECT-TYPE
    SYNTAX	SnmpAdminString (SIZE (0..11))
    MAX-ACCESS	read-only
    STATUS	current
    DESCRIPTION
	"
	Fld OID Name:	avCmStatusStationRangeConnPort9
	Fld OID:	enterprises.6889.2.73.8.1.31.1.1.14
	Fld Form/Rpt:	STATIONS
	Fld Format:	Single
	Fld(s) Name:	Connected Port
	Fld Descr:	A DisplayString Object that contains the seventh port 
			connected to the station.
	"
    ::= { avCmStatusStationRangeEntry 14 }

avCmStatusStationRangeConnPort10	OBJECT-TYPE
    SYNTAX	SnmpAdminString (SIZE (0..11))
    MAX-ACCESS	read-only
    STATUS	current
    DESCRIPTION
	"
	Fld OID Name:	avCmStatusStationRangeConnPort10
	Fld OID:	enterprises.6889.2.73.8.1.31.1.1.15
	Fld Form/Rpt:	STATIONS
	Fld Format:	Single
	Fld(s) Name:	Connected Port
	Fld Descr:	A DisplayString Object that contains the seventh port 
			connected to the station.
	"
    ::= { avCmStatusStationRangeEntry 15 }

avCmStatusStationRangeSACactive	OBJECT-TYPE
    SYNTAX	SnmpAdminString (SIZE (0..4))
    MAX-ACCESS	read-only
    STATUS	current
    DESCRIPTION
	"
	Fld OID Name:	avCmStatusStationRangeSACactive 
	Fld OID:	enterprises.6889.2.73.8.1.31.1.1.16
	Fld Form/Rpt:	STATIONS
	Fld Format:	Single
	Fld(s) Name:	SAC Activated
	Fld Descr:	An object containing whether the stations Send All
			Calls (SAC) button is activated.
	"
    ::= { avCmStatusStationRangeEntry 16 }

avCmStatusStationRangeCFdestExt	OBJECT-TYPE
    SYNTAX	SnmpAdminString (SIZE (0..39))
    MAX-ACCESS	read-only
    STATUS	current
    DESCRIPTION
	"
	Fld OID Name:	avCmStatusStationRangeCFdestExt
	Fld OID:	enterprises.6889.2.73.8.1.31.1.1.17
	Fld Form/Rpt:	STATIONS
	Fld Format:	Single
	Fld(s) Name:	Call Forward Destination Extension
	Fld Descr:	An object containing whether the stations Send All
			Calls (SAC) button is activated.
	"
    ::= { avCmStatusStationRangeEntry 17 }

avCmStatusStationRangeRingCutOff	OBJECT-TYPE
    SYNTAX	SnmpAdminString (SIZE (0..39))
    MAX-ACCESS	read-only
    STATUS	current
    DESCRIPTION
	"
	Fld OID Name:	avCmStatusStationRangeRingCutOff
	Fld OID:	enterprises.6889.2.73.8.1.31.1.1.18
	Fld Form/Rpt:	STATIONS
	Fld Format:	Single
	Fld(s) Name:	Ringer Cutoff
	Fld Descr:	An object containing whether Ring Cut Off
			is activated for the station.
	"
    ::= { avCmStatusStationRangeEntry 18 }

avCmStatusStationRangeSerialNbr	OBJECT-TYPE
    SYNTAX	SnmpAdminString (SIZE (0..12))
    MAX-ACCESS	read-only
    STATUS	current
    DESCRIPTION
	"
	Fld OID Name:	avCmStatusStationRangeSerialNbr
	Fld OID:	enterprises.6889.2.73.8.1.31.1.1.19
	Fld Form/Rpt:	STATIONS
	Fld Format:	Single
	Fld(s) Name:	Serial Number
	Fld Descr:	An object containing the station serial number.
	"
    ::= { avCmStatusStationRangeEntry 19 }

avCmStatusStationRangePartID	OBJECT-TYPE
    SYNTAX	SnmpAdminString (SIZE (0..12))
    MAX-ACCESS	read-only
    STATUS	current
    DESCRIPTION
	"
	Fld OID Name:	avCmStatusStationRangePartID
	Fld OID:	enterprises.6889.2.73.8.1.31.1.1.20
	Fld Form/Rpt:	STATIONS
	Fld Format:	Single
	Fld(s) Name:	Part ID
	Fld Descr:	An object containing the station Part ID.
	"
    ::= { avCmStatusStationRangeEntry 20 }

avCmStatusStationRangeSwitchPort	OBJECT-TYPE
    SYNTAX	SnmpAdminString (SIZE (0..8))
    MAX-ACCESS	read-only
    STATUS	current
    DESCRIPTION
	"
	Fld OID Name:	avCmStatusStationRangeSwitchPort
	Fld OID:	enterprises.6889.2.73.8.1.31.1.1.21
	Fld Form/Rpt:	STATIONS
	Fld Format:	Single
	Fld(s) Name:	Switch Port
	Fld Descr:	An object containing the station switch port.
	"
    ::= { avCmStatusStationRangeEntry 21 }

avCmStatusStationRangeSwitchIPAddr	OBJECT-TYPE
    SYNTAX	SnmpAdminString (SIZE (0..40))
    MAX-ACCESS	read-only
    STATUS	current
    DESCRIPTION
	"
	Fld OID Name:	avCmStatusStationRangeSwitchIPAddr
	Fld OID:	enterprises.6889.2.73.8.1.31.1.1.22
	Fld Form/Rpt:	STATIONS
	Fld Format:	Single
	Fld(s) Name:	Switch End IP Address
	Fld Descr:	A DisplayString Object that contains the switch-end IP 
			address for the station.
	"
    ::= { avCmStatusStationRangeEntry 22 }

avCmStatusStationRangeSwitchIPPort	OBJECT-TYPE
    SYNTAX	SnmpAdminString (SIZE (0..6))
    MAX-ACCESS	read-only
    STATUS	current
    DESCRIPTION
	"
	Fld OID Name:	avCmStatusStationRangeSwitchIPPort
	Fld OID:	enterprises.6889.2.73.8.1.31.1.1.23
	Fld Form/Rpt:	STATIONS
	Fld Format:	Single
	Fld(s) Name:	Switch End IP Port
	Fld Descr:	A DisplayString Object that contains the switch-end IP 
			port number for the station.
	"
    ::= { avCmStatusStationRangeEntry 23 }

avCmStatusStationRangeSetIPAddr	OBJECT-TYPE
    SYNTAX	SnmpAdminString (SIZE (0..40))
    MAX-ACCESS	read-only
    STATUS	current
    DESCRIPTION
	"
	Fld OID Name:	avCmStatusStationRangeSetIPAddr
	Fld OID:	enterprises.6889.2.73.8.1.31.1.1.24
	Fld Form/Rpt:	STATIONS
	Fld Format:	Single
	Fld(s) Name:	Set End IP Address
	Fld Descr:	A DisplayString Object that contains the set-end IP 
			address for the station.
	"
    ::= { avCmStatusStationRangeEntry 24 }

avCmStatusStationRangeSetIPPort	OBJECT-TYPE
    SYNTAX	SnmpAdminString (SIZE (0..8))
    MAX-ACCESS	read-only
    STATUS	current
    DESCRIPTION
	"
	Fld OID Name:	avCmStatusStationRangeSetIPPort
	Fld OID:	enterprises.6889.2.73.8.1.31.1.1.25
	Fld Form/Rpt:	STATIONS
	Fld Format:	Single
	Fld(s) Name:	Set End IP Port
	Fld Descr:	A DisplayString Object that contains the set-end IP 
			port for the station.
	"
    ::= { avCmStatusStationRangeEntry 25 }


-- ******************** avCmMeasOccSum Group *************************


-- MIB GROUP DESCRIPTION

-- MIB Group Name:
--		avCmMeasOccSum Group
-- OID:
--		enterprises.6889.2.73.8.1.32
-- Description:
--		The avCmMeasOccSum MIB Group uses the "list measurements 
--		occupancy summary" command to retrieve the summary of
--		occupancy information.  
--		
-- Releases Supported:
--		CM6.3.100 and greater
-- Polling Type:
--		Performance/Utilization
-- Polling Interval:
--		No more than once an hour. However, the form is
--		completely updated once every 24 hours.
-- Default Caching Interval
-- 		300 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements occupancy summary
-- Form/Report Name:
--		1. OCCUPANCY SUMMARY MEASUREMENTS
-- Reference Document:
--		1. A detailed description of the command and form can be
--		   found in document referenced by REF_DOC_4 in the
--		   DOCUMENT REFERENCE SECTION.
-- Command Permission/User-profile:
--		1. No special permissions needed.

avCmMeasOccSum	OBJECT IDENTIFIER ::= { avCmObjects 32 }

avCmMeasOccSumTable	OBJECT-TYPE
    SYNTAX	SEQUENCE OF AvCmMeasOccSumEntry
    MAX-ACCESS	not-accessible
    STATUS	current
    DESCRIPTION
	"
	Fld OID Name:	avCmMeasOccSumEntry
	Fld OID:	enterprises.6889.2.73.8.1.32.1
	Fld Form/Rpt:	NA
	Fld Format:	NA
	Fld(s) Name:	NA
	Fld Descr:	A list of the avCmMeasOccSum entries
	"
    ::= { avCmMeasOccSum 1 }

avCmMeasOccSumEntry	OBJECT-TYPE
    SYNTAX	AvCmMeasOccSumEntry
    MAX-ACCESS	not-accessible
    STATUS	current
    DESCRIPTION
	"
	Fld OID Name:	avCmMeasOccSumEntry
	Fld OID:	enterprises.6889.2.73.8.1.32.1.1
	Fld Form/Rpt:	NA
	Fld Format:	NA
	Fld(s) Name:	NA
	Fld Descr:	A avCmMeasOccSum entry containing objects of the
			avCmMeasOccSum information sent by the switch.
	"
    INDEX    { avCmMeasOccSumIdx }
    ::= { avCmMeasOccSumTable 1 }

AvCmMeasOccSumEntry ::= SEQUENCE {
		avCmMeasOccSumIdx
		    Integer32,
		avCmMeasOccSumMeasHour
		    Integer32,
		avCmMeasOccSumRunDate
		    SnmpAdminString,
		avCmMeasOccSumPeakHour
		    Integer32,
		avCmMeasOccSumStatOcc
		    Integer32,
		avCmMeasOccSumCPOcc
		    Integer32,
		avCmMeasOccSumSMOcc
		    Integer32,
		avCmMeasOccSumIdleOcc
		    Integer32,
		avCmMeasOccSumTotCall
		    Integer32,
		avCmMeasOccSumTandCall
		    Integer32,
		avCmMeasOccSumTotConn
		    Integer32,
		avCmMeasOccSumIntcomAtt
		    Integer32,
		avCmMeasOccSumIncAtt
		    Integer32,
		avCmMeasOccSumOutAtt
		    Integer32,
		avCmMeasOccSumPnetAtt
		    Integer32
		}

avCmMeasOccSumIdx	OBJECT-TYPE
    SYNTAX	Integer32 (0..2300)
    MAX-ACCESS	not-accessible
    STATUS	current
    DESCRIPTION
	"
	Fld OID Name:	avCmMeasOccSumIdx
	Fld OID:	enterprises.6889.2.73.8.1.32.1.1.1
	Fld Format:	NA
	Fld(s) Name:	NA
	Fld Descr:	An object that uniquely identifies each Hour of data.
	"
    ::= { avCmMeasOccSumEntry 1 }

avCmMeasOccSumMeasHour	OBJECT-TYPE
    SYNTAX	Integer32 (0..2300)
    MAX-ACCESS	read-only
    STATUS	current
    DESCRIPTION
	"
	Fld OID Name:	avCmMeasOccSumMeasHour
	Fld OID:	enterprises.6889.2.73.8.1.32.1.1.2
	Fld Form/Rpt:	OCCUPANCY SUMMARY MEASUREMENTS
	Fld Format:	Single Field
	Fld(s) Name:	Meas Hour
	Fld Descr:	An object containing the Hour the measurement was taken.
	"
    ::= { avCmMeasOccSumEntry 2 }

avCmMeasOccSumRunDate	OBJECT-TYPE
    SYNTAX	SnmpAdminString (SIZE (0..27))
    MAX-ACCESS	read-only
    STATUS	current
    DESCRIPTION
	"
	Fld OID Name:	avCmMeasOccSumRunDate
	Fld OID:	enterprises.6889.2.73.8.1.32.1.1.3
	Fld Form/Rpt:	OCCUPANCY SUMMARY MEASUREMENTS
	Fld Format:	Single Field
	Fld(s) Name:	Date
	Fld Descr:	An object containing the Date the command was executed.
	"
    ::= { avCmMeasOccSumEntry 3 }

avCmMeasOccSumPeakHour 	OBJECT-TYPE
    SYNTAX	Integer32 (0..2300)
    MAX-ACCESS	read-only
    STATUS	current
    DESCRIPTION
	"
	Fld OID Name:	avCmMeasOccSumPeakHour 
	Fld OID:	enterprises.6889.2.73.8.1.32.1.1.4
	Fld Form/Rpt:	OCCUPANCY SUMMARY MEASUREMENTS
	Fld Format:	Single Field
	Fld(s) Name:	Peak Hour For Occupancy
	Fld Descr:	An object that contains the Peak Hour for Occupancy.
	"
    ::= { avCmMeasOccSumEntry 4 }

avCmMeasOccSumStatOcc	OBJECT-TYPE
    SYNTAX	Integer32 (0..100)
    MAX-ACCESS	read-only
    STATUS	current
    DESCRIPTION
	"
	Fld OID Name:	avCmMeasOccSumStatOcc
	Fld OID:	enterprises.6889.2.73.8.1.32.1.1.5
	Fld Form/Rpt:	OCCUPANCY SUMMARY MEASUREMENTS
	Fld Format:	Single Field
	Fld(s) Name:	Static Occ
	Fld Descr:	Object containing the processor utilized by static 
			processes.
	"
    ::= { avCmMeasOccSumEntry 5 }

avCmMeasOccSumCPOcc	OBJECT-TYPE
    SYNTAX	Integer32 (0..100)
    MAX-ACCESS	read-only
    STATUS	current
    DESCRIPTION
	"
	Fld OID Name:	avCmMeasOccSumCPOcc
	Fld OID:	enterprises.6889.2.73.8.1.32.1.1.6
	Fld Form/Rpt:	OCCUPANCY SUMMARY MEASUREMENTS
	Fld Format:	Single Field
	Fld(s) Name:	CP Occ
	Fld Descr:	An object containing the processor occupancy utilized 
			by Call  Processing processes.
	"
    ::= { avCmMeasOccSumEntry 6 }

avCmMeasOccSumSMOcc	OBJECT-TYPE
    SYNTAX	Integer32 (0..100)
    MAX-ACCESS	read-only
    STATUS	current
    DESCRIPTION
	"
	Fld OID Name:	avCmMeasOccSumSMOcc
	Fld OID:	enterprises.6889.2.73.8.1.32.1.1.7
	Fld Form/Rpt:	OCCUPANCY SUMMARY MEASUREMENTS
	Fld Format:	Single Field
	Fld(s) Name:	CP Occ
	Fld Descr:	An object containing the processor occupancy utilized 
			by System Management processes.
	"
    ::= { avCmMeasOccSumEntry 7 }

avCmMeasOccSumIdleOcc	OBJECT-TYPE
    SYNTAX	Integer32 (0..100)
    MAX-ACCESS	read-only
    STATUS	current
    DESCRIPTION
	"
	Fld OID Name:	avCmMeasOccSumIdleOcc
	Fld OID:	enterprises.6889.2.73.8.1.32.1.1.8
	Fld Form/Rpt:	OCCUPANCY SUMMARY MEASUREMENTS
	Fld Format:	Single Field
	Fld(s) Name:	Idle Occ
	Fld Descr:	An object containing the processor occupancy 
			that is unused.
	"
    ::= { avCmMeasOccSumEntry 8 }

avCmMeasOccSumTotCall	OBJECT-TYPE
    SYNTAX	Integer32 (0..100)
    MAX-ACCESS	read-only
    STATUS	current
    DESCRIPTION
	"
	Fld OID Name:	avCmMeasOccSumTotCall
	Fld OID:	enterprises.6889.2.73.8.1.32.1.1.9
	Fld Form/Rpt:	OCCUPANCY SUMMARY MEASUREMENTS
	Fld Format:	Single Field
	Fld(s) Name:	Total Calls
	Fld Descr:	An object containing total calls connected for the 
			measurement hour.
	"
    ::= { avCmMeasOccSumEntry 9 }

avCmMeasOccSumTandCall	OBJECT-TYPE
    SYNTAX	Integer32 (0..100)
    MAX-ACCESS	read-only
    STATUS	current
    DESCRIPTION
	"
	Fld OID Name:	avCmMeasOccSumTandCall
	Fld OID:	enterprises.6889.2.73.8.1.32.1.1.10
	Fld Form/Rpt:	OCCUPANCY SUMMARY MEASUREMENTS
	Fld Format:	Single Field
	Fld(s) Name:	Tandem Calls
	Fld Descr:	An object containing trunk-to-trunk calls connected for
			the measurement hour.
	"
    ::= { avCmMeasOccSumEntry 10 }

avCmMeasOccSumTotConn	OBJECT-TYPE
    SYNTAX	Integer32 (0..100)
    MAX-ACCESS	read-only
    STATUS	current
    DESCRIPTION
	"
	Fld OID Name:	avCmMeasOccSumTotConn
	Fld OID:	enterprises.6889.2.73.8.1.32.1.1.11
	Fld Form/Rpt:	OCCUPANCY SUMMARY MEASUREMENTS
	Fld Format:	Single Field
	Fld(s) Name:	Total Conn
	Fld Descr:	An object containing the total calls connected for
			the measurement hour.
	"
    ::= { avCmMeasOccSumEntry 11 }

avCmMeasOccSumIntcomAtt	OBJECT-TYPE
    SYNTAX	Integer32 (0..100)
    MAX-ACCESS	read-only
    STATUS	current
    DESCRIPTION
	"
	Fld OID Name:	avCmMeasOccSumIntcomAtt
	Fld OID:	enterprises.6889.2.73.8.1.32.1.1.12
	Fld Form/Rpt:	OCCUPANCY SUMMARY MEASUREMENTS
	Fld Format:	Single Field
	Fld(s) Name:	Intcom Atmpts
	Fld Descr:	An object containing the number of extension-to-
			extension calls on the same switch and partially 
			completed calls for the measurement hour.
	"
    ::= { avCmMeasOccSumEntry 12 }

avCmMeasOccSumIncAtt	OBJECT-TYPE
    SYNTAX	Integer32 (0..100)
    MAX-ACCESS	read-only
    STATUS	current
    DESCRIPTION
	"
	Fld OID Name:	avCmMeasOccSumIncAtt
	Fld OID:	enterprises.6889.2.73.8.1.32.1.1.13
	Fld Form/Rpt:	OCCUPANCY SUMMARY MEASUREMENTS
	Fld Format:	Single Field
	Fld(s) Name:	Inc Atmpts
	Fld Descr:	An object containing the number of incoming trunk 
			seizures from public network facilities.
	"
    ::= { avCmMeasOccSumEntry 13 }

avCmMeasOccSumOutAtt	OBJECT-TYPE
    SYNTAX	Integer32 (0..100)
    MAX-ACCESS	read-only
    STATUS	current
    DESCRIPTION
	"
	Fld OID Name:	avCmMeasOccSumOutAtt
	Fld OID:	enterprises.6889.2.73.8.1.32.1.1.14
	Fld Form/Rpt:	OCCUPANCY SUMMARY MEASUREMENTS
	Fld Format:	Single Field
	Fld(s) Name:	Out Atmpts
	Fld Descr:	An object containing the number of outgoing trunk 
			seizures from public network facilities.
	"
    ::= { avCmMeasOccSumEntry 14 }

avCmMeasOccSumPnetAtt	OBJECT-TYPE
    SYNTAX	Integer32 (0..100)
    MAX-ACCESS	read-only
    STATUS	current
    DESCRIPTION
	"
	Fld OID Name:	avCmMeasOccSumPnetAtt
	Fld OID:	enterprises.6889.2.73.8.1.32.1.1.15
	Fld Form/Rpt:	OCCUPANCY SUMMARY MEASUREMENTS
	Fld Format:	Single Field
	Fld(s) Name:	Pnet Atmpts
	Fld Descr:	An object containing the number of trunk 
			seizures from public network facilities.
	"
    ::= { avCmMeasOccSumEntry 15 }

-- ******************** avCmMeasOccLstHr Group *************************


-- MIB GROUP DESCRIPTION

-- MIB Group Name:
--		avCmMeasOccLstHr Group
-- OID:
--		enterprises.6889.2.73.8.1.33
-- Description:
--		The avCmMeasOccLstHr MIB Group uses the "list measurements 
--		occupancy last-hour" command to retrieve the occupancy data
--		from the last hour  
--		
-- Releases Supported:
--		CM6.3.100 and greater
-- Polling Type:
--		Performance/Utilization
-- Polling Interval:
--		No more than once every 6 minutes, However, no
-- 		more than once an hour is recommended.
-- Default Caching Interval
-- 		300 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements occupancy last-hour
-- Form/Report Name:
--		1. OCCUPANCY LAST-HOUR MEASUREMENTS
-- Reference Document:
--		1. A detailed description of the command and form can be
--		   found in document referenced by REF_DOC_4 in the
--		   DOCUMENT REFERENCE SECTION.
-- Command Permission/User-profile:
--		1. No special permissions needed.

avCmMeasOccLstHr	OBJECT IDENTIFIER ::= { avCmObjects 33 }

avCmMeasOccLstHrTable	OBJECT-TYPE
    SYNTAX	SEQUENCE OF AvCmMeasOccLstHrEntry
    MAX-ACCESS	not-accessible
    STATUS	current
    DESCRIPTION
	"
	Fld OID Name:	avCmMeasOccLstHrEntry
	Fld OID:	enterprises.6889.2.73.8.1.33.1
	Fld Form/Rpt:	NA
	Fld Format:	NA
	Fld(s) Name:	NA
	Fld Descr:	A list of the avCmMeasOccLstHr entries
	"
    ::= { avCmMeasOccLstHr 1 }

avCmMeasOccLstHrEntry	OBJECT-TYPE
    SYNTAX	AvCmMeasOccLstHrEntry
    MAX-ACCESS	not-accessible
    STATUS	current
    DESCRIPTION
	"
	Fld OID Name:	avCmMeasOccLstHrEntry
	Fld OID:	enterprises.6889.2.73.8.1.33.1.1
	Fld Form/Rpt:	NA
	Fld Format:	NA
	Fld(s) Name:	NA
	Fld Descr:	A avCmMeasOccLstHr entry containing objects of the
			avCmMeasOccLstHr information sent by the switch.
	"
    INDEX    { avCmMeasOccLstHrIdx }
    ::= { avCmMeasOccLstHrTable 1 }

AvCmMeasOccLstHrEntry ::= SEQUENCE {
		avCmMeasOccLstHrIdx
		    Integer32,
		avCmMeasOccLstHrMeasMinute
		    SnmpAdminString,
		avCmMeasOccLstHrRunDate
		    SnmpAdminString,
		avCmMeasOccLstHrStatOcc
		    Integer32,
		avCmMeasOccLstHrCPOcc
		    Integer32,
		avCmMeasOccLstHrSMOcc
		    Integer32,
		avCmMeasOccLstHrIdleOcc
		    Integer32,
		avCmMeasOccLstHrTotCall
		    Integer32,
		avCmMeasOccLstHrTandCall
		    Integer32,
		avCmMeasOccLstHrTotConn
		    Integer32,
		avCmMeasOccLstHrIntcomAtt
		    Integer32,
		avCmMeasOccLstHrIncAtt
		    Integer32,
		avCmMeasOccLstHrOutAtt
		    Integer32,
		avCmMeasOccLstHrPnetAtt
		    Integer32
		}

avCmMeasOccLstHrIdx	OBJECT-TYPE
    SYNTAX	Integer32 (0..2400)
    MAX-ACCESS	not-accessible
    STATUS	current
    DESCRIPTION
	"
	Fld OID Name:	avCmMeasOccLstHrIdx
	Fld OID:	enterprises.6889.2.73.8.1.33.1.1.1
	Fld Format:	NA
	Fld(s) Name:	NA
	Fld Descr:	An object that uniquely identifies each Hour of data.
	"
    ::= { avCmMeasOccLstHrEntry 1 }

avCmMeasOccLstHrMeasMinute	OBJECT-TYPE
    SYNTAX	SnmpAdminString (SIZE (0..6))
    MAX-ACCESS	read-only
    STATUS	current
    DESCRIPTION
	"
	Fld OID Name:	avCmMeasOccLstHrMeasMinute
	Fld OID:	enterprises.6889.2.73.8.1.33.1.1.2
	Fld Form/Rpt:	OCCUPANCY LAST-HOUR MEASUREMENTS
	Fld Format:	Single Field
	Fld(s) Name:	Meas Minute
	Fld Descr:	An object containing the hour and minute the 
			measurement was taken.
	"
    ::= { avCmMeasOccLstHrEntry 2 }

avCmMeasOccLstHrRunDate	OBJECT-TYPE
    SYNTAX	SnmpAdminString (SIZE (0..27))
    MAX-ACCESS	read-only
    STATUS	current
    DESCRIPTION
	"
	Fld OID Name:	avCmMeasOccLstHrRunDate
	Fld OID:	enterprises.6889.2.73.8.1.33.1.1.3
	Fld Form/Rpt:	OCCUPANCY LAST-HOUR MEASUREMENTS
	Fld Format:	Single Field
	Fld(s) Name:	Date
	Fld Descr:	An object containing the Date the command was executed.
	"
    ::= { avCmMeasOccLstHrEntry 3 }

avCmMeasOccLstHrStatOcc	OBJECT-TYPE
    SYNTAX	Integer32 (0..100)
    MAX-ACCESS	read-only
    STATUS	current
    DESCRIPTION
	"
	Fld OID Name:	avCmMeasOccLstHrStatOcc
	Fld OID:	enterprises.6889.2.73.8.1.33.1.1.4
	Fld Form/Rpt:	OCCUPANCY LAST-HOUR MEASUREMENTS
	Fld Format:	Single Field
	Fld(s) Name:	Static Occ
	Fld Descr:	Object containing the processor utilized by static 
			processes.
	"
    ::= { avCmMeasOccLstHrEntry 4 }

avCmMeasOccLstHrCPOcc	OBJECT-TYPE
    SYNTAX	Integer32 (0..100)
    MAX-ACCESS	read-only
    STATUS	current
    DESCRIPTION
	"
	Fld OID Name:	avCmMeasOccLstHrCPOcc
	Fld OID:	enterprises.6889.2.73.8.1.33.1.1.5
	Fld Form/Rpt:	OCCUPANCY LAST-HOUR MEASUREMENTS
	Fld Format:	Single Field
	Fld(s) Name:	CP Occ
	Fld Descr:	An object containing the processor occupancy utilized 
			by Call  Processing processes.
	"
    ::= { avCmMeasOccLstHrEntry 5 }

avCmMeasOccLstHrSMOcc	OBJECT-TYPE
    SYNTAX	Integer32 (0..100)
    MAX-ACCESS	read-only
    STATUS	current
    DESCRIPTION
	"
	Fld OID Name:	avCmMeasOccLstHrSMOcc
	Fld OID:	enterprises.6889.2.73.8.1.33.1.1.6
	Fld Form/Rpt:	OCCUPANCY LAST-HOUR MEASUREMENTS
	Fld Format:	Single Field
	Fld(s) Name:	CP Occ
	Fld Descr:	An object containing the processor occupancy utilized 
			by System Management processes.
	"
    ::= { avCmMeasOccLstHrEntry 6 }

avCmMeasOccLstHrIdleOcc	OBJECT-TYPE
    SYNTAX	Integer32 (0..100)
    MAX-ACCESS	read-only
    STATUS	current
    DESCRIPTION
	"
	Fld OID Name:	avCmMeasOccLstHrIdleOcc
	Fld OID:	enterprises.6889.2.73.8.1.33.1.1.7
	Fld Form/Rpt:	OCCUPANCY LAST-HOUR MEASUREMENTS
	Fld Format:	Single Field
	Fld(s) Name:	Idle Occ
	Fld Descr:	An object containing the processor occupancy 
			that is unused.
	"
    ::= { avCmMeasOccLstHrEntry 7 }

avCmMeasOccLstHrTotCall	OBJECT-TYPE
    SYNTAX	Integer32 (0..100)
    MAX-ACCESS	read-only
    STATUS	current
    DESCRIPTION
	"
	Fld OID Name:	avCmMeasOccLstHrTotCall
	Fld OID:	enterprises.6889.2.73.8.1.33.1.1.8
	Fld Form/Rpt:	OCCUPANCY LAST-HOUR MEASUREMENTS
	Fld Format:	Single Field
	Fld(s) Name:	Total Calls
	Fld Descr:	An object containing total calls connected for the 
			measurement hour.
	"
    ::= { avCmMeasOccLstHrEntry 8 }

avCmMeasOccLstHrTandCall	OBJECT-TYPE
    SYNTAX	Integer32 (0..100)
    MAX-ACCESS	read-only
    STATUS	current
    DESCRIPTION
	"
	Fld OID Name:	avCmMeasOccLstHrTandCall
	Fld OID:	enterprises.6889.2.73.8.1.33.1.1.9
	Fld Form/Rpt:	OCCUPANCY LAST-HOUR MEASUREMENTS
	Fld Format:	Single Field
	Fld(s) Name:	Tandem Calls
	Fld Descr:	An object containing trunk-to-trunk calls connected for
			the measurement hour.
	"
    ::= { avCmMeasOccLstHrEntry 9 }

avCmMeasOccLstHrTotConn	OBJECT-TYPE
    SYNTAX	Integer32 (0..100)
    MAX-ACCESS	read-only
    STATUS	current
    DESCRIPTION
	"
	Fld OID Name:	avCmMeasOccLstHrTotConn
	Fld OID:	enterprises.6889.2.73.8.1.33.1.1.10
	Fld Form/Rpt:	OCCUPANCY LAST-HOUR MEASUREMENTS
	Fld Format:	Single Field
	Fld(s) Name:	Total Conn
	Fld Descr:	An object containing the total calls connected for
			the measurement hour.
	"
    ::= { avCmMeasOccLstHrEntry 10 }

avCmMeasOccLstHrIntcomAtt	OBJECT-TYPE
    SYNTAX	Integer32 (0..100)
    MAX-ACCESS	read-only
    STATUS	current
    DESCRIPTION
	"
	Fld OID Name:	avCmMeasOccLstHrIntcomAtt
	Fld OID:	enterprises.6889.2.73.8.1.33.1.1.11
	Fld Form/Rpt:	OCCUPANCY LAST-HOUR MEASUREMENTS
	Fld Format:	Single Field
	Fld(s) Name:	Intcom Atmpts
	Fld Descr:	An object containing the number of extension-to-
			extension calls on the same switch and partially 
			completed calls for the measurement hour.
	"
    ::= { avCmMeasOccLstHrEntry 11 }

avCmMeasOccLstHrIncAtt	OBJECT-TYPE
    SYNTAX	Integer32 (0..100)
    MAX-ACCESS	read-only
    STATUS	current
    DESCRIPTION
	"
	Fld OID Name:	avCmMeasOccLstHrIncAtt
	Fld OID:	enterprises.6889.2.73.8.1.33.1.1.12
	Fld Form/Rpt:	OCCUPANCY LAST-HOUR MEASUREMENTS
	Fld Format:	Single Field
	Fld(s) Name:	Inc Atmpts
	Fld Descr:	An object containing the number of incoming trunk 
			seizures from public network facilities.
	"
    ::= { avCmMeasOccLstHrEntry 12 }

avCmMeasOccLstHrOutAtt	OBJECT-TYPE
    SYNTAX	Integer32 (0..100)
    MAX-ACCESS	read-only
    STATUS	current
    DESCRIPTION
	"
	Fld OID Name:	avCmMeasOccLstHrOutAtt
	Fld OID:	enterprises.6889.2.73.8.1.33.1.1.13
	Fld Form/Rpt:	OCCUPANCY LAST-HOUR MEASUREMENTS
	Fld Format:	Single Field
	Fld(s) Name:	Out Atmpts
	Fld Descr:	An object containing the number of outgoing trunk 
			seizures from public network facilities.
	"
    ::= { avCmMeasOccLstHrEntry 13 }

avCmMeasOccLstHrPnetAtt	OBJECT-TYPE
    SYNTAX	Integer32 (0..100)
    MAX-ACCESS	read-only
    STATUS	current
    DESCRIPTION
	"
	Fld OID Name:	avCmMeasOccLstHrPnetAtt
	Fld OID:	enterprises.6889.2.73.8.1.33.1.1.14
	Fld Form/Rpt:	OCCUPANCY LAST-HOUR MEASUREMENTS
	Fld Format:	Single Field
	Fld(s) Name:	Pnet Atmpts
	Fld Descr:	An object containing the number of trunk 
			seizures from public network facilities.
	"
    ::= { avCmMeasOccLstHrEntry 14 }

-- ******************** avCmMeasOccBusIntvl Group *************************

-- MIB GROUP DESCRIPTION

-- MIB Group Name:
--		avCmMeasOccBusIntvl Group
-- OID:
--		enterprises.6889.2.73.8.1.34
-- Description:
--		The avCmMeasOccBusIntvl MIB Group uses the "list measurements 
--		occupancy busiest-intervals" command to retrieve the occupancy 
--		data from the busiest intervals.
--		
-- Releases Supported:
--		CM6.3.100 and greater
-- Polling Type:
--		Performance/Utilization
-- Polling Interval:
--		No more than once a day.
-- Default Caching Interval
-- 		300 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements occupancy busiest intervals
-- Form/Report Name:
--		1. OCCUPANCY BUSIEST 3-MINUTE INTERVALS MEASUREMENTS
-- Reference Document:
--		1. A detailed description of the command and form can be
--		   found in document referenced by REF_DOC_4 in the
--		   DOCUMENT REFERENCE SECTION.
-- Command Permission/User-profile:
--		1. No special permissions needed.

avCmMeasOccBusIntvl	OBJECT IDENTIFIER ::= { avCmObjects 34 }

avCmMeasOccBusIntvlTable	OBJECT-TYPE
    SYNTAX	SEQUENCE OF AvCmMeasOccBusIntvlEntry
    MAX-ACCESS	not-accessible
    STATUS	current
    DESCRIPTION
	"
	Fld OID Name:	avCmMeasOccBusIntvlEntry
	Fld OID:	enterprises.6889.2.73.8.1.34.1
	Fld Form/Rpt:	NA
	Fld Format:	NA
	Fld(s) Name:	NA
	Fld Descr:	A list of the avCmMeasOccBusIntvl entries
	"
    ::= { avCmMeasOccBusIntvl 1 }

avCmMeasOccBusIntvlEntry	OBJECT-TYPE
    SYNTAX	AvCmMeasOccBusIntvlEntry
    MAX-ACCESS	not-accessible
    STATUS	current
    DESCRIPTION
	"
	Fld OID Name:	avCmMeasOccBusIntvlEntry
	Fld OID:	enterprises.6889.2.73.8.1.34.1.1
	Fld Form/Rpt:	NA
	Fld Format:	NA
	Fld(s) Name:	NA
	Fld Descr:	A avCmMeasOccBusIntvl entry containing objects of the
			avCmMeasOccBusIntvl information sent by the switch.
	"
    INDEX    { avCmMeasOccBusIntvlIdx }
    ::= { avCmMeasOccBusIntvlTable 1 }

AvCmMeasOccBusIntvlEntry ::= SEQUENCE {
		avCmMeasOccBusIntvlIdx
		    Integer32,
		avCmMeasOccBusIntvlDateofOcc
		    SnmpAdminString,
		avCmMeasOccBusIntvlRunDate
		    SnmpAdminString,
		avCmMeasOccBusIntvlStatOcc
		    Integer32,
		avCmMeasOccBusIntvlCPOcc
		    Integer32,
		avCmMeasOccBusIntvlSMOcc
		    Integer32,
		avCmMeasOccBusIntvlIdleOcc
		    Integer32,
		avCmMeasOccBusIntvlTotCall
		    Integer32,
		avCmMeasOccBusIntvlTandCall
		    Integer32,
		avCmMeasOccBusIntvlTotConn
		    Integer32,
		avCmMeasOccBusIntvlIntcomAtt
		    Integer32,
		avCmMeasOccBusIntvlIncAtt
		    Integer32,
		avCmMeasOccBusIntvlOutAtt
		    Integer32,
		avCmMeasOccBusIntvlPnetAtt
		    Integer32
		}

avCmMeasOccBusIntvlIdx	OBJECT-TYPE
    SYNTAX	Integer32 (0..2300)
    MAX-ACCESS	not-accessible
    STATUS	current
    DESCRIPTION
	"
	Fld OID Name:	avCmMeasOccBusIntvlIdx
	Fld OID:	enterprises.6889.2.73.8.1.34.1.1.1
	Fld Format:	NA
	Fld(s) Name:	NA
	Fld Descr:	An object that uniquely identifies each Increment of 
			data.
	"
    ::= { avCmMeasOccBusIntvlEntry 1 }

avCmMeasOccBusIntvlDateofOcc	OBJECT-TYPE
    SYNTAX	SnmpAdminString (SIZE (0..12))
    MAX-ACCESS	read-only
    STATUS	current
    DESCRIPTION
	"
	Fld OID Name:	avCmMeasOccBusIntvlDateofOcc
	Fld OID:	enterprises.6889.2.73.8.1.34.1.1.2
	Fld Form/Rpt:	OCCUPANCY BUSIEST 3-MINUTE INTERVALS MEASUREMENTS
	Fld Format:	Single Field
	Fld(s) Name:	Meas Hour
	Fld Descr:	An object containing the date and time of occurrence.
	"
    ::= { avCmMeasOccBusIntvlEntry 2 }

avCmMeasOccBusIntvlRunDate	OBJECT-TYPE
    SYNTAX	SnmpAdminString (SIZE (0..27))
    MAX-ACCESS	read-only
    STATUS	current
    DESCRIPTION
	"
	Fld OID Name:	avCmMeasOccBusIntvlRunDate
	Fld OID:	enterprises.6889.2.73.8.1.34.1.1.3
	Fld Form/Rpt:	OCCUPANCY BUSIEST 3-MINUTE INTERVALS MEASUREMENTS
	Fld Format:	Single Field
	Fld(s) Name:	Date
	Fld Descr:	An object containing the Date the command was executed.
	"
    ::= { avCmMeasOccBusIntvlEntry 3 }

avCmMeasOccBusIntvlStatOcc	OBJECT-TYPE
    SYNTAX	Integer32 (0..100)
    MAX-ACCESS	read-only
    STATUS	current
    DESCRIPTION
	"
	Fld OID Name:	avCmMeasOccBusIntvlStatOcc
	Fld OID:	enterprises.6889.2.73.8.1.34.1.1.4
	Fld Form/Rpt:	OCCUPANCY BUSIEST 3-MINUTE INTERVALS MEASUREMENTS
	Fld Format:	Single Field
	Fld(s) Name:	Static Occ
	Fld Descr:	Object containing the processor utilized by static 
			processes.
	"
    ::= { avCmMeasOccBusIntvlEntry 4 }

avCmMeasOccBusIntvlCPOcc	OBJECT-TYPE
    SYNTAX	Integer32 (0..100)
    MAX-ACCESS	read-only
    STATUS	current
    DESCRIPTION
	"
	Fld OID Name:	avCmMeasOccBusIntvlCPOcc
	Fld OID:	enterprises.6889.2.73.8.1.34.1.1.5
	Fld Form/Rpt:	OCCUPANCY BUSIEST 3-MINUTE INTERVALS MEASUREMENTS
	Fld Format:	Single Field
	Fld(s) Name:	CP Occ
	Fld Descr:	An object containing the processor occupancy utilized 
			by Call  Processing processes.
	"
    ::= { avCmMeasOccBusIntvlEntry 5 }

avCmMeasOccBusIntvlSMOcc	OBJECT-TYPE
    SYNTAX	Integer32 (0..100)
    MAX-ACCESS	read-only
    STATUS	current
    DESCRIPTION
	"
	Fld OID Name:	avCmMeasOccBusIntvlSMOcc
	Fld OID:	enterprises.6889.2.73.8.1.34.1.1.6
	Fld Form/Rpt:	OCCUPANCY BUSIEST 3-MINUTE INTERVALS MEASUREMENTS
	Fld Format:	Single Field
	Fld(s) Name:	SM Occ
	Fld Descr:	An object containing the processor occupancy utilized 
			by System Management processes.
	"
    ::= { avCmMeasOccBusIntvlEntry 6 }

avCmMeasOccBusIntvlIdleOcc	OBJECT-TYPE
    SYNTAX	Integer32 (0..100)
    MAX-ACCESS	read-only
    STATUS	current
    DESCRIPTION
	"
	Fld OID Name:	avCmMeasOccBusIntvlIdleOcc
	Fld OID:	enterprises.6889.2.73.8.1.34.1.1.7
	Fld Form/Rpt:	OCCUPANCY BUSIEST 3-MINUTE INTERVALS MEASUREMENTS
	Fld Format:	Single Field
	Fld(s) Name:	Idle Occ
	Fld Descr:	An object containing the processor occupancy 
			that is unused.
	"
    ::= { avCmMeasOccBusIntvlEntry 7 }

avCmMeasOccBusIntvlTotCall	OBJECT-TYPE
    SYNTAX	Integer32 (0..100)
    MAX-ACCESS	read-only
    STATUS	current
    DESCRIPTION
	"
	Fld OID Name:	avCmMeasOccBusIntvlTotCall
	Fld OID:	enterprises.6889.2.73.8.1.34.1.1.8
	Fld Form/Rpt:	OCCUPANCY BUSIEST 3-MINUTE INTERVALS MEASUREMENTS
	Fld Format:	Single Field
	Fld(s) Name:	Total Calls
	Fld Descr:	An object containing total calls connected for the 
			measurement hour.
	"
    ::= { avCmMeasOccBusIntvlEntry 8 }

avCmMeasOccBusIntvlTandCall	OBJECT-TYPE
    SYNTAX	Integer32 (0..100)
    MAX-ACCESS	read-only
    STATUS	current
    DESCRIPTION
	"
	Fld OID Name:	avCmMeasOccBusIntvlTandCall
	Fld OID:	enterprises.6889.2.73.8.1.34.1.1.9
	Fld Form/Rpt:	OCCUPANCY BUSIEST 3-MINUTE INTERVALS MEASUREMENTS
	Fld Format:	Single Field
	Fld(s) Name:	Tandem Calls
	Fld Descr:	An object containing trunk-to-trunk calls connected for
			the measurement hour.
	"
    ::= { avCmMeasOccBusIntvlEntry 9 }

avCmMeasOccBusIntvlTotConn	OBJECT-TYPE
    SYNTAX	Integer32 (0..100)
    MAX-ACCESS	read-only
    STATUS	current
    DESCRIPTION
	"
	Fld OID Name:	avCmMeasOccBusIntvlTotConn
	Fld OID:	enterprises.6889.2.73.8.1.34.1.1.10
	Fld Form/Rpt:	OCCUPANCY BUSIEST 3-MINUTE INTERVALS MEASUREMENTS
	Fld Format:	Single Field
	Fld(s) Name:	Total Conn
	Fld Descr:	An object containing the total calls connected for
			the measurement hour.
	"
    ::= { avCmMeasOccBusIntvlEntry 10 }

avCmMeasOccBusIntvlIntcomAtt	OBJECT-TYPE
    SYNTAX	Integer32 (0..100)
    MAX-ACCESS	read-only
    STATUS	current
    DESCRIPTION
	"
	Fld OID Name:	avCmMeasOccBusIntvlIntcomAtt
	Fld OID:	enterprises.6889.2.73.8.1.34.1.1.11
	Fld Form/Rpt:	OCCUPANCY BUSIEST 3-MINUTE INTERVALS MEASUREMENTS
	Fld Format:	Single Field
	Fld(s) Name:	Intcom Atmpts
	Fld Descr:	An object containing the number of extension-to-
			extension calls on the same switch and partially 
			completed calls for the measurement hour.
	"
    ::= { avCmMeasOccBusIntvlEntry 11 }

avCmMeasOccBusIntvlIncAtt	OBJECT-TYPE
    SYNTAX	Integer32 (0..100)
    MAX-ACCESS	read-only
    STATUS	current
    DESCRIPTION
	"
	Fld OID Name:	avCmMeasOccBusIntvlIncAtt
	Fld OID:	enterprises.6889.2.73.8.1.34.1.1.12
	Fld Form/Rpt:	OCCUPANCY BUSIEST 3-MINUTE INTERVALS MEASUREMENTS
	Fld Format:	Single Field
	Fld(s) Name:	Inc Atmpts
	Fld Descr:	An object containing the number of incoming trunk 
			seizures from public network facilities.
	"
    ::= { avCmMeasOccBusIntvlEntry 12 }

avCmMeasOccBusIntvlOutAtt	OBJECT-TYPE
    SYNTAX	Integer32 (0..100)
    MAX-ACCESS	read-only
    STATUS	current
    DESCRIPTION
	"
	Fld OID Name:	avCmMeasOccBusIntvlOutAtt
	Fld OID:	enterprises.6889.2.73.8.1.34.1.1.13
	Fld Form/Rpt:	OCCUPANCY BUSIEST 3-MINUTE INTERVALS MEASUREMENTS
	Fld Format:	Single Field
	Fld(s) Name:	Out Atmpts
	Fld Descr:	An object containing the number of outgoing trunk 
			seizures from public network facilities.
	"
    ::= { avCmMeasOccBusIntvlEntry 13 }

avCmMeasOccBusIntvlPnetAtt	OBJECT-TYPE
    SYNTAX	Integer32 (0..100)
    MAX-ACCESS	read-only
    STATUS	current
    DESCRIPTION
	"
	Fld OID Name:	avCmMeasOccBusIntvlPnetAtt
	Fld OID:	enterprises.6889.2.73.8.1.34.1.1.14
	Fld Form/Rpt:	OCCUPANCY BUSIEST 3-MINUTE INTERVALS MEASUREMENTS
	Fld Format:	Single Field
	Fld(s) Name:	Pnet Atmpts
	Fld Descr:	An object containing the number of trunk 
			seizures from public network facilities.
	"
    ::= { avCmMeasOccBusIntvlEntry 14 }

-- ******************** avCmMeasTrkGrpSumLstHr Group *************************

-- MIB GROUP DESCRIPTION

-- MIB Group Name:
--		avCmMeasTrkGrpSumLstHr Group
-- OID:
--		enterprises.6889.2.73.8.1.35
-- Description:
--		The avCmMeasTrkGrpSumLstHr MIB Group uses the "list measurements
--		trunk-group summary last-hour" command to retrieve trunk data 
--		from the last hour.
--		
-- Releases Supported:
--		CM6.3.100 and greater
-- Polling Type:
--		Performance/Utilization
-- Polling Interval:
--		No more than once an hour because the data is only updated
--		near the beginning of the hour.
-- Default Caching Interval
-- 		300 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements trunk-group summary last-hour
-- Form/Report Name:
--		1. TRUNK GROUP SUMMARY REPORT
-- Reference Document:
--		1. A detailed description of the command and form can be
--		   found in document referenced by REF_DOC_4 in the
--		   DOCUMENT REFERENCE SECTION.
-- Command Permission/User-profile:
--		1. No special permissions needed.

avCmMeasTrkGrpSumLstHr	OBJECT IDENTIFIER ::= { avCmObjects 35 }

avCmMeasTrkGrpSumLstHrTable	OBJECT-TYPE
    SYNTAX	SEQUENCE OF AvCmMeasTrkGrpSumLstHrEntry
    MAX-ACCESS	not-accessible
    STATUS	current
    DESCRIPTION
	"
	Fld OID Name:	avCmMeasTrkGrpSumLstHrEntry
	Fld OID:	enterprises.6889.2.73.8.1.35.1
	Fld Form/Rpt:	NA
	Fld Format:	NA
	Fld(s) Name:	NA
	Fld Descr:	A list of the avCmMeasTrkGrpSumLstHr entries
	"
    ::= { avCmMeasTrkGrpSumLstHr 1 }

avCmMeasTrkGrpSumLstHrEntry	OBJECT-TYPE
    SYNTAX	AvCmMeasTrkGrpSumLstHrEntry
    MAX-ACCESS	not-accessible
    STATUS	current
    DESCRIPTION
	"
	Fld OID Name:	avCmMeasTrkGrpSumLstHrEntry
	Fld OID:	enterprises.6889.2.73.8.1.35.1.1
	Fld Form/Rpt:	NA
	Fld Format:	NA
	Fld(s) Name:	NA
	Fld Descr:	A avCmMeasTrkGrpSumLstHr entry containing objects of the
			avCmMeasTrkGrpSumLstHr information sent by the switch.
	"
    INDEX    { avCmMeasTrkGrpSumLstHrTrunkGrpIdx }
    ::= { avCmMeasTrkGrpSumLstHrTable 1 }

AvCmMeasTrkGrpSumLstHrEntry ::= SEQUENCE {
		avCmMeasTrkGrpSumLstHrTrunkGrpIdx
		    Integer32,
		avCmMeasTrkGrpSumLstHrTrunkGroup
		    Integer32,
		avCmMeasTrkGrpSumLstHrRunDate
		    SnmpAdminString,
		avCmMeasTrkGrpSumLstHrMeasHour
		    Integer32,
		avCmMeasTrkGrpSumLstHrGroupSize
		    Integer32,
		avCmMeasTrkGrpSumLstHrTotalUsage
		    Integer32,
		avCmMeasTrkGrpSumLstHrTotalSeize 
		    Integer32,
		avCmMeasTrkGrpSumLstHrIncSeize
		    Integer32,
		avCmMeasTrkGrpSumLstHrGrpOvflow
		    Integer32,
		avCmMeasTrkGrpSumLstHrQueSiz
		    Integer32,
		avCmMeasTrkGrpSumLstHrCallQued
		    Integer32,
		avCmMeasTrkGrpSumLstHrQueOvf
		    Integer32,
		avCmMeasTrkGrpSumLstHrQueAbd
		    Integer32,
		avCmMeasTrkGrpSumLstHrOutSrv
		    Integer32,
		avCmMeasTrkGrpSumLstHrPercentAtb
		    Integer32,
		avCmMeasTrkGrpSumLstHrPercentOutBlk
		    Integer32
		}

avCmMeasTrkGrpSumLstHrTrunkGrpIdx	OBJECT-TYPE
    SYNTAX	Integer32 (0..2000)
    MAX-ACCESS	not-accessible
    STATUS	current
    DESCRIPTION
	"
	Fld OID Name:	avCmMeasTrkGrpSumLstHrTrunkGrpIdx
	Fld OID:	enterprises.6889.2.73.8.1.35.1.1.1
	Fld Format:	NA
	Fld(s) Name:	NA
	Fld Descr:	An object that uniquely identifies each Increment of 
			data.
	"
    ::= { avCmMeasTrkGrpSumLstHrEntry 1 }

avCmMeasTrkGrpSumLstHrTrunkGroup	OBJECT-TYPE
    SYNTAX	Integer32 (0..2000)
    MAX-ACCESS	read-only
    STATUS	current
    DESCRIPTION
	"
	Fld OID Name:	avCmMeasTrkGrpSumLstHrTrunkGroup
	Fld OID:	enterprises.6889.2.73.8.1.35.1.1.2
	Fld Form/Rpt:	TRUNK GROUP SUMMARY REPORT
	Fld Format:	Single Field
	Fld(s) Name:	Trunk Group
	Fld Descr:	An object containing the trunk group number.
	"
    ::= { avCmMeasTrkGrpSumLstHrEntry 2 }

avCmMeasTrkGrpSumLstHrRunDate	OBJECT-TYPE
    SYNTAX	SnmpAdminString (SIZE (0..27))
    MAX-ACCESS	read-only
    STATUS	current
    DESCRIPTION
	"
	Fld OID Name:	avCmMeasTrkGrpSumLstHrRunDate
	Fld OID:	enterprises.6889.2.73.8.1.35.1.1.3
	Fld Form/Rpt:	TRUNK GROUP SUMMARY REPORT
	Fld Format:	Single Field
	Fld(s) Name:	Date
	Fld Descr:	An object containing the Date the command was executed.
	"
    ::= { avCmMeasTrkGrpSumLstHrEntry 3 }

avCmMeasTrkGrpSumLstHrMeasHour	OBJECT-TYPE
    SYNTAX	Integer32 (0..2300)
    MAX-ACCESS	read-only
    STATUS	current
    DESCRIPTION
	"
	Fld OID Name:	avCmMeasTrkGrpSumLstHrMeasHour
	Fld OID:	enterprises.6889.2.73.8.1.35.1.1.4
	Fld Form/Rpt:	TRUNK GROUP SUMMARY REPORT
	Fld Format:	Single Field
	Fld(s) Name:	Meas Hour
	Fld Descr:	An object containing the Hour the measurement was taken.
	"
    ::= { avCmMeasTrkGrpSumLstHrEntry 4 }

avCmMeasTrkGrpSumLstHrGroupSize	OBJECT-TYPE
    SYNTAX	Integer32 (0..255)
    MAX-ACCESS	read-only
    STATUS	current
    DESCRIPTION
	"
	Fld OID Name:	avCmMeasTrkGrpSumLstHrGroupSize
	Fld OID:	enterprises.6889.2.73.8.1.35.1.1.5
	Fld Form/Rpt:	TRUNK GROUP SUMMARY REPORT
	Fld Format:	Single Field
	Fld(s) Name:	Grp Siz
	Fld Descr:	An object containing the number of administered trunks
			in the trunk group.
	"
    ::= { avCmMeasTrkGrpSumLstHrEntry 5 }

avCmMeasTrkGrpSumLstHrTotalUsage	OBJECT-TYPE
    SYNTAX	Integer32 (0..9999)
    MAX-ACCESS	read-only
    STATUS	current
    DESCRIPTION
	"
	Fld OID Name:	avCmMeasTrkGrpSumLstHrTotalUsage
	Fld OID:	enterprises.6889.2.73.8.1.35.1.1.6
	Fld Form/Rpt:	TRUNK GROUP SUMMARY REPORT
	Fld Format:	Single Field
	Fld(s) Name:	Total Usage
	Fld Descr:	An object containing the total time trunks are busy 
			with calls during the measurement period (in CCS).
	"
    ::= { avCmMeasTrkGrpSumLstHrEntry 6 }

avCmMeasTrkGrpSumLstHrTotalSeize	OBJECT-TYPE
    SYNTAX	Integer32 (0..999999)
    MAX-ACCESS	read-only
    STATUS	current
    DESCRIPTION
	"
	Fld OID Name:	avCmMeasTrkGrpSumLstHrTotalSeize
	Fld OID:	enterprises.6889.2.73.8.1.35.1.1.7
	Fld Form/Rpt:	TRUNK GROUP SUMMARY REPORT
	Fld Format:	Single Field
	Fld(s) Name:	Total Seize
	Fld Descr:	An object containing the number of times a trunk was 
			seized in the group including false starts, don't 
			answer and busy.
	"
    ::= { avCmMeasTrkGrpSumLstHrEntry 7 }

avCmMeasTrkGrpSumLstHrIncSeize	OBJECT-TYPE
    SYNTAX	Integer32 (0..999999)
    MAX-ACCESS	read-only
    STATUS	current
    DESCRIPTION
	"
	Fld OID Name:	avCmMeasTrkGrpSumLstHrIncSeize
	Fld OID:	enterprises.6889.2.73.8.1.35.1.1.8
	Fld Form/Rpt:	TRUNK GROUP SUMMARY REPORT
	Fld Format:	Single Field
	Fld(s) Name:	Inc Seize
	Fld Descr:	An object containing the number of incoming seizures 
			carried on the trunk group.
	"
    ::= { avCmMeasTrkGrpSumLstHrEntry 8 }

avCmMeasTrkGrpSumLstHrGrpOvflow	OBJECT-TYPE
    SYNTAX	Integer32 (0..99999)
    MAX-ACCESS	read-only
    STATUS	current
    DESCRIPTION
	"
	Fld OID Name:	avCmMeasTrkGrpSumLstHrGrpOvflow
	Fld OID:	enterprises.6889.2.73.8.1.35.1.1.9
	Fld Form/Rpt:	TRUNK GROUP SUMMARY REPORT
	Fld Format:	Single Field
	Fld(s) Name:	Grp Ovfl
	Fld Descr:	An object containing the number of calls offered to a 
			trunk group that are not carried or queued.
	"
    ::= { avCmMeasTrkGrpSumLstHrEntry 9 }

avCmMeasTrkGrpSumLstHrQueSiz	OBJECT-TYPE
    SYNTAX	Integer32 (0..9999)
    MAX-ACCESS	read-only
    STATUS	current
    DESCRIPTION
	"
	Fld OID Name:	avCmMeasTrkGrpSumLstHrQueSiz
	Fld OID:	enterprises.6889.2.73.8.1.35.1.1.10
	Fld Form/Rpt:	TRUNK GROUP SUMMARY REPORT
	Fld Format:	Single Field
	Fld(s) Name:	Que Siz
	Fld Descr:	An object containing a number that identifies 
			the number of slots assigned to the trunk group queue.
	"
    ::= { avCmMeasTrkGrpSumLstHrEntry 10 }

avCmMeasTrkGrpSumLstHrCallQued	OBJECT-TYPE
    SYNTAX	Integer32 (0..9999)
    MAX-ACCESS	read-only
    STATUS	current
    DESCRIPTION
	"
	Fld OID Name:	avCmMeasTrkGrpSumLstHrCallQued
	Fld OID:	enterprises.6889.2.73.8.1.35.1.1.11
	Fld Form/Rpt:	TRUNK GROUP SUMMARY REPORT
	Fld Format:	Single Field
	Fld(s) Name:	Call Qued
	Fld Descr:	An object containing the total number of calls that
			entered the trunk group queue after finding all trunks
			busy.
	"
    ::= { avCmMeasTrkGrpSumLstHrEntry 11 }

avCmMeasTrkGrpSumLstHrQueOvf	OBJECT-TYPE
    SYNTAX	Integer32 (0..9999)
    MAX-ACCESS	read-only
    STATUS	current
    DESCRIPTION
	"
	Fld OID Name:	avCmMeasTrkGrpSumLstHrQueOvf
	Fld OID:	enterprises.6889.2.73.8.1.35.1.1.12
	Fld Form/Rpt:	TRUNK GROUP SUMMARY REPORT
	Fld Format:	Single Field
	Fld(s) Name:	Que Ovf
	Fld Descr:	An object containing the total number of calls that 
			were denied because the queue was full.
	"
    ::= { avCmMeasTrkGrpSumLstHrEntry 12 }

avCmMeasTrkGrpSumLstHrQueAbd	OBJECT-TYPE
    SYNTAX	Integer32 (0..9999)
    MAX-ACCESS	read-only
    STATUS	current
    DESCRIPTION
	"
	Fld OID Name:	avCmMeasTrkGrpSumLstHrQueAbd
	Fld OID:	enterprises.6889.2.73.8.1.35.1.1.13
	Fld Form/Rpt:	TRUNK GROUP SUMMARY REPORT
	Fld Format:	Single Field
	Fld(s) Name:	Que Abd
	Fld Descr:	An object containing the total number of calls that 
			were removed from the queue (i.e., due to queue timeout
			 or user cancel).
	"
    ::= { avCmMeasTrkGrpSumLstHrEntry 13 }

avCmMeasTrkGrpSumLstHrOutSrv	OBJECT-TYPE
    SYNTAX	Integer32 (0..999)
    MAX-ACCESS	read-only
    STATUS	current
    DESCRIPTION
	"
	Fld OID Name:	avCmMeasTrkGrpSumLstHrOutSrv
	Fld OID:	enterprises.6889.2.73.8.1.35.1.1.14
	Fld Form/Rpt:	TRUNK GROUP SUMMARY REPORT
	Fld Format:	Single Field
	Fld(s) Name:	Out Srv
	Fld Descr:	An object containing the number of trunks in the group 
			that are out of service (maintenance busy).
	"
    ::= { avCmMeasTrkGrpSumLstHrEntry 14 }

avCmMeasTrkGrpSumLstHrPercentAtb	OBJECT-TYPE
    SYNTAX	Integer32 (0..100)
    MAX-ACCESS	read-only
    STATUS	current
    DESCRIPTION
	"
	Fld OID Name:	avCmMeasTrkGrpSumLstHrPercentAtb
	Fld OID:	enterprises.6889.2.73.8.1.35.1.1.15
	Fld Form/Rpt:	TRUNK GROUP SUMMARY REPORT
	Fld Format:	Single Field
	Fld(s) Name:	% ATB 
	Fld Descr:	An object containing the percentage of time all trunks 
			in the group were simultaneously in use.
	"
    ::= { avCmMeasTrkGrpSumLstHrEntry 15 }

avCmMeasTrkGrpSumLstHrPercentOutBlk	OBJECT-TYPE
    SYNTAX	Integer32 (0..100)
    MAX-ACCESS	read-only
    STATUS	current
    DESCRIPTION
	"
	Fld OID Name:	avCmMeasTrkGrpSumLstHrPercentOutBlk
	Fld OID:	enterprises.6889.2.73.8.1.35.1.1.16
	Fld Form/Rpt:	TRUNK GROUP SUMMARY REPORT
	Fld Format:	Single Field
	Fld(s) Name:	% Out Blk 
	Fld Descr:	An object containing the percentage of offered calls 
			that are not carried on the group.
	"
    ::= { avCmMeasTrkGrpSumLstHrEntry 16 }

-- ******************** avCmMeasTrkGrpSumToday Group *************************


-- MIB GROUP DESCRIPTION

-- MIB Group Name:
--		avCmMeasTrkGrpSumToday Group
-- OID:
--		enterprises.6889.2.73.8.1.36
-- Description:
--		The avCmMeasTrkGrpSumToday MIB Group uses the "list measurements
--		trunk-group summary today-hour" command to retrieve trunk data 
--		from today.
--		
-- Releases Supported:
--		CM6.3.100 and greater
-- Polling Type:
--		Performance/Utilization
-- Polling Interval:
--		No more than once an hour because the data is only updated
--		near the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements trunk-group summary Today
-- Form/Report Name:
--		1. TRUNK GROUP SUMMARY REPORT
-- Reference Document:
--		1. A detailed description of the command and form can be
--		   found in document referenced by REF_DOC_4 in the
--		   DOCUMENT REFERENCE SECTION.
-- Command Permission/User-profile:
--		1. No special permissions needed.

avCmMeasTrkGrpSumToday	OBJECT IDENTIFIER ::= { avCmObjects 36 }

avCmMeasTrkGrpSumTodayTable	OBJECT-TYPE
    SYNTAX	SEQUENCE OF AvCmMeasTrkGrpSumTodayEntry
    MAX-ACCESS	not-accessible
    STATUS	current
    DESCRIPTION
	"
	Fld OID Name:	avCmMeasTrkGrpSumTodayEntry
	Fld OID:	enterprises.6889.2.73.8.1.36.1
	Fld Form/Rpt:	NA
	Fld Format:	NA
	Fld(s) Name:	NA
	Fld Descr:	A list of the avCmMeasTrkGrpSumToday entries
	"
    ::= { avCmMeasTrkGrpSumToday 1 }

avCmMeasTrkGrpSumTodayEntry	OBJECT-TYPE
    SYNTAX	AvCmMeasTrkGrpSumTodayEntry
    MAX-ACCESS	not-accessible
    STATUS	current
    DESCRIPTION
	"
	Fld OID Name:	avCmMeasTrkGrpSumTodayEntry
	Fld OID:	enterprises.6889.2.73.8.1.36.1.1
	Fld Form/Rpt:	NA
	Fld Format:	NA
	Fld(s) Name:	NA
	Fld Descr:	A avCmMeasTrkGrpSumToday entry containing objects of the
			avCmMeasTrkGrpSumToday information sent by the switch.
	"
    INDEX    { avCmMeasTrkGrpSumTodayTrunkGrpIdx }
    ::= { avCmMeasTrkGrpSumTodayTable 1 }

AvCmMeasTrkGrpSumTodayEntry ::= SEQUENCE {
		avCmMeasTrkGrpSumTodayTrunkGrpIdx
		    Integer32,
		avCmMeasTrkGrpSumTodayTrunkGroup
		    Integer32,
		avCmMeasTrkGrpSumTodayRunDate
		    SnmpAdminString,
		avCmMeasTrkGrpSumTodayPeakHour
		    Integer32,
		avCmMeasTrkGrpSumTodayMeasHour
		    Integer32,
		avCmMeasTrkGrpSumTodayGroupSize
		    Integer32,
		avCmMeasTrkGrpSumTodayTotalUsage
		    Integer32,
		avCmMeasTrkGrpSumTodayTotalSeize 
		    Integer32,
		avCmMeasTrkGrpSumTodayIncSeize
		    Integer32,
		avCmMeasTrkGrpSumTodayGrpOvflow
		    Integer32,
		avCmMeasTrkGrpSumTodayQueSiz
		    Integer32,
		avCmMeasTrkGrpSumTodayCallQued
		    Integer32,
		avCmMeasTrkGrpSumTodayQueOvf
		    Integer32,
		avCmMeasTrkGrpSumTodayQueAbd
		    Integer32,
		avCmMeasTrkGrpSumTodayOutSrv
		    Integer32,
		avCmMeasTrkGrpSumTodayPercentAtb
		    Integer32,
		avCmMeasTrkGrpSumTodayPercentOutBlk
		    Integer32
		}

avCmMeasTrkGrpSumTodayTrunkGrpIdx	OBJECT-TYPE
    SYNTAX	Integer32 (0..2000)
    MAX-ACCESS	not-accessible
    STATUS	current
    DESCRIPTION
	"
	Fld OID Name:	avCmMeasTrkGrpSumTodayTrunkGrpIdx
	Fld OID:	enterprises.6889.2.73.8.1.36.1.1.1
	Fld Format:	NA
	Fld(s) Name:	NA
	Fld Descr:	An object that uniquely identifies each Increment of 
			data.
	"
    ::= { avCmMeasTrkGrpSumTodayEntry 1 }

avCmMeasTrkGrpSumTodayTrunkGroup	OBJECT-TYPE
    SYNTAX	Integer32 (0..2000)
    MAX-ACCESS	read-only
    STATUS	current
    DESCRIPTION
	"
	Fld OID Name:	avCmMeasTrkGrpSumTodayTrunkGroup
	Fld OID:	enterprises.6889.2.73.8.1.36.1.1.2
	Fld Form/Rpt:	TRUNK GROUP SUMMARY REPORT
	Fld Format:	Single Field
	Fld(s) Name:	Trunk Group
	Fld Descr:	An object containing the trunk group number.
	"
    ::= { avCmMeasTrkGrpSumTodayEntry 2 }

avCmMeasTrkGrpSumTodayRunDate	OBJECT-TYPE
    SYNTAX	SnmpAdminString (SIZE (0..27))
    MAX-ACCESS	read-only
    STATUS	current
    DESCRIPTION
	"
	Fld OID Name:	avCmMeasTrkGrpSumTodayRunDate
	Fld OID:	enterprises.6889.2.73.8.1.36.1.1.3
	Fld Form/Rpt:	TRUNK GROUP SUMMARY REPORT
	Fld Format:	Single Field
	Fld(s) Name:	Date
	Fld Descr:	An object containing the Date the command was executed.
	"
    ::= { avCmMeasTrkGrpSumTodayEntry 3 }

avCmMeasTrkGrpSumTodayPeakHour   OBJECT-TYPE
    SYNTAX	Integer32 (0..2300)
    MAX-ACCESS  read-only
    STATUS      current
    DESCRIPTION
        "
        Fld OID Name:   avCmMeasTrkGrpSumTodayPeakHour
        Fld OID:        enterprises.6889.2.73.8.1.36.1.1.4
        Fld Form/Rpt:   TRUNK GROUP SUMMARY REPORT
        Fld Format:     Single Field
        Fld(s) Name:    Peak Hour For All Trunk Groups
        Fld Descr:      An object containing the peak traffic hour for all
			trunk-groups.
        "
    ::= { avCmMeasTrkGrpSumTodayEntry 4 }


avCmMeasTrkGrpSumTodayMeasHour	OBJECT-TYPE
    SYNTAX	Integer32 (0..2300)
    MAX-ACCESS	read-only
    STATUS	current
    DESCRIPTION
	"
	Fld OID Name:	avCmMeasTrkGrpSumTodayMeasHour
	Fld OID:	enterprises.6889.2.73.8.1.36.1.1.5
	Fld Form/Rpt:	TRUNK GROUP SUMMARY REPORT
	Fld Format:	Single Field
	Fld(s) Name:	Meas Hour
	Fld Descr:	An object containing the Hour the measurement was taken.
	"
    ::= { avCmMeasTrkGrpSumTodayEntry 5 }

avCmMeasTrkGrpSumTodayGroupSize	OBJECT-TYPE
    SYNTAX	Integer32 (0..255)
    MAX-ACCESS	read-only
    STATUS	current
    DESCRIPTION
	"
	Fld OID Name:	avCmMeasTrkGrpSumTodayGroupSize
	Fld OID:	enterprises.6889.2.73.8.1.36.1.1.6
	Fld Form/Rpt:	TRUNK GROUP SUMMARY REPORT
	Fld Format:	Single Field
	Fld(s) Name:	Grp Siz
	Fld Descr:	An object containing the number of administered trunks
			in the trunk group.
	"
    ::= { avCmMeasTrkGrpSumTodayEntry 6 }

avCmMeasTrkGrpSumTodayTotalUsage	OBJECT-TYPE
    SYNTAX	Integer32 (0..9999)
    MAX-ACCESS	read-only
    STATUS	current
    DESCRIPTION
	"
	Fld OID Name:	avCmMeasTrkGrpSumTodayTotalUsage
	Fld OID:	enterprises.6889.2.73.8.1.36.1.1.7
	Fld Form/Rpt:	TRUNK GROUP SUMMARY REPORT
	Fld Format:	Single Field
	Fld(s) Name:	Total Usage
	Fld Descr:	An object containing the total time trunks are busy 
			with calls during the measurement period (in CCS).
	"
    ::= { avCmMeasTrkGrpSumTodayEntry 7 }

avCmMeasTrkGrpSumTodayTotalSeize	OBJECT-TYPE
    SYNTAX	Integer32 (0..999999)
    MAX-ACCESS	read-only
    STATUS	current
    DESCRIPTION
	"
	Fld OID Name:	avCmMeasTrkGrpSumTodayTotalSeize
	Fld OID:	enterprises.6889.2.73.8.1.36.1.1.8
	Fld Form/Rpt:	TRUNK GROUP SUMMARY REPORT
	Fld Format:	Single Field
	Fld(s) Name:	Total Seize
	Fld Descr:	An object containing the number of times a trunk was 
			seized in the group including false starts, don't 
			answer and busy.
	"
    ::= { avCmMeasTrkGrpSumTodayEntry 8 }

avCmMeasTrkGrpSumTodayIncSeize	OBJECT-TYPE
    SYNTAX	Integer32 (0..999999)
    MAX-ACCESS	read-only
    STATUS	current
    DESCRIPTION
	"
	Fld OID Name:	avCmMeasTrkGrpSumTodayIncSeize
	Fld OID:	enterprises.6889.2.73.8.1.36.1.1.9
	Fld Form/Rpt:	TRUNK GROUP SUMMARY REPORT
	Fld Format:	Single Field
	Fld(s) Name:	Inc Seize
	Fld Descr:	An object containing the number of incoming seizures 
			carried on the trunk group.
	"
    ::= { avCmMeasTrkGrpSumTodayEntry 9 }

avCmMeasTrkGrpSumTodayGrpOvflow	OBJECT-TYPE
    SYNTAX	Integer32 (0..99999)
    MAX-ACCESS	read-only
    STATUS	current
    DESCRIPTION
	"
	Fld OID Name:	avCmMeasTrkGrpSumTodayGrpOvflow
	Fld OID:	enterprises.6889.2.73.8.1.36.1.1.10
	Fld Form/Rpt:	TRUNK GROUP SUMMARY REPORT
	Fld Format:	Single Field
	Fld(s) Name:	Grp Ovfl
	Fld Descr:	An object containing the number of calls offered to a 
			trunk group that are not carried or queued.
	"
    ::= { avCmMeasTrkGrpSumTodayEntry 10 }

avCmMeasTrkGrpSumTodayQueSiz	OBJECT-TYPE
    SYNTAX	Integer32 (0..9999)
    MAX-ACCESS	read-only
    STATUS	current
    DESCRIPTION
	"
	Fld OID Name:	avCmMeasTrkGrpSumTodayQueSiz
	Fld OID:	enterprises.6889.2.73.8.1.36.1.1.11
	Fld Form/Rpt:	TRUNK GROUP SUMMARY REPORT
	Fld Format:	Single Field
	Fld(s) Name:	Que Siz
	Fld Descr:	An object containing a number that identifies 
			the number of slots assigned to the trunk group queue.
	"
    ::= { avCmMeasTrkGrpSumTodayEntry 11 }

avCmMeasTrkGrpSumTodayCallQued	OBJECT-TYPE
    SYNTAX	Integer32 (0..9999)
    MAX-ACCESS	read-only
    STATUS	current
    DESCRIPTION
	"
	Fld OID Name:	avCmMeasTrkGrpSumTodayCallQued
	Fld OID:	enterprises.6889.2.73.8.1.36.1.1.12
	Fld Form/Rpt:	TRUNK GROUP SUMMARY REPORT
	Fld Format:	Single Field
	Fld(s) Name:	Call Qued
	Fld Descr:	An object containing the total number of calls that 
			entered the trunk group queue after finding all trunks 
			busy.

	"
    ::= { avCmMeasTrkGrpSumTodayEntry 12 }

avCmMeasTrkGrpSumTodayQueOvf	OBJECT-TYPE
    SYNTAX	Integer32 (0..9999)
    MAX-ACCESS	read-only
    STATUS	current
    DESCRIPTION
	"
	Fld OID Name:	avCmMeasTrkGrpSumTodayQueOvf
	Fld OID:	enterprises.6889.2.73.8.1.36.1.1.13
	Fld Form/Rpt:	TRUNK GROUP SUMMARY REPORT
	Fld Format:	Single Field
	Fld(s) Name:	Que Ovf
	Fld Descr:	An object containing the total number of calls that 
			were denied because the queue was full.
	"
    ::= { avCmMeasTrkGrpSumTodayEntry 13 }

avCmMeasTrkGrpSumTodayQueAbd	OBJECT-TYPE
    SYNTAX	Integer32 (0..9999)
    MAX-ACCESS	read-only
    STATUS	current
    DESCRIPTION
	"
	Fld OID Name:	avCmMeasTrkGrpSumTodayQueAbd
	Fld OID:	enterprises.6889.2.73.8.1.36.1.1.14
	Fld Form/Rpt:	TRUNK GROUP SUMMARY REPORT
	Fld Format:	Single Field
	Fld(s) Name:	Que Abd
	Fld Descr:	An object containing the total number of calls that 
			were removed from the queue (i.e., due to queue timeout
			 or user cancel).
	"
    ::= { avCmMeasTrkGrpSumTodayEntry 14 }

avCmMeasTrkGrpSumTodayOutSrv	OBJECT-TYPE
    SYNTAX	Integer32 (0..999)
    MAX-ACCESS	read-only
    STATUS	current
    DESCRIPTION
	"
	Fld OID Name:	avCmMeasTrkGrpSumTodayOutSrv
	Fld OID:	enterprises.6889.2.73.8.1.36.1.1.15
	Fld Form/Rpt:	TRUNK GROUP SUMMARY REPORT
	Fld Format:	Single Field
	Fld(s) Name:	Out Srv
	Fld Descr:	An object containing the number of trunks in the group 
			that are out of service (maintenance busy).
	"
    ::= { avCmMeasTrkGrpSumTodayEntry 15 }

avCmMeasTrkGrpSumTodayPercentAtb	OBJECT-TYPE
    SYNTAX	Integer32 (0..100)
    MAX-ACCESS	read-only
    STATUS	current
    DESCRIPTION
	"
	Fld OID Name:	avCmMeasTrkGrpSumTodayPercentAtb
	Fld OID:	enterprises.6889.2.73.8.1.36.1.1.16
	Fld Form/Rpt:	TRUNK GROUP SUMMARY REPORT
	Fld Format:	Single Field
	Fld(s) Name:	% ATB 
	Fld Descr:	An object containing the percentage of time all trunks 
			in the group were simultaneously in use.
	"
    ::= { avCmMeasTrkGrpSumTodayEntry 16 }

avCmMeasTrkGrpSumTodayPercentOutBlk	OBJECT-TYPE
    SYNTAX	Integer32 (0..100)
    MAX-ACCESS	read-only
    STATUS	current
    DESCRIPTION
	"
	Fld OID Name:	avCmMeasTrkGrpSumTodayPercentOutBlk
	Fld OID:	enterprises.6889.2.73.8.1.36.1.1.17
	Fld Form/Rpt:	TRUNK GROUP SUMMARY REPORT
	Fld Format:	Single Field
	Fld(s) Name:	% Out Blk 
	Fld Descr:	An object containing the percentage of offered calls 
			that are not carried on the group.
	"
    ::= { avCmMeasTrkGrpSumTodayEntry 17 }

-- ******************** avCmMeasTrkGrpSumYest Group *************************

-- MIB GROUP DESCRIPTION

-- MIB Group Name:
--		avCmMeasTrkGrpSumYest Group
-- OID:
--		enterprises.6889.2.73.8.1.37
-- Description:
--		The avCmMeasTrkGrpSumYest MIB Group uses the "list measurements
--		trunk-group summary yesterday" command to retrieve trunk data 
--		from yesterday.
--		
-- Releases Supported:
--		CM6.3.100 and greater
-- Polling Type:
--		Performance/Utilization
-- Polling Interval:
--		No more than once a day because the data is only updated
--		near the beginning of the day.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements trunk-group summary yesterday
-- Form/Report Name:
--		1. TRUNK GROUP SUMMARY REPORT
-- Reference Document:
--		1. A detailed description of the command and form can be
--		   found in document referenced by REF_DOC_4 in the
--		   DOCUMENT REFERENCE SECTION.
-- Command Permission/User-profile:
--		1. No special permissions needed.

avCmMeasTrkGrpSumYest	OBJECT IDENTIFIER ::= { avCmObjects 37 }

avCmMeasTrkGrpSumYestTable	OBJECT-TYPE
    SYNTAX	SEQUENCE OF AvCmMeasTrkGrpSumYestEntry
    MAX-ACCESS	not-accessible
    STATUS	current
    DESCRIPTION
	"
	Fld OID Name:	avCmMeasTrkGrpSumYestEntry
	Fld OID:	enterprises.6889.2.73.8.1.37.1
	Fld Form/Rpt:	NA
	Fld Format:	NA
	Fld(s) Name:	NA
	Fld Descr:	A list of the avCmMeasTrkGrpSumYest entries
	"
    ::= { avCmMeasTrkGrpSumYest 1 }

avCmMeasTrkGrpSumYestEntry	OBJECT-TYPE
    SYNTAX	AvCmMeasTrkGrpSumYestEntry
    MAX-ACCESS	not-accessible
    STATUS	current
    DESCRIPTION
	"
	Fld OID Name:	avCmMeasTrkGrpSumYestEntry
	Fld OID:	enterprises.6889.2.73.8.1.37.1.1
	Fld Form/Rpt:	NA
	Fld Format:	NA
	Fld(s) Name:	NA
	Fld Descr:	A avCmMeasTrkGrpSumYest entry containing objects of the
			avCmMeasTrkGrpSumYest information sent by the switch.
	"
    INDEX    { avCmMeasTrkGrpSumYestTrunkGrpIdx }
    ::= { avCmMeasTrkGrpSumYestTable 1 }

AvCmMeasTrkGrpSumYestEntry ::= SEQUENCE {
		avCmMeasTrkGrpSumYestTrunkGrpIdx
		    Integer32,
		avCmMeasTrkGrpSumYestTrunkGroup
		    Integer32,
		avCmMeasTrkGrpSumYestRunDate
		    SnmpAdminString,
		avCmMeasTrkGrpSumYestPeakHour
		    Integer32,
		avCmMeasTrkGrpSumYestMeasHour
		    Integer32,
		avCmMeasTrkGrpSumYestGroupSize
		    Integer32,
		avCmMeasTrkGrpSumYestTotalUsage
		    Integer32,
		avCmMeasTrkGrpSumYestTotalSeize 
		    Integer32,
		avCmMeasTrkGrpSumYestIncSeize
		    Integer32,
		avCmMeasTrkGrpSumYestGrpOvflow
		    Integer32,
		avCmMeasTrkGrpSumYestQueSiz
		    Integer32,
		avCmMeasTrkGrpSumYestCallQued
		    Integer32,
		avCmMeasTrkGrpSumYestQueOvf
		    Integer32,
		avCmMeasTrkGrpSumYestQueAbd
		    Integer32,
		avCmMeasTrkGrpSumYestOutSrv
		    Integer32,
		avCmMeasTrkGrpSumYestPercentAtb
		    Integer32,
		avCmMeasTrkGrpSumYestPercentOutBlk
		    Integer32
		}

avCmMeasTrkGrpSumYestTrunkGrpIdx	OBJECT-TYPE
    SYNTAX	Integer32 (0..2000)
    MAX-ACCESS	not-accessible
    STATUS	current
    DESCRIPTION
	"
	Fld OID Name:	avCmMeasTrkGrpSumYestTrunkGrpIdx
	Fld OID:	enterprises.6889.2.73.8.1.37.1.1.1
	Fld Format:	NA
	Fld(s) Name:	NA
	Fld Descr:	An object that uniquely identifies each Increment of 
			data.
	"
    ::= { avCmMeasTrkGrpSumYestEntry 1 }

avCmMeasTrkGrpSumYestTrunkGroup	OBJECT-TYPE
    SYNTAX	Integer32 (0..2000)
    MAX-ACCESS	read-only
    STATUS	current
    DESCRIPTION
	"
	Fld OID Name:	avCmMeasTrkGrpSumYestTrunkGroup
	Fld OID:	enterprises.6889.2.73.8.1.37.1.1.2
	Fld Form/Rpt:	TRUNK GROUP SUMMARY REPORT
	Fld Format:	Single Field
	Fld(s) Name:	Trunk Group
	Fld Descr:	An object containing the trunk group number.
	"
    ::= { avCmMeasTrkGrpSumYestEntry 2 }

avCmMeasTrkGrpSumYestRunDate	OBJECT-TYPE
    SYNTAX	SnmpAdminString (SIZE (0..27))
    MAX-ACCESS	read-only
    STATUS	current
    DESCRIPTION
	"
	Fld OID Name:	avCmMeasTrkGrpSumYestRunDate
	Fld OID:	enterprises.6889.2.73.8.1.37.1.1.3
	Fld Form/Rpt:	TRUNK GROUP SUMMARY REPORT
	Fld Format:	Single Field
	Fld(s) Name:	Date
	Fld Descr:	An object containing the Date the command was executed.
	"
    ::= { avCmMeasTrkGrpSumYestEntry 3 }

avCmMeasTrkGrpSumYestPeakHour   OBJECT-TYPE
    SYNTAX	Integer32 (0..2300)
    MAX-ACCESS  read-only
    STATUS      current
    DESCRIPTION
        "
        Fld OID Name:   avCmMeasTrkGrpSumYestPeakHour
        Fld OID:        enterprises.6889.2.73.8.1.37.1.1.4
        Fld Form/Rpt:   TRUNK GROUP SUMMARY REPORT
        Fld Format:     Single Field
        Fld(s) Name:    Peak Hour
        Fld Descr:      An object containing the peak traffic hour.
        "
    ::= { avCmMeasTrkGrpSumYestEntry 4 }


avCmMeasTrkGrpSumYestMeasHour	OBJECT-TYPE
    SYNTAX	Integer32 (0..2300)
    MAX-ACCESS	read-only
    STATUS	current
    DESCRIPTION
	"
	Fld OID Name:	avCmMeasTrkGrpSumYestMeasHour
	Fld OID:	enterprises.6889.2.73.8.1.37.1.1.5
	Fld Form/Rpt:	TRUNK GROUP SUMMARY REPORT
	Fld Format:	Single Field
	Fld(s) Name:	Meas Hour
	Fld Descr:	An object containing the Hour the measurement was taken.
	"
    ::= { avCmMeasTrkGrpSumYestEntry 5 }

avCmMeasTrkGrpSumYestGroupSize	OBJECT-TYPE
    SYNTAX	Integer32 (0..255)
    MAX-ACCESS	read-only
    STATUS	current
    DESCRIPTION
	"
	Fld OID Name:	avCmMeasTrkGrpSumYestGroupSize
	Fld OID:	enterprises.6889.2.73.8.1.37.1.1.6
	Fld Form/Rpt:	TRUNK GROUP SUMMARY REPORT
	Fld Format:	Single Field
	Fld(s) Name:	Grp Siz
	Fld Descr:	An object containing the number of administered trunks
			in the trunk group.
	"
    ::= { avCmMeasTrkGrpSumYestEntry 6 }

avCmMeasTrkGrpSumYestTotalUsage	OBJECT-TYPE
    SYNTAX	Integer32 (0..9999)
    MAX-ACCESS	read-only
    STATUS	current
    DESCRIPTION
	"
	Fld OID Name:	avCmMeasTrkGrpSumYestTotalUsage
	Fld OID:	enterprises.6889.2.73.8.1.37.1.1.7
	Fld Form/Rpt:	TRUNK GROUP SUMMARY REPORT
	Fld Format:	Single Field
	Fld(s) Name:	Total Usage
	Fld Descr:	An object containing the total time trunks are busy 
			with calls during the measurement period (in CCS).
	"
    ::= { avCmMeasTrkGrpSumYestEntry 7 }

avCmMeasTrkGrpSumYestTotalSeize	OBJECT-TYPE
    SYNTAX	Integer32 (0..999999)
    MAX-ACCESS	read-only
    STATUS	current
    DESCRIPTION
	"
	Fld OID Name:	avCmMeasTrkGrpSumYestTotalSeize
	Fld OID:	enterprises.6889.2.73.8.1.37.1.1.8
	Fld Form/Rpt:	TRUNK GROUP SUMMARY REPORT
	Fld Format:	Single Field
	Fld(s) Name:	Total Seize
	Fld Descr:	An object containing the number of times a trunk was 
			seized in the group including false starts, don't 
			answer and busy.
	"
    ::= { avCmMeasTrkGrpSumYestEntry 8 }

avCmMeasTrkGrpSumYestIncSeize	OBJECT-TYPE
    SYNTAX	Integer32 (0..999999)
    MAX-ACCESS	read-only
    STATUS	current
    DESCRIPTION
	"
	Fld OID Name:	avCmMeasTrkGrpSumYestIncSeize
	Fld OID:	enterprises.6889.2.73.8.1.37.1.1.9
	Fld Form/Rpt:	TRUNK GROUP SUMMARY REPORT
	Fld Format:	Single Field
	Fld(s) Name:	Inc Seize
	Fld Descr:	An object containing the number of incoming seizures 
			carried on the trunk group.
	"
    ::= { avCmMeasTrkGrpSumYestEntry 9 }

avCmMeasTrkGrpSumYestGrpOvflow	OBJECT-TYPE
    SYNTAX	Integer32 (0..99999)
    MAX-ACCESS	read-only
    STATUS	current
    DESCRIPTION
	"
	Fld OID Name:	avCmMeasTrkGrpSumYestGrpOvflow
	Fld OID:	enterprises.6889.2.73.8.1.37.1.1.10
	Fld Form/Rpt:	TRUNK GROUP SUMMARY REPORT
	Fld Format:	Single Field
	Fld(s) Name:	Grp Ovfl
	Fld Descr:	An object containing the number of calls offered to a 
			trunk group that are not carried or queued.
	"
    ::= { avCmMeasTrkGrpSumYestEntry 10 }

avCmMeasTrkGrpSumYestQueSiz	OBJECT-TYPE
    SYNTAX	Integer32 (0..9999)
    MAX-ACCESS	read-only
    STATUS	current
    DESCRIPTION
	"
	Fld OID Name:	avCmMeasTrkGrpSumYestQueSiz
	Fld OID:	enterprises.6889.2.73.8.1.37.1.1.11
	Fld Form/Rpt:	TRUNK GROUP SUMMARY REPORT
	Fld Format:	Single Field
	Fld(s) Name:	Que Siz
	Fld Descr:	An object containing a number that identifies 
			the number of slots assigned to the trunk group queue.
	"
    ::= { avCmMeasTrkGrpSumYestEntry 11 }

avCmMeasTrkGrpSumYestCallQued	OBJECT-TYPE
    SYNTAX	Integer32 (0..9999)
    MAX-ACCESS	read-only
    STATUS	current
    DESCRIPTION
	"
	Fld OID Name:	avCmMeasTrkGrpSumYestCallQued
	Fld OID:	enterprises.6889.2.73.8.1.37.1.1.12
	Fld Form/Rpt:	TRUNK GROUP SUMMARY REPORT
	Fld Format:	Single Field
	Fld(s) Name:	Call Qued
	Fld Descr:	An object containing the total number of calls that 
			entered the trunk group queue after finding all trunks 
			busy.

	"
    ::= { avCmMeasTrkGrpSumYestEntry 12 }

avCmMeasTrkGrpSumYestQueOvf	OBJECT-TYPE
    SYNTAX	Integer32 (0..9999)
    MAX-ACCESS	read-only
    STATUS	current
    DESCRIPTION
	"
	Fld OID Name:	avCmMeasTrkGrpSumYestQueOvf
	Fld OID:	enterprises.6889.2.73.8.1.37.1.1.13
	Fld Form/Rpt:	TRUNK GROUP SUMMARY REPORT
	Fld Format:	Single Field
	Fld(s) Name:	Que Ovf
	Fld Descr:	An object containing the total number of calls that 
			were not queued because the queue was full.
	"
    ::= { avCmMeasTrkGrpSumYestEntry 13 }

avCmMeasTrkGrpSumYestQueAbd	OBJECT-TYPE
    SYNTAX	Integer32 (0..9999)
    MAX-ACCESS	read-only
    STATUS	current
    DESCRIPTION
	"
	Fld OID Name:	avCmMeasTrkGrpSumYestQueAbd
	Fld OID:	enterprises.6889.2.73.8.1.37.1.1.14
	Fld Form/Rpt:	TRUNK GROUP SUMMARY REPORT
	Fld Format:	Single Field
	Fld(s) Name:	Que Abd
	Fld Descr:	An object containing the total number of calls that 
			were removed from the queue (i.e., due to queue timeout
			 or user cancel).
	"
    ::= { avCmMeasTrkGrpSumYestEntry 14 }

avCmMeasTrkGrpSumYestOutSrv	OBJECT-TYPE
    SYNTAX	Integer32 (0..999)
    MAX-ACCESS	read-only
    STATUS	current
    DESCRIPTION
	"
	Fld OID Name:	avCmMeasTrkGrpSumYestOutSrv
	Fld OID:	enterprises.6889.2.73.8.1.37.1.1.15
	Fld Form/Rpt:	TRUNK GROUP SUMMARY REPORT
	Fld Format:	Single Field
	Fld(s) Name:	Out Srv
	Fld Descr:	An object containing the number of trunks in the group 
			that are out of service (maintenance busy).
	"
    ::= { avCmMeasTrkGrpSumYestEntry 15 }

avCmMeasTrkGrpSumYestPercentAtb	OBJECT-TYPE
    SYNTAX	Integer32 (0..100)
    MAX-ACCESS	read-only
    STATUS	current
    DESCRIPTION
	"
	Fld OID Name:	avCmMeasTrkGrpSumYestPercentAtb
	Fld OID:	enterprises.6889.2.73.8.1.37.1.1.16
	Fld Form/Rpt:	TRUNK GROUP SUMMARY REPORT
	Fld Format:	Single Field
	Fld(s) Name:	% ATB 
	Fld Descr:	An object containing the percentage of time all trunks 
			in the group were simultaneously in use.
	"
    ::= { avCmMeasTrkGrpSumYestEntry 16 }

avCmMeasTrkGrpSumYestPercentOutBlk	OBJECT-TYPE
    SYNTAX	Integer32 (0..100)
    MAX-ACCESS	read-only
    STATUS	current
    DESCRIPTION
	"
	Fld OID Name:	avCmMeasTrkGrpSumYestPercentOutBlk
	Fld OID:	enterprises.6889.2.73.8.1.37.1.1.17
	Fld Form/Rpt:	TRUNK GROUP SUMMARY REPORT
	Fld Format:	Single Field
	Fld(s) Name:	% Out Blk 
	Fld Descr:	An object containing the percentage of offered calls 
			that are not carried on the group.
	"
    ::= { avCmMeasTrkGrpSumYestEntry 17 }

-- ******************** avCmMeasOutTrkLstHr Group *************************

-- MIB GROUP DESCRIPTION

-- MIB Group Name:
--		avCmMeasOutTrkLstHr Group
-- OID:
--		enterprises.6889.2.73.8.1.38
-- Description:
--		The avCmMeasOutTrkLstHr MIB Group uses the "list measurements
--		outage-trunk last-hour" command to retrieve trunk outage data 
--		from the last hour.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements outage-trunk last-hour
-- Form/Report Name:
--		1. TRUNK OUT OF SERVICE REPORT
-- Reference Document:
--		1. A detailed description of the command and form can be
--		   found in document referenced by REF_DOC_4 in the
--		   DOCUMENT REFERENCE SECTION.
-- Command Permission/User-profile:
--		1. No special permissions needed.

avCmMeasOutTrkLstHr	OBJECT IDENTIFIER ::= { avCmObjects 38 }

avCmMeasOutTrkLstHrTable	OBJECT-TYPE
    SYNTAX	SEQUENCE OF AvCmMeasOutTrkLstHrEntry
    MAX-ACCESS	not-accessible
    STATUS	current
    DESCRIPTION
	"
	Fld OID Name:	avCmMeasOutTrkLstHrEntry
	Fld OID:	enterprises.6889.2.73.8.1.38.1
	Fld Form/Rpt:	NA
	Fld Format:	NA
	Fld(s) Name:	NA
	Fld Descr:	A list of the avCmMeasOutTrkLstHr entries
	"
    ::= { avCmMeasOutTrkLstHr 1 }

avCmMeasOutTrkLstHrEntry	OBJECT-TYPE
    SYNTAX	AvCmMeasOutTrkLstHrEntry
    MAX-ACCESS	not-accessible
    STATUS	current
    DESCRIPTION
	"
	Fld OID Name:	avCmMeasOutTrkLstHrEntry
	Fld OID:	enterprises.6889.2.73.8.1.38.1.1
	Fld Form/Rpt:	NA
	Fld Format:	NA
	Fld(s) Name:	NA
	Fld Descr:	A avCmMeasOutTrkLstHr entry containing objects of the
			avCmMeasOutTrkLstHr information sent by the switch.
	"
    INDEX   { avCmMeasOutTrkLstHrTrunkGrpIdx, avCmMeasOutTrkLstHrGrpMbrIdx }
    ::= { avCmMeasOutTrkLstHrTable 1 }

AvCmMeasOutTrkLstHrEntry ::= SEQUENCE {
		avCmMeasOutTrkLstHrTrunkGrpIdx
		    Integer32,
		avCmMeasOutTrkLstHrGrpMbrIdx
		    Integer32,
		avCmMeasOutTrkLstHrTrunkGroup
		    Integer32,
		avCmMeasOutTrkLstHrRunDate
		    SnmpAdminString,
		avCmMeasOutTrkLstHrGrpSize
		    Integer32,
		avCmMeasOutTrkLstHrGrpMbr
		    Integer32,
		avCmMeasOutTrkLstHrOutages
		    Integer32
		}

avCmMeasOutTrkLstHrTrunkGrpIdx	OBJECT-TYPE
    SYNTAX	Integer32 (0..2000)
    MAX-ACCESS	not-accessible
    STATUS	current
    DESCRIPTION
	"
	Fld OID Name:	avCmMeasOutTrkLstHrTrunkGrpIdx
	Fld OID:	enterprises.6889.2.73.8.1.38.1.1.1
	Fld Format:	NA
	Fld(s) Name:	NA
	Fld Descr:	An object that uniquely identifies each Increment of 
			data.
	"
    ::= { avCmMeasOutTrkLstHrEntry 1 }

avCmMeasOutTrkLstHrGrpMbrIdx	OBJECT-TYPE
    SYNTAX	Integer32 (0..255)
    MAX-ACCESS	not-accessible
    STATUS	current
    DESCRIPTION
	"
	Fld OID Name:	avCmMeasOutTrkLstHrGrpMbrIdx
	Fld OID:	enterprises.6889.2.73.8.1.38.1.1.2
	Fld Format:	NA
	Fld(s) Name:	NA
	Fld Descr:	An object that uniquely identifies each Increment of 
			data.
	"
    ::= { avCmMeasOutTrkLstHrEntry 2 }

avCmMeasOutTrkLstHrTrunkGroup	OBJECT-TYPE
    SYNTAX	Integer32 (0..2000)
    MAX-ACCESS	read-only
    STATUS	current
    DESCRIPTION
	"
	Fld OID Name:	avCmMeasOutTrkLstHrTrunkGroup
	Fld OID:	enterprises.6889.2.73.8.1.38.1.1.3
	Fld Form/Rpt:	TRUNK OUT OF SERVICE REPORT
	Fld Format:	Single Field
	Fld(s) Name:	Grp No.
	Fld Descr:	An object containing the trunk-group number.
	"
    ::= { avCmMeasOutTrkLstHrEntry 3 }

avCmMeasOutTrkLstHrRunDate	OBJECT-TYPE
    SYNTAX	SnmpAdminString (SIZE (0..27))
    MAX-ACCESS	read-only
    STATUS	current
    DESCRIPTION
	"
	Fld OID Name:	avCmMeasOutTrkLstHrRunDate
	Fld OID:	enterprises.6889.2.73.8.1.38.1.1.4
	Fld Form/Rpt:	TRUNK OUT OF SERVICE REPORT
	Fld Format:	Single Field
	Fld(s) Name:	Date
	Fld Descr:	An object containing the Date the command was executed.
	"
    ::= { avCmMeasOutTrkLstHrEntry 4 }

avCmMeasOutTrkLstHrGrpSize   OBJECT-TYPE
    SYNTAX	Integer32 (0..999)
    MAX-ACCESS  read-only
    STATUS      current
    DESCRIPTION
        "
        Fld OID Name:   avCmMeasOutTrkLstHrGrpSize
        Fld OID:        enterprises.6889.2.73.8.1.38.1.1.5
        Fld Form/Rpt:   TRUNK OUT OF SERVICE REPORT
        Fld Format:     Single Field
        Fld(s) Name:    Grp Size
        Fld Descr:      An object containing the number of members.
        "
    ::= { avCmMeasOutTrkLstHrEntry 5 }


avCmMeasOutTrkLstHrGrpMbr	OBJECT-TYPE
    SYNTAX	Integer32 (0..2300)
    MAX-ACCESS	read-only
    STATUS	current
    DESCRIPTION
	"
	Fld OID Name:	avCmMeasOutTrkLstHrGrpMbr
	Fld OID:	enterprises.6889.2.73.8.1.38.1.1.6
	Fld Form/Rpt:	TRUNK OUT OF SERVICE REPORT
	Fld Format:	Single Field
	Fld(s) Name:	Grp Mbr#
	Fld Descr:	An object containing the member that was out of service.
	"
    ::= { avCmMeasOutTrkLstHrEntry 6 }

avCmMeasOutTrkLstHrOutages	OBJECT-TYPE
    SYNTAX	Integer32 (0..999)
    MAX-ACCESS	read-only
    STATUS	current
    DESCRIPTION
	"
	Fld OID Name:	avCmMeasOutTrkLstHrOutages
	Fld OID:	enterprises.6889.2.73.8.1.38.1.1.7
	Fld Form/Rpt:	TRUNK OUT OF SERVICE REPORT
	Fld Format:	Single Field
	Fld(s) Name:	#Sampled Outages
	Fld Descr:	An object containing the number of sampled outages
			for the trunk group member.
	"
    ::= { avCmMeasOutTrkLstHrEntry 7 }


-- ******************** avCmMeasOutTrkToday Group *************************

-- MIB GROUP DESCRIPTION

-- MIB Group Name:
--		avCmMeasOutTrkToday Group
-- OID:
--		enterprises.6889.2.73.8.1.39
-- Description:
--		The avCmMeasOutTrkToday MIB Group uses the "list measurements
--		outage-trunk today" command to retrieve trunk outage data 
--		from the today.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements outage-trunk today
-- Form/Report Name:
--		1. TRUNK OUT OF SERVICE REPORT
-- Reference Document:
--		1. A detailed description of the command and form can be
--		   found in document referenced by REF_DOC_4 in the
--		   DOCUMENT REFERENCE SECTION.
-- Command Permission/User-profile:
--		1. No special permissions needed.

avCmMeasOutTrkToday	OBJECT IDENTIFIER ::= { avCmObjects 39 }

avCmMeasOutTrkTodayTable	OBJECT-TYPE
    SYNTAX	SEQUENCE OF AvCmMeasOutTrkTodayEntry
    MAX-ACCESS	not-accessible
    STATUS	current
    DESCRIPTION
	"
	Fld OID Name:	avCmMeasOutTrkTodayEntry
	Fld OID:	enterprises.6889.2.73.8.1.39.1
	Fld Form/Rpt:	NA
	Fld Format:	NA
	Fld(s) Name:	NA
	Fld Descr:	A list of the avCmMeasOutTrkToday entries
	"
    ::= { avCmMeasOutTrkToday 1 }

avCmMeasOutTrkTodayEntry	OBJECT-TYPE
    SYNTAX	AvCmMeasOutTrkTodayEntry
    MAX-ACCESS	not-accessible
    STATUS	current
    DESCRIPTION
	"
	Fld OID Name:	avCmMeasOutTrkTodayEntry
	Fld OID:	enterprises.6889.2.73.8.1.39.1.1
	Fld Form/Rpt:	NA
	Fld Format:	NA
	Fld(s) Name:	NA
	Fld Descr:	A avCmMeasOutTrkToday entry containing objects of the
			avCmMeasOutTrkToday information sent by the switch.
	"
    INDEX    { avCmMeasOutTrkTodayTrunkGrpIdx, avCmMeasOutTrkTodayGrpMbrIdx }
    ::= { avCmMeasOutTrkTodayTable 1 }

AvCmMeasOutTrkTodayEntry ::= SEQUENCE {
		avCmMeasOutTrkTodayTrunkGrpIdx
		    Integer32,
		avCmMeasOutTrkTodayGrpMbrIdx
		    Integer32,
		avCmMeasOutTrkTodayTrunkGroup
		    Integer32,
		avCmMeasOutTrkTodayRunDate
		    SnmpAdminString,
		avCmMeasOutTrkTodayGrpSize
		    Integer32,
		avCmMeasOutTrkTodayGrpMbr
		    Integer32,
		avCmMeasOutTrkTodayOutages
		    Integer32
		}

avCmMeasOutTrkTodayTrunkGrpIdx	OBJECT-TYPE
    SYNTAX	Integer32 (0..2000)
    MAX-ACCESS	not-accessible
    STATUS	current
    DESCRIPTION
	"
	Fld OID Name:	avCmMeasOutTrkTodayTrunkGrpIdx
	Fld OID:	enterprises.6889.2.73.8.1.39.1.1.1
	Fld Format:	NA
	Fld(s) Name:	NA
	Fld Descr:	An object that uniquely identifies each Increment of 
			data.
	"
    ::= { avCmMeasOutTrkTodayEntry 1 }

avCmMeasOutTrkTodayGrpMbrIdx	OBJECT-TYPE
    SYNTAX	Integer32 (0..255)
    MAX-ACCESS	not-accessible
    STATUS	current
    DESCRIPTION
	"
	Fld OID Name:	avCmMeasOutTrkTodayGrpMbrIdx
	Fld OID:	enterprises.6889.2.73.8.1.39.1.1.2
	Fld Format:	NA
	Fld(s) Name:	NA
	Fld Descr:	An object that uniquely identifies each Increment of 
			data.
	"
    ::= { avCmMeasOutTrkTodayEntry 2 }

avCmMeasOutTrkTodayTrunkGroup	OBJECT-TYPE
    SYNTAX	Integer32 (0..2000)
    MAX-ACCESS	read-only
    STATUS	current
    DESCRIPTION
	"
	Fld OID Name:	avCmMeasOutTrkTodayTrunkGroup
	Fld OID:	enterprises.6889.2.73.8.1.39.1.1.3
	Fld Form/Rpt:	TRUNK OUT OF SERVICE REPORT
	Fld Format:	Single Field
	Fld(s) Name:	Grp No.
	Fld Descr:	An object containing the trunk group number.
	"
    ::= { avCmMeasOutTrkTodayEntry 3 }

avCmMeasOutTrkTodayRunDate	OBJECT-TYPE
    SYNTAX	SnmpAdminString (SIZE (0..27))
    MAX-ACCESS	read-only
    STATUS	current
    DESCRIPTION
	"
	Fld OID Name:	avCmMeasOutTrkTodayRunDate
	Fld OID:	enterprises.6889.2.73.8.1.39.1.1.4
	Fld Form/Rpt:	TRUNK OUT OF SERVICE REPORT
	Fld Format:	Single Field
	Fld(s) Name:	Date
	Fld Descr:	An object containing the Date the command was executed.
	"
    ::= { avCmMeasOutTrkTodayEntry 4 }

avCmMeasOutTrkTodayGrpSize   OBJECT-TYPE
    SYNTAX	Integer32 (0..999)
    MAX-ACCESS  read-only
    STATUS      current
    DESCRIPTION
        "
        Fld OID Name:   avCmMeasOutTrkTodayGrpSize
        Fld OID:        enterprises.6889.2.73.8.1.39.1.1.5
        Fld Form/Rpt:   TRUNK OUT OF SERVICE REPORT
        Fld Format:     Single Field
        Fld(s) Name:    Grp Size
        Fld Descr:      An object containing the number of members in the group.
        "
    ::= { avCmMeasOutTrkTodayEntry 5 }


avCmMeasOutTrkTodayGrpMbr	OBJECT-TYPE
    SYNTAX	Integer32 (0..2300)
    MAX-ACCESS	read-only
    STATUS	current
    DESCRIPTION
	"
	Fld OID Name:	avCmMeasOutTrkTodayGrpMbr
	Fld OID:	enterprises.6889.2.73.8.1.39.1.1.6
	Fld Form/Rpt:	TRUNK OUT OF SERVICE REPORT
	Fld Format:	Single Field
	Fld(s) Name:	Grp Mbr#
	Fld Descr:	An object containing the member that was out of service.
	"
    ::= { avCmMeasOutTrkTodayEntry 6 }

avCmMeasOutTrkTodayOutages	OBJECT-TYPE
    SYNTAX	Integer32 (0..999)
    MAX-ACCESS	read-only
    STATUS	current
    DESCRIPTION
	"
	Fld OID Name:	avCmMeasOutTrkTodayOutages
	Fld OID:	enterprises.6889.2.73.8.1.39.1.1.7
	Fld Form/Rpt:	TRUNK OUT OF SERVICE REPORT
	Fld Format:	Single Field
	Fld(s) Name:	#Sampled Outages
	Fld Descr:	An object containing the number of sampled outages
			for the trunk group member.
	"
    ::= { avCmMeasOutTrkTodayEntry 7 }

-- ******************** avCmMeasOutTrkYest Group *************************

-- MIB GROUP DESCRIPTION

-- MIB Group Name:
--		avCmMeasOutTrkYest Group
-- OID:
--		enterprises.6889.2.73.8.1.40
-- Description:
--		The avCmMeasOutTrkYest MIB Group uses the "list measurements
--		outage-trunk yesterday" command to retrieve trunk outage data 
--		from yesterday.
--		
-- Releases Supported:
--		CM6.3.100 and greater
-- Polling Type:
--		Performance/Utilization
-- Polling Interval:
--		No more than once a day because the data is only updated
--		after the beginning of the new day.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements outage-trunk yesterday
-- Form/Report Name:
--		1. TRUNK OUT OF SERVICE REPORT
-- Reference Document:
--		1. A detailed description of the command and form can be
--		   found in document referenced by REF_DOC_4 in the
--		   DOCUMENT REFERENCE SECTION.
-- Command Permission/User-profile:
--		1. No special permissions needed.

avCmMeasOutTrkYest	OBJECT IDENTIFIER ::= { avCmObjects 40 }

avCmMeasOutTrkYestTable	OBJECT-TYPE
    SYNTAX	SEQUENCE OF AvCmMeasOutTrkYestEntry
    MAX-ACCESS	not-accessible
    STATUS	current
    DESCRIPTION
	"
	Fld OID Name:	avCmMeasOutTrkYestEntry
	Fld OID:	enterprises.6889.2.73.8.1.40.1
	Fld Form/Rpt:	NA
	Fld Format:	NA
	Fld(s) Name:	NA
	Fld Descr:	A list of the avCmMeasOutTrkYest entries
	"
    ::= { avCmMeasOutTrkYest 1 }

avCmMeasOutTrkYestEntry	OBJECT-TYPE
    SYNTAX	AvCmMeasOutTrkYestEntry
    MAX-ACCESS	not-accessible
    STATUS	current
    DESCRIPTION
	"
	Fld OID Name:	avCmMeasOutTrkYestEntry
	Fld OID:	enterprises.6889.2.73.8.1.40.1.1
	Fld Form/Rpt:	NA
	Fld Format:	NA
	Fld(s) Name:	NA
	Fld Descr:	A avCmMeasOutTrkYest entry containing objects of the
			avCmMeasOutTrkYest information sent by the switch.
	"
    INDEX    { avCmMeasOutTrkYestTrunkGrpIdx, avCmMeasOutTrkYestGrpMbrIdx }
    ::= { avCmMeasOutTrkYestTable 1 }

AvCmMeasOutTrkYestEntry ::= SEQUENCE {
		avCmMeasOutTrkYestTrunkGrpIdx
		    Integer32,
		avCmMeasOutTrkYestGrpMbrIdx
		    Integer32,
		avCmMeasOutTrkYestTrunkGroup
		    Integer32,
		avCmMeasOutTrkYestRunDate
		    SnmpAdminString,
		avCmMeasOutTrkYestGrpSize
		    Integer32,
		avCmMeasOutTrkYestGrpMbr
		    Integer32,
		avCmMeasOutTrkYestOutages
		    Integer32
		}

avCmMeasOutTrkYestTrunkGrpIdx	OBJECT-TYPE
    SYNTAX	Integer32 (0..2000)
    MAX-ACCESS	not-accessible
    STATUS	current
    DESCRIPTION
	"
	Fld OID Name:	avCmMeasOutTrkYestTrunkGrpIdx
	Fld OID:	enterprises.6889.2.73.8.1.40.1.1.1
	Fld Format:	NA
	Fld(s) Name:	NA
	Fld Descr:	An object that uniquely identifies each Increment of 
			data.
	"
    ::= { avCmMeasOutTrkYestEntry 1 }

avCmMeasOutTrkYestGrpMbrIdx	OBJECT-TYPE
    SYNTAX	Integer32 (0..255)
    MAX-ACCESS	not-accessible
    STATUS	current
    DESCRIPTION
	"
	Fld OID Name:	avCmMeasOutTrkYestGrpMbrIdx
	Fld OID:	enterprises.6889.2.73.8.1.40.1.1.2
	Fld Format:	NA
	Fld(s) Name:	NA
	Fld Descr:	An object that uniquely identifies each Increment of 
			data.
	"
    ::= { avCmMeasOutTrkYestEntry 2 }

avCmMeasOutTrkYestTrunkGroup	OBJECT-TYPE
    SYNTAX	Integer32 (0..2000)
    MAX-ACCESS	read-only
    STATUS	current
    DESCRIPTION
	"
	Fld OID Name:	avCmMeasOutTrkYestTrunkGroup
	Fld OID:	enterprises.6889.2.73.8.1.40.1.1.3
	Fld Form/Rpt:	TRUNK OUT OF SERVICE REPORT
	Fld Format:	Single Field
	Fld(s) Name:	Trunk Group
	Fld Descr:	An object containing the trunk-group number.
	"
    ::= { avCmMeasOutTrkYestEntry 3 }

avCmMeasOutTrkYestRunDate	OBJECT-TYPE
    SYNTAX	SnmpAdminString (SIZE (0..27))
    MAX-ACCESS	read-only
    STATUS	current
    DESCRIPTION
	"
	Fld OID Name:	avCmMeasOutTrkYestRunDate
	Fld OID:	enterprises.6889.2.73.8.1.40.1.1.4
	Fld Form/Rpt:	TRUNK OUT OF SERVICE REPORT
	Fld Format:	Single Field
	Fld(s) Name:	Date
	Fld Descr:	An object containing the Date the command was executed.
	"
    ::= { avCmMeasOutTrkYestEntry 4 }

avCmMeasOutTrkYestGrpSize   OBJECT-TYPE
    SYNTAX	Integer32 (0..999)
    MAX-ACCESS  read-only
    STATUS      current
    DESCRIPTION
        "
        Fld OID Name:   avCmMeasOutTrkYestGrpSize
        Fld OID:        enterprises.6889.2.73.8.1.40.1.1.5
        Fld Form/Rpt:   TRUNK OUT OF SERVICE REPORT
        Fld Format:     Single Field
        Fld(s) Name:    Grp Size
        Fld Descr:      An object containing the number of members.
        "
    ::= { avCmMeasOutTrkYestEntry 5 }


avCmMeasOutTrkYestGrpMbr	OBJECT-TYPE
    SYNTAX	Integer32 (0..2300)
    MAX-ACCESS	read-only
    STATUS	current
    DESCRIPTION
	"
	Fld OID Name:	avCmMeasOutTrkYestGrpMbr
	Fld OID:	enterprises.6889.2.73.8.1.40.1.1.6
	Fld Form/Rpt:	TRUNK OUT OF SERVICE REPORT
	Fld Format:	Single Field
	Fld(s) Name:	Grp Mbr
	Fld Descr:	An object containing the member that was out of service.
	"
    ::= { avCmMeasOutTrkYestEntry 6 }

avCmMeasOutTrkYestOutages	OBJECT-TYPE
    SYNTAX	Integer32 (0..999)
    MAX-ACCESS	read-only
    STATUS	current
    DESCRIPTION
	"
	Fld OID Name:	avCmMeasOutTrkYestOutages
	Fld OID:	enterprises.6889.2.73.8.1.40.1.1.7
	Fld Form/Rpt:	TRUNK OUT OF SERVICE REPORT
	Fld Format:	Single Field
	Fld(s) Name:	Sampled Outages
	Fld Descr:	An object containing the number of outages
			for the trunk member.
	"
    ::= { avCmMeasOutTrkYestEntry 7 }



-- ******************** avCmMeasLightUseTrkLstHr Group *************************

-- MIB GROUP DESCRIPTION

-- MIB Group Name:
--		avCmMeasLightUseTrkLstHr Group
-- OID:
--		enterprises.6889.2.73.8.1.41
-- Description:
--		The avCmMeasLightUseTrkLstHr MIB Group uses the 
--		"list measurements lightly-used-trunk last-hour" command to 
--		retrieve lightly used trunk data from the last hour.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements lightly-used-trunk last-hour
-- Form/Report Name:
--		1. TRUNK LIGHTLY USED REPORT
-- Reference Document:
--		1. A detailed description of the command and form can be
--		   found in document referenced by REF_DOC_4 in the
--		   DOCUMENT REFERENCE SECTION.
-- Command Permission/User-profile:
--		1. No special permissions needed.

avCmMeasLightUseTrkLstHr	OBJECT IDENTIFIER ::= { avCmObjects 41 }

avCmMeasLightUseTrkLstHrTable	OBJECT-TYPE
    SYNTAX	SEQUENCE OF AvCmMeasLightUseTrkLstHrEntry
    MAX-ACCESS	not-accessible
    STATUS	current
    DESCRIPTION
	"
	Fld OID Name:	avCmMeasLightUseTrkLstHrEntry
	Fld OID:	enterprises.6889.2.73.8.1.41.1
	Fld Form/Rpt:	NA
	Fld Format:	NA
	Fld(s) Name:	NA
	Fld Descr:	A list of the avCmMeasLightUseTrkLstHr entries
	"
    ::= { avCmMeasLightUseTrkLstHr 1 }

avCmMeasLightUseTrkLstHrEntry	OBJECT-TYPE
    SYNTAX	AvCmMeasLightUseTrkLstHrEntry
    MAX-ACCESS	not-accessible
    STATUS	current
    DESCRIPTION
	"
	Fld OID Name:	avCmMeasLightUseTrkLstHrEntry
	Fld OID:	enterprises.6889.2.73.8.1.41.1.1
	Fld Form/Rpt:	NA
	Fld Format:	NA
	Fld(s) Name:	NA
	Fld Descr:	A avCmMeasLightUseTrkLstHr entry containing objects of the
			avCmMeasLightUseTrkLstHr information sent by the switch.
	"
  INDEX {avCmMeasLightUseTrkLstHrTrunkGrpIdx, avCmMeasLightUseTrkLstHrGrpMbrIdx}
    ::= { avCmMeasLightUseTrkLstHrTable 1 }

AvCmMeasLightUseTrkLstHrEntry ::= SEQUENCE {
		avCmMeasLightUseTrkLstHrTrunkGrpIdx
		    Integer32,
		avCmMeasLightUseTrkLstHrGrpMbrIdx
		    Integer32,
		avCmMeasLightUseTrkLstHrTrunkGroup
		    Integer32,
		avCmMeasLightUseTrkLstHrRunDate
		    SnmpAdminString,
		avCmMeasLightUseTrkLstHrGrpSize
		    Integer32,
		avCmMeasLightUseTrkLstHrGrpMbr
		    Integer32,
		avCmMeasLightUseTrkLstHrCallsCarried
		    Integer32
		}

avCmMeasLightUseTrkLstHrTrunkGrpIdx	OBJECT-TYPE
    SYNTAX	Integer32 (0..2000)
    MAX-ACCESS	not-accessible
    STATUS	current
    DESCRIPTION
	"
	Fld OID Name:	avCmMeasLightUseTrkLstHrTrunkGrpIdx
	Fld OID:	enterprises.6889.2.73.8.1.41.1.1.1
	Fld Format:	NA
	Fld(s) Name:	NA
	Fld Descr:	An object that uniquely identifies each Increment of 
			data.
	"
    ::= { avCmMeasLightUseTrkLstHrEntry 1 }

avCmMeasLightUseTrkLstHrGrpMbrIdx	OBJECT-TYPE
    SYNTAX	Integer32 (0..255)
    MAX-ACCESS	not-accessible
    STATUS	current
    DESCRIPTION
	"
	Fld OID Name:	avCmMeasLightUseTrkLstHrGrpMbrIdx
	Fld OID:	enterprises.6889.2.73.8.1.41.1.1.2
	Fld Format:	NA
	Fld(s) Name:	NA
	Fld Descr:	An object that uniquely identifies each Increment of 
			data.
	"
    ::= { avCmMeasLightUseTrkLstHrEntry 2 }

avCmMeasLightUseTrkLstHrTrunkGroup	OBJECT-TYPE
    SYNTAX	Integer32 (0..2000)
    MAX-ACCESS	read-only
    STATUS	current
    DESCRIPTION
	"
	Fld OID Name:	avCmMeasLightUseTrkLstHrTrunkGroup
	Fld OID:	enterprises.6889.2.73.8.1.41.1.1.3
	Fld Form/Rpt:	TRUNK LIGHTLY USED REPORT
	Fld Format:	Single Field
	Fld(s) Name:	Trunk Group
	Fld Descr:	An object containing the trunk-group number.
	"
    ::= { avCmMeasLightUseTrkLstHrEntry 3 }

avCmMeasLightUseTrkLstHrRunDate	OBJECT-TYPE
    SYNTAX	SnmpAdminString (SIZE (0..27))
    MAX-ACCESS	read-only
    STATUS	current
    DESCRIPTION
	"
	Fld OID Name:	avCmMeasLightUseTrkLstHrRunDate
	Fld OID:	enterprises.6889.2.73.8.1.41.1.1.4
	Fld Form/Rpt:	TRUNK LIGHTLY USED REPORT
	Fld Format:	Single Field
	Fld(s) Name:	Date
	Fld Descr:	An object containing the Date the command was executed.
	"
    ::= { avCmMeasLightUseTrkLstHrEntry 4 }

avCmMeasLightUseTrkLstHrGrpSize   OBJECT-TYPE
    SYNTAX	Integer32 (0..999)
    MAX-ACCESS  read-only
    STATUS      current
    DESCRIPTION
        "
        Fld OID Name:   avCmMeasLightUseTrkLstHrGrpSize
        Fld OID:        enterprises.6889.2.73.8.1.41.1.1.5
        Fld Form/Rpt:   TRUNK LIGHTLY USED REPORT
        Fld Format:     Single Field
        Fld(s) Name:    Grp Size
        Fld Descr:      An object containing the number of members.
        "
    ::= { avCmMeasLightUseTrkLstHrEntry 5 }


avCmMeasLightUseTrkLstHrGrpMbr	OBJECT-TYPE
    SYNTAX	Integer32 (0..999)
    MAX-ACCESS	read-only
    STATUS	current
    DESCRIPTION
	"
	Fld OID Name:	avCmMeasLightUseTrkLstHrGrpMbr
	Fld OID:	enterprises.6889.2.73.8.1.41.1.1.6
	Fld Form/Rpt:	TRUNK LIGHTLY USED REPORT
	Fld Format:	Single Field
	Fld(s) Name:	Grp Mbr#
	Fld Descr:	An object containing the member that is lightly used.
	"
    ::= { avCmMeasLightUseTrkLstHrEntry 6 }

avCmMeasLightUseTrkLstHrCallsCarried	OBJECT-TYPE
    SYNTAX	Integer32 (0..9999)
    MAX-ACCESS	read-only
    STATUS	current
    DESCRIPTION
	"
	Fld OID Name:	avCmMeasLightUseTrkLstHrCallsCarried
	Fld OID:	enterprises.6889.2.73.8.1.41.1.1.7
	Fld Form/Rpt:	TRUNK LIGHTLY USED REPORT
	Fld Format:	Single Field
	Fld(s) Name:	Calls Carried
	Fld Descr:	An object containing the number of calls carried
			over the trunk member.
	"
    ::= { avCmMeasLightUseTrkLstHrEntry 7 }

-- ******************** avCmMeasLightUseTrkToday Group *************************

-- MIB GROUP DESCRIPTION

-- MIB Group Name:
--		avCmMeasLightUseTrkToday Group
-- OID:
--		enterprises.6889.2.73.8.1.42
-- Description:
--		The avCmMeasLightUseTrkToday MIB Group uses the 
--		"list measurements lightly-used-trunk today" command to 
--		retrieve lightly used trunk data from today.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements lightly-used-trunk today
-- Form/Report Name:
--		1. TRUNK LIGHTLY USED REPORT
-- Reference Document:
--		1. A detailed description of the command and form can be
--		   found in document referenced by REF_DOC_4 in the
--		   DOCUMENT REFERENCE SECTION.
-- Command Permission/User-profile:
--		1. No special permissions needed.

avCmMeasLightUseTrkToday	OBJECT IDENTIFIER ::= { avCmObjects 42 }

avCmMeasLightUseTrkTodayTable	OBJECT-TYPE
    SYNTAX	SEQUENCE OF AvCmMeasLightUseTrkTodayEntry
    MAX-ACCESS	not-accessible
    STATUS	current
    DESCRIPTION
	"
	Fld OID Name:	avCmMeasLightUseTrkTodayEntry
	Fld OID:	enterprises.6889.2.73.8.1.42.1
	Fld Form/Rpt:	NA
	Fld Format:	NA
	Fld(s) Name:	NA
	Fld Descr:	A list of the avCmMeasLightUseTrkToday entries
	"
    ::= { avCmMeasLightUseTrkToday 1 }

avCmMeasLightUseTrkTodayEntry	OBJECT-TYPE
    SYNTAX	AvCmMeasLightUseTrkTodayEntry
    MAX-ACCESS	not-accessible
    STATUS	current
    DESCRIPTION
	"
	Fld OID Name:	avCmMeasLightUseTrkTodayEntry
	Fld OID:	enterprises.6889.2.73.8.1.42.1.1
	Fld Form/Rpt:	NA
	Fld Format:	NA
	Fld(s) Name:	NA
	Fld Descr:	A avCmMeasLightUseTrkToday entry containing objects of the
			avCmMeasLightUseTrkToday information sent by the switch.
	"
    INDEX    { avCmMeasLightUseTrkTodayTrunkGrpIdx,
				avCmMeasLightUseTrkTodayGrpMbrIdx }
    ::= { avCmMeasLightUseTrkTodayTable 1 }

AvCmMeasLightUseTrkTodayEntry ::= SEQUENCE {
		avCmMeasLightUseTrkTodayTrunkGrpIdx
		    Integer32,
		avCmMeasLightUseTrkTodayGrpMbrIdx
		    Integer32,
		avCmMeasLightUseTrkTodayTrunkGroup
		    Integer32,
		avCmMeasLightUseTrkTodayRunDate
		    SnmpAdminString,
		avCmMeasLightUseTrkTodayGrpSize
		    Integer32,
		avCmMeasLightUseTrkTodayGrpMbr
		    Integer32,
		avCmMeasLightUseTrkTodayCallsCarried
		    Integer32
		}

avCmMeasLightUseTrkTodayTrunkGrpIdx	OBJECT-TYPE
    SYNTAX	Integer32 (0..2000)
    MAX-ACCESS	not-accessible
    STATUS	current
    DESCRIPTION
	"
	Fld OID Name:	avCmMeasLightUseTrkTodayTrunkGrpIdx
	Fld OID:	enterprises.6889.2.73.8.1.42.1.1.1
	Fld Format:	NA
	Fld(s) Name:	NA
	Fld Descr:	An object that uniquely identifies each Increment of 
			data.
	"
    ::= { avCmMeasLightUseTrkTodayEntry 1 }

avCmMeasLightUseTrkTodayGrpMbrIdx	OBJECT-TYPE
    SYNTAX	Integer32 (0..255)
    MAX-ACCESS	not-accessible
    STATUS	current
    DESCRIPTION
	"
	Fld OID Name:	avCmMeasLightUseTrkTodayGrpMbrIdx
	Fld OID:	enterprises.6889.2.73.8.1.42.1.1.2
	Fld Format:	NA
	Fld(s) Name:	NA
	Fld Descr:	An object that uniquely identifies each Increment of 
			data.
	"
    ::= { avCmMeasLightUseTrkTodayEntry 2 }

avCmMeasLightUseTrkTodayTrunkGroup	OBJECT-TYPE
    SYNTAX	Integer32 (0..2000)
    MAX-ACCESS	read-only
    STATUS	current
    DESCRIPTION
	"
	Fld OID Name:	avCmMeasLightUseTrkTodayTrunkGroup
	Fld OID:	enterprises.6889.2.73.8.1.42.1.1.3
	Fld Form/Rpt:	TRUNK LIGHTLY USED REPORT
	Fld Format:	Single Field
	Fld(s) Name:	Trunk Group
	Fld Descr:	An object containing the trunk-group number.
	"
    ::= { avCmMeasLightUseTrkTodayEntry 3 }

avCmMeasLightUseTrkTodayRunDate	OBJECT-TYPE
    SYNTAX	SnmpAdminString (SIZE (0..27))
    MAX-ACCESS	read-only
    STATUS	current
    DESCRIPTION
	"
	Fld OID Name:	avCmMeasLightUseTrkTodayRunDate
	Fld OID:	enterprises.6889.2.73.8.1.42.1.1.4
	Fld Form/Rpt:	TRUNK LIGHTLY USED REPORT
	Fld Format:	Single Field
	Fld(s) Name:	Date
	Fld Descr:	An object containing the Date the command was executed.
	"
    ::= { avCmMeasLightUseTrkTodayEntry 4 }

avCmMeasLightUseTrkTodayGrpSize   OBJECT-TYPE
    SYNTAX	Integer32 (0..999)
    MAX-ACCESS  read-only
    STATUS      current
    DESCRIPTION
        "
        Fld OID Name:   avCmMeasLightUseTrkTodayGrpSize
        Fld OID:        enterprises.6889.2.73.8.1.42.1.1.5
        Fld Form/Rpt:   TRUNK LIGHTLY USED REPORT
        Fld Format:     Single Field
        Fld(s) Name:    Grp Size
        Fld Descr:      An object containing the number of members.
        "
    ::= { avCmMeasLightUseTrkTodayEntry 5 }


avCmMeasLightUseTrkTodayGrpMbr	OBJECT-TYPE
    SYNTAX	Integer32 (0..999)
    MAX-ACCESS	read-only
    STATUS	current
    DESCRIPTION
	"
	Fld OID Name:	avCmMeasLightUseTrkTodayGrpMbr
	Fld OID:	enterprises.6889.2.73.8.1.42.1.1.6
	Fld Form/Rpt:	TRUNK LIGHTLY USED REPORT
	Fld Format:	Single Field
	Fld(s) Name:	Grp Mbr#
	Fld Descr:	An object containing the member that is lightly used.
	"
    ::= { avCmMeasLightUseTrkTodayEntry 6 }

avCmMeasLightUseTrkTodayCallsCarried	OBJECT-TYPE
    SYNTAX	Integer32 (0..9999)
    MAX-ACCESS	read-only
    STATUS	current
    DESCRIPTION
	"
	Fld OID Name:	avCmMeasLightUseTrkTodayCallsCarried
	Fld OID:	enterprises.6889.2.73.8.1.42.1.1.7
	Fld Form/Rpt:	TRUNK LIGHTLY USED REPORT
	Fld Format:	Single Field
	Fld(s) Name:	Calls Carried
	Fld Descr:	An object containing the number of calls carried
			over the trunk member.
	"
    ::= { avCmMeasLightUseTrkTodayEntry 7 }


-- ******************** avCmMeasLightUseTrkYest Group *************************

-- MIB GROUP DESCRIPTION

-- MIB Group Name:
--		avCmMeasLightUseTrkYest Group
-- OID:
--		enterprises.6889.2.73.8.1.43
-- Description:
--		The avCmMeasLightUseTrkYest MIB Group uses the 
--		"list measurements lightly-used-trunk yesterday" command to 
--		retrieve lightly used trunk data from yesterday.
--		
-- Releases Supported:
--		CM6.3.100 and greater
-- Polling Type:
--		Performance/Utilization
-- Polling Interval:
--		No more than once a  day because the data is only updated
--		after the beginning of the day.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements lightly-used-trunk yesterday
-- Form/Report Name:
--		1. TRUNK LIGHTLY USED REPORT
-- Reference Document:
--		1. A detailed description of the command and form can be
--		   found in document referenced by REF_DOC_4 in the
--		   DOCUMENT REFERENCE SECTION.
-- Command Permission/User-profile:
--		1. No special permissions needed.

avCmMeasLightUseTrkYest	OBJECT IDENTIFIER ::= { avCmObjects 43 }

avCmMeasLightUseTrkYestTable	OBJECT-TYPE
    SYNTAX	SEQUENCE OF AvCmMeasLightUseTrkYestEntry
    MAX-ACCESS	not-accessible
    STATUS	current
    DESCRIPTION
	"
	Fld OID Name:	avCmMeasLightUseTrkYestEntry
	Fld OID:	enterprises.6889.2.73.8.1.43.1
	Fld Form/Rpt:	NA
	Fld Format:	NA
	Fld(s) Name:	NA
	Fld Descr:	A list of the avCmMeasLightUseTrkYest entries
	"
    ::= { avCmMeasLightUseTrkYest 1 }

avCmMeasLightUseTrkYestEntry	OBJECT-TYPE
    SYNTAX	AvCmMeasLightUseTrkYestEntry
    MAX-ACCESS	not-accessible
    STATUS	current
    DESCRIPTION
	"
	Fld OID Name:	avCmMeasLightUseTrkYestEntry
	Fld OID:	enterprises.6889.2.73.8.1.43.1.1
	Fld Form/Rpt:	NA
	Fld Format:	NA
	Fld(s) Name:	NA
	Fld Descr:	A avCmMeasLightUseTrkYest entry containing objects of the
			avCmMeasLightUseTrkYest information sent by the switch.
	"
    INDEX    { avCmMeasLightUseTrkYestTrunkGrpIdx, 
			avCmMeasLightUseTrkYestGrpMbrIdx }
    ::= { avCmMeasLightUseTrkYestTable 1 }

AvCmMeasLightUseTrkYestEntry ::= SEQUENCE {
		avCmMeasLightUseTrkYestTrunkGrpIdx
		    Integer32,
		avCmMeasLightUseTrkYestGrpMbrIdx
		    Integer32,
		avCmMeasLightUseTrkYestTrunkGroup
		    Integer32,
		avCmMeasLightUseTrkYestRunDate
		    SnmpAdminString,
		avCmMeasLightUseTrkYestGrpSize
		    Integer32,
		avCmMeasLightUseTrkYestGrpMbr
		    Integer32,
		avCmMeasLightUseTrkYestCallsCarried
		    Integer32
		}

avCmMeasLightUseTrkYestTrunkGrpIdx	OBJECT-TYPE
    SYNTAX	Integer32 (0..2000)
    MAX-ACCESS	not-accessible
    STATUS	current
    DESCRIPTION
	"
	Fld OID Name:	avCmMeasLightUseTrkYestTrunkGrpIdx
	Fld OID:	enterprises.6889.2.73.8.1.43.1.1.1
	Fld Format:	NA
	Fld(s) Name:	NA
	Fld Descr:	An object that uniquely identifies each Increment of 
			data.
	"
    ::= { avCmMeasLightUseTrkYestEntry 1 }

avCmMeasLightUseTrkYestGrpMbrIdx       OBJECT-TYPE
    SYNTAX      Integer32 (0..255)
    MAX-ACCESS  not-accessible
    STATUS      current
    DESCRIPTION
        "
        Fld OID Name:   avCmMeasLightUseTrkYestGrpMbrIdx
        Fld OID:        enterprises.6889.2.73.8.1.43.1.1.2
        Fld Format:     NA
        Fld(s) Name:    NA
        Fld Descr:      An object that uniquely identifies each Increment of
                        data.
        "
    ::= { avCmMeasLightUseTrkYestEntry 2 }


avCmMeasLightUseTrkYestTrunkGroup	OBJECT-TYPE
    SYNTAX	Integer32 (0..2000)
    MAX-ACCESS	read-only
    STATUS	current
    DESCRIPTION
	"
	Fld OID Name:	avCmMeasLightUseTrkYestTrunkGroup
	Fld OID:	enterprises.6889.2.73.8.1.43.1.1.3
	Fld Form/Rpt:	TRUNK LIGHTLY USED REPORT
	Fld Format:	Single Field
	Fld(s) Name:	Trunk Group
	Fld Descr:	An object containing the trunk-group number.
	"
    ::= { avCmMeasLightUseTrkYestEntry 3 }

avCmMeasLightUseTrkYestRunDate	OBJECT-TYPE
    SYNTAX	SnmpAdminString (SIZE (0..27))
    MAX-ACCESS	read-only
    STATUS	current
    DESCRIPTION
	"
	Fld OID Name:	avCmMeasLightUseTrkYestRunDate
	Fld OID:	enterprises.6889.2.73.8.1.43.1.1.4
	Fld Form/Rpt:	TRUNK LIGHTLY USED REPORT
	Fld Format:	Single Field
	Fld(s) Name:	Date
	Fld Descr:	An object containing the Date the command was executed.
	"
    ::= { avCmMeasLightUseTrkYestEntry 4 }

avCmMeasLightUseTrkYestGrpSize   OBJECT-TYPE
    SYNTAX	Integer32 (0..999)
    MAX-ACCESS  read-only
    STATUS      current
    DESCRIPTION
        "
        Fld OID Name:   avCmMeasLightUseTrkYestGrpSize
        Fld OID:        enterprises.6889.2.73.8.1.43.1.1.5
        Fld Form/Rpt:   TRUNK LIGHTLY USED REPORT
        Fld Format:     Single Field
        Fld(s) Name:    Grp Size
        Fld Descr:      An object containing the number of members.
        "
    ::= { avCmMeasLightUseTrkYestEntry 5 }


avCmMeasLightUseTrkYestGrpMbr	OBJECT-TYPE
    SYNTAX	Integer32 (0..999)
    MAX-ACCESS	read-only
    STATUS	current
    DESCRIPTION
	"
	Fld OID Name:	avCmMeasLightUseTrkYestGrpMbr
	Fld OID:	enterprises.6889.2.73.8.1.43.1.1.6
	Fld Form/Rpt:	TRUNK LIGHTLY USED REPORT
	Fld Format:	Single Field
	Fld(s) Name:	Grp Mbr#
	Fld Descr:	An object containing the member that is lightly used.
	"
    ::= { avCmMeasLightUseTrkYestEntry 6 }

avCmMeasLightUseTrkYestCallsCarried	OBJECT-TYPE
    SYNTAX	Integer32 (0..9999)
    MAX-ACCESS	read-only
    STATUS	current
    DESCRIPTION
	"
	Fld OID Name:	avCmMeasLightUseTrkYestCallsCarried
	Fld OID:	enterprises.6889.2.73.8.1.43.1.1.7
	Fld Form/Rpt:	TRUNK LIGHTLY USED REPORT
	Fld Format:	Single Field
	Fld(s) Name:	Calls Carried
	Fld Descr:	An object containing the number of calls carried
			over the trunk member.
	"
    ::= { avCmMeasLightUseTrkYestEntry 7 }

-- ******************** avCmMeasSecViolationSum Group *************************

-- MIB GROUP DESCRIPTION

-- MIB Group Name:
--		avCmMeasSecViolationSum Group
-- OID:
--		enterprises.6889.2.73.8.1.44
-- Description:
--		The avCmMeasSecViolationSum MIB Group uses the 
--		"list measurements security-violations summary" command to 
--		retrieve security violation data.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. list measurements security-violations summary
-- Form/Report Name:
--		1. SECURITY VIOLATIONS SUMMARY REPORT
-- Reference Document:
--		1. A detailed description of the command and form can be
--		   found in document referenced by REF_DOC_4 in the
--		   DOCUMENT REFERENCE SECTION.
-- Command Permission/User-profile:
--		1. No special permissions needed.

avCmMeasSecViolationSum	OBJECT IDENTIFIER ::= { avCmObjects 44 }

avCmMeasSecViolationSumTable	OBJECT-TYPE
    SYNTAX	SEQUENCE OF AvCmMeasSecViolationSumEntry
    MAX-ACCESS	not-accessible
    STATUS	current
    DESCRIPTION
	"
	Fld OID Name:	avCmMeasSecViolationSumEntry
	Fld OID:	enterprises.6889.2.73.8.1.44.1
	Fld Form/Rpt:	NA
	Fld Format:	NA
	Fld(s) Name:	NA
	Fld Descr:	A list of the avCmMeasSecViolationSum entries
	"
    ::= { avCmMeasSecViolationSum 1 }

avCmMeasSecViolationSumEntry	OBJECT-TYPE
    SYNTAX	AvCmMeasSecViolationSumEntry
    MAX-ACCESS	not-accessible
    STATUS	current
    DESCRIPTION
	"
	Fld OID Name:	avCmMeasSecViolationSumEntry
	Fld OID:	enterprises.6889.2.73.8.1.44.1.1
	Fld Form/Rpt:	NA
	Fld Format:	NA
	Fld(s) Name:	NA
	Fld Descr:	A avCmMeasSecViolationSum entry containing objects of the
			avCmMeasSecViolationSum information sent by the switch.
	"
    INDEX    { avCmMeasSecViolationSumPortTypeIdx }
    ::= { avCmMeasSecViolationSumTable 1 }

AvCmMeasSecViolationSumEntry ::= SEQUENCE {
		avCmMeasSecViolationSumPortTypeIdx
		    SnmpAdminString,
		avCmMeasSecViolationSumPortType
		    SnmpAdminString,
		avCmMeasSecViolationSumRunDate
		    SnmpAdminString,
		avCmMeasSecViolationSumCountSince
		    SnmpAdminString,
		avCmMeasSecViolationSumValidBC
		    Integer32,
		avCmMeasSecViolationSumInvalidBC
		    Integer32,
		avCmMeasSecViolationSumBC
		    Integer32,
		avCmMeasSecViolationSumValidStnSecCode
		    Integer32,
		avCmMeasSecViolationSumInvalidStnSecCode
		    Integer32,
		avCmMeasSecViolationSumValidTrkSecCode
		    Integer32,
		avCmMeasSecViolationSumInvalidTrkSecCode
		    Integer32,
		avCmMeasSecViolationSumTotValidSecCode
		    Integer32,
		avCmMeasSecViolationSumTotInvalidSecCode
		    Integer32,
		avCmMeasSecViolationSumTotSecCode
		    Integer32,
		avCmMeasSecViolationSumValidStnAC
		    Integer32,
		avCmMeasSecViolationSumInvalidStnAC
		    Integer32,
		avCmMeasSecViolationSumValidTrkAC
		    Integer32,
		avCmMeasSecViolationSumInvalidTrkAC
		    Integer32,
		avCmMeasSecViolationSumValidRemAccAC
		    Integer32,
		avCmMeasSecViolationSumInvalidRemAccAC
		    Integer32,
		avCmMeasSecViolationSumValidAtdAC
		    Integer32,
		avCmMeasSecViolationSumInvalidAtdAC
		    Integer32,
		avCmMeasSecViolationSumValidTotAC
		    Integer32,
		avCmMeasSecViolationSumInvalidTotAC
		    Integer32,
		avCmMeasSecViolationSumTotAC
		    Integer32
		}

avCmMeasSecViolationSumPortTypeIdx	OBJECT-TYPE
    SYNTAX	SnmpAdminString (SIZE (0..11))
    MAX-ACCESS	not-accessible
    STATUS	current
    DESCRIPTION
	"
	Fld OID Name:	avCmMeasSecViolationSumPortTypeIdx
	Fld OID:	enterprises.6889.2.73.8.1.44.1.1.1
	Fld Format:	NA
	Fld(s) Name:	NA
	Fld Descr:	An object that uniquely identifies each Increment of 
			data.
	"
    ::= { avCmMeasSecViolationSumEntry 1 }

avCmMeasSecViolationSumPortType	OBJECT-TYPE
    SYNTAX	SnmpAdminString (SIZE (0..11))
    MAX-ACCESS	read-only
    STATUS	current
    DESCRIPTION
	"
	Fld OID Name:	avCmMeasSecViolationSumPortType
	Fld OID:	enterprises.6889.2.73.8.1.44.1.1.2
	Fld Form/Rpt:	SECURITY VIOLATIONS SUMMARY REPORT
	Fld Format:	Single Field
	Fld(s) Name:	Port Type
	Fld Descr:	An object containing the port type.
	"
    ::= { avCmMeasSecViolationSumEntry 2 }

avCmMeasSecViolationSumRunDate	OBJECT-TYPE
    SYNTAX	SnmpAdminString (SIZE (0..28))
    MAX-ACCESS	read-only
    STATUS	current
    DESCRIPTION
	"
	Fld OID Name:	avCmMeasSecViolationSumRunDate
	Fld OID:	enterprises.6889.2.73.8.1.44.1.1.3
	Fld Form/Rpt:	SECURITY VIOLATIONS SUMMARY REPORT
	Fld Format:	Single Field
	Fld(s) Name:	Date
	Fld Descr:	An object containing the Date the command was executed.
	"
    ::= { avCmMeasSecViolationSumEntry 3 }

avCmMeasSecViolationSumCountSince   OBJECT-TYPE
    SYNTAX	SnmpAdminString (SIZE (0..28))
    MAX-ACCESS  read-only
    STATUS      current
    DESCRIPTION
        "
        Fld OID Name:   avCmMeasSecViolationSumCountSince
        Fld OID:        enterprises.6889.2.73.8.1.44.1.1.4
        Fld Form/Rpt:   SECURITY VIOLATIONS SUMMARY REPORT
        Fld Format:     Single Field
        Fld(s) Name:    Counted Since
        Fld Descr:      An object containing when the counts started being kept.
        "
    ::= { avCmMeasSecViolationSumEntry 4 }


avCmMeasSecViolationSumValidBC	OBJECT-TYPE
    SYNTAX	Integer32 (0..9999999)
    MAX-ACCESS	read-only
    STATUS	current
    DESCRIPTION
	"
	Fld OID Name:	avCmMeasSecViolationSumValidBC
	Fld OID:	enterprises.6889.2.73.8.1.44.1.1.5
	Fld Form/Rpt:	SECURITY VIOLATIONS SUMMARY REPORT
	Fld Format:	Single Field
	Fld(s) Name:	Valid Barrier Codes
	Fld Descr:	An object containing the total number of times a user 
			entered a valid barrier code.
	"
    ::= { avCmMeasSecViolationSumEntry 5 }

avCmMeasSecViolationSumInvalidBC	OBJECT-TYPE
    SYNTAX	Integer32 (0..9999999)
    MAX-ACCESS	read-only
    STATUS	current
    DESCRIPTION
	"
	Fld OID Name:	avCmMeasSecViolationSumInvalidBC
	Fld OID:	enterprises.6889.2.73.8.1.44.1.1.6
	Fld Form/Rpt:	SECURITY VIOLATIONS SUMMARY REPORT
	Fld Format:	Single Field
	Fld(s) Name:	Invalid Barrier Codes
	Fld Descr:	An object containing the total number of times a user 
			entered an invalid barrier code.
	"
    ::= { avCmMeasSecViolationSumEntry 6 }

avCmMeasSecViolationSumBC        OBJECT-TYPE
    SYNTAX      Integer32 (0..9999999)
    MAX-ACCESS  read-only
    STATUS      current
    DESCRIPTION
        "
        Fld OID Name:   avCmMeasSecViolationSumBC
        Fld OID:        enterprises.6889.2.73.8.1.44.1.1.7
        Fld Form/Rpt:   SECURITY VIOLATIONS SUMMARY REPORT
        Fld Format:     Single Field
        Fld(s) Name:    Total Barrier Codes
        Fld Descr:      An object containing the total number of security 
			violations for barrier codes.
        "
    ::= { avCmMeasSecViolationSumEntry 7 }


avCmMeasSecViolationSumValidStnSecCode        OBJECT-TYPE
    SYNTAX      Integer32 (0..9999999)
    MAX-ACCESS  read-only
    STATUS      current
    DESCRIPTION
        "
        Fld OID Name:   avCmMeasSecViolationSumValidStnSecCode
        Fld OID:        enterprises.6889.2.73.8.1.44.1.1.8
        Fld Form/Rpt:   SECURITY VIOLATIONS SUMMARY REPORT
        Fld Format:     Single Field
        Fld(s) Name:    Valid Station Security Codes
        Fld Descr:      An object containing the number of calls originating 
			from stations that generated valid station security 
			codes.
        "
    ::= { avCmMeasSecViolationSumEntry 8 }


avCmMeasSecViolationSumInvalidStnSecCode        OBJECT-TYPE
    SYNTAX      Integer32 (0..9999999)
    MAX-ACCESS  read-only
    STATUS      current
    DESCRIPTION
        "
        Fld OID Name:   avCmMeasSecViolationSumInvalidStnSecCode
        Fld OID:        enterprises.6889.2.73.8.1.44.1.1.9
        Fld Form/Rpt:   SECURITY VIOLATIONS SUMMARY REPORT
        Fld Format:     Single Field
        Fld(s) Name:    Invalid Station Security Codes
        Fld Descr:      An object containing the number of calls originating 
                        from stations that generated invalid station security 
                        codes.
        "
    ::= { avCmMeasSecViolationSumEntry 9 }

avCmMeasSecViolationSumValidTrkSecCode        OBJECT-TYPE
    SYNTAX      Integer32 (0..9999999)
    MAX-ACCESS  read-only
    STATUS      current
    DESCRIPTION
        "
        Fld OID Name:   avCmMeasSecViolationSumValidTrkSecCode
        Fld OID:        enterprises.6889.2.73.8.1.44.1.1.10
        Fld Form/Rpt:   SECURITY VIOLATIONS SUMMARY REPORT
        Fld Format:     Single Field
        Fld(s) Name:    Valid Trunk Security Codes
        Fld Descr:      An object containing the number of calls originating 
                        from trunks that generated valid station security 
                        codes.
        "
    ::= { avCmMeasSecViolationSumEntry 10 }

avCmMeasSecViolationSumInvalidTrkSecCode        OBJECT-TYPE
    SYNTAX      Integer32 (0..9999999)
    MAX-ACCESS  read-only
    STATUS      current
    DESCRIPTION
        "
        Fld OID Name:   avCmMeasSecViolationSumInvalidTrkSecCode
        Fld OID:        enterprises.6889.2.73.8.1.44.1.1.11
        Fld Form/Rpt:   SECURITY VIOLATIONS SUMMARY REPORT
        Fld Format:     Single Field
        Fld(s) Name:    Invalid Trunk Security Codes
        Fld Descr:      An object containing the number of calls originating 
                        from trunks that generated invalid station security 
                        codes.
        "
    ::= { avCmMeasSecViolationSumEntry 11 }

avCmMeasSecViolationSumTotValidSecCode        OBJECT-TYPE
    SYNTAX      Integer32 (0..9999999)
    MAX-ACCESS  read-only
    STATUS      current
    DESCRIPTION
        "
        Fld OID Name:   avCmMeasSecViolationSumTotValidSecCode
        Fld OID:        enterprises.6889.2.73.8.1.44.1.1.12
        Fld Form/Rpt:   SECURITY VIOLATIONS SUMMARY REPORT
        Fld Format:     Single Field
        Fld(s) Name:    Total Valid Security Codes
        Fld Descr:      An object containing the number of total calls that 
			generated valid station security codes.
        "
    ::= { avCmMeasSecViolationSumEntry 12 }


avCmMeasSecViolationSumTotInvalidSecCode        OBJECT-TYPE
    SYNTAX      Integer32 (0..9999999)
    MAX-ACCESS  read-only
    STATUS      current
    DESCRIPTION
        "
        Fld OID Name:   avCmMeasSecViolationSumTotInvalidStnSecCode
        Fld OID:        enterprises.6889.2.73.8.1.44.1.1.13
        Fld Form/Rpt:   SECURITY VIOLATIONS SUMMARY REPORT
        Fld Format:     Single Field
        Fld(s) Name:    Total Invalid Security Codes
        Fld Descr:      An object containing the number of total calls that 
			generated invalid station security codes.
        "
    ::= { avCmMeasSecViolationSumEntry 13 }

avCmMeasSecViolationSumTotSecCode        OBJECT-TYPE
    SYNTAX      Integer32 (0..9999999)
    MAX-ACCESS  read-only
    STATUS      current
    DESCRIPTION
        "
        Fld OID Name:   avCmMeasSecViolationSumTotSecCode
        Fld OID:        enterprises.6889.2.73.8.1.44.1.1.14
        Fld Form/Rpt:   SECURITY VIOLATIONS SUMMARY REPORT
        Fld Format:     Single Field
        Fld(s) Name:    Total Station Security Code Violations
        Fld Descr:      An object containing the number of total calls that
                        generated station security violations.
        "
    ::= { avCmMeasSecViolationSumEntry 14 }

avCmMeasSecViolationSumValidStnAC        OBJECT-TYPE
    SYNTAX      Integer32 (0..9999999)
    MAX-ACCESS  read-only
    STATUS      current
    DESCRIPTION
        "
        Fld OID Name:   avCmMeasSecViolationSumValidStnAC
        Fld OID:        enterprises.6889.2.73.8.1.44.1.1.15
        Fld Form/Rpt:   SECURITY VIOLATIONS SUMMARY REPORT
        Fld Format:     Single Field
        Fld(s) Name:    Valid Station Authorization Codes
        Fld Descr:      An object containing the number of calls originating 
			from stations that generated valid authorization codes.
        "
    ::= { avCmMeasSecViolationSumEntry 15 }

avCmMeasSecViolationSumInvalidStnAC        OBJECT-TYPE
    SYNTAX      Integer32 (0..9999999)
    MAX-ACCESS  read-only
    STATUS      current
    DESCRIPTION
        "
        Fld OID Name:   avCmMeasSecViolationSumInvalidStnAC
        Fld OID:        enterprises.6889.2.73.8.1.44.1.1.16
        Fld Form/Rpt:   SECURITY VIOLATIONS SUMMARY REPORT
        Fld Format:     Single Field
        Fld(s) Name:    Invalid Station Authorization Codes
        Fld Descr:      An object containing the number of calls originating 
                        from stations that generated invalid authorization 
			codes.
        "
    ::= { avCmMeasSecViolationSumEntry 16 }


avCmMeasSecViolationSumValidTrkAC        OBJECT-TYPE
    SYNTAX      Integer32 (0..9999999)
    MAX-ACCESS  read-only
    STATUS      current
    DESCRIPTION
        "
        Fld OID Name:   avCmMeasSecViolationSumValidTrkAC
        Fld OID:        enterprises.6889.2.73.8.1.44.1.1.17
        Fld Form/Rpt:   SECURITY VIOLATIONS SUMMARY REPORT
        Fld Format:     Single Field
        Fld(s) Name:    Valid Trunk Authorization Codes
        Fld Descr:      An object containing the number of calls originating
                        from trunks that generated valid authorization
                        codes.
        "
    ::= { avCmMeasSecViolationSumEntry 17 }

avCmMeasSecViolationSumInvalidTrkAC        OBJECT-TYPE
    SYNTAX      Integer32 (0..9999999)
    MAX-ACCESS  read-only
    STATUS      current
    DESCRIPTION
        "
        Fld OID Name:   avCmMeasSecViolationSumInvalidTrkAC
        Fld OID:        enterprises.6889.2.73.8.1.44.1.1.18
        Fld Form/Rpt:   SECURITY VIOLATIONS SUMMARY REPORT
        Fld Format:     Single Field
        Fld(s) Name:    Invalid Trunk Authorization Codes
        Fld Descr:      An object containing the number of calls originating
                        from trunks that generated invalid authorization
                        codes.
        "
    ::= { avCmMeasSecViolationSumEntry 18 }


avCmMeasSecViolationSumValidRemAccAC        OBJECT-TYPE
    SYNTAX      Integer32 (0..9999999)
    MAX-ACCESS  read-only
    STATUS      current
    DESCRIPTION
        "
        Fld OID Name:   avCmMeasSecViolationSumValidRemAccAC
        Fld OID:        enterprises.6889.2.73.8.1.44.1.1.19
        Fld Form/Rpt:   SECURITY VIOLATIONS SUMMARY REPORT
        Fld Format:     Single Field
        Fld(s) Name:    Valid Remote Access Authorization Codes
        Fld Descr:      An object containing the number of calls originating 
			from remote access that generated valid authorization 
			codes.
        "
    ::= { avCmMeasSecViolationSumEntry 19 }


avCmMeasSecViolationSumInvalidRemAccAC        OBJECT-TYPE
    SYNTAX      Integer32 (0..9999999)
    MAX-ACCESS  read-only
    STATUS      current
    DESCRIPTION
        "
        Fld OID Name:   avCmMeasSecViolationSumInvalidRemAccAC
        Fld OID:        enterprises.6889.2.73.8.1.44.1.1.20
        Fld Form/Rpt:   SECURITY VIOLATIONS SUMMARY REPORT
        Fld Format:     Single Field
        Fld(s) Name:    Invalid Remote Access Authorization Codes
        Fld Descr:      An object containing the number of calls originating 
                        from remote access that generated invalid authorization 
                        codes.
        "
    ::= { avCmMeasSecViolationSumEntry 20 }


avCmMeasSecViolationSumValidAtdAC        OBJECT-TYPE
    SYNTAX      Integer32 (0..9999999)
    MAX-ACCESS  read-only
    STATUS      current
    DESCRIPTION
        "
        Fld OID Name:   avCmMeasSecViolationSumValidAtdAC
        Fld OID:        enterprises.6889.2.73.8.1.44.1.1.21
        Fld Form/Rpt:   SECURITY VIOLATIONS SUMMARY REPORT
        Fld Format:     Single Field
        Fld(s) Name:    Valid Attendant Authorization Codes
        Fld Descr:      An object containing the number of calls originating 
                        from attendants that generated valid authorization 
                        codes.
        "
    ::= { avCmMeasSecViolationSumEntry 21 }


avCmMeasSecViolationSumInvalidAtdAC        OBJECT-TYPE
    SYNTAX      Integer32 (0..9999999)
    MAX-ACCESS  read-only
    STATUS      current
    DESCRIPTION
        "
        Fld OID Name:   avCmMeasSecViolationSumInvalidAtdAC
        Fld OID:        enterprises.6889.2.73.8.1.44.1.1.22
        Fld Form/Rpt:   SECURITY VIOLATIONS SUMMARY REPORT
        Fld Format:     Single Field
        Fld(s) Name:    Invalid Attendant Authorization Codes
        Fld Descr:      An object containing the number of calls originating 
                        from attendants that generated invalid authorization 
                        codes.
        "
    ::= { avCmMeasSecViolationSumEntry 22 }


avCmMeasSecViolationSumValidTotAC        OBJECT-TYPE
    SYNTAX      Integer32 (0..9999999)
    MAX-ACCESS  read-only
    STATUS      current
    DESCRIPTION
        "
        Fld OID Name:   avCmMeasSecViolationSumValidTotAC
        Fld OID:        enterprises.6889.2.73.8.1.44.1.1.23
        Fld Form/Rpt:   SECURITY VIOLATIONS SUMMARY REPORT
        Fld Format:     Single Field
        Fld(s) Name:    Total Valid Authorization Codes
        Fld Descr:      An object containing the number of calls 
                        that generated valid authorization 
                        codes.
        "
    ::= { avCmMeasSecViolationSumEntry 23 }

avCmMeasSecViolationSumInvalidTotAC        OBJECT-TYPE
    SYNTAX      Integer32 (0..9999999)
    MAX-ACCESS  read-only
    STATUS      current
    DESCRIPTION
        "
        Fld OID Name:   avCmMeasSecViolationSumInvalidTotAC
        Fld OID:        enterprises.6889.2.73.8.1.44.1.1.24
        Fld Form/Rpt:   SECURITY VIOLATIONS SUMMARY REPORT
        Fld Format:     Single Field
        Fld(s) Name:    Total Invalid Authorization Codes
        Fld Descr:      An object containing the number of calls 
                        that generated invalid authorization 
                        codes.
        "
    ::= { avCmMeasSecViolationSumEntry 24 }

avCmMeasSecViolationSumTotAC        OBJECT-TYPE
    SYNTAX      Integer32 (0..9999999)
    MAX-ACCESS  read-only
    STATUS      current
    DESCRIPTION
        "
        Fld OID Name:   avCmMeasSecViolationSumTotAC
        Fld OID:        enterprises.6889.2.73.8.1.44.1.1.25
        Fld Form/Rpt:   SECURITY VIOLATIONS SUMMARY REPORT
        Fld Format:     Single Field
        Fld(s) Name:    Total Authorization Code Security Violations
        Fld Descr:      An object containing the number of calls 
                        that generated security violations for authorization 
                        codes.
        "
    ::= { avCmMeasSecViolationSumEntry 25 }

-- ******************** avCmListMedGateway Group *************************

-- MIB GROUP DESCRIPTION

-- MIB Group Name:
--		avCmListMedGateway Group
-- OID:
--		enterprises.6889.2.73.8.1.45
-- Description:
--		The avCmListMedGateway MIB Group uses the 
--		"list media-gateway" command to 
-- 		retrieve media-gateway data.
--		
-- Releases Supported:
--		CM6.3.100 and greater
-- Polling Type:
--		Inventory
-- Polling Interval:
--		No more than once a day.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. list media-gateway
-- Form/Report Name:
--		1. MEDIA-GATEWAY REPORT
-- Reference Document:
--		1. A detailed description of the command and form can be
--		   found in document referenced by REF_DOC_5 and REF_DOC_3 in 
--		   the DOCUMENT REFERENCE SECTION.
-- Command Permission/User-profile:
--		1. No special permissions needed.

avCmListMedGateway	OBJECT IDENTIFIER ::= { avCmObjects 45 }

avCmListMedGatewayTable	OBJECT-TYPE
    SYNTAX	SEQUENCE OF AvCmListMedGatewayEntry
    MAX-ACCESS	not-accessible
    STATUS	current
    DESCRIPTION
	"
	Fld OID Name:	avCmListMedGatewayEntry
	Fld OID:	enterprises.6889.2.73.8.1.45.1
	Fld Form/Rpt:	NA
	Fld Format:	NA
	Fld(s) Name:	NA
	Fld Descr:	A list of the avCmListMedGateway entries
	"
    ::= { avCmListMedGateway 1 }

avCmListMedGatewayEntry	OBJECT-TYPE
    SYNTAX	AvCmListMedGatewayEntry
    MAX-ACCESS	not-accessible
    STATUS	current
    DESCRIPTION
	"
	Fld OID Name:	avCmListMedGatewayEntry
	Fld OID:	enterprises.6889.2.73.8.1.45.1.1
	Fld Form/Rpt:	NA
	Fld Format:	NA
	Fld(s) Name:	NA
	Fld Descr:	A avCmListMedGateway entry containing objects of the
			avCmListMedGateway information sent by the switch.
	"
    INDEX    { avCmListMedGatewayNumIdx }
    ::= { avCmListMedGatewayTable 1 }

AvCmListMedGatewayEntry ::= SEQUENCE {
		avCmListMedGatewayNumIdx
		    Integer32,
		avCmListMedGatewayNumber
		    Integer32,
		avCmListMedGatewayName
		    SnmpAdminString,
		avCmListMedGatewaySerNum
		    SnmpAdminString,
		avCmListMedGatewayFWVersHWVint
		    SnmpAdminString,
		avCmListMedGatewayRecRule
		    SnmpAdminString,
		avCmListMedGatewayIPV4Address
		    SnmpAdminString,
		avCmListMedGatewayIPV6Address
		    SnmpAdminString,
		avCmListMedGatewayContrlAddr
		    SnmpAdminString,
		avCmListMedGatewayType
		    SnmpAdminString,
		avCmListMedGatewayRegion
		    Integer32,
		avCmListMedGatewayRegistered
		    SnmpAdminString
		}

avCmListMedGatewayNumIdx	OBJECT-TYPE
    SYNTAX	Integer32 (0..250)
    MAX-ACCESS	not-accessible
    STATUS	current
    DESCRIPTION
	"
	Fld OID Name:	avCmListMedGatewayNumIdx
	Fld OID:	enterprises.6889.2.73.8.1.45.1.1.1
	Fld Format:	NA
	Fld(s) Name:	NA
	Fld Descr:	An object that uniquely identifies each Increment of 
			data.
	"
    ::= { avCmListMedGatewayEntry 1 }

avCmListMedGatewayNumber	OBJECT-TYPE
    SYNTAX	Integer32 (0..250)
    MAX-ACCESS	read-only
    STATUS	current
    DESCRIPTION
	"
	Fld OID Name:	avCmListMedGatewayNumber
	Fld OID:	enterprises.6889.2.73.8.1.45.1.1.2
	Fld Form/Rpt:	MEDIA-GATEWAY REPORT
	Fld Format:	Single Field
	Fld(s) Name:	Num
	Fld Descr:	An object containing the Gateway Number.
	"
    ::= { avCmListMedGatewayEntry 2 }

avCmListMedGatewayName	OBJECT-TYPE
    SYNTAX	SnmpAdminString (SIZE (0..21))
    MAX-ACCESS	read-only
    STATUS	current
    DESCRIPTION
	"
	Fld OID Name:	avCmListMedGatewayName
	Fld OID:	enterprises.6889.2.73.8.1.45.1.1.3
	Fld Form/Rpt:	MEDIA-GATEWAY REPORT
	Fld Format:	Single Field
	Fld(s) Name:	Name
	Fld Descr:	An object containing the Name of the gateway.
	"
    ::= { avCmListMedGatewayEntry 3 }

avCmListMedGatewaySerNum   OBJECT-TYPE
    SYNTAX	SnmpAdminString (SIZE (0..13))
    MAX-ACCESS  read-only
    STATUS      current
    DESCRIPTION
        "
        Fld OID Name:   avCmListMedGatewaySerNum
        Fld OID:        enterprises.6889.2.73.8.1.45.1.1.4
        Fld Form/Rpt:   MEDIA-GATEWAY REPORT
        Fld Format:     Single Field
        Fld(s) Name:    Serial Number
        Fld Descr:      An object containing the Serial Number.
        "
    ::= { avCmListMedGatewayEntry 4 }


avCmListMedGatewayFWVersHWVint	OBJECT-TYPE
    SYNTAX	SnmpAdminString (SIZE (0..17))
    MAX-ACCESS	read-only
    STATUS	current
    DESCRIPTION
	"
	Fld OID Name:	avCmListMedGatewayFWVersHWVint
	Fld OID:	enterprises.6889.2.73.8.1.45.1.1.5
	Fld Form/Rpt:	MEDIA-GATEWAY REPORT
	Fld Format:	Single Field
	Fld(s) Name:	FW Version/HW Vintage
	Fld Descr:	An object containing the FW Version/HW Vintage.
	"
    ::= { avCmListMedGatewayEntry 5 }

avCmListMedGatewayRecRule	OBJECT-TYPE
    SYNTAX	SnmpAdminString (SIZE (0..5))
    MAX-ACCESS	read-only
    STATUS	current
    DESCRIPTION
	"
	Fld OID Name:	avCmListMedGatewayRecRule
	Fld OID:	enterprises.6889.2.73.8.1.45.1.1.6
	Fld Form/Rpt:	MEDIA-GATEWAY REPORT
	Fld Format:	Single Field
	Fld(s) Name:	RecRule
	Fld Descr:	An object containing the recovery rule for the gateway.
	"
    ::= { avCmListMedGatewayEntry 6 }

avCmListMedGatewayIPV4Address        OBJECT-TYPE
    SYNTAX	SnmpAdminString (SIZE (0..16))
    MAX-ACCESS  read-only
    STATUS      current
    DESCRIPTION
        "
        Fld OID Name:   avCmListMedGatewayIPV4Address
        Fld OID:        enterprises.6889.2.73.8.1.45.1.1.7
        Fld Form/Rpt:   MEDIA-GATEWAY REPORT
        Fld Format:     Single Field
        Fld(s) Name:    IPV4 Address
        Fld Descr:      An object containing the IPV4 Address of the gateway.
        "
    ::= { avCmListMedGatewayEntry 7 }


avCmListMedGatewayIPV6Address        OBJECT-TYPE
    SYNTAX	SnmpAdminString (SIZE (0..41))
    MAX-ACCESS  read-only
    STATUS      current
    DESCRIPTION
        "
        Fld OID Name:   avCmListMedGatewayIPV6Address
        Fld OID:        enterprises.6889.2.73.8.1.45.1.1.8
        Fld Form/Rpt:   MEDIA-GATEWAY REPORT
        Fld Format:     Single Field
        Fld(s) Name:    IPV6 Address
        Fld Descr:      An object containing the IPV6 Address of the gateway.
        "
    ::= { avCmListMedGatewayEntry 8 }


avCmListMedGatewayContrlAddr        OBJECT-TYPE
    SYNTAX	SnmpAdminString (SIZE (0..41))
    MAX-ACCESS  read-only
    STATUS      current
    DESCRIPTION
        "
        Fld OID Name:   avCmListMedGatewayContrlAddr
        Fld OID:        enterprises.6889.2.73.8.1.45.1.1.9
        Fld Form/Rpt:   MEDIA-GATEWAY REPORT
        Fld Format:     Single Field
        Fld(s) Name:    Cntrl IP Addr
        Fld Descr:      An object containing the control IP Address.
        "
    ::= { avCmListMedGatewayEntry 9 }


avCmListMedGatewayType        OBJECT-TYPE
    SYNTAX	SnmpAdminString (SIZE (0..9))
    MAX-ACCESS  read-only
    STATUS      current
    DESCRIPTION
        "
        Fld OID Name:   avCmListMedGatewayType
        Fld OID:        enterprises.6889.2.73.8.1.45.1.1.10
        Fld Form/Rpt:   MEDIA-GATEWAY REPORT
        Fld Format:     Single Field
        Fld(s) Name:    Type
        Fld Descr:      An object containing the gateway type.
        "
    ::= { avCmListMedGatewayEntry 10 }

avCmListMedGatewayRegion        OBJECT-TYPE
    SYNTAX      Integer32 (0..250)
    MAX-ACCESS  read-only
    STATUS      current
    DESCRIPTION
        "
        Fld OID Name:   avCmListMedGatewayRegion
        Fld OID:        enterprises.6889.2.73.8.1.45.1.1.11
        Fld Form/Rpt:   MEDIA-GATEWAY REPORT
        Fld Format:     Single Field
        Fld(s) Name:    NetRgn
        Fld Descr:      An object containing the network region assigned to
			the gateway.
        "
    ::= { avCmListMedGatewayEntry 11 }

avCmListMedGatewayRegistered        OBJECT-TYPE
    SYNTAX	SnmpAdminString (SIZE (0..2))
    MAX-ACCESS  read-only
    STATUS      current
    DESCRIPTION
        "
        Fld OID Name:   avCmListMedGatewayRegistered
        Fld OID:        enterprises.6889.2.73.8.1.45.1.1.12
        Fld Form/Rpt:   MEDIA-GATEWAY REPORT
        Fld Format:     Single Field
        Fld(s) Name:    Reg?
        Fld Descr:      An object containing whether the gateway is registered.
        "
    ::= { avCmListMedGatewayEntry 12 }

-- ******************** avCmListConfigMedGateway Group *************************

-- MIB GROUP DESCRIPTION

-- MIB Group Name:
--		avCmListConfigMedGateway Group
-- OID:
--		enterprises.6889.2.73.8.1.46
-- Description:
--		The avCmListConfigMedGateway MIB Group uses the 
--		"list configuration media-gateway" command to 
-- 		retrieve media-gateway data.
--		
-- Releases Supported:
--		CM6.3.100 and greater
-- Polling Type:
--		Inventory
-- Polling Interval:
--		No more than once a day or after configuration changes.
-- Default Caching Interval
-- 		600 seconds
-- Timeout Interval:
--		Initial Timeout should be set to 20 seconds.
-- Retry Interval:
--		Initial Retry should be set to 3.
-- Limitations:
--		Red/High - The data collected by this MIB Group will
--		increase as the number of boards in the system increase.
--		Consequently the data collected by this MIB Group could be
--		very large and therefore may take a very long time to collect
--		and could impact system performance.
-- Command Type:
--		1. SAT
-- Command:
--		1. list configuration media-gateway
-- Form/Report Name:
--		1. SYSTEM CONFIGURATION
-- Reference Document:
--		1. A detailed description of the command and form can be
--		   found in document referenced by REF_DOC_1 in the
--		   DOCUMENT REFERENCE SECTION.
-- Command Permission/User-profile:
--		1. No special permissions needed.

avCmListConfigMedGateway	OBJECT IDENTIFIER ::= { avCmObjects 46 }

avCmListConfigMedGatewayTable	OBJECT-TYPE
    SYNTAX	SEQUENCE OF AvCmListConfigMedGatewayEntry
    MAX-ACCESS	not-accessible
    STATUS	current
    DESCRIPTION
	"
	Fld OID Name:	avCmListConfigMedGatewayEntry
	Fld OID:	enterprises.6889.2.73.8.1.46.1
	Fld Form/Rpt:	NA
	Fld Format:	NA
	Fld(s) Name:	NA
	Fld Descr:	A list of the avCmListConfigMedGateway entries
	"
    ::= { avCmListConfigMedGateway 1 }

avCmListConfigMedGatewayEntry	OBJECT-TYPE
    SYNTAX	AvCmListConfigMedGatewayEntry
    MAX-ACCESS	not-accessible
    STATUS	current
    DESCRIPTION
	"
	Fld OID Name:	avCmListConfigMedGatewayEntry
	Fld OID:	enterprises.6889.2.73.8.1.46.1.1
	Fld Form/Rpt:	NA
	Fld Format:	NA
	Fld(s) Name:	NA
	Fld Descr:	A avCmListConfigMedGateway entry containing objects of 
			the avCmListConfigMedGateway information sent by the 
			switch.
	"
    INDEX    {avCmListConfigMedGatewayNumIdx, avCmListConfigMedGatewayBoardIdx}
    ::= { avCmListConfigMedGatewayTable 1 }

AvCmListConfigMedGatewayEntry ::= SEQUENCE {
                avCmListConfigMedGatewayNumIdx
                    Integer32,
                avCmListConfigMedGatewayBoardIdx
                    SnmpAdminString,
                avCmListConfigMedGatewayBoardNumber
                    SnmpAdminString,
                avCmListConfigMedGatewayBoardType
                    SnmpAdminString,
                avCmListConfigMedGatewayCode
                    SnmpAdminString,
                avCmListConfigMedGatewayVintage
                    SnmpAdminString,
                avCmListConfigMedGatewayAssignedPorts
                    SnmpAdminString
		}

avCmListConfigMedGatewayNumIdx	OBJECT-TYPE
    SYNTAX      Integer32 (0..250)
    MAX-ACCESS	not-accessible
    STATUS	current
    DESCRIPTION
	"
	Fld OID Name:	avCmListConfigMedGatewayNumIdx
	Fld OID:	enterprises.6889.2.73.8.1.46.1.1.1
	Fld Form/Rpt:	NA
	Fld Format:	NA
	Fld(s) Name:	NA
	Fld Descr:	An object that contains that uniquely identifies
			a media-gateway.
	"
    ::= { avCmListConfigMedGatewayEntry 1 }

avCmListConfigMedGatewayBoardIdx	OBJECT-TYPE
    SYNTAX	SnmpAdminString (SIZE (0..10))
    MAX-ACCESS	not-accessible
    STATUS	current
    DESCRIPTION
	"
	Fld OID Name:	avCmListConfigMedGatewayBoardIdx
	Fld OID:	enterprises.6889.2.73.8.1.46.1.1.2
	Fld Form/Rpt:	NA
	Fld Format:	NA
	Fld(s) Name:	NA
	Fld Descr:	An object that contains that uniquely identifies
			a board based on its location in the system.  The
			syntax for the Board Number is as follows:
			cabinet(01-64):carrier(A-E):slot(01-20).
	"
    ::= { avCmListConfigMedGatewayEntry 2 }

avCmListConfigMedGatewayBoardNumber	OBJECT-TYPE
    SYNTAX	SnmpAdminString (SIZE (0..8))
    MAX-ACCESS	read-only
    STATUS	current
    DESCRIPTION
	"
	Fld OID Name:	avCmListConfigMedGatewayBoardNumber
	Fld OID:	enterprises.6889.2.73.8.1.46.1.1.3
	Fld Form/Rpt:	SYSTEM CONFIGURATION
	Fld Format:	Single Field
	Fld(s) Name:	Board Number
	Fld Descr:	An object that contains that uniquely identifies
			a board based on its location in the system.  The
			syntax for the Board Number is as follows:
			cabinet(01-64):carrier(A-E):slot(01-20).
	"
    ::= { avCmListConfigMedGatewayEntry 3 }

avCmListConfigMedGatewayBoardType	OBJECT-TYPE
    SYNTAX	SnmpAdminString (SIZE (0..20))
    MAX-ACCESS	read-only
    STATUS	current
    DESCRIPTION
	"
	Fld OID Name:	avCmListConfigMedGatewayBoardType
	Fld OID:	enterprises.6889.2.73.8.1.46.1.1.4
	Fld Form/Rpt:	SYSTEM CONFIGURATION
	Fld Format:	Single Field
	Fld(s) Name:	Board Type
	Fld Descr:	An object containing the type of board.
	"
    ::= { avCmListConfigMedGatewayEntry 4 }

avCmListConfigMedGatewayCode	OBJECT-TYPE
    SYNTAX	SnmpAdminString (SIZE (0..11))
    MAX-ACCESS	read-only
    STATUS	current
    DESCRIPTION
	"
	Fld OID Name:	avCmListConfigMedGatewayCode
	Fld  OID:	enterprises.6889.2.73.8.1.46.1.1.5
	Fld Form/Rpt:	SYSTEM CONFIGURATION
	Fld Format:	Multiple Field: Board Code and Board Suffix
	Fld(s) Name:	Code
	Fld Descr:	An object that contains a the board code and suffix
			of the board.
	"
    ::= { avCmListConfigMedGatewayEntry 5 }

avCmListConfigMedGatewayVintage	OBJECT-TYPE
    SYNTAX	SnmpAdminString (SIZE (0..11))
    MAX-ACCESS	read-only
    STATUS	current
    DESCRIPTION
	"
	Fld OID Name:	avCmListConfigMedGatewayVintage
	Fld OID:	enterprises.6889.2.73.8.1.46.1.1.6
	Fld Form/Rpt:	SYSTEM CONFIGURATION
	Fld Format:	Single Field
	Fld(s) Name:	Vintage
	Fld Descr:	An object that contains vintage of the board.
	"
    ::= { avCmListConfigMedGatewayEntry 6 }

avCmListConfigMedGatewayAssignedPorts	OBJECT-TYPE
    SYNTAX	SnmpAdminString (SIZE (0..193))
    MAX-ACCESS	read-only
    STATUS	current
    DESCRIPTION
	"
	Fld OID Name:	avCmListConfigMedGatewayPorts
	Fld OID:	enterprises.6889.2.73.8.1.46.1.1.7
	Fld Form/Rpt:	SYSTEM CONFIGURATION
	Fld Format:	Multiple - List of ports administered on the board.
	Fld(s) Name:	Assigned Ports
	Fld Descr:	An object that specifies the assignment of the port.
			A string representing integers identical to the port
			numbers that are assigned.
			The char (u) indicates that the port is unassigned.
			The char (t) indicates that the port is assigned
			via the TTI feature.
			The char (p) indicates that the port is assigned via
			the PSA feature.
			A NULL char or string indicates that the port(s) does
			not exist or is not administered on that board.
	"
    ::= { avCmListConfigMedGatewayEntry 7 }

-- ******************** avCmStatusMedGateway Group *************************

-- MIB GROUP DESCRIPTION

-- MIB Group Name:
--		avCmStatusMedGateway
-- OID:
--		enterprises.6889.2.73.8.1.47
-- Description:
--		The avCmStatusMedGateway MIB Group uses the "status 
--		media-gateways" command to retrieve the gateway
--		health  information.
--		
-- Releases Supported:
--		CM6.3.100 and greater
-- Polling Type:
--		Configuration, Inventory, and Performance/Utilization
-- Polling Interval:
--		No more than once every 10 minutes.
-- Default Caching Interval
-- 		600 seconds
-- Timeout Interval:
--		Initial Timeout should be set to 15 seconds.
-- Retry Interval:
--		Initial Retry should be set to 3.
-- Limitations:
--		Yellow/Medium - The data collected by this MIB Group
--		may have some impact on the system.
-- Command Type:
--		1. SAT
-- Command:
--		1. status media-gateways
-- Form/Report Name:
--		1. GATEWAY STATUS
-- Reference Document:
--		1. A detailed description of the command and form can be
--		   found in document referenced by REF_DOC_1 in the
--		   DOCUMENT REFERENCE SECTION.
-- Command Permission/User-profile:
--		1. No special permissions needed.

avCmStatusMedGateway	OBJECT IDENTIFIER ::= { avCmObjects 47 }

avCmStatusMedGatewayAlmMajor    OBJECT-TYPE
    SYNTAX	Integer32 (0..9999)
    MAX-ACCESS	read-only
    STATUS	current
    DESCRIPTION
	"
	Fld OID Name:	avCmStatusMedGatewayAlmMajor
	Fld OID:	enterprises.6889.2.73.8.1.47.1
	Fld Form/Rpt:	status media-gateways
	Fld Format:	Single Field
	Fld(s) Name:	Alarms Major
	Fld Descr:	An object that contains the number of major alarms.
	"
    ::= { avCmStatusMedGateway 1 }

avCmStatusMedGatewayAlmMinor	OBJECT-TYPE
    SYNTAX	Integer32 (0..9999)
    MAX-ACCESS	read-only
    STATUS	current
    DESCRIPTION
	"
	Fld OID Name:	avCmStatusMedGatewayAlmMinor
	Fld OID:	enterprises.6889.2.73.8.1.47.2
	Fld Form/Rpt:	status media-gateways
	Fld Format:	Single Field
	Fld(s) Name:	Alarms Minor
	Fld Descr:	An object that contains the number of Minor Alarms.
	"
    ::= { avCmStatusMedGateway 2 }

avCmStatusMedGatewayAlmWarning 	OBJECT-TYPE
    SYNTAX	Integer32 (0..9999)
    MAX-ACCESS	read-only
    STATUS	current
    DESCRIPTION
	"
	Fld OID Name:	avCmStatusMedGatewayAlmWarning
	Fld OID:	enterprises.6889.2.73.8.1.47.3
	Fld Form/Rpt:	status media-gateways
	Fld Format:	Single Field
	Fld(s) Name:	Alarms Warning
	Fld Descr:	An object that contains the number of Warning Alarms.
	"
    ::= { avCmStatusMedGateway 3 }


avCmStatusMedGatewayBusyOutTrunks 	OBJECT-TYPE
    SYNTAX      Integer32 (0..9999)
    MAX-ACCESS	read-only
    STATUS	current
    DESCRIPTION
	"
	Fld OID Name:	avCmStatusMedGatewayBusyOutTrunks 
	Fld OID:	enterprises.6889.2.73.8.1.47.4
	Fld Form/Rpt:	status media-gateways
	Fld Format:	Single Field
	Fld(s) Name:	BUSYOUT Trunks
	Fld Descr:	An object that contains the number of Busied Out Trunks.
	"
    ::= { avCmStatusMedGateway 4 }

avCmStatusMedGatewayBusyOutStations	OBJECT-TYPE
    SYNTAX      Integer32 (0..9999)
    MAX-ACCESS	read-only
    STATUS	current
    DESCRIPTION
	"
	Fld OID Name:	avCmStatusMedGatewayBusyOutStations
	Fld OID:	enterprises.6889.2.73.8.1.47.5
	Fld Form/Rpt:	status media-gateways
	Fld Format:	Single Field
	Fld(s) Name:	BUSYOUT Stations
	Fld Descr:	An object that contains the number of Busied Out 
			Stations.
	"
    ::= { avCmStatusMedGateway 5 }

avCmStatusMedGatewayH248LinksDown	OBJECT-TYPE
    SYNTAX      Integer32 (0..9999)
    MAX-ACCESS	read-only
    STATUS	current
    DESCRIPTION
	"
	Fld OID Name:	avCmStatusMedGatewayH248LinksDown
	Fld OID:	enterprises.6889.2.73.8.1.47.6
	Fld Form/Rpt:	status media-gateways
	Fld Format:	Single Field
	Fld(s) Name:	Links Down
	Fld Descr:	An object containing the total number of media gateways
			administered in a system that do not have a H.248 link
			established to the media gateway controller.
	"
    ::= { avCmStatusMedGateway 6 }


avCmStatusMedGatewayH248LinksUp	OBJECT-TYPE
    SYNTAX      Integer32 (0..9999)
    MAX-ACCESS	read-only
    STATUS	current
    DESCRIPTION
	"
	Fld OID Name:	avCmStatusMedGatewayH248LinksUp
	Fld OID:	enterprises.6889.2.73.8.1.47.7
	Fld Form/Rpt:	status media-gateways
	Fld Format:	Single Field
	Fld(s) Name:	Links Up
	Fld Descr:	An object containing the total number of media gateways 
			administered in a system that do have a H.248 link 
			established to the media gateway controller.
	"
    ::= { avCmStatusMedGateway 7 }

avCmStatusMedGatewayNbrLogins	OBJECT-TYPE
    SYNTAX      Integer32 (0..99)
    MAX-ACCESS	read-only
    STATUS	current
    DESCRIPTION
	"
	Fld OID Name:	avCmStatusMedGatewayNbrLogins
	Fld OID:	enterprises.6889.2.73.8.1.47.8
	Fld Form/Rpt:	status media-gateways
	Fld Format:	Single Field
	Fld(s) Name:	# Logins
	Fld Descr:	An object containing the total number of logins into 
			the system.
	"
    ::= { avCmStatusMedGateway 8 }

avCmStatusMedGatewayAlarms1 	OBJECT-TYPE
    SYNTAX	SnmpAdminString (SIZE (0..31))
    MAX-ACCESS	read-only
    STATUS	current
    DESCRIPTION
	"
	Fld OID Name:	avCmStatusMedGatewayAlarms1
	Fld OID:	enterprises.6889.2.73.8.1.47.9
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 9 }

avCmStatusMedGatewayAlarms2	OBJECT-TYPE
    SYNTAX	SnmpAdminString (SIZE (0..31))
    MAX-ACCESS	read-only
    STATUS	current
    DESCRIPTION
	"
	Fld OID Name:	avCmStatusMedGatewayAlarms2
	Fld OID:	enterprises.6889.2.73.8.1.47.10
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 10 }

avCmStatusMedGatewayAlarms3	OBJECT-TYPE
    SYNTAX	SnmpAdminString (SIZE (0..31))
    MAX-ACCESS	read-only
    STATUS	current
    DESCRIPTION
	"
	Fld OID Name:	avCmStatusMedGatewayAlarms3
	Fld OID:	enterprises.6889.2.73.8.1.47.11
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 11 }

avCmStatusMedGatewayAlarms4	OBJECT-TYPE
    SYNTAX	SnmpAdminString (SIZE (0..31))
    MAX-ACCESS	read-only
    STATUS	current
    DESCRIPTION
	"
	Fld OID Name:	avCmStatusMedGatewayAlarms4
	Fld OID:	enterprises.6889.2.73.8.1.47.12
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 12 }

avCmStatusMedGatewayAlarms5	OBJECT-TYPE
    SYNTAX	SnmpAdminString (SIZE (0..31))
    MAX-ACCESS	read-only
    STATUS	current
    DESCRIPTION
	"
	Fld OID Name:	avCmStatusMedGatewayAlarms5
	Fld OID:	enterprises.6889.2.73.8.1.47.13
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 13 }

avCmStatusMedGatewayAlarms6	OBJECT-TYPE
    SYNTAX	SnmpAdminString (SIZE (0..31))
    MAX-ACCESS	read-only
    STATUS	current
    DESCRIPTION
	"
	Fld OID Name:	avCmStatusMedGatewayAlarms6
	Fld OID:	enterprises.6889.2.73.8.1.47.14
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 14 }

avCmStatusMedGatewayAlarms7	OBJECT-TYPE
    SYNTAX	SnmpAdminString (SIZE (0..31))
    MAX-ACCESS	read-only
    STATUS	current
    DESCRIPTION
	"
	Fld OID Name:	avCmStatusMedGatewayAlarms7
	Fld OID:	enterprises.6889.2.73.8.1.47.15
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 15 }

avCmStatusMedGatewayAlarms8	OBJECT-TYPE
    SYNTAX	SnmpAdminString (SIZE (0..31))
    MAX-ACCESS	read-only
    STATUS	current
    DESCRIPTION
	"
	Fld OID Name:	avCmStatusMedGatewayAlarms8
	Fld OID:	enterprises.6889.2.73.8.1.47.16
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 16 }

avCmStatusMedGatewayAlarms9	OBJECT-TYPE
    SYNTAX	SnmpAdminString (SIZE (0..31))
    MAX-ACCESS	read-only
    STATUS	current
    DESCRIPTION
	"
	Fld OID Name:	avCmStatusMedGatewayAlarms9
	Fld OID:	enterprises.6889.2.73.8.1.47.17
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 17 }

avCmStatusMedGatewayAlarms10	OBJECT-TYPE
    SYNTAX	SnmpAdminString (SIZE (0..31))
    MAX-ACCESS	read-only
    STATUS	current
    DESCRIPTION
	"
	Fld OID Name:	avCmStatusMedGatewayAlarms10
	Fld OID:	enterprises.6889.2.73.8.1.47.18
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 18 }

avCmStatusMedGatewayAlarms11	OBJECT-TYPE
    SYNTAX	SnmpAdminString (SIZE (0..31))
    MAX-ACCESS	read-only
    STATUS	current
    DESCRIPTION
	"
	Fld OID Name:	avCmStatusMedGatewayAlarms11
	Fld OID:	enterprises.6889.2.73.8.1.47.19
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 19 }

avCmStatusMedGatewayAlarms12	OBJECT-TYPE
    SYNTAX	SnmpAdminString (SIZE (0..31))
    MAX-ACCESS	read-only
    STATUS	current
    DESCRIPTION
	"
	Fld OID Name:	avCmStatusMedGatewayAlarms12
	Fld OID:	enterprises.6889.2.73.8.1.47.20
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 20 }

avCmStatusMedGatewayAlarms13	OBJECT-TYPE
    SYNTAX	SnmpAdminString (SIZE (0..31))
    MAX-ACCESS	read-only
    STATUS	current
    DESCRIPTION
	"
	Fld OID Name:	avCmStatusMedGatewayAlarms13
	Fld OID:	enterprises.6889.2.73.8.1.47.21
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 21 }

avCmStatusMedGatewayAlarms14	OBJECT-TYPE
    SYNTAX	SnmpAdminString (SIZE (0..31))
    MAX-ACCESS	read-only
    STATUS	current
    DESCRIPTION
	"
	Fld OID Name:	avCmStatusMedGatewayAlarms14
	Fld OID:	enterprises.6889.2.73.8.1.47.22
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 22 }

avCmStatusMedGatewayAlarms15	OBJECT-TYPE
    SYNTAX	SnmpAdminString (SIZE (0..31))
    MAX-ACCESS	read-only
    STATUS	current
    DESCRIPTION
	"
	Fld OID Name:	avCmStatusMedGatewayAlarms15
	Fld OID:	enterprises.6889.2.73.8.1.47.23
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 23 }

avCmStatusMedGatewayAlarms16	OBJECT-TYPE
    SYNTAX	SnmpAdminString (SIZE (0..31))
    MAX-ACCESS	read-only
    STATUS	current
    DESCRIPTION
	"
	Fld OID Name:	avCmStatusMedGatewayAlarms16
	Fld OID:	enterprises.6889.2.73.8.1.47.24
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 24 }

avCmStatusMedGatewayAlarms17	OBJECT-TYPE
    SYNTAX	SnmpAdminString (SIZE (0..31))
    MAX-ACCESS	read-only
    STATUS	current
    DESCRIPTION
	"
	Fld OID Name:	avCmStatusMedGatewayAlarms17
	Fld OID:	enterprises.6889.2.73.8.1.47.25
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 25 }

avCmStatusMedGatewayAlarms18	OBJECT-TYPE
    SYNTAX	SnmpAdminString (SIZE (0..31))
    MAX-ACCESS	read-only
    STATUS	current
    DESCRIPTION
	"
	Fld OID Name:	avCmStatusMedGatewayAlarms18
	Fld OID:	enterprises.6889.2.73.8.1.47.26
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 26 }

avCmStatusMedGatewayAlarms19	OBJECT-TYPE
    SYNTAX	SnmpAdminString (SIZE (0..31))
    MAX-ACCESS	read-only
    STATUS	current
    DESCRIPTION
	"
	Fld OID Name:	avCmStatusMedGatewayAlarms19
	Fld OID:	enterprises.6889.2.73.8.1.47.27
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 27 }

avCmStatusMedGatewayAlarms20	OBJECT-TYPE
    SYNTAX	SnmpAdminString (SIZE (0..31))
    MAX-ACCESS	read-only
    STATUS	current
    DESCRIPTION
	"
	Fld OID Name:	avCmStatusMedGatewayAlarms20
	Fld OID:	enterprises.6889.2.73.8.1.47.28
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 28 }

avCmStatusMedGatewayAlarms21	OBJECT-TYPE
    SYNTAX	SnmpAdminString (SIZE (0..31))
    MAX-ACCESS	read-only
    STATUS	current
    DESCRIPTION
	"
	Fld OID Name:	avCmStatusMedGatewayAlarms21
	Fld OID:	enterprises.6889.2.73.8.1.47.29
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 29 }

avCmStatusMedGatewayAlarms22	OBJECT-TYPE
    SYNTAX	SnmpAdminString (SIZE (0..31))
    MAX-ACCESS	read-only
    STATUS	current
    DESCRIPTION
	"
	Fld OID Name:	avCmStatusMedGatewayAlarms22
	Fld OID:	enterprises.6889.2.73.8.1.47.31
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 30 }

avCmStatusMedGatewayAlarms23	OBJECT-TYPE
    SYNTAX	SnmpAdminString (SIZE (0..31))
    MAX-ACCESS	read-only
    STATUS	current
    DESCRIPTION
	"
	Fld OID Name:	avCmStatusMedGatewayAlarms23
	Fld OID:	enterprises.6889.2.73.8.1.47.31
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 31 }

avCmStatusMedGatewayAlarms24	OBJECT-TYPE
    SYNTAX	SnmpAdminString (SIZE (0..31))
    MAX-ACCESS	read-only
    STATUS	current
    DESCRIPTION
	"
	Fld OID Name:	avCmStatusMedGatewayAlarms24
	Fld OID:	enterprises.6889.2.73.8.1.47.32
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 32 }

avCmStatusMedGatewayAlarms25	OBJECT-TYPE
    SYNTAX	SnmpAdminString (SIZE (0..31))
    MAX-ACCESS	read-only
    STATUS	current
    DESCRIPTION
	"
	Fld OID Name:	avCmStatusMedGatewayAlarms25
	Fld OID:	enterprises.6889.2.73.8.1.47.33
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 33 }

avCmStatusMedGatewayAlarms26	OBJECT-TYPE
    SYNTAX	SnmpAdminString (SIZE (0..31))
    MAX-ACCESS	read-only
    STATUS	current
    DESCRIPTION
	"
	Fld OID Name:	avCmStatusMedGatewayAlarms26
	Fld OID:	enterprises.6889.2.73.8.1.47.34
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 34 }

avCmStatusMedGatewayAlarms27	OBJECT-TYPE
    SYNTAX	SnmpAdminString (SIZE (0..31))
    MAX-ACCESS	read-only
    STATUS	current
    DESCRIPTION
	"
	Fld OID Name:	avCmStatusMedGatewayAlarms27
	Fld OID:	enterprises.6889.2.73.8.1.47.35
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 35 }

avCmStatusMedGatewayAlarms28	OBJECT-TYPE
    SYNTAX	SnmpAdminString (SIZE (0..31))
    MAX-ACCESS	read-only
    STATUS	current
    DESCRIPTION
	"
	Fld OID Name:	avCmStatusMedGatewayAlarms28
	Fld OID:	enterprises.6889.2.73.8.1.47.36
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 36 }

avCmStatusMedGatewayAlarms29	OBJECT-TYPE
    SYNTAX	SnmpAdminString (SIZE (0..31))
    MAX-ACCESS	read-only
    STATUS	current
    DESCRIPTION
	"
	Fld OID Name:	avCmStatusMedGatewayAlarms29
	Fld OID:	enterprises.6889.2.73.8.1.47.37
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 37 }

avCmStatusMedGatewayAlarms30	OBJECT-TYPE
    SYNTAX	SnmpAdminString (SIZE (0..31))
    MAX-ACCESS	read-only
    STATUS	current
    DESCRIPTION
	"
	Fld OID Name:	avCmStatusMedGatewayAlarms30
	Fld OID:	enterprises.6889.2.73.8.1.47.38
	Fld Form/Rpt:	status media-gateways
	Fld Format:	Single Field with the following Labels:
			MG  Mj  Mn Wn Lk
	Fld(s) Name:	Alarms
	Fld Descr:	An object containing the status of the first set of 
			eight media gateways, including the number of major 
			alarms, minor alarms, warnings, and the H.248 link 
			status for each specific media gateway number.
	"
    ::= { avCmStatusMedGateway 38 }

avCmStatusMedGatewayAlarms31    OBJECT-TYPE
    SYNTAX      SnmpAdminString (SIZE (0..31))
    MAX-ACCESS  read-only
    STATUS      current
    DESCRIPTION
        "
        Fld OID Name:   avCmStatusMedGatewayAlarms31
        Fld OID:        enterprises.6889.2.73.8.1.47.39
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 39 }

avCmStatusMedGatewayAlarms32    OBJECT-TYPE
    SYNTAX      SnmpAdminString (SIZE (0..31))
    MAX-ACCESS  read-only
    STATUS      current
    DESCRIPTION
        "
        Fld OID Name:   avCmStatusMedGatewayAlarms32
        Fld OID:        enterprises.6889.2.73.8.1.47.40
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 40 }

avCmStatusMedGatewayAlarms33    OBJECT-TYPE
    SYNTAX      SnmpAdminString (SIZE (0..31))
    MAX-ACCESS  read-only
    STATUS      current
    DESCRIPTION
        "
        Fld OID Name:   avCmStatusMedGatewayAlarms33
        Fld OID:        enterprises.6889.2.73.8.1.47.41
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 41 }

avCmStatusMedGatewayAlarms34    OBJECT-TYPE
    SYNTAX      SnmpAdminString (SIZE (0..31))
    MAX-ACCESS  read-only
    STATUS      current
    DESCRIPTION
        "
        Fld OID Name:   avCmStatusMedGatewayAlarms34
        Fld OID:        enterprises.6889.2.73.8.1.47.42
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 42 }

avCmStatusMedGatewayAlarms35    OBJECT-TYPE
    SYNTAX      SnmpAdminString (SIZE (0..31))
    MAX-ACCESS  read-only
    STATUS      current
    DESCRIPTION
        "
        Fld OID Name:   avCmStatusMedGatewayAlarms35
        Fld OID:        enterprises.6889.2.73.8.1.47.43
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 43 }

avCmStatusMedGatewayAlarms36    OBJECT-TYPE
    SYNTAX      SnmpAdminString (SIZE (0..31))
    MAX-ACCESS  read-only
    STATUS      current
    DESCRIPTION
        "
        Fld OID Name:   avCmStatusMedGatewayAlarms36
        Fld OID:        enterprises.6889.2.73.8.1.47.44
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 44 }

avCmStatusMedGatewayAlarms37    OBJECT-TYPE
    SYNTAX      SnmpAdminString (SIZE (0..31))
    MAX-ACCESS  read-only
    STATUS      current
    DESCRIPTION
        "
        Fld OID Name:   avCmStatusMedGatewayAlarms37
        Fld OID:        enterprises.6889.2.73.8.1.47.45
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 45 }

avCmStatusMedGatewayAlarms38    OBJECT-TYPE
    SYNTAX      SnmpAdminString (SIZE (0..31))
    MAX-ACCESS  read-only
    STATUS      current
    DESCRIPTION
        "
        Fld OID Name:   avCmStatusMedGatewayAlarms38
        Fld OID:        enterprises.6889.2.73.8.1.47.46
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 46 }

avCmStatusMedGatewayAlarms39    OBJECT-TYPE
    SYNTAX      SnmpAdminString (SIZE (0..31))
    MAX-ACCESS  read-only
    STATUS      current
    DESCRIPTION
        "
        Fld OID Name:   avCmStatusMedGatewayAlarms39
        Fld OID:        enterprises.6889.2.73.8.1.47.47
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 47 }

avCmStatusMedGatewayAlarms40    OBJECT-TYPE
    SYNTAX      SnmpAdminString (SIZE (0..31))
    MAX-ACCESS  read-only
    STATUS      current
    DESCRIPTION
        "
        Fld OID Name:   avCmStatusMedGatewayAlarms40
        Fld OID:        enterprises.6889.2.73.8.1.47.48
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 48 }

avCmStatusMedGatewayAlarms41    OBJECT-TYPE
    SYNTAX      SnmpAdminString (SIZE (0..31))
    MAX-ACCESS  read-only
    STATUS      current
    DESCRIPTION
        "
        Fld OID Name:   avCmStatusMedGatewayAlarms41
        Fld OID:        enterprises.6889.2.73.8.1.47.49
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 49 }

avCmStatusMedGatewayAlarms42    OBJECT-TYPE
    SYNTAX      SnmpAdminString (SIZE (0..31))
    MAX-ACCESS  read-only
    STATUS      current
    DESCRIPTION
        "
        Fld OID Name:   avCmStatusMedGatewayAlarms42
        Fld OID:        enterprises.6889.2.73.8.1.47.50
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 50 }

avCmStatusMedGatewayAlarms43    OBJECT-TYPE
    SYNTAX      SnmpAdminString (SIZE (0..31))
    MAX-ACCESS  read-only
    STATUS      current
    DESCRIPTION
        "
        Fld OID Name:   avCmStatusMedGatewayAlarms43
        Fld OID:        enterprises.6889.2.73.8.1.47.51
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 51 }

avCmStatusMedGatewayAlarms44    OBJECT-TYPE
    SYNTAX      SnmpAdminString (SIZE (0..31))
    MAX-ACCESS  read-only
    STATUS      current
    DESCRIPTION
        "
        Fld OID Name:   avCmStatusMedGatewayAlarms44
        Fld OID:        enterprises.6889.2.73.8.1.47.52
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 52 }

avCmStatusMedGatewayAlarms45    OBJECT-TYPE
    SYNTAX      SnmpAdminString (SIZE (0..31))
    MAX-ACCESS  read-only
    STATUS      current
    DESCRIPTION
        "
        Fld OID Name:   avCmStatusMedGatewayAlarms45
        Fld OID:        enterprises.6889.2.73.8.1.47.53
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 53 }

avCmStatusMedGatewayAlarms46    OBJECT-TYPE
    SYNTAX      SnmpAdminString (SIZE (0..31))
    MAX-ACCESS  read-only
    STATUS      current
    DESCRIPTION
        "
        Fld OID Name:   avCmStatusMedGatewayAlarms46
        Fld OID:        enterprises.6889.2.73.8.1.47.54
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 54 }

avCmStatusMedGatewayAlarms47    OBJECT-TYPE
    SYNTAX      SnmpAdminString (SIZE (0..31))
    MAX-ACCESS  read-only
    STATUS      current
    DESCRIPTION
        "
        Fld OID Name:   avCmStatusMedGatewayAlarms47
        Fld OID:        enterprises.6889.2.73.8.1.47.55
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 55 }

avCmStatusMedGatewayAlarms48    OBJECT-TYPE
    SYNTAX      SnmpAdminString (SIZE (0..31))
    MAX-ACCESS  read-only
    STATUS      current
    DESCRIPTION
        "
        Fld OID Name:   avCmStatusMedGatewayAlarms48
        Fld OID:        enterprises.6889.2.73.8.1.47.56
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 56 }

avCmStatusMedGatewayAlarms49    OBJECT-TYPE
    SYNTAX      SnmpAdminString (SIZE (0..31))
    MAX-ACCESS  read-only
    STATUS      current
    DESCRIPTION
        "
        Fld OID Name:   avCmStatusMedGatewayAlarms49
        Fld OID:        enterprises.6889.2.73.8.1.47.57
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 57 }

avCmStatusMedGatewayAlarms50    OBJECT-TYPE
    SYNTAX      SnmpAdminString (SIZE (0..31))
    MAX-ACCESS  read-only
    STATUS      current
    DESCRIPTION
        "
        Fld OID Name:   avCmStatusMedGatewayAlarms50
        Fld OID:        enterprises.6889.2.73.8.1.47.58
        Fld Form/Rpt:   status media-gateways
        Fld(s) Name:    Alarms
        Fld Descr:      An object containing the status of the first set of
                        eight media gateways, including the number of major
                        alarms, minor alarms, warnings, and the H.248 link
                        status for each specific media gateway number.
        "
    ::= { avCmStatusMedGateway 58 }

avCmStatusMedGatewayAlarms51    OBJECT-TYPE
    SYNTAX      SnmpAdminString (SIZE (0..31))
    MAX-ACCESS  read-only
    STATUS      current
    DESCRIPTION
        "
        Fld OID Name:   avCmStatusMedGatewayAlarms51
        Fld OID:        enterprises.6889.2.73.8.1.47.59
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 59 }

avCmStatusMedGatewayAlarms52    OBJECT-TYPE
    SYNTAX      SnmpAdminString (SIZE (0..31))
    MAX-ACCESS  read-only
    STATUS      current
    DESCRIPTION
        "
        Fld OID Name:   avCmStatusMedGatewayAlarms52
        Fld OID:        enterprises.6889.2.73.8.1.47.60
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 60 }

avCmStatusMedGatewayAlarms53    OBJECT-TYPE
    SYNTAX      SnmpAdminString (SIZE (0..31))
    MAX-ACCESS  read-only
    STATUS      current
    DESCRIPTION
        "
        Fld OID Name:   avCmStatusMedGatewayAlarms53
        Fld OID:        enterprises.6889.2.73.8.1.47.61
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 61 }

avCmStatusMedGatewayAlarms54    OBJECT-TYPE
    SYNTAX      SnmpAdminString (SIZE (0..31))
    MAX-ACCESS  read-only
    STATUS      current
    DESCRIPTION
        "
        Fld OID Name:   avCmStatusMedGatewayAlarms54
        Fld OID:        enterprises.6889.2.73.8.1.47.62
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 62 }

avCmStatusMedGatewayAlarms55    OBJECT-TYPE
    SYNTAX      SnmpAdminString (SIZE (0..31))
    MAX-ACCESS  read-only
    STATUS      current
    DESCRIPTION
        "
        Fld OID Name:   avCmStatusMedGatewayAlarms55
        Fld OID:        enterprises.6889.2.73.8.1.47.63
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 63 }

avCmStatusMedGatewayAlarms56    OBJECT-TYPE
    SYNTAX      SnmpAdminString (SIZE (0..31))
    MAX-ACCESS  read-only
    STATUS      current
    DESCRIPTION
        "
        Fld OID Name:   avCmStatusMedGatewayAlarms56
        Fld OID:        enterprises.6889.2.73.8.1.47.64
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 64 }

avCmStatusMedGatewayAlarms57    OBJECT-TYPE
    SYNTAX      SnmpAdminString (SIZE (0..31))
    MAX-ACCESS  read-only
    STATUS      current
    DESCRIPTION
        "
        Fld OID Name:   avCmStatusMedGatewayAlarms57
        Fld OID:        enterprises.6889.2.73.8.1.47.65
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 65 }

avCmStatusMedGatewayAlarms58    OBJECT-TYPE
    SYNTAX      SnmpAdminString (SIZE (0..31))
    MAX-ACCESS  read-only
    STATUS      current
    DESCRIPTION
        "
        Fld OID Name:   avCmStatusMedGatewayAlarms58
        Fld OID:        enterprises.6889.2.73.8.1.47.66
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 66 }

avCmStatusMedGatewayAlarms59    OBJECT-TYPE
    SYNTAX      SnmpAdminString (SIZE (0..31))
    MAX-ACCESS  read-only
    STATUS      current
    DESCRIPTION
        "
        Fld OID Name:   avCmStatusMedGatewayAlarms59
        Fld OID:        enterprises.6889.2.73.8.1.47.67
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 67 }

avCmStatusMedGatewayAlarms60    OBJECT-TYPE
    SYNTAX      SnmpAdminString (SIZE (0..31))
    MAX-ACCESS  read-only
    STATUS      current
    DESCRIPTION
        "
        Fld OID Name:   avCmStatusMedGatewayAlarms60
        Fld OID:        enterprises.6889.2.73.8.1.47.68
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 68 }


avCmStatusMedGatewayAlarms61    OBJECT-TYPE
    SYNTAX      SnmpAdminString (SIZE (0..31))
    MAX-ACCESS  read-only
    STATUS      current
    DESCRIPTION
        "
        Fld OID Name:   avCmStatusMedGatewayAlarms61
        Fld OID:        enterprises.6889.2.73.8.1.47.69
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 69 }


avCmStatusMedGatewayAlarms62    OBJECT-TYPE
    SYNTAX      SnmpAdminString (SIZE (0..31))
    MAX-ACCESS  read-only
    STATUS      current
    DESCRIPTION
        "
        Fld OID Name:   avCmStatusMedGatewayAlarms62
        Fld OID:        enterprises.6889.2.73.8.1.47.70
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 70 }


avCmStatusMedGatewayAlarms63    OBJECT-TYPE
    SYNTAX      SnmpAdminString (SIZE (0..31))
    MAX-ACCESS  read-only
    STATUS      current
    DESCRIPTION
        "
        Fld OID Name:   avCmStatusMedGatewayAlarms63
        Fld OID:        enterprises.6889.2.73.8.1.47.71
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 71 }


avCmStatusMedGatewayAlarms64    OBJECT-TYPE
    SYNTAX      SnmpAdminString (SIZE (0..31))
    MAX-ACCESS  read-only
    STATUS      current
    DESCRIPTION
        "
        Fld OID Name:   avCmStatusMedGatewayAlarms64
        Fld OID:        enterprises.6889.2.73.8.1.47.72
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 72 }


avCmStatusMedGatewayAlarms65    OBJECT-TYPE
    SYNTAX      SnmpAdminString (SIZE (0..31))
    MAX-ACCESS  read-only
    STATUS      current
    DESCRIPTION
        "
        Fld OID Name:   avCmStatusMedGatewayAlarms65
        Fld OID:        enterprises.6889.2.73.8.1.47.73
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 73 }


avCmStatusMedGatewayAlarms66    OBJECT-TYPE
    SYNTAX      SnmpAdminString (SIZE (0..31))
    MAX-ACCESS  read-only
    STATUS      current
    DESCRIPTION
        "
        Fld OID Name:   avCmStatusMedGatewayAlarms66
        Fld OID:        enterprises.6889.2.73.8.1.47.74
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 74 }


avCmStatusMedGatewayAlarms67    OBJECT-TYPE
    SYNTAX      SnmpAdminString (SIZE (0..31))
    MAX-ACCESS  read-only
    STATUS      current
    DESCRIPTION
        "
        Fld OID Name:   avCmStatusMedGatewayAlarms67
        Fld OID:        enterprises.6889.2.73.8.1.47.75
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 75 }


avCmStatusMedGatewayAlarms68    OBJECT-TYPE
    SYNTAX      SnmpAdminString (SIZE (0..31))
    MAX-ACCESS  read-only
    STATUS      current
    DESCRIPTION
        "
        Fld OID Name:   avCmStatusMedGatewayAlarms68
        Fld OID:        enterprises.6889.2.73.8.1.47.76
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 76 }


avCmStatusMedGatewayAlarms69    OBJECT-TYPE
    SYNTAX      SnmpAdminString (SIZE (0..31))
    MAX-ACCESS  read-only
    STATUS      current
    DESCRIPTION
        "
        Fld OID Name:   avCmStatusMedGatewayAlarms69
        Fld OID:        enterprises.6889.2.73.8.1.47.77
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 77 }


avCmStatusMedGatewayAlarms70    OBJECT-TYPE
    SYNTAX      SnmpAdminString (SIZE (0..31))
    MAX-ACCESS  read-only
    STATUS      current
    DESCRIPTION
        "
        Fld OID Name:   avCmStatusMedGatewayAlarms70
        Fld OID:        enterprises.6889.2.73.8.1.47.78
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 78 }


avCmStatusMedGatewayAlarms71    OBJECT-TYPE
    SYNTAX      SnmpAdminString (SIZE (0..31))
    MAX-ACCESS  read-only
    STATUS      current
    DESCRIPTION
        "
        Fld OID Name:   avCmStatusMedGatewayAlarms71
        Fld OID:        enterprises.6889.2.73.8.1.47.79
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 79 }


avCmStatusMedGatewayAlarms72    OBJECT-TYPE
    SYNTAX      SnmpAdminString (SIZE (0..31))
    MAX-ACCESS  read-only
    STATUS      current
    DESCRIPTION
        "
        Fld OID Name:   avCmStatusMedGatewayAlarms72
        Fld OID:        enterprises.6889.2.73.8.1.47.80
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 80 }


avCmStatusMedGatewayAlarms73    OBJECT-TYPE
    SYNTAX      SnmpAdminString (SIZE (0..31))
    MAX-ACCESS  read-only
    STATUS      current
    DESCRIPTION
        "
        Fld OID Name:   avCmStatusMedGatewayAlarms73
        Fld OID:        enterprises.6889.2.73.8.1.47.81
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 81 }


avCmStatusMedGatewayAlarms74    OBJECT-TYPE
    SYNTAX      SnmpAdminString (SIZE (0..31))
    MAX-ACCESS  read-only
    STATUS      current
    DESCRIPTION
        "
        Fld OID Name:   avCmStatusMedGatewayAlarms74
        Fld OID:        enterprises.6889.2.73.8.1.47.82
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 82 }


avCmStatusMedGatewayAlarms75    OBJECT-TYPE
    SYNTAX      SnmpAdminString (SIZE (0..31))
    MAX-ACCESS  read-only
    STATUS      current
    DESCRIPTION
        "
        Fld OID Name:   avCmStatusMedGatewayAlarms75
        Fld OID:        enterprises.6889.2.73.8.1.47.83
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 83 }


avCmStatusMedGatewayAlarms76    OBJECT-TYPE
    SYNTAX      SnmpAdminString (SIZE (0..31))
    MAX-ACCESS  read-only
    STATUS      current
    DESCRIPTION
        "
        Fld OID Name:   avCmStatusMedGatewayAlarms76
        Fld OID:        enterprises.6889.2.73.8.1.47.84
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 84 }


avCmStatusMedGatewayAlarms77    OBJECT-TYPE
    SYNTAX      SnmpAdminString (SIZE (0..31))
    MAX-ACCESS  read-only
    STATUS      current
    DESCRIPTION
        "
        Fld OID Name:   avCmStatusMedGatewayAlarms77
        Fld OID:        enterprises.6889.2.73.8.1.47.85
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 85 }


avCmStatusMedGatewayAlarms78    OBJECT-TYPE
    SYNTAX      SnmpAdminString (SIZE (0..31))
    MAX-ACCESS  read-only
    STATUS      current
    DESCRIPTION
        "
        Fld OID Name:   avCmStatusMedGatewayAlarms78
        Fld OID:        enterprises.6889.2.73.8.1.47.86
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 86 }


avCmStatusMedGatewayAlarms79    OBJECT-TYPE
    SYNTAX      SnmpAdminString (SIZE (0..31))
    MAX-ACCESS  read-only
    STATUS      current
    DESCRIPTION
        "
        Fld OID Name:   avCmStatusMedGatewayAlarms87
        Fld OID:        enterprises.6889.2.73.8.1.47.68
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 87 }


avCmStatusMedGatewayAlarms80    OBJECT-TYPE
    SYNTAX      SnmpAdminString (SIZE (0..31))
    MAX-ACCESS  read-only
    STATUS      current
    DESCRIPTION
        "
        Fld OID Name:   avCmStatusMedGatewayAlarms80
        Fld OID:        enterprises.6889.2.73.8.1.47.88
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 88 }


avCmStatusMedGatewayAlarms81    OBJECT-TYPE
    SYNTAX      SnmpAdminString (SIZE (0..31))
    MAX-ACCESS  read-only
    STATUS      current
    DESCRIPTION
        "
        Fld OID Name:   avCmStatusMedGatewayAlarms81
        Fld OID:        enterprises.6889.2.73.8.1.47.89
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 89 }


avCmStatusMedGatewayAlarms82    OBJECT-TYPE
    SYNTAX      SnmpAdminString (SIZE (0..31))
    MAX-ACCESS  read-only
    STATUS      current
    DESCRIPTION
        "
        Fld OID Name:   avCmStatusMedGatewayAlarms82
        Fld OID:        enterprises.6889.2.73.8.1.47.90
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 90 }


avCmStatusMedGatewayAlarms83    OBJECT-TYPE
    SYNTAX      SnmpAdminString (SIZE (0..31))
    MAX-ACCESS  read-only
    STATUS      current
    DESCRIPTION
        "
        Fld OID Name:   avCmStatusMedGatewayAlarms83
        Fld OID:        enterprises.6889.2.73.8.1.47.91
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 91 }


avCmStatusMedGatewayAlarms84    OBJECT-TYPE
    SYNTAX      SnmpAdminString (SIZE (0..31))
    MAX-ACCESS  read-only
    STATUS      current
    DESCRIPTION
        "
        Fld OID Name:   avCmStatusMedGatewayAlarms84
        Fld OID:        enterprises.6889.2.73.8.1.47.92
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 92 }


avCmStatusMedGatewayAlarms85    OBJECT-TYPE
    SYNTAX      SnmpAdminString (SIZE (0..31))
    MAX-ACCESS  read-only
    STATUS      current
    DESCRIPTION
        "
        Fld OID Name:   avCmStatusMedGatewayAlarms85
        Fld OID:        enterprises.6889.2.73.8.1.47.93
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 93 }


avCmStatusMedGatewayAlarms86    OBJECT-TYPE
    SYNTAX      SnmpAdminString (SIZE (0..31))
    MAX-ACCESS  read-only
    STATUS      current
    DESCRIPTION
        "
        Fld OID Name:   avCmStatusMedGatewayAlarms86
        Fld OID:        enterprises.6889.2.73.8.1.47.94
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 94 }


avCmStatusMedGatewayAlarms87    OBJECT-TYPE
    SYNTAX      SnmpAdminString (SIZE (0..31))
    MAX-ACCESS  read-only
    STATUS      current
    DESCRIPTION
        "
        Fld OID Name:   avCmStatusMedGatewayAlarms87
        Fld OID:        enterprises.6889.2.73.8.1.47.95
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 95 }


avCmStatusMedGatewayAlarms88    OBJECT-TYPE
    SYNTAX      SnmpAdminString (SIZE (0..31))
    MAX-ACCESS  read-only
    STATUS      current
    DESCRIPTION
        "
        Fld OID Name:   avCmStatusMedGatewayAlarms88
        Fld OID:        enterprises.6889.2.73.8.1.47.96
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 96 }


avCmStatusMedGatewayAlarms89    OBJECT-TYPE
    SYNTAX      SnmpAdminString (SIZE (0..31))
    MAX-ACCESS  read-only
    STATUS      current
    DESCRIPTION
        "
        Fld OID Name:   avCmStatusMedGatewayAlarms89
        Fld OID:        enterprises.6889.2.73.8.1.47.97
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 97 }


avCmStatusMedGatewayAlarms90    OBJECT-TYPE
    SYNTAX      SnmpAdminString (SIZE (0..31))
    MAX-ACCESS  read-only
    STATUS      current
    DESCRIPTION
        "
        Fld OID Name:   avCmStatusMedGatewayAlarms90
        Fld OID:        enterprises.6889.2.73.8.1.47.98
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 98 }

avCmStatusMedGatewayAlarms91    OBJECT-TYPE
    SYNTAX      SnmpAdminString (SIZE (0..31))
    MAX-ACCESS  read-only
    STATUS      current
    DESCRIPTION
        "
        Fld OID Name:   avCmStatusMedGatewayAlarms91
        Fld OID:        enterprises.6889.2.73.8.1.47.99
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 99 }

avCmStatusMedGatewayAlarms92    OBJECT-TYPE
    SYNTAX      SnmpAdminString (SIZE (0..31))
    MAX-ACCESS  read-only
    STATUS      current
    DESCRIPTION
        "
        Fld OID Name:   avCmStatusMedGatewayAlarms92
        Fld OID:        enterprises.6889.2.73.8.1.47.100
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 100 }

avCmStatusMedGatewayAlarms93    OBJECT-TYPE
    SYNTAX      SnmpAdminString (SIZE (0..31))
    MAX-ACCESS  read-only
    STATUS      current
    DESCRIPTION
        "
        Fld OID Name:   avCmStatusMedGatewayAlarms93
        Fld OID:        enterprises.6889.2.73.8.1.47.101
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 101 }

avCmStatusMedGatewayAlarms94    OBJECT-TYPE
    SYNTAX      SnmpAdminString (SIZE (0..31))
    MAX-ACCESS  read-only
    STATUS      current
    DESCRIPTION
        "
        Fld OID Name:   avCmStatusMedGatewayAlarms94
        Fld OID:        enterprises.6889.2.73.8.1.47.102
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 102 }

avCmStatusMedGatewayAlarms95    OBJECT-TYPE
    SYNTAX      SnmpAdminString (SIZE (0..31))
    MAX-ACCESS  read-only
    STATUS      current
    DESCRIPTION
        "
        Fld OID Name:   avCmStatusMedGatewayAlarms95
        Fld OID:        enterprises.6889.2.73.8.1.47.103
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 103 }

avCmStatusMedGatewayAlarms96    OBJECT-TYPE
    SYNTAX      SnmpAdminString (SIZE (0..31))
    MAX-ACCESS  read-only
    STATUS      current
    DESCRIPTION
        "
        Fld OID Name:   avCmStatusMedGatewayAlarms96
        Fld OID:        enterprises.6889.2.73.8.1.47.104
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 104 }

avCmStatusMedGatewayAlarms97    OBJECT-TYPE
    SYNTAX      SnmpAdminString (SIZE (0..31))
    MAX-ACCESS  read-only
    STATUS      current
    DESCRIPTION
        "
        Fld OID Name:   avCmStatusMedGatewayAlarms97
        Fld OID:        enterprises.6889.2.73.8.1.47.105
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 105 }

avCmStatusMedGatewayAlarms98    OBJECT-TYPE
    SYNTAX      SnmpAdminString (SIZE (0..31))
    MAX-ACCESS  read-only
    STATUS      current
    DESCRIPTION
        "
        Fld OID Name:   avCmStatusMedGatewayAlarms98
        Fld OID:        enterprises.6889.2.73.8.1.47.106
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 106 }

avCmStatusMedGatewayAlarms99    OBJECT-TYPE
    SYNTAX      SnmpAdminString (SIZE (0..31))
    MAX-ACCESS  read-only
    STATUS      current
    DESCRIPTION
        "
        Fld OID Name:   avCmStatusMedGatewayAlarms99
        Fld OID:        enterprises.6889.2.73.8.1.47.107
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 107 }

avCmStatusMedGatewayAlarms100    OBJECT-TYPE
    SYNTAX      SnmpAdminString (SIZE (0..31))
    MAX-ACCESS  read-only
    STATUS      current
    DESCRIPTION
        "
        Fld OID Name:   avCmStatusMedGatewayAlarms100
        Fld OID:        enterprises.6889.2.73.8.1.47.108
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 108 }

avCmStatusMedGatewayAlarms101    OBJECT-TYPE
    SYNTAX      SnmpAdminString (SIZE (0..31))
    MAX-ACCESS  read-only
    STATUS      current
    DESCRIPTION
        "
        Fld OID Name:   avCmStatusMedGatewayAlarms101
        Fld OID:        enterprises.6889.2.73.8.1.47.109
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 109 }

avCmStatusMedGatewayAlarms102    OBJECT-TYPE
    SYNTAX      SnmpAdminString (SIZE (0..31))
    MAX-ACCESS  read-only
    STATUS      current
    DESCRIPTION
        "
        Fld OID Name:   avCmStatusMedGatewayAlarms102
        Fld OID:        enterprises.6889.2.73.8.1.47.110
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 110 }

avCmStatusMedGatewayAlarms103    OBJECT-TYPE
    SYNTAX      SnmpAdminString (SIZE (0..31))
    MAX-ACCESS  read-only
    STATUS      current
    DESCRIPTION
        "
        Fld OID Name:   avCmStatusMedGatewayAlarms103
        Fld OID:        enterprises.6889.2.73.8.1.47.111
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 111 }

avCmStatusMedGatewayAlarms104    OBJECT-TYPE
    SYNTAX      SnmpAdminString (SIZE (0..31))
    MAX-ACCESS  read-only
    STATUS      current
    DESCRIPTION
        "
        Fld OID Name:   avCmStatusMedGatewayAlarms104
        Fld OID:        enterprises.6889.2.73.8.1.47.112
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 112 }

avCmStatusMedGatewayAlarms105    OBJECT-TYPE
    SYNTAX      SnmpAdminString (SIZE (0..31))
    MAX-ACCESS  read-only
    STATUS      current
    DESCRIPTION
        "
        Fld OID Name:   avCmStatusMedGatewayAlarms105
        Fld OID:        enterprises.6889.2.73.8.1.47.113
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 113 }

avCmStatusMedGatewayAlarms106    OBJECT-TYPE
    SYNTAX      SnmpAdminString (SIZE (0..31))
    MAX-ACCESS  read-only
    STATUS      current
    DESCRIPTION
        "
        Fld OID Name:   avCmStatusMedGatewayAlarms106
        Fld OID:        enterprises.6889.2.73.8.1.47.114
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 114 }

avCmStatusMedGatewayAlarms107    OBJECT-TYPE
    SYNTAX      SnmpAdminString (SIZE (0..31))
    MAX-ACCESS  read-only
    STATUS      current
    DESCRIPTION
        "
        Fld OID Name:   avCmStatusMedGatewayAlarms107
        Fld OID:        enterprises.6889.2.73.8.1.47.115
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 115 }

avCmStatusMedGatewayAlarms108    OBJECT-TYPE
    SYNTAX      SnmpAdminString (SIZE (0..31))
    MAX-ACCESS  read-only
    STATUS      current
    DESCRIPTION
        "
        Fld OID Name:   avCmStatusMedGatewayAlarms108
        Fld OID:        enterprises.6889.2.73.8.1.47.116
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 116 }

avCmStatusMedGatewayAlarms109    OBJECT-TYPE
    SYNTAX      SnmpAdminString (SIZE (0..31))
    MAX-ACCESS  read-only
    STATUS      current
    DESCRIPTION
        "
        Fld OID Name:   avCmStatusMedGatewayAlarms109
        Fld OID:        enterprises.6889.2.73.8.1.47.117
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 117 }

avCmStatusMedGatewayAlarms110    OBJECT-TYPE
    SYNTAX      SnmpAdminString (SIZE (0..31))
    MAX-ACCESS  read-only
    STATUS      current
    DESCRIPTION
        "
        Fld OID Name:   avCmStatusMedGatewayAlarms110
        Fld OID:        enterprises.6889.2.73.8.1.47.118
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 118 }

avCmStatusMedGatewayAlarms111    OBJECT-TYPE
    SYNTAX      SnmpAdminString (SIZE (0..31))
    MAX-ACCESS  read-only
    STATUS      current
    DESCRIPTION
        "
        Fld OID Name:   avCmStatusMedGatewayAlarms111
        Fld OID:        enterprises.6889.2.73.8.1.47.119
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 119 }

avCmStatusMedGatewayAlarms112    OBJECT-TYPE
    SYNTAX      SnmpAdminString (SIZE (0..31))
    MAX-ACCESS  read-only
    STATUS      current
    DESCRIPTION
        "
        Fld OID Name:   avCmStatusMedGatewayAlarms112
        Fld OID:        enterprises.6889.2.73.8.1.47.120
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 120 }

avCmStatusMedGatewayAlarms113    OBJECT-TYPE
    SYNTAX      SnmpAdminString (SIZE (0..31))
    MAX-ACCESS  read-only
    STATUS      current
    DESCRIPTION
        "
        Fld OID Name:   avCmStatusMedGatewayAlarms113
        Fld OID:        enterprises.6889.2.73.8.1.47.121
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 121 }

avCmStatusMedGatewayAlarms114    OBJECT-TYPE
    SYNTAX      SnmpAdminString (SIZE (0..31))
    MAX-ACCESS  read-only
    STATUS      current
    DESCRIPTION
        "
        Fld OID Name:   avCmStatusMedGatewayAlarms114
        Fld OID:        enterprises.6889.2.73.8.1.47.122
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 122 }

avCmStatusMedGatewayAlarms115    OBJECT-TYPE
    SYNTAX      SnmpAdminString (SIZE (0..31))
    MAX-ACCESS  read-only
    STATUS      current
    DESCRIPTION
        "
        Fld OID Name:   avCmStatusMedGatewayAlarms115
        Fld OID:        enterprises.6889.2.73.8.1.47.123
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 123 }

avCmStatusMedGatewayAlarms116    OBJECT-TYPE
    SYNTAX      SnmpAdminString (SIZE (0..31))
    MAX-ACCESS  read-only
    STATUS      current
    DESCRIPTION
        "
        Fld OID Name:   avCmStatusMedGatewayAlarms116
        Fld OID:        enterprises.6889.2.73.8.1.47.124
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 124 }

avCmStatusMedGatewayAlarms117    OBJECT-TYPE
    SYNTAX      SnmpAdminString (SIZE (0..31))
    MAX-ACCESS  read-only
    STATUS      current
    DESCRIPTION
        "
        Fld OID Name:   avCmStatusMedGatewayAlarms117
        Fld OID:        enterprises.6889.2.73.8.1.47.125
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 125 }

avCmStatusMedGatewayAlarms118    OBJECT-TYPE
    SYNTAX      SnmpAdminString (SIZE (0..31))
    MAX-ACCESS  read-only
    STATUS      current
    DESCRIPTION
        "
        Fld OID Name:   avCmStatusMedGatewayAlarms118
        Fld OID:        enterprises.6889.2.73.8.1.47.126
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 126 }

avCmStatusMedGatewayAlarms119    OBJECT-TYPE
    SYNTAX      SnmpAdminString (SIZE (0..31))
    MAX-ACCESS  read-only
    STATUS      current
    DESCRIPTION
        "
        Fld OID Name:   avCmStatusMedGatewayAlarms119
        Fld OID:        enterprises.6889.2.73.8.1.47.127
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 127 }

avCmStatusMedGatewayAlarms120    OBJECT-TYPE
    SYNTAX      SnmpAdminString (SIZE (0..31))
    MAX-ACCESS  read-only
    STATUS      current
    DESCRIPTION
        "
        Fld OID Name:   avCmStatusMedGatewayAlarms120
        Fld OID:        enterprises.6889.2.73.8.1.47.128
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 128 }

avCmStatusMedGatewayAlarms121    OBJECT-TYPE
    SYNTAX      SnmpAdminString (SIZE (0..31))
    MAX-ACCESS  read-only
    STATUS      current
    DESCRIPTION
        "
        Fld OID Name:   avCmStatusMedGatewayAlarms121
        Fld OID:        enterprises.6889.2.73.8.1.47.129
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 129 }

avCmStatusMedGatewayAlarms122    OBJECT-TYPE
    SYNTAX      SnmpAdminString (SIZE (0..31))
    MAX-ACCESS  read-only
    STATUS      current
    DESCRIPTION
        "
        Fld OID Name:   avCmStatusMedGatewayAlarms122
        Fld OID:        enterprises.6889.2.73.8.1.47.130
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 130 }

avCmStatusMedGatewayAlarms123    OBJECT-TYPE
    SYNTAX      SnmpAdminString (SIZE (0..31))
    MAX-ACCESS  read-only
    STATUS      current
    DESCRIPTION
        "
        Fld OID Name:   avCmStatusMedGatewayAlarms123
        Fld OID:        enterprises.6889.2.73.8.1.47.131
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 131 }

avCmStatusMedGatewayAlarms124    OBJECT-TYPE
    SYNTAX      SnmpAdminString (SIZE (0..31))
    MAX-ACCESS  read-only
    STATUS      current
    DESCRIPTION
        "
        Fld OID Name:   avCmStatusMedGatewayAlarms124
        Fld OID:        enterprises.6889.2.73.8.1.47.132
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 132 }

avCmStatusMedGatewayAlarms125    OBJECT-TYPE
    SYNTAX      SnmpAdminString (SIZE (0..31))
    MAX-ACCESS  read-only
    STATUS      current
    DESCRIPTION
        "
        Fld OID Name:   avCmStatusMedGatewayAlarms125
        Fld OID:        enterprises.6889.2.73.8.1.47.133
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 133 }

avCmStatusMedGatewayAlarms126    OBJECT-TYPE
    SYNTAX      SnmpAdminString (SIZE (0..31))
    MAX-ACCESS  read-only
    STATUS      current
    DESCRIPTION
        "
        Fld OID Name:   avCmStatusMedGatewayAlarms126
        Fld OID:        enterprises.6889.2.73.8.1.47.134
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 134 }

avCmStatusMedGatewayAlarms127    OBJECT-TYPE
    SYNTAX      SnmpAdminString (SIZE (0..31))
    MAX-ACCESS  read-only
    STATUS      current
    DESCRIPTION
        "
        Fld OID Name:   avCmStatusMedGatewayAlarms127
        Fld OID:        enterprises.6889.2.73.8.1.47.135
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 135 }

avCmStatusMedGatewayAlarms128    OBJECT-TYPE
    SYNTAX      SnmpAdminString (SIZE (0..31))
    MAX-ACCESS  read-only
    STATUS      current
    DESCRIPTION
        "
        Fld OID Name:   avCmStatusMedGatewayAlarms128
        Fld OID:        enterprises.6889.2.73.8.1.47.136
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 136 }

avCmStatusMedGatewayAlarms129    OBJECT-TYPE
    SYNTAX      SnmpAdminString (SIZE (0..31))
    MAX-ACCESS  read-only
    STATUS      current
    DESCRIPTION
        "
        Fld OID Name:   avCmStatusMedGatewayAlarms129
        Fld OID:        enterprises.6889.2.73.8.1.47.137
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 137 }

avCmStatusMedGatewayAlarms130    OBJECT-TYPE
    SYNTAX      SnmpAdminString (SIZE (0..31))
    MAX-ACCESS  read-only
    STATUS      current
    DESCRIPTION
        "
        Fld OID Name:   avCmStatusMedGatewayAlarms130
        Fld OID:        enterprises.6889.2.73.8.1.47.138
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 138 }

avCmStatusMedGatewayAlarms131    OBJECT-TYPE
    SYNTAX      SnmpAdminString (SIZE (0..31))
    MAX-ACCESS  read-only
    STATUS      current
    DESCRIPTION
        "
        Fld OID Name:   avCmStatusMedGatewayAlarms131
        Fld OID:        enterprises.6889.2.73.8.1.47.139
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 139 }

avCmStatusMedGatewayAlarms132    OBJECT-TYPE
    SYNTAX      SnmpAdminString (SIZE (0..31))
    MAX-ACCESS  read-only
    STATUS      current
    DESCRIPTION
        "
        Fld OID Name:   avCmStatusMedGatewayAlarms132
        Fld OID:        enterprises.6889.2.73.8.1.47.140
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 140 }

avCmStatusMedGatewayAlarms133    OBJECT-TYPE
    SYNTAX      SnmpAdminString (SIZE (0..31))
    MAX-ACCESS  read-only
    STATUS      current
    DESCRIPTION
        "
        Fld OID Name:   avCmStatusMedGatewayAlarms133
        Fld OID:        enterprises.6889.2.73.8.1.47.141
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 141 }

avCmStatusMedGatewayAlarms134    OBJECT-TYPE
    SYNTAX      SnmpAdminString (SIZE (0..31))
    MAX-ACCESS  read-only
    STATUS      current
    DESCRIPTION
        "
        Fld OID Name:   avCmStatusMedGatewayAlarms134
        Fld OID:        enterprises.6889.2.73.8.1.47.142
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 142 }

avCmStatusMedGatewayAlarms135    OBJECT-TYPE
    SYNTAX      SnmpAdminString (SIZE (0..31))
    MAX-ACCESS  read-only
    STATUS      current
    DESCRIPTION
        "
        Fld OID Name:   avCmStatusMedGatewayAlarms135
        Fld OID:        enterprises.6889.2.73.8.1.47.143
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 143 }

avCmStatusMedGatewayAlarms136    OBJECT-TYPE
    SYNTAX      SnmpAdminString (SIZE (0..31))
    MAX-ACCESS  read-only
    STATUS      current
    DESCRIPTION
        "
        Fld OID Name:   avCmStatusMedGatewayAlarms136
        Fld OID:        enterprises.6889.2.73.8.1.47.144
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 144 }

avCmStatusMedGatewayAlarms137    OBJECT-TYPE
    SYNTAX      SnmpAdminString (SIZE (0..31))
    MAX-ACCESS  read-only
    STATUS      current
    DESCRIPTION
        "
        Fld OID Name:   avCmStatusMedGatewayAlarms137
        Fld OID:        enterprises.6889.2.73.8.1.47.145
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 145 }

avCmStatusMedGatewayAlarms138    OBJECT-TYPE
    SYNTAX      SnmpAdminString (SIZE (0..31))
    MAX-ACCESS  read-only
    STATUS      current
    DESCRIPTION
        "
        Fld OID Name:   avCmStatusMedGatewayAlarms138
        Fld OID:        enterprises.6889.2.73.8.1.47.146
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 146 }

avCmStatusMedGatewayAlarms139    OBJECT-TYPE
    SYNTAX      SnmpAdminString (SIZE (0..31))
    MAX-ACCESS  read-only
    STATUS      current
    DESCRIPTION
        "
        Fld OID Name:   avCmStatusMedGatewayAlarms139
        Fld OID:        enterprises.6889.2.73.8.1.47.147
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 147 }

avCmStatusMedGatewayAlarms140    OBJECT-TYPE
    SYNTAX      SnmpAdminString (SIZE (0..31))
    MAX-ACCESS  read-only
    STATUS      current
    DESCRIPTION
        "
        Fld OID Name:   avCmStatusMedGatewayAlarms140
        Fld OID:        enterprises.6889.2.73.8.1.47.148
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 148 }

avCmStatusMedGatewayAlarms141    OBJECT-TYPE
    SYNTAX      SnmpAdminString (SIZE (0..31))
    MAX-ACCESS  read-only
    STATUS      current
    DESCRIPTION
        "
        Fld OID Name:   avCmStatusMedGatewayAlarms141
        Fld OID:        enterprises.6889.2.73.8.1.47.149
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 149 }

avCmStatusMedGatewayAlarms142    OBJECT-TYPE
    SYNTAX      SnmpAdminString (SIZE (0..31))
    MAX-ACCESS  read-only
    STATUS      current
    DESCRIPTION
        "
        Fld OID Name:   avCmStatusMedGatewayAlarms142
        Fld OID:        enterprises.6889.2.73.8.1.47.150
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 150 }

avCmStatusMedGatewayAlarms143    OBJECT-TYPE
    SYNTAX      SnmpAdminString (SIZE (0..31))
    MAX-ACCESS  read-only
    STATUS      current
    DESCRIPTION
        "
        Fld OID Name:   avCmStatusMedGatewayAlarms143
        Fld OID:        enterprises.6889.2.73.8.1.47.151
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 151 }

avCmStatusMedGatewayAlarms144    OBJECT-TYPE
    SYNTAX      SnmpAdminString (SIZE (0..31))
    MAX-ACCESS  read-only
    STATUS      current
    DESCRIPTION
        "
        Fld OID Name:   avCmStatusMedGatewayAlarms144
        Fld OID:        enterprises.6889.2.73.8.1.47.152
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 152 }

avCmStatusMedGatewayAlarms145    OBJECT-TYPE
    SYNTAX      SnmpAdminString (SIZE (0..31))
    MAX-ACCESS  read-only
    STATUS      current
    DESCRIPTION
        "
        Fld OID Name:   avCmStatusMedGatewayAlarms145
        Fld OID:        enterprises.6889.2.73.8.1.47.153
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 153 }

avCmStatusMedGatewayAlarms146    OBJECT-TYPE
    SYNTAX      SnmpAdminString (SIZE (0..31))
    MAX-ACCESS  read-only
    STATUS      current
    DESCRIPTION
        "
        Fld OID Name:   avCmStatusMedGatewayAlarms146
        Fld OID:        enterprises.6889.2.73.8.1.47.154
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 154 }

avCmStatusMedGatewayAlarms147    OBJECT-TYPE
    SYNTAX      SnmpAdminString (SIZE (0..31))
    MAX-ACCESS  read-only
    STATUS      current
    DESCRIPTION
        "
        Fld OID Name:   avCmStatusMedGatewayAlarms147
        Fld OID:        enterprises.6889.2.73.8.1.47.155
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 155 }

avCmStatusMedGatewayAlarms148    OBJECT-TYPE
    SYNTAX      SnmpAdminString (SIZE (0..31))
    MAX-ACCESS  read-only
    STATUS      current
    DESCRIPTION
        "
        Fld OID Name:   avCmStatusMedGatewayAlarms148
        Fld OID:        enterprises.6889.2.73.8.1.47.156
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 156 }

avCmStatusMedGatewayAlarms149    OBJECT-TYPE
    SYNTAX      SnmpAdminString (SIZE (0..31))
    MAX-ACCESS  read-only
    STATUS      current
    DESCRIPTION
        "
        Fld OID Name:   avCmStatusMedGatewayAlarms149
        Fld OID:        enterprises.6889.2.73.8.1.47.157
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 157 }

avCmStatusMedGatewayAlarms150    OBJECT-TYPE
    SYNTAX      SnmpAdminString (SIZE (0..31))
    MAX-ACCESS  read-only
    STATUS      current
    DESCRIPTION
        "
        Fld OID Name:   avCmStatusMedGatewayAlarms150
        Fld OID:        enterprises.6889.2.73.8.1.47.158
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 158 }

avCmStatusMedGatewayAlarms151    OBJECT-TYPE
    SYNTAX      SnmpAdminString (SIZE (0..31))
    MAX-ACCESS  read-only
    STATUS      current
    DESCRIPTION
        "
        Fld OID Name:   avCmStatusMedGatewayAlarms151
        Fld OID:        enterprises.6889.2.73.8.1.47.159
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 159 }

avCmStatusMedGatewayAlarms152    OBJECT-TYPE
    SYNTAX      SnmpAdminString (SIZE (0..31))
    MAX-ACCESS  read-only
    STATUS      current
    DESCRIPTION
        "
        Fld OID Name:   avCmStatusMedGatewayAlarms152
        Fld OID:        enterprises.6889.2.73.8.1.47.160
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 160 }

avCmStatusMedGatewayAlarms153    OBJECT-TYPE
    SYNTAX      SnmpAdminString (SIZE (0..31))
    MAX-ACCESS  read-only
    STATUS      current
    DESCRIPTION
        "
        Fld OID Name:   avCmStatusMedGatewayAlarms153
        Fld OID:        enterprises.6889.2.73.8.1.47.161
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 161 }

avCmStatusMedGatewayAlarms154    OBJECT-TYPE
    SYNTAX      SnmpAdminString (SIZE (0..31))
    MAX-ACCESS  read-only
    STATUS      current
    DESCRIPTION
        "
        Fld OID Name:   avCmStatusMedGatewayAlarms154
        Fld OID:        enterprises.6889.2.73.8.1.47.162
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 162 }

avCmStatusMedGatewayAlarms155    OBJECT-TYPE
    SYNTAX      SnmpAdminString (SIZE (0..31))
    MAX-ACCESS  read-only
    STATUS      current
    DESCRIPTION
        "
        Fld OID Name:   avCmStatusMedGatewayAlarms155
        Fld OID:        enterprises.6889.2.73.8.1.47.163
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 163 }

avCmStatusMedGatewayAlarms156    OBJECT-TYPE
    SYNTAX      SnmpAdminString (SIZE (0..31))
    MAX-ACCESS  read-only
    STATUS      current
    DESCRIPTION
        "
        Fld OID Name:   avCmStatusMedGatewayAlarms156
        Fld OID:        enterprises.6889.2.73.8.1.47.164
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 164 }

avCmStatusMedGatewayAlarms157    OBJECT-TYPE
    SYNTAX      SnmpAdminString (SIZE (0..31))
    MAX-ACCESS  read-only
    STATUS      current
    DESCRIPTION
        "
        Fld OID Name:   avCmStatusMedGatewayAlarms157
        Fld OID:        enterprises.6889.2.73.8.1.47.165
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 165 }

avCmStatusMedGatewayAlarms158    OBJECT-TYPE
    SYNTAX      SnmpAdminString (SIZE (0..31))
    MAX-ACCESS  read-only
    STATUS      current
    DESCRIPTION
        "
        Fld OID Name:   avCmStatusMedGatewayAlarms158
        Fld OID:        enterprises.6889.2.73.8.1.47.166
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 166 }

avCmStatusMedGatewayAlarms159    OBJECT-TYPE
    SYNTAX      SnmpAdminString (SIZE (0..31))
    MAX-ACCESS  read-only
    STATUS      current
    DESCRIPTION
        "
        Fld OID Name:   avCmStatusMedGatewayAlarms159
        Fld OID:        enterprises.6889.2.73.8.1.47.167
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 167 }

avCmStatusMedGatewayAlarms160    OBJECT-TYPE
    SYNTAX      SnmpAdminString (SIZE (0..31))
    MAX-ACCESS  read-only
    STATUS      current
    DESCRIPTION
        "
        Fld OID Name:   avCmStatusMedGatewayAlarms160
        Fld OID:        enterprises.6889.2.73.8.1.47.168
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 168 }

avCmStatusMedGatewayAlarms161    OBJECT-TYPE
    SYNTAX      SnmpAdminString (SIZE (0..31))
    MAX-ACCESS  read-only
    STATUS      current
    DESCRIPTION
        "
        Fld OID Name:   avCmStatusMedGatewayAlarms161
        Fld OID:        enterprises.6889.2.73.8.1.47.169
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 169 }

avCmStatusMedGatewayAlarms162    OBJECT-TYPE
    SYNTAX      SnmpAdminString (SIZE (0..31))
    MAX-ACCESS  read-only
    STATUS      current
    DESCRIPTION
        "
        Fld OID Name:   avCmStatusMedGatewayAlarms162
        Fld OID:        enterprises.6889.2.73.8.1.47.170
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 170 }

avCmStatusMedGatewayAlarms163    OBJECT-TYPE
    SYNTAX      SnmpAdminString (SIZE (0..31))
    MAX-ACCESS  read-only
    STATUS      current
    DESCRIPTION
        "
        Fld OID Name:   avCmStatusMedGatewayAlarms163
        Fld OID:        enterprises.6889.2.73.8.1.47.171
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 171 }

avCmStatusMedGatewayAlarms164    OBJECT-TYPE
    SYNTAX      SnmpAdminString (SIZE (0..31))
    MAX-ACCESS  read-only
    STATUS      current
    DESCRIPTION
        "
        Fld OID Name:   avCmStatusMedGatewayAlarms164
        Fld OID:        enterprises.6889.2.73.8.1.47.172
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 172 }

avCmStatusMedGatewayAlarms165    OBJECT-TYPE
    SYNTAX      SnmpAdminString (SIZE (0..31))
    MAX-ACCESS  read-only
    STATUS      current
    DESCRIPTION
        "
        Fld OID Name:   avCmStatusMedGatewayAlarms165
        Fld OID:        enterprises.6889.2.73.8.1.47.173
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 173 }

avCmStatusMedGatewayAlarms166    OBJECT-TYPE
    SYNTAX      SnmpAdminString (SIZE (0..31))
    MAX-ACCESS  read-only
    STATUS      current
    DESCRIPTION
        "
        Fld OID Name:   avCmStatusMedGatewayAlarms166
        Fld OID:        enterprises.6889.2.73.8.1.47.174
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 174 }

avCmStatusMedGatewayAlarms167    OBJECT-TYPE
    SYNTAX      SnmpAdminString (SIZE (0..31))
    MAX-ACCESS  read-only
    STATUS      current
    DESCRIPTION
        "
        Fld OID Name:   avCmStatusMedGatewayAlarms167
        Fld OID:        enterprises.6889.2.73.8.1.47.175
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 175 }

avCmStatusMedGatewayAlarms168    OBJECT-TYPE
    SYNTAX      SnmpAdminString (SIZE (0..31))
    MAX-ACCESS  read-only
    STATUS      current
    DESCRIPTION
        "
        Fld OID Name:   avCmStatusMedGatewayAlarms168
        Fld OID:        enterprises.6889.2.73.8.1.47.176
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 176 }

avCmStatusMedGatewayAlarms169    OBJECT-TYPE
    SYNTAX      SnmpAdminString (SIZE (0..31))
    MAX-ACCESS  read-only
    STATUS      current
    DESCRIPTION
        "
        Fld OID Name:   avCmStatusMedGatewayAlarms169
        Fld OID:        enterprises.6889.2.73.8.1.47.177
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 177 }

avCmStatusMedGatewayAlarms170    OBJECT-TYPE
    SYNTAX      SnmpAdminString (SIZE (0..31))
    MAX-ACCESS  read-only
    STATUS      current
    DESCRIPTION
        "
        Fld OID Name:   avCmStatusMedGatewayAlarms170
        Fld OID:        enterprises.6889.2.73.8.1.47.178
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 178 }

avCmStatusMedGatewayAlarms171    OBJECT-TYPE
    SYNTAX      SnmpAdminString (SIZE (0..31))
    MAX-ACCESS  read-only
    STATUS      current
    DESCRIPTION
        "
        Fld OID Name:   avCmStatusMedGatewayAlarms171
        Fld OID:        enterprises.6889.2.73.8.1.47.179
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 179 }

avCmStatusMedGatewayAlarms172    OBJECT-TYPE
    SYNTAX      SnmpAdminString (SIZE (0..31))
    MAX-ACCESS  read-only
    STATUS      current
    DESCRIPTION
        "
        Fld OID Name:   avCmStatusMedGatewayAlarms172
        Fld OID:        enterprises.6889.2.73.8.1.47.180
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 180 }

avCmStatusMedGatewayAlarms173    OBJECT-TYPE
    SYNTAX      SnmpAdminString (SIZE (0..31))
    MAX-ACCESS  read-only
    STATUS      current
    DESCRIPTION
        "
        Fld OID Name:   avCmStatusMedGatewayAlarms173
        Fld OID:        enterprises.6889.2.73.8.1.47.181
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 181 }

avCmStatusMedGatewayAlarms174    OBJECT-TYPE
    SYNTAX      SnmpAdminString (SIZE (0..31))
    MAX-ACCESS  read-only
    STATUS      current
    DESCRIPTION
        "
        Fld OID Name:   avCmStatusMedGatewayAlarms174
        Fld OID:        enterprises.6889.2.73.8.1.47.182
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 182 }

avCmStatusMedGatewayAlarms175    OBJECT-TYPE
    SYNTAX      SnmpAdminString (SIZE (0..31))
    MAX-ACCESS  read-only
    STATUS      current
    DESCRIPTION
        "
        Fld OID Name:   avCmStatusMedGatewayAlarms175
        Fld OID:        enterprises.6889.2.73.8.1.47.183
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 183 }

avCmStatusMedGatewayAlarms176    OBJECT-TYPE
    SYNTAX      SnmpAdminString (SIZE (0..31))
    MAX-ACCESS  read-only
    STATUS      current
    DESCRIPTION
        "
        Fld OID Name:   avCmStatusMedGatewayAlarms176
        Fld OID:        enterprises.6889.2.73.8.1.47.184
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 184 }

avCmStatusMedGatewayAlarms177    OBJECT-TYPE
    SYNTAX      SnmpAdminString (SIZE (0..31))
    MAX-ACCESS  read-only
    STATUS      current
    DESCRIPTION
        "
        Fld OID Name:   avCmStatusMedGatewayAlarms177
        Fld OID:        enterprises.6889.2.73.8.1.47.185
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 185 }

avCmStatusMedGatewayAlarms178    OBJECT-TYPE
    SYNTAX      SnmpAdminString (SIZE (0..31))
    MAX-ACCESS  read-only
    STATUS      current
    DESCRIPTION
        "
        Fld OID Name:   avCmStatusMedGatewayAlarms178
        Fld OID:        enterprises.6889.2.73.8.1.47.186
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 186 }

avCmStatusMedGatewayAlarms179    OBJECT-TYPE
    SYNTAX      SnmpAdminString (SIZE (0..31))
    MAX-ACCESS  read-only
    STATUS      current
    DESCRIPTION
        "
        Fld OID Name:   avCmStatusMedGatewayAlarms179
        Fld OID:        enterprises.6889.2.73.8.1.47.187
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 187 }

avCmStatusMedGatewayAlarms180    OBJECT-TYPE
    SYNTAX      SnmpAdminString (SIZE (0..31))
    MAX-ACCESS  read-only
    STATUS      current
    DESCRIPTION
        "
        Fld OID Name:   avCmStatusMedGatewayAlarms180
        Fld OID:        enterprises.6889.2.73.8.1.47.188
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 188 }

avCmStatusMedGatewayAlarms181    OBJECT-TYPE
    SYNTAX      SnmpAdminString (SIZE (0..31))
    MAX-ACCESS  read-only
    STATUS      current
    DESCRIPTION
        "
        Fld OID Name:   avCmStatusMedGatewayAlarms181
        Fld OID:        enterprises.6889.2.73.8.1.47.189
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 189 }

avCmStatusMedGatewayAlarms182    OBJECT-TYPE
    SYNTAX      SnmpAdminString (SIZE (0..31))
    MAX-ACCESS  read-only
    STATUS      current
    DESCRIPTION
        "
        Fld OID Name:   avCmStatusMedGatewayAlarms182
        Fld OID:        enterprises.6889.2.73.8.1.47.190
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 190 }

avCmStatusMedGatewayAlarms183    OBJECT-TYPE
    SYNTAX      SnmpAdminString (SIZE (0..31))
    MAX-ACCESS  read-only
    STATUS      current
    DESCRIPTION
        "
        Fld OID Name:   avCmStatusMedGatewayAlarms183
        Fld OID:        enterprises.6889.2.73.8.1.47.191
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 191 }

avCmStatusMedGatewayAlarms184    OBJECT-TYPE
    SYNTAX      SnmpAdminString (SIZE (0..31))
    MAX-ACCESS  read-only
    STATUS      current
    DESCRIPTION
        "
        Fld OID Name:   avCmStatusMedGatewayAlarms184
        Fld OID:        enterprises.6889.2.73.8.1.47.192
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 192 }

avCmStatusMedGatewayAlarms185    OBJECT-TYPE
    SYNTAX      SnmpAdminString (SIZE (0..31))
    MAX-ACCESS  read-only
    STATUS      current
    DESCRIPTION
        "
        Fld OID Name:   avCmStatusMedGatewayAlarms185
        Fld OID:        enterprises.6889.2.73.8.1.47.193
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 193 }

avCmStatusMedGatewayAlarms186    OBJECT-TYPE
    SYNTAX      SnmpAdminString (SIZE (0..31))
    MAX-ACCESS  read-only
    STATUS      current
    DESCRIPTION
        "
        Fld OID Name:   avCmStatusMedGatewayAlarms186
        Fld OID:        enterprises.6889.2.73.8.1.47.194
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 194 }

avCmStatusMedGatewayAlarms187    OBJECT-TYPE
    SYNTAX      SnmpAdminString (SIZE (0..31))
    MAX-ACCESS  read-only
    STATUS      current
    DESCRIPTION
        "
        Fld OID Name:   avCmStatusMedGatewayAlarms187
        Fld OID:        enterprises.6889.2.73.8.1.47.195
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 195 }

avCmStatusMedGatewayAlarms188    OBJECT-TYPE
    SYNTAX      SnmpAdminString (SIZE (0..31))
    MAX-ACCESS  read-only
    STATUS      current
    DESCRIPTION
        "
        Fld OID Name:   avCmStatusMedGatewayAlarms188
        Fld OID:        enterprises.6889.2.73.8.1.47.196
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 196 }

avCmStatusMedGatewayAlarms189    OBJECT-TYPE
    SYNTAX      SnmpAdminString (SIZE (0..31))
    MAX-ACCESS  read-only
    STATUS      current
    DESCRIPTION
        "
        Fld OID Name:   avCmStatusMedGatewayAlarms189
        Fld OID:        enterprises.6889.2.73.8.1.47.197
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 197 }

avCmStatusMedGatewayAlarms190    OBJECT-TYPE
    SYNTAX      SnmpAdminString (SIZE (0..31))
    MAX-ACCESS  read-only
    STATUS      current
    DESCRIPTION
        "
        Fld OID Name:   avCmStatusMedGatewayAlarms190
        Fld OID:        enterprises.6889.2.73.8.1.47.198
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 198 }

avCmStatusMedGatewayAlarms191    OBJECT-TYPE
    SYNTAX      SnmpAdminString (SIZE (0..31))
    MAX-ACCESS  read-only
    STATUS      current
    DESCRIPTION
        "
        Fld OID Name:   avCmStatusMedGatewayAlarms191
        Fld OID:        enterprises.6889.2.73.8.1.47.199
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 199 }

avCmStatusMedGatewayAlarms192    OBJECT-TYPE
    SYNTAX      SnmpAdminString (SIZE (0..31))
    MAX-ACCESS  read-only
    STATUS      current
    DESCRIPTION
        "
        Fld OID Name:   avCmStatusMedGatewayAlarms192
        Fld OID:        enterprises.6889.2.73.8.1.47.200
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 200 }

avCmStatusMedGatewayAlarms193    OBJECT-TYPE
    SYNTAX      SnmpAdminString (SIZE (0..31))
    MAX-ACCESS  read-only
    STATUS      current
    DESCRIPTION
        "
        Fld OID Name:   avCmStatusMedGatewayAlarms193
        Fld OID:        enterprises.6889.2.73.8.1.47.201
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 201 }

avCmStatusMedGatewayAlarms194    OBJECT-TYPE
    SYNTAX      SnmpAdminString (SIZE (0..31))
    MAX-ACCESS  read-only
    STATUS      current
    DESCRIPTION
        "
        Fld OID Name:   avCmStatusMedGatewayAlarms194
        Fld OID:        enterprises.6889.2.73.8.1.47.202
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 202 }

avCmStatusMedGatewayAlarms195    OBJECT-TYPE
    SYNTAX      SnmpAdminString (SIZE (0..31))
    MAX-ACCESS  read-only
    STATUS      current
    DESCRIPTION
        "
        Fld OID Name:   avCmStatusMedGatewayAlarms195
        Fld OID:        enterprises.6889.2.73.8.1.47.203
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 203 }

avCmStatusMedGatewayAlarms196    OBJECT-TYPE
    SYNTAX      SnmpAdminString (SIZE (0..31))
    MAX-ACCESS  read-only
    STATUS      current
    DESCRIPTION
        "
        Fld OID Name:   avCmStatusMedGatewayAlarms196
        Fld OID:        enterprises.6889.2.73.8.1.47.204
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 204 }

avCmStatusMedGatewayAlarms197    OBJECT-TYPE
    SYNTAX      SnmpAdminString (SIZE (0..31))
    MAX-ACCESS  read-only
    STATUS      current
    DESCRIPTION
        "
        Fld OID Name:   avCmStatusMedGatewayAlarms197
        Fld OID:        enterprises.6889.2.73.8.1.47.205
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 205 }

avCmStatusMedGatewayAlarms198    OBJECT-TYPE
    SYNTAX      SnmpAdminString (SIZE (0..31))
    MAX-ACCESS  read-only
    STATUS      current
    DESCRIPTION
        "
        Fld OID Name:   avCmStatusMedGatewayAlarms198
        Fld OID:        enterprises.6889.2.73.8.1.47.206
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 206 }

avCmStatusMedGatewayAlarms199    OBJECT-TYPE
    SYNTAX      SnmpAdminString (SIZE (0..31))
    MAX-ACCESS  read-only
    STATUS      current
    DESCRIPTION
        "
        Fld OID Name:   avCmStatusMedGatewayAlarms199
        Fld OID:        enterprises.6889.2.73.8.1.47.207
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 207 }

avCmStatusMedGatewayAlarms200    OBJECT-TYPE
    SYNTAX      SnmpAdminString (SIZE (0..31))
    MAX-ACCESS  read-only
    STATUS      current
    DESCRIPTION
        "
        Fld OID Name:   avCmStatusMedGatewayAlarms200
        Fld OID:        enterprises.6889.2.73.8.1.47.208
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 208 }

avCmStatusMedGatewayAlarms201    OBJECT-TYPE
    SYNTAX      SnmpAdminString (SIZE (0..31))
    MAX-ACCESS  read-only
    STATUS      current
    DESCRIPTION
        "
        Fld OID Name:   avCmStatusMedGatewayAlarms201
        Fld OID:        enterprises.6889.2.73.8.1.47.209
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 209 }

avCmStatusMedGatewayAlarms202    OBJECT-TYPE
    SYNTAX      SnmpAdminString (SIZE (0..31))
    MAX-ACCESS  read-only
    STATUS      current
    DESCRIPTION
        "
        Fld OID Name:   avCmStatusMedGatewayAlarms202
        Fld OID:        enterprises.6889.2.73.8.1.47.210
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 210 }

avCmStatusMedGatewayAlarms203    OBJECT-TYPE
    SYNTAX      SnmpAdminString (SIZE (0..31))
    MAX-ACCESS  read-only
    STATUS      current
    DESCRIPTION
        "
        Fld OID Name:   avCmStatusMedGatewayAlarms203
        Fld OID:        enterprises.6889.2.73.8.1.47.211
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 211 }

avCmStatusMedGatewayAlarms204    OBJECT-TYPE
    SYNTAX      SnmpAdminString (SIZE (0..31))
    MAX-ACCESS  read-only
    STATUS      current
    DESCRIPTION
        "
        Fld OID Name:   avCmStatusMedGatewayAlarms204
        Fld OID:        enterprises.6889.2.73.8.1.47.212
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 212 }

avCmStatusMedGatewayAlarms205    OBJECT-TYPE
    SYNTAX      SnmpAdminString (SIZE (0..31))
    MAX-ACCESS  read-only
    STATUS      current
    DESCRIPTION
        "
        Fld OID Name:   avCmStatusMedGatewayAlarms205
        Fld OID:        enterprises.6889.2.73.8.1.47.213
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 213 }

avCmStatusMedGatewayAlarms206    OBJECT-TYPE
    SYNTAX      SnmpAdminString (SIZE (0..31))
    MAX-ACCESS  read-only
    STATUS      current
    DESCRIPTION
        "
        Fld OID Name:   avCmStatusMedGatewayAlarms206
        Fld OID:        enterprises.6889.2.73.8.1.47.214
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 214 }

avCmStatusMedGatewayAlarms207    OBJECT-TYPE
    SYNTAX      SnmpAdminString (SIZE (0..31))
    MAX-ACCESS  read-only
    STATUS      current
    DESCRIPTION
        "
        Fld OID Name:   avCmStatusMedGatewayAlarms207
        Fld OID:        enterprises.6889.2.73.8.1.47.215
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 215 }

avCmStatusMedGatewayAlarms208    OBJECT-TYPE
    SYNTAX      SnmpAdminString (SIZE (0..31))
    MAX-ACCESS  read-only
    STATUS      current
    DESCRIPTION
        "
        Fld OID Name:   avCmStatusMedGatewayAlarms208
        Fld OID:        enterprises.6889.2.73.8.1.47.216
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 216 }

avCmStatusMedGatewayAlarms209    OBJECT-TYPE
    SYNTAX      SnmpAdminString (SIZE (0..31))
    MAX-ACCESS  read-only
    STATUS      current
    DESCRIPTION
        "
        Fld OID Name:   avCmStatusMedGatewayAlarms209
        Fld OID:        enterprises.6889.2.73.8.1.47.217
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 217 }

avCmStatusMedGatewayAlarms210    OBJECT-TYPE
    SYNTAX      SnmpAdminString (SIZE (0..31))
    MAX-ACCESS  read-only
    STATUS      current
    DESCRIPTION
        "
        Fld OID Name:   avCmStatusMedGatewayAlarms210
        Fld OID:        enterprises.6889.2.73.8.1.47.218
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 218 }

avCmStatusMedGatewayAlarms211    OBJECT-TYPE
    SYNTAX      SnmpAdminString (SIZE (0..31))
    MAX-ACCESS  read-only
    STATUS      current
    DESCRIPTION
        "
        Fld OID Name:   avCmStatusMedGatewayAlarms211
        Fld OID:        enterprises.6889.2.73.8.1.47.219
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 219 }

avCmStatusMedGatewayAlarms212    OBJECT-TYPE
    SYNTAX      SnmpAdminString (SIZE (0..31))
    MAX-ACCESS  read-only
    STATUS      current
    DESCRIPTION
        "
        Fld OID Name:   avCmStatusMedGatewayAlarms212
        Fld OID:        enterprises.6889.2.73.8.1.47.220
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 220 }

avCmStatusMedGatewayAlarms213    OBJECT-TYPE
    SYNTAX      SnmpAdminString (SIZE (0..31))
    MAX-ACCESS  read-only
    STATUS      current
    DESCRIPTION
        "
        Fld OID Name:   avCmStatusMedGatewayAlarms213
        Fld OID:        enterprises.6889.2.73.8.1.47.221
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 221 }

avCmStatusMedGatewayAlarms214    OBJECT-TYPE
    SYNTAX      SnmpAdminString (SIZE (0..31))
    MAX-ACCESS  read-only
    STATUS      current
    DESCRIPTION
        "
        Fld OID Name:   avCmStatusMedGatewayAlarms214
        Fld OID:        enterprises.6889.2.73.8.1.47.222
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 222 }

avCmStatusMedGatewayAlarms215    OBJECT-TYPE
    SYNTAX      SnmpAdminString (SIZE (0..31))
    MAX-ACCESS  read-only
    STATUS      current
    DESCRIPTION
        "
        Fld OID Name:   avCmStatusMedGatewayAlarms215
        Fld OID:        enterprises.6889.2.73.8.1.47.223
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 223 }

avCmStatusMedGatewayAlarms216    OBJECT-TYPE
    SYNTAX      SnmpAdminString (SIZE (0..31))
    MAX-ACCESS  read-only
    STATUS      current
    DESCRIPTION
        "
        Fld OID Name:   avCmStatusMedGatewayAlarms216
        Fld OID:        enterprises.6889.2.73.8.1.47.224
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 224 }

avCmStatusMedGatewayAlarms217    OBJECT-TYPE
    SYNTAX      SnmpAdminString (SIZE (0..31))
    MAX-ACCESS  read-only
    STATUS      current
    DESCRIPTION
        "
        Fld OID Name:   avCmStatusMedGatewayAlarms217
        Fld OID:        enterprises.6889.2.73.8.1.47.225
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 225 }

avCmStatusMedGatewayAlarms218    OBJECT-TYPE
    SYNTAX      SnmpAdminString (SIZE (0..31))
    MAX-ACCESS  read-only
    STATUS      current
    DESCRIPTION
        "
        Fld OID Name:   avCmStatusMedGatewayAlarms218
        Fld OID:        enterprises.6889.2.73.8.1.47.226
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 226 }

avCmStatusMedGatewayAlarms219    OBJECT-TYPE
    SYNTAX      SnmpAdminString (SIZE (0..31))
    MAX-ACCESS  read-only
    STATUS      current
    DESCRIPTION
        "
        Fld OID Name:   avCmStatusMedGatewayAlarms219
        Fld OID:        enterprises.6889.2.73.8.1.47.227
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 227 }

avCmStatusMedGatewayAlarms220    OBJECT-TYPE
    SYNTAX      SnmpAdminString (SIZE (0..31))
    MAX-ACCESS  read-only
    STATUS      current
    DESCRIPTION
        "
        Fld OID Name:   avCmStatusMedGatewayAlarms220
        Fld OID:        enterprises.6889.2.73.8.1.47.228
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 228 }

avCmStatusMedGatewayAlarms221    OBJECT-TYPE
    SYNTAX      SnmpAdminString (SIZE (0..31))
    MAX-ACCESS  read-only
    STATUS      current
    DESCRIPTION
        "
        Fld OID Name:   avCmStatusMedGatewayAlarms221
        Fld OID:        enterprises.6889.2.73.8.1.47.229
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 229 }

avCmStatusMedGatewayAlarms222    OBJECT-TYPE
    SYNTAX      SnmpAdminString (SIZE (0..31))
    MAX-ACCESS  read-only
    STATUS      current
    DESCRIPTION
        "
        Fld OID Name:   avCmStatusMedGatewayAlarms222
        Fld OID:        enterprises.6889.2.73.8.1.47.230
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 230 }

avCmStatusMedGatewayAlarms223    OBJECT-TYPE
    SYNTAX      SnmpAdminString (SIZE (0..31))
    MAX-ACCESS  read-only
    STATUS      current
    DESCRIPTION
        "
        Fld OID Name:   avCmStatusMedGatewayAlarms223
        Fld OID:        enterprises.6889.2.73.8.1.47.231
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 231 }

avCmStatusMedGatewayAlarms224    OBJECT-TYPE
    SYNTAX      SnmpAdminString (SIZE (0..31))
    MAX-ACCESS  read-only
    STATUS      current
    DESCRIPTION
        "
        Fld OID Name:   avCmStatusMedGatewayAlarms224
        Fld OID:        enterprises.6889.2.73.8.1.47.232
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 232 }

avCmStatusMedGatewayAlarms225    OBJECT-TYPE
    SYNTAX      SnmpAdminString (SIZE (0..31))
    MAX-ACCESS  read-only
    STATUS      current
    DESCRIPTION
        "
        Fld OID Name:   avCmStatusMedGatewayAlarms225
        Fld OID:        enterprises.6889.2.73.8.1.47.233
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 233 }

avCmStatusMedGatewayAlarms226    OBJECT-TYPE
    SYNTAX      SnmpAdminString (SIZE (0..31))
    MAX-ACCESS  read-only
    STATUS      current
    DESCRIPTION
        "
        Fld OID Name:   avCmStatusMedGatewayAlarms226
        Fld OID:        enterprises.6889.2.73.8.1.47.234
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 234 }

avCmStatusMedGatewayAlarms227    OBJECT-TYPE
    SYNTAX      SnmpAdminString (SIZE (0..31))
    MAX-ACCESS  read-only
    STATUS      current
    DESCRIPTION
        "
        Fld OID Name:   avCmStatusMedGatewayAlarms227
        Fld OID:        enterprises.6889.2.73.8.1.47.235
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 235 }

avCmStatusMedGatewayAlarms228    OBJECT-TYPE
    SYNTAX      SnmpAdminString (SIZE (0..31))
    MAX-ACCESS  read-only
    STATUS      current
    DESCRIPTION
        "
        Fld OID Name:   avCmStatusMedGatewayAlarms228
        Fld OID:        enterprises.6889.2.73.8.1.47.236
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 236 }

avCmStatusMedGatewayAlarms229    OBJECT-TYPE
    SYNTAX      SnmpAdminString (SIZE (0..331))
    MAX-ACCESS  read-only
    STATUS      current
    DESCRIPTION
        "
        Fld OID Name:   avCmStatusMedGatewayAlarms229
        Fld OID:        enterprises.6889.2.73.8.1.47.237
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 237 }

avCmStatusMedGatewayAlarms230    OBJECT-TYPE
    SYNTAX      SnmpAdminString (SIZE (0..31))
    MAX-ACCESS  read-only
    STATUS      current
    DESCRIPTION
        "
        Fld OID Name:   avCmStatusMedGatewayAlarms230
        Fld OID:        enterprises.6889.2.73.8.1.47.238
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 238 }

avCmStatusMedGatewayAlarms231    OBJECT-TYPE
    SYNTAX      SnmpAdminString (SIZE (0..31))
    MAX-ACCESS  read-only
    STATUS      current
    DESCRIPTION
        "
        Fld OID Name:   avCmStatusMedGatewayAlarms231
        Fld OID:        enterprises.6889.2.73.8.1.47.239
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 239 }

avCmStatusMedGatewayAlarms232    OBJECT-TYPE
    SYNTAX      SnmpAdminString (SIZE (0..31))
    MAX-ACCESS  read-only
    STATUS      current
    DESCRIPTION
        "
        Fld OID Name:   avCmStatusMedGatewayAlarms232
        Fld OID:        enterprises.6889.2.73.8.1.47.240
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 240 }

avCmStatusMedGatewayAlarms233    OBJECT-TYPE
    SYNTAX      SnmpAdminString (SIZE (0..31))
    MAX-ACCESS  read-only
    STATUS      current
    DESCRIPTION
        "
        Fld OID Name:   avCmStatusMedGatewayAlarms233
        Fld OID:        enterprises.6889.2.73.8.1.47.241
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 241 }

avCmStatusMedGatewayAlarms234    OBJECT-TYPE
    SYNTAX      SnmpAdminString (SIZE (0..31))
    MAX-ACCESS  read-only
    STATUS      current
    DESCRIPTION
        "
        Fld OID Name:   avCmStatusMedGatewayAlarms234
        Fld OID:        enterprises.6889.2.73.8.1.47.242
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 242 }

avCmStatusMedGatewayAlarms235    OBJECT-TYPE
    SYNTAX      SnmpAdminString (SIZE (0..31))
    MAX-ACCESS  read-only
    STATUS      current
    DESCRIPTION
        "
        Fld OID Name:   avCmStatusMedGatewayAlarms235
        Fld OID:        enterprises.6889.2.73.8.1.47.243
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 243 }

avCmStatusMedGatewayAlarms236    OBJECT-TYPE
    SYNTAX      SnmpAdminString (SIZE (0..31))
    MAX-ACCESS  read-only
    STATUS      current
    DESCRIPTION
        "
        Fld OID Name:   avCmStatusMedGatewayAlarms236
        Fld OID:        enterprises.6889.2.73.8.1.47.244
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 244 }

avCmStatusMedGatewayAlarms237    OBJECT-TYPE
    SYNTAX      SnmpAdminString (SIZE (0..31))
    MAX-ACCESS  read-only
    STATUS      current
    DESCRIPTION
        "
        Fld OID Name:   avCmStatusMedGatewayAlarms237
        Fld OID:        enterprises.6889.2.73.8.1.47.245
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 245 }

avCmStatusMedGatewayAlarms238    OBJECT-TYPE
    SYNTAX      SnmpAdminString (SIZE (0..31))
    MAX-ACCESS  read-only
    STATUS      current
    DESCRIPTION
        "
        Fld OID Name:   avCmStatusMedGatewayAlarms238
        Fld OID:        enterprises.6889.2.73.8.1.47.246
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 246 }

avCmStatusMedGatewayAlarms239    OBJECT-TYPE
    SYNTAX      SnmpAdminString (SIZE (0..31))
    MAX-ACCESS  read-only
    STATUS      current
    DESCRIPTION
        "
        Fld OID Name:   avCmStatusMedGatewayAlarms239
        Fld OID:        enterprises.6889.2.73.8.1.47.247
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 247 }

avCmStatusMedGatewayAlarms240    OBJECT-TYPE
    SYNTAX      SnmpAdminString (SIZE (0..31))
    MAX-ACCESS  read-only
    STATUS      current
    DESCRIPTION
        "
        Fld OID Name:   avCmStatusMedGatewayAlarms240
        Fld OID:        enterprises.6889.2.73.8.1.47.248
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 248 }

avCmStatusMedGatewayAlarms241    OBJECT-TYPE
    SYNTAX      SnmpAdminString (SIZE (0..31))
    MAX-ACCESS  read-only
    STATUS      current
    DESCRIPTION
        "
        Fld OID Name:   avCmStatusMedGatewayAlarms241
        Fld OID:        enterprises.6889.2.73.8.1.47.249
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 249 }

avCmStatusMedGatewayAlarms242    OBJECT-TYPE
    SYNTAX      SnmpAdminString (SIZE (0..31))
    MAX-ACCESS  read-only
    STATUS      current
    DESCRIPTION
        "
        Fld OID Name:   avCmStatusMedGatewayAlarms242
        Fld OID:        enterprises.6889.2.73.8.1.47.250
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 250 }

avCmStatusMedGatewayAlarms243    OBJECT-TYPE
    SYNTAX      SnmpAdminString (SIZE (0..31))
    MAX-ACCESS  read-only
    STATUS      current
    DESCRIPTION
        "
        Fld OID Name:   avCmStatusMedGatewayAlarms243
        Fld OID:        enterprises.6889.2.73.8.1.47.251
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 251 }

avCmStatusMedGatewayAlarms244    OBJECT-TYPE
    SYNTAX      SnmpAdminString (SIZE (0..31))
    MAX-ACCESS  read-only
    STATUS      current
    DESCRIPTION
        "
        Fld OID Name:   avCmStatusMedGatewayAlarms244
        Fld OID:        enterprises.6889.2.73.8.1.47.252
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 252 }

avCmStatusMedGatewayAlarms245    OBJECT-TYPE
    SYNTAX      SnmpAdminString (SIZE (0..31))
    MAX-ACCESS  read-only
    STATUS      current
    DESCRIPTION
        "
        Fld OID Name:   avCmStatusMedGatewayAlarms245
        Fld OID:        enterprises.6889.2.73.8.1.47.253
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 253 }

avCmStatusMedGatewayAlarms246    OBJECT-TYPE
    SYNTAX      SnmpAdminString (SIZE (0..31))
    MAX-ACCESS  read-only
    STATUS      current
    DESCRIPTION
        "
        Fld OID Name:   avCmStatusMedGatewayAlarms246
        Fld OID:        enterprises.6889.2.73.8.1.47.254
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 254 }

avCmStatusMedGatewayAlarms247    OBJECT-TYPE
    SYNTAX      SnmpAdminString (SIZE (0..31))
    MAX-ACCESS  read-only
    STATUS      current
    DESCRIPTION
        "
        Fld OID Name:   avCmStatusMedGatewayAlarms247
        Fld OID:        enterprises.6889.2.73.8.1.47.255
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 255 }

avCmStatusMedGatewayAlarms248    OBJECT-TYPE
    SYNTAX      SnmpAdminString (SIZE (0..31))
    MAX-ACCESS  read-only
    STATUS      current
    DESCRIPTION
        "
        Fld OID Name:   avCmStatusMedGatewayAlarms248
        Fld OID:        enterprises.6889.2.73.8.1.47.256
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 256 }

avCmStatusMedGatewayAlarms249    OBJECT-TYPE
    SYNTAX      SnmpAdminString (SIZE (0..31))
    MAX-ACCESS  read-only
    STATUS      current
    DESCRIPTION
        "
        Fld OID Name:   avCmStatusMedGatewayAlarms249
        Fld OID:        enterprises.6889.2.73.8.1.47.257
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 257 }

avCmStatusMedGatewayAlarms250    OBJECT-TYPE
    SYNTAX      SnmpAdminString (SIZE (0..31))
    MAX-ACCESS  read-only
    STATUS      current
    DESCRIPTION
        "
        Fld OID Name:   avCmStatusMedGatewayAlarms250
        Fld OID:        enterprises.6889.2.73.8.1.47.258
        Fld Form/Rpt:   status media-gateways
	Fld Format:	Single Field with the following Labels:
			MG  Mj  Mn Wn Lk
        Fld(s) Name:    Alarms
        Fld Descr:      An object containing the status of the first set of
                        eight media gateways, including the number of major
                        alarms, minor alarms, warnings, and the H.248 link
                        status for each specific media gateway number.
        "
    ::= { avCmStatusMedGateway 258 }


-- ******************** avCmListIpUnregistered Group *************************

-- MIB GROUP DESCRIPTION

-- MIB Group Name:
--		avCmListIpUnregistered Group
-- OID:
--		enterprises.6889.2.73.8.1.48
-- Description:
--		The avCmListIpUnregistered MIB Group uses the 
--		"list multimedia ip-unregistered" command to 
-- 		retrieve unregistered end-point data.
--		
-- Releases Supported:
--		CM6.3.100 and greater
-- Polling Type:
--		Inventory
-- Polling Interval:
--		No more than once every 20 minutes.
-- Default Caching Interval
-- 		600 seconds
-- Timeout Interval:
--		Initial Timeout should be set to 20 seconds.
-- Retry Interval:
--		Initial Retry should be set to 3.
-- Limitations:
--              Yellow/Medium - The data collected by this MIB Group
--              may have some impact on the system.
-- Command Type:
--		1. SAT
-- Command:
--		1. list multimedia ip-unregistered
-- Form/Report Name:
--		1. UNREGISTERED IP TELEPHONES
-- Reference Document:
--		1. A detailed description of the command and form can be
--		   found in document referenced by REF_DOC_3 in the
--		   DOCUMENT REFERENCE SECTION.
-- Command Permission/User-profile:
--		1. No special permissions needed.

avCmListIpUnregistered	OBJECT IDENTIFIER ::= { avCmObjects 48 }

avCmListIpUnregisteredTable	OBJECT-TYPE
    SYNTAX	SEQUENCE OF AvCmListIpUnregisteredEntry
    MAX-ACCESS	not-accessible
    STATUS	current
    DESCRIPTION
	"
	Fld OID Name:	avCmListIpUnregisteredEntry
	Fld OID:	enterprises.6889.2.73.8.1.48.1
	Fld Form/Rpt:	NA
	Fld Format:	NA
	Fld(s) Name:	NA
	Fld Descr:	A list of the avCmListIpUnregistered entries
	"
    ::= { avCmListIpUnregistered 1 }

avCmListIpUnregisteredEntry	OBJECT-TYPE
    SYNTAX	AvCmListIpUnregisteredEntry
    MAX-ACCESS	not-accessible
    STATUS	current
    DESCRIPTION
	"
	Fld OID Name:	avCmListIpUnregisteredEntry
	Fld OID:	enterprises.6889.2.73.8.1.48.1.1
	Fld Form/Rpt:	NA
	Fld Format:	NA
	Fld(s) Name:	NA
	Fld Descr:	A avCmListIpUnregistered entry containing objects of the
			avCmListIpUnregistered information sent by the switch.
	"
    INDEX    { avCmListIpUnregisteredExtIdx }
    ::= { avCmListIpUnregisteredTable 1 }

AvCmListIpUnregisteredEntry ::= SEQUENCE {
		avCmListIpUnregisteredExtIdx
		    SnmpAdminString,
		avCmListIpUnregisteredExtension
		    SnmpAdminString,
		avCmListIpUnregisteredPort
		    SnmpAdminString,
		avCmListIpUnregisteredRegistered
		    SnmpAdminString
		}

avCmListIpUnregisteredExtIdx	OBJECT-TYPE
    SYNTAX	SnmpAdminString (SIZE (0..17))
    MAX-ACCESS	not-accessible
    STATUS	current
    DESCRIPTION
	"
	Fld OID Name:	avCmListIpUnregisteredExtIdx
	Fld OID:	enterprises.6889.2.73.8.1.48.1.1.1
	Fld Format:	NA
	Fld(s) Name:	NA
	Fld Descr:	An object that uniquely identifies each Increment of 
			data.
	"
    ::= { avCmListIpUnregisteredEntry 1 }

avCmListIpUnregisteredExtension	OBJECT-TYPE
    SYNTAX	SnmpAdminString (SIZE (0..17))
    MAX-ACCESS	read-only
    STATUS	current
    DESCRIPTION
	"
	Fld OID Name:	avCmListIpUnregisteredExtension
	Fld OID:	enterprises.6889.2.73.8.1.48.1.1.2
	Fld Form/Rpt:	UNREGISTERED IP TELEPHONES
	Fld Format:	Single Field
	Fld(s) Name:	Extension
	Fld Descr:	An object containing the Extension.
	"
    ::= { avCmListIpUnregisteredEntry 2 }

avCmListIpUnregisteredPort	OBJECT-TYPE
    SYNTAX	SnmpAdminString (SIZE (0..9))
    MAX-ACCESS	read-only
    STATUS	current
    DESCRIPTION
	"
	Fld OID Name:	avCmListIpUnregisteredPort
	Fld OID:	enterprises.6889.2.73.8.1.48.1.1.3
	Fld Form/Rpt:	UNREGISTERED IP TELEPHONES
	Fld Format:	Single Field
	Fld(s) Name:	Port
	Fld Descr:	An object containing the Port of the unregistered
			end-point.
	"
    ::= { avCmListIpUnregisteredEntry 3 }

avCmListIpUnregisteredRegistered   OBJECT-TYPE
    SYNTAX	SnmpAdminString (SIZE (0..2))
    MAX-ACCESS  read-only
    STATUS      current
    DESCRIPTION
        "
        Fld OID Name:   avCmListIpUnregisteredRegistered
        Fld OID:        enterprises.6889.2.73.8.1.48.1.1.4
        Fld Form/Rpt:   UNREGISTERED IP TELEPHONES
        Fld Format:     Single Field
        Fld(s) Name:    Registered?
        Fld Descr:      An object containing a 'y' or 'n' value indicating
			whether the end-point is registered.
        "
    ::= { avCmListIpUnregisteredEntry 4 }


-- ******************** avCmListSurvProcess Group *************************

-- MIB GROUP DESCRIPTION

-- MIB Group Name:
--		avCmListSurvProcess Group
-- OID:
--		enterprises.6889.2.73.8.1.49
-- Description:
--		The avCmListSurvProcess MIB Group uses the 
--		"list survivable-processor" command to 
-- 		retrieve survivable-processor data.
--		
-- Releases Supported:
--		CM6.3.100 and greater
-- Polling Type:
--		Inventory
-- Polling Interval:
--		No more than once a day.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. list survivable-processor
-- Form/Report Name:
--		1. SURVIVABLE PROCESSORS
-- Reference Document:
--		1. A detailed description of the command and form can be
--		   found in document referenced by REF_DOC_3 in the
--		   DOCUMENT REFERENCE SECTION.
-- Command Permission/User-profile:
--		1. No special permissions needed.

avCmListSurvProcess	OBJECT IDENTIFIER ::= { avCmObjects 49 }

avCmListSurvProcessTable	OBJECT-TYPE
    SYNTAX	SEQUENCE OF AvCmListSurvProcessEntry
    MAX-ACCESS	not-accessible
    STATUS	current
    DESCRIPTION
	"
	Fld OID Name:	avCmListSurvProcessEntry
	Fld OID:	enterprises.6889.2.73.8.1.49.1
	Fld Form/Rpt:	NA
	Fld Format:	NA
	Fld(s) Name:	NA
	Fld Descr:	A list of the avCmListSurvProcess entries
	"
    ::= { avCmListSurvProcess 1 }

avCmListSurvProcessEntry	OBJECT-TYPE
    SYNTAX	AvCmListSurvProcessEntry
    MAX-ACCESS	not-accessible
    STATUS	current
    DESCRIPTION
	"
	Fld OID Name:	avCmListSurvProcessEntry
	Fld OID:	enterprises.6889.2.73.8.1.49.1.1
	Fld Form/Rpt:	NA
	Fld Format:	NA
	Fld(s) Name:	NA
	Fld Descr:	A avCmListSurvProcess entry containing objects of the
			avCmListSurvProcess information sent by the switch.
	"
    INDEX    { avCmListSurvProcessNumIdx }
    ::= { avCmListSurvProcessTable 1 }

AvCmListSurvProcessEntry ::= SEQUENCE {
		avCmListSurvProcessNumIdx
		    Integer32,
		avCmListSurvProcessNumber
		    Integer32,
		avCmListSurvProcessName
		    SnmpAdminString,
		avCmListSurvProcessType
		    SnmpAdminString,
		avCmListSurvProcessReg
		    SnmpAdminString,
		avCmListSurvProcessAct
		    SnmpAdminString,
		avCmListSurvProcessTransUpdated
		    SnmpAdminString,
		avCmListSurvProcessNetRgn
		    Integer32,
		avCmListSurvProcessIpAddress
		    SnmpAdminString,
		avCmListSurvProcessIPV6Name
		    SnmpAdminString,
		avCmListSurvProcessIPV6Address
		    SnmpAdminString
		}

avCmListSurvProcessNumIdx	OBJECT-TYPE
    SYNTAX      Integer32 (0..9999)
    MAX-ACCESS	not-accessible
    STATUS	current
    DESCRIPTION
	"
	Fld OID Name:	avCmListSurvProcessNumIdx
	Fld OID:	enterprises.6889.2.73.8.1.49.1.1.1
	Fld Format:	NA
	Fld(s) Name:	NA
	Fld Descr:	An object that uniquely identifies each Increment of 
			data.
	"
    ::= { avCmListSurvProcessEntry 1 }

avCmListSurvProcessNumber	OBJECT-TYPE
    SYNTAX      Integer32 (0..9999)
    MAX-ACCESS	read-only
    STATUS	current
    DESCRIPTION
	"
	Fld OID Name:	avCmListSurvProcessNumber
	Fld OID:	enterprises.6889.2.73.8.1.49.1.1.2
	Fld Form/Rpt:	SURVIVABLE PROCESSORS
	Fld Format:	Single Field
	Fld(s) Name:	Number
	Fld Descr:	An object containing the Record Number.
	"
    ::= { avCmListSurvProcessEntry 2 }

avCmListSurvProcessName	OBJECT-TYPE
    SYNTAX	SnmpAdminString (SIZE (0..16))
    MAX-ACCESS	read-only
    STATUS	current
    DESCRIPTION
	"
	Fld OID Name:	avCmListSurvProcessName
	Fld OID:	enterprises.6889.2.73.8.1.49.1.1.3
	Fld Form/Rpt:	SURVIVABLE PROCESSORS
	Fld Format:	Single Field
	Fld(s) Name:	Name
	Fld Descr:	An object containing the Name of the survivable 
			processor.
	"
    ::= { avCmListSurvProcessEntry 3 }

avCmListSurvProcessType   OBJECT-TYPE
    SYNTAX	SnmpAdminString (SIZE (0..6))
    MAX-ACCESS  read-only
    STATUS      current
    DESCRIPTION
        "
        Fld OID Name:   avCmListSurvProcessType
        Fld OID:        enterprises.6889.2.73.8.1.49.1.1.4
        Fld Form/Rpt:   SURVIVABLE PROCESSORS
        Fld Format:     Single Field
        Fld(s) Name:    Type
        Fld Descr:      An object containing the type of survivable processor.
        "
    ::= { avCmListSurvProcessEntry 4 }


avCmListSurvProcessReg   OBJECT-TYPE
    SYNTAX	SnmpAdminString (SIZE (0..2))
    MAX-ACCESS  read-only
    STATUS      current
    DESCRIPTION
        "
        Fld OID Name:   avCmListSurvProcessReg
        Fld OID:        enterprises.6889.2.73.8.1.49.1.1.5
        Fld Form/Rpt:   SURVIVABLE PROCESSORS
        Fld Format:     Single Field
        Fld(s) Name:    Reg
        Fld Descr:      An object containing whether the survivable processor
			is registered.
        "
    ::= { avCmListSurvProcessEntry 5 }


avCmListSurvProcessAct   OBJECT-TYPE
    SYNTAX	SnmpAdminString (SIZE (0..2))
    MAX-ACCESS  read-only
    STATUS      current
    DESCRIPTION
        "
        Fld OID Name:   avCmListSurvProcessAct
        Fld OID:        enterprises.6889.2.73.8.1.49.1.1.6
        Fld Form/Rpt:   SURVIVABLE PROCESSORS
        Fld Format:     Single Field
        Fld(s) Name:    Act
        Fld Descr:      An object containing whether the survivable processor
			is active.
        "
    ::= { avCmListSurvProcessEntry 6 }


avCmListSurvProcessTransUpdated   OBJECT-TYPE
    SYNTAX	SnmpAdminString (SIZE (0..18))
    MAX-ACCESS  read-only
    STATUS      current
    DESCRIPTION
        "
        Fld OID Name:   avCmListSurvProcessTransUpdated
        Fld OID:        enterprises.6889.2.73.8.1.49.1.1.7
        Fld Form/Rpt:   SURVIVABLE PROCESSORS
        Fld Format:     Single Field
        Fld(s) Name:    Translations Updated
        Fld Descr:      An object containing when the survivable processor
			translations were last updated.
        "
    ::= { avCmListSurvProcessEntry 7 }


avCmListSurvProcessNetRgn   OBJECT-TYPE
    SYNTAX      Integer32 (0..9999)
    MAX-ACCESS  read-only
    STATUS      current
    DESCRIPTION
        "
        Fld OID Name:   avCmListSurvProcessNetRgn
        Fld OID:        enterprises.6889.2.73.8.1.49.1.1.8
        Fld Form/Rpt:   SURVIVABLE PROCESSORS
        Fld Format:     Single Field
        Fld(s) Name:    Net Rgn
        Fld Descr:      An object containing the network region the survivable 
			processor is using.
        "
    ::= { avCmListSurvProcessEntry 8 }


avCmListSurvProcessIpAddress   OBJECT-TYPE
    SYNTAX	SnmpAdminString (SIZE (0..41))
    MAX-ACCESS  read-only
    STATUS      current
    DESCRIPTION
        "
        Fld OID Name:   avCmListSurvProcessIpAddress
        Fld OID:        enterprises.6889.2.73.8.1.49.1.1.9
        Fld Form/Rpt:   SURVIVABLE PROCESSORS
        Fld Format:     Single Field
        Fld(s) Name:    IP Address
        Fld Descr:      An object containing the IP address the survivable 
			processor is using.
        "
    ::= { avCmListSurvProcessEntry 9 }

avCmListSurvProcessIPV6Name   OBJECT-TYPE
    SYNTAX	SnmpAdminString (SIZE (0..16))
    MAX-ACCESS  read-only
    STATUS      current
    DESCRIPTION
        "
        Fld OID Name:   avCmListSurvProcessIPV6Name
        Fld OID:        enterprises.6889.2.73.8.1.49.1.1.10
        Fld Form/Rpt:   SURVIVABLE PROCESSORS
        Fld Format:     Single Field
        Fld(s) Name:    IPV6 Address Name 
        Fld Descr:      An object containing the Name of the IPV6 address the
			survivable processor is using.
        "
    ::= { avCmListSurvProcessEntry 10 }

avCmListSurvProcessIPV6Address   OBJECT-TYPE
    SYNTAX	SnmpAdminString (SIZE (0..41))
    MAX-ACCESS  read-only
    STATUS      current
    DESCRIPTION
        "
        Fld OID Name:   avCmListSurvProcessIPV6Address
        Fld OID:        enterprises.6889.2.73.8.1.49.1.1.11
        Fld Form/Rpt:   SURVIVABLE PROCESSORS
        Fld Format:     Single Field
        Fld(s) Name:    IPV6 Address
        Fld Descr:      An object containing the IPV6 address the
			survivable processor is using.
        "
    ::= { avCmListSurvProcessEntry 11 }

-- ******************** avCmDispSurvProcess Group *************************

-- MIB GROUP DESCRIPTION

-- MIB Group Name:
--		avCmDispSurvProcess Group
-- OID:
--		enterprises.6889.2.73.8.1.50
-- Description:
--		The avCmDispSurvProcess MIB Group uses the 
--		"display survivable-processor xxx" command to 
-- 		retrieve survivable-processor data.
--		
-- Releases Supported:
--		CM6.3.100 and greater
-- Polling Type:
--		Inventory
-- Polling Interval:
--		No more than once a day.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. display survivable-processor
-- Form/Report Name:
--		1. SURVIVABLE PROCESSORS
-- Reference Document:
--		1. Information about SURVIVABLE PROCESSORS can be
--		   found in document referenced by REF_DOC_5 in the
--		   DOCUMENT REFERENCE SECTION.
-- Command Permission/User-profile:
--		1. No special permissions needed.

avCmDispSurvProcess	OBJECT IDENTIFIER ::= { avCmObjects 50 }

avCmDispSurvProcessTable	OBJECT-TYPE
    SYNTAX	SEQUENCE OF AvCmDispSurvProcessEntry
    MAX-ACCESS	not-accessible
    STATUS	current
    DESCRIPTION
	"
	Fld OID Name:	avCmDispSurvProcessEntry
	Fld OID:	enterprises.6889.2.73.8.1.50.1
	Fld Form/Rpt:	NA
	Fld Format:	NA
	Fld(s) Name:	NA
	Fld Descr:	A list of the avCmDispSurvProcess entries
	"
    ::= { avCmDispSurvProcess 1 }

avCmDispSurvProcessEntry        OBJECT-TYPE
    SYNTAX      AvCmDispSurvProcessEntry
    MAX-ACCESS  not-accessible
    STATUS      current
    DESCRIPTION
        "
        Fld OID Name:   avCmDispSurvProcessEntry
        Fld OID:        enterprises.6889.2.73.8.1.49.1.1
        Fld Form/Rpt:   NA
        Fld Format:     NA
        Fld(s) Name:    NA
        Fld Descr:      A avCmDispSurvProcess entry containing objects of the
                        avCmDispSurvProcess information sent by the switch.
        "
    INDEX    { avCmDispSurvProcessNameIdx }
    ::= { avCmDispSurvProcessTable 1 }

AvCmDispSurvProcessEntry ::= SEQUENCE {
		avCmDispSurvProcessNameIdx
		    SnmpAdminString,
		avCmDispSurvProcessNodeName
		    SnmpAdminString,
		avCmDispSurvProcessType
		    SnmpAdminString,
		avCmDispSurvProcessClusterId
		    Integer32,
		avCmDispSurvProcessActivesrvIP
		    SnmpAdminString,
		avCmDispSurvProcessAID
		    Integer32,
		avCmDispSurvProcessAnodename
		    SnmpAdminString,
		avCmDispSurvProcessAIP
		    SnmpAdminString,
		avCmDispSurvProcessBID
		    Integer32,
		avCmDispSurvProcessBnodename
		    SnmpAdminString,
		avCmDispSurvProcessBIP
		    SnmpAdminString,
		avCmDispSurvProcessSystemPref
		    SnmpAdminString,
		avCmDispSurvProcessPriorityscore
		    Integer32,
		avCmDispSurvProcessLocalPref
		    SnmpAdminString,
		avCmDispSurvProcessLocalOnly
		    SnmpAdminString,
		avCmDispSurvProcessV6NodeName
		    SnmpAdminString,
		avCmDispSurvProcessV6IP
		    SnmpAdminString,
		avCmDispSurvProcessAV6NodeName
		    SnmpAdminString,
		avCmDispSurvProcessAV6IP
		    SnmpAdminString,
		avCmDispSurvProcessBV6NodeName
		    SnmpAdminString,
		avCmDispSurvProcessBV6IP
		    SnmpAdminString
		}

avCmDispSurvProcessNameIdx	OBJECT-TYPE
    SYNTAX	SnmpAdminString (SIZE (0..16))
    MAX-ACCESS	not-accessible
    STATUS	current
    DESCRIPTION
	"
	Fld OID Name:	avCmDispSurvProcessNameIdx
	Fld OID:	enterprises.6889.2.73.8.1.50.1.1.1
	Fld Format:	NA
	Fld(s) Name:	NA
	Fld Descr:	An object that uniquely identifies each Increment of 
			data.
	"
    ::= { avCmDispSurvProcessEntry 1 }

avCmDispSurvProcessNodeName	OBJECT-TYPE
    SYNTAX	SnmpAdminString (SIZE (0..16))
    MAX-ACCESS	read-only
    STATUS	current
    DESCRIPTION
	"
	Fld OID Name:	avCmDispSurvProcessNodeName
	Fld OID:	enterprises.6889.2.73.8.1.50.1.1.2
	Fld Form/Rpt:	SURVIVABLE PROCESSORS
	Fld Format:	Single Field
	Fld(s) Name:	Name
	Fld Descr:	An object containing the Name of the survivable 
			processor.
	"
    ::= { avCmDispSurvProcessEntry 2 }

avCmDispSurvProcessType   OBJECT-TYPE
    SYNTAX	SnmpAdminString (SIZE (0..13))
    MAX-ACCESS  read-only
    STATUS      current
    DESCRIPTION
        "
        Fld OID Name:   avCmDispSurvProcessType
        Fld OID:        enterprises.6889.2.73.8.1.50.1.1.3
        Fld Form/Rpt:   SURVIVABLE PROCESSORS
        Fld Format:     Single Field
        Fld(s) Name:    Type
        Fld Descr:      An object containing the type of survivable processor.
        "
    ::= { avCmDispSurvProcessEntry 3 }


avCmDispSurvProcessClusterId   OBJECT-TYPE
    SYNTAX      Integer32 (0..9999)
    MAX-ACCESS  read-only
    STATUS      current
    DESCRIPTION
        "
        Fld OID Name:   avCmDispSurvProcessClusterId
        Fld OID:        enterprises.6889.2.73.8.1.50.1.1.4
        Fld Form/Rpt:   SURVIVABLE PROCESSORS
        Fld Format:     Single Field
        Fld(s) Name:    Cluster ID/MID
        Fld Descr:      An object containing the cluster id or MID of the
			survivable processor.
        "
    ::= { avCmDispSurvProcessEntry 4 }


avCmDispSurvProcessActivesrvIP   OBJECT-TYPE
    SYNTAX	SnmpAdminString (SIZE (0..41))
    MAX-ACCESS  read-only
    STATUS      current
    DESCRIPTION
        "
        Fld OID Name:   avCmDispSurvProcessActivesrvIP
        Fld OID:        enterprises.6889.2.73.8.1.50.1.1.5
        Fld Form/Rpt:   SURVIVABLE PROCESSORS
        Fld Format:     Single Field
        Fld(s) Name:    ACTI Address
        Fld Descr:      An object containing the survivable processor
			Active IP Address.
        "
    ::= { avCmDispSurvProcessEntry 5 }


avCmDispSurvProcessAID   OBJECT-TYPE
    SYNTAX      Integer32 (0..999)
    MAX-ACCESS  read-only
    STATUS      current
    DESCRIPTION
        "
        Fld OID Name:   avCmDispSurvProcessAID
        Fld OID:        enterprises.6889.2.73.8.1.50.1.1.6
        Fld Form/Rpt:   SURVIVABLE PROCESSORS
        Fld Format:     Single Field
        Fld(s) Name:    A Server ID
        Fld Descr:      An object containing the survivable processor
			A Server ID.
        "
    ::= { avCmDispSurvProcessEntry 6 }


avCmDispSurvProcessAnodename   OBJECT-TYPE
    SYNTAX	SnmpAdminString (SIZE (0..16))
    MAX-ACCESS  read-only
    STATUS      current
    DESCRIPTION
        "
        Fld OID Name:   avCmDispSurvProcessAnodename
        Fld OID:        enterprises.6889.2.73.8.1.50.1.1.7
        Fld Form/Rpt:   SURVIVABLE PROCESSORS
        Fld Format:     Single Field
        Fld(s) Name:    SERVER A  V4 Node Name
        Fld Descr:      An object containing the survivable processor
			SERVER A V4 Node Name.
        "
    ::= { avCmDispSurvProcessEntry 7 }


avCmDispSurvProcessAIP   OBJECT-TYPE
    SYNTAX	SnmpAdminString (SIZE (0..41))
    MAX-ACCESS  read-only
    STATUS      current
    DESCRIPTION
        "
        Fld OID Name:   avCmDispSurvProcessAIP
        Fld OID:        enterprises.6889.2.73.8.1.50.1.1.8
        Fld Form/Rpt:   SURVIVABLE PROCESSORS
        Fld Format:     Single Field
        Fld(s) Name:    SERVER A V4 Address
        Fld Descr:      An object containing the survivable 
			processor SERVER A V4 IP Address.
        "
    ::= { avCmDispSurvProcessEntry 8 }


avCmDispSurvProcessBID   OBJECT-TYPE
    SYNTAX      Integer32 (0..999)
    MAX-ACCESS  read-only
    STATUS      current
    DESCRIPTION
        "
        Fld OID Name:   avCmDispSurvProcessBID
        Fld OID:        enterprises.6889.2.73.8.1.50.1.1.9
        Fld Form/Rpt:   SURVIVABLE PROCESSORS
        Fld Format:     Single Field
        Fld(s) Name:    SERVER B  Server ID
        Fld Descr:      An object containing the survivable processor 
			SERVER B  Server ID.
        "
    ::= { avCmDispSurvProcessEntry 9 }

avCmDispSurvProcessBnodename   OBJECT-TYPE
    SYNTAX	SnmpAdminString (SIZE (0..16))
    MAX-ACCESS  read-only
    STATUS      current
    DESCRIPTION
        "
        Fld OID Name:   avCmDispSurvProcessBnodename
        Fld OID:        enterprises.6889.2.73.8.1.50.1.1.10
        Fld Form/Rpt:   SURVIVABLE PROCESSORS
        Fld Format:     Single Field
        Fld(s) Name:    SERVER B V4 Node Name
        Fld Descr:      An object containing the survivable processor
			SERVER B V4 Node Name.
        "
    ::= { avCmDispSurvProcessEntry 10 }

avCmDispSurvProcessBIP   OBJECT-TYPE
    SYNTAX	SnmpAdminString (SIZE (0..41))
    MAX-ACCESS  read-only
    STATUS      current
    DESCRIPTION
        "
        Fld OID Name:   avCmDispSurvProcessBIP
        Fld OID:        enterprises.6889.2.73.8.1.50.1.1.11
        Fld Form/Rpt:   SURVIVABLE PROCESSORS
        Fld Format:     Single Field
        Fld(s) Name:    SERVER B Address
        Fld Descr:      An object containing the server B IP address the
			survivable processor is using.
        "
    ::= { avCmDispSurvProcessEntry 11 }

avCmDispSurvProcessSystemPref   OBJECT-TYPE
    SYNTAX      SnmpAdminString (SIZE (0..2))
    MAX-ACCESS  read-only
    STATUS      current
    DESCRIPTION
        "
        Fld OID Name:   avCmDispSurvProcessSystemPref
        Fld OID:        enterprises.6889.2.73.8.1.50.1.1.12
        Fld Form/Rpt:   SURVIVABLE PROCESSORS
        Fld Format:     Single Field
        Fld(s) Name:    System Preferred
        Fld Descr:      An object containing whether System Preferred enabled
                        for the survivable processor.
        "
    ::= { avCmDispSurvProcessEntry 12 }

avCmDispSurvProcessPriorityscore   OBJECT-TYPE
    SYNTAX      Integer32 (0..100)
    MAX-ACCESS  read-only
    STATUS      current
    DESCRIPTION
        "
        Fld OID Name:   avCmDispSurvProcessPriorityscore
        Fld OID:        enterprises.6889.2.73.8.1.50.1.1.13
        Fld Form/Rpt:   SURVIVABLE PROCESSORS
        Fld Format:     Single Field
        Fld(s) Name:    Priority Score
        Fld Descr:      An object containing the Priority Score 
                        for the survivable processor.
        "
    ::= { avCmDispSurvProcessEntry 13 }

avCmDispSurvProcessLocalPref   OBJECT-TYPE
    SYNTAX      SnmpAdminString (SIZE (0..2))
    MAX-ACCESS  read-only
    STATUS      current
    DESCRIPTION
        "
        Fld OID Name:   avCmDispSurvProcessLocalPref
        Fld OID:        enterprises.6889.2.73.8.1.50.1.1.14
        Fld Form/Rpt:   SURVIVABLE PROCESSORS
        Fld Format:     Single Field
        Fld(s) Name:    Local Preferred
        Fld Descr:      An object containing whether Local Preferred enabled
                        for the survivable processor.
        "
    ::= { avCmDispSurvProcessEntry 14 }


avCmDispSurvProcessLocalOnly   OBJECT-TYPE
    SYNTAX      SnmpAdminString (SIZE (0..2))
    MAX-ACCESS  read-only
    STATUS      current
    DESCRIPTION
        "
        Fld OID Name:   avCmDispSurvProcessLocalOnly
        Fld OID:        enterprises.6889.2.73.8.1.50.1.1.15
        Fld Form/Rpt:   SURVIVABLE PROCESSORS
        Fld Format:     Single Field
        Fld(s) Name:    Local Only
        Fld Descr:      An object containing whether Local Only enabled
                        for the survivable processor.
        "
    ::= { avCmDispSurvProcessEntry 15 }

avCmDispSurvProcessV6NodeName   OBJECT-TYPE
    SYNTAX      SnmpAdminString (SIZE (0..16))
    MAX-ACCESS  read-only
    STATUS      current
    DESCRIPTION
        "
        Fld OID Name:   avCmDispSurvProcessV6NodeName
        Fld OID:        enterprises.6889.2.73.8.1.50.1.1.16
        Fld Form/Rpt:   SURVIVABLE PROCESSORS
        Fld Format:     Single Field
        Fld(s) Name:    V6 Node Name
        Fld Descr:      An object containing the IPV6 Node Name
                        for the survivable processor.
        "
    ::= { avCmDispSurvProcessEntry 16 }

avCmDispSurvProcessV6IP   OBJECT-TYPE
    SYNTAX      SnmpAdminString (SIZE (0..41))
    MAX-ACCESS  read-only
    STATUS      current
    DESCRIPTION
        "
        Fld OID Name:   avCmDispSurvProcessV6IP
        Fld OID:        enterprises.6889.2.73.8.1.50.1.1.17
        Fld Form/Rpt:   SURVIVABLE PROCESSORS
        Fld Format:     Single Field
        Fld(s) Name:    V6 Address
        Fld Descr:      An object containing the IPV6 Address
                        for the survivable processor.
        "
    ::= { avCmDispSurvProcessEntry 17 }


avCmDispSurvProcessAV6NodeName   OBJECT-TYPE
    SYNTAX      SnmpAdminString (SIZE (0..16))
    MAX-ACCESS  read-only
    STATUS      current
    DESCRIPTION
        "
        Fld OID Name:   avCmDispSurvProcessAV6NodeName
        Fld OID:        enterprises.6889.2.73.8.1.50.1.1.18
        Fld Form/Rpt:   SURVIVABLE PROCESSORS
        Fld Format:     Single Field
        Fld(s) Name:    SERVER A V6 Node Name
        Fld Descr:      An object containing the server A IPV6 Node Name
                        for the survivable processor.
        "
    ::= { avCmDispSurvProcessEntry 18 }

avCmDispSurvProcessAV6IP   OBJECT-TYPE
    SYNTAX      SnmpAdminString (SIZE (0..41))
    MAX-ACCESS  read-only
    STATUS      current
    DESCRIPTION
        "
        Fld OID Name:   avCmDispSurvProcessAV6IP
        Fld OID:        enterprises.6889.2.73.8.1.50.1.1.19
        Fld Form/Rpt:   SURVIVABLE PROCESSORS
        Fld Format:     Single Field
        Fld(s) Name:    SERVER A V6 Address
        Fld Descr:      An object containing the server A IPV6 Address
                        for the survivable processor.
        "
    ::= { avCmDispSurvProcessEntry 19 }

avCmDispSurvProcessBV6NodeName   OBJECT-TYPE
    SYNTAX      SnmpAdminString (SIZE (0..16))
    MAX-ACCESS  read-only
    STATUS      current
    DESCRIPTION
        "
        Fld OID Name:   avCmDispSurvProcessBV6NodeName
        Fld OID:        enterprises.6889.2.73.8.1.50.1.1.20
        Fld Form/Rpt:   SURVIVABLE PROCESSORS
        Fld Format:     Single Field
        Fld(s) Name:    SERVER B V6 Node Name
        Fld Descr:      An object containing the server B IPV6 Node Name
                        for the survivable processor.
        "
    ::= { avCmDispSurvProcessEntry 20 }

avCmDispSurvProcessBV6IP   OBJECT-TYPE
    SYNTAX      SnmpAdminString (SIZE (0..41))
    MAX-ACCESS  read-only
    STATUS      current
    DESCRIPTION
        "
        Fld OID Name:   avCmDispSurvProcessBV6IP
        Fld OID:        enterprises.6889.2.73.8.1.50.1.1.21
        Fld Form/Rpt:   SURVIVABLE PROCESSORS
        Fld Format:     Single Field
        Fld(s) Name:    SERVER B V6 Address
        Fld Descr:      An object containing the server B IPV6 Address
                        for the survivable processor.
        "
    ::= { avCmDispSurvProcessEntry 21 }

-- ******************** avCmListNodeNamesAll Group *************************

-- MIB GROUP DESCRIPTION

-- MIB Group Name:
--		avCmListNodeNamesAll Group
-- OID:
--		enterprises.6889.2.73.8.1.51
-- Description:
--		The avCmListNodeNamesAll MIB Group uses the 
--		"list node-names all" command to 
-- 		retrieve node name data.
--		
-- Releases Supported:
--		CM6.3.100 and greater
-- Polling Type:
--		Inventory
-- Polling Interval:
--		No more than once a day.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. list  node-names all
-- Form/Report Name:
--		1. NODE NAMES
-- Reference Document:
--		1. Information about NODE NAMES can be
--		   found in document referenced by REF_DOC_5 in the
--		   DOCUMENT REFERENCE SECTION.
-- Command Permission/User-profile:
--		1. No special permissions needed.

avCmListNodeNamesAll	OBJECT IDENTIFIER ::= { avCmObjects 51 }

avCmListNodeNamesAllTable	OBJECT-TYPE
    SYNTAX	SEQUENCE OF AvCmListNodeNamesAllEntry
    MAX-ACCESS	not-accessible
    STATUS	current
    DESCRIPTION
	"
	Fld OID Name:	avCmListNodeNamesAllEntry
	Fld OID:	enterprises.6889.2.73.8.1.51.1
	Fld Form/Rpt:	NA
	Fld Format:	NA
	Fld(s) Name:	NA
	Fld Descr:	A list of the avCmListNodeNamesAll entries
	"
    ::= { avCmListNodeNamesAll 1 }

avCmListNodeNamesAllEntry	OBJECT-TYPE
    SYNTAX	AvCmListNodeNamesAllEntry
    MAX-ACCESS	not-accessible
    STATUS	current
    DESCRIPTION
	"
	Fld OID Name:	avCmListNodeNamesAllEntry
	Fld OID:	enterprises.6889.2.73.8.1.51.1.1
	Fld Form/Rpt:	NA
	Fld Format:	NA
	Fld(s) Name:	NA
	Fld Descr:	A avCmListNodeNamesAll entry containing objects of the
			avCmListNodeNamesAll information sent by the switch.
	"
    INDEX    { avCmListNodeNamesAllNameIdx }
    ::= { avCmListNodeNamesAllTable 1 }

AvCmListNodeNamesAllEntry ::= SEQUENCE {
		avCmListNodeNamesAllNameIdx
		    SnmpAdminString,
		avCmListNodeNamesAllName
		    SnmpAdminString,
		avCmListNodeNamesAllType
		    SnmpAdminString,
		avCmListNodeNamesAllIPAddress
		    SnmpAdminString
		}

avCmListNodeNamesAllNameIdx	OBJECT-TYPE
    SYNTAX	SnmpAdminString (SIZE (0..16))
    MAX-ACCESS	not-accessible
    STATUS	current
    DESCRIPTION
	"
	Fld OID Name:	avCmListNodeNamesAllNameIdx
	Fld OID:	enterprises.6889.2.73.8.1.51.1.1.1
	Fld Format:	NA
	Fld(s) Name:	NA
	Fld Descr:	An object that uniquely identifies each Increment of 
			data.
	"
    ::= { avCmListNodeNamesAllEntry 1 }

avCmListNodeNamesAllName	OBJECT-TYPE
    SYNTAX	SnmpAdminString (SIZE (0..16))
    MAX-ACCESS	read-only
    STATUS	current
    DESCRIPTION
	"
	Fld OID Name:	avCmListNodeNamesAllExtension
	Fld OID:	enterprises.6889.2.73.8.1.51.1.1.2
	Fld Form/Rpt:	NODE NAMES
	Fld Format:	Single Field
	Fld(s) Name:	Name
	Fld Descr:	An object containing the Name of the node.
	"
    ::= { avCmListNodeNamesAllEntry 2 }

avCmListNodeNamesAllType	OBJECT-TYPE
    SYNTAX	SnmpAdminString (SIZE (0..6))
    MAX-ACCESS	read-only
    STATUS	current
    DESCRIPTION
	"
	Fld OID Name:	avCmListNodeNamesAllType
	Fld OID:	enterprises.6889.2.73.8.1.51.1.1.3
	Fld Form/Rpt:	NODE NAMES
	Fld Format:	Single Field
	Fld(s) Name:	Type
	Fld Descr:	An object containing the type of node name.
	"
    ::= { avCmListNodeNamesAllEntry 3 }

avCmListNodeNamesAllIPAddress   OBJECT-TYPE
    SYNTAX	SnmpAdminString (SIZE (0..41))
    MAX-ACCESS  read-only
    STATUS      current
    DESCRIPTION
        "
        Fld OID Name:   avCmListNodeNamesAllIPAddress
        Fld OID:        enterprises.6889.2.73.8.1.51.1.1.4
        Fld Form/Rpt:   NODE NAMES
        Fld Format:     Single Field
        Fld(s) Name:    IP Address
        Fld Descr:      An object containing either an IPV4 or IPV6
			IP Address.
	"
    ::= { avCmListNodeNamesAllEntry 4 }

-- ******************** avCmListNodeNamesV4 Group *************************

-- MIB GROUP DESCRIPTION

-- MIB Group Name:
--		avCmListNodeNamesV4 Group
-- OID:
--		enterprises.6889.2.73.8.1.52
-- Description:
--		The avCmListNodeNamesV4 MIB Group uses the 
--		"list node-names v4" command to 
-- 		retrieve  IPV4 address node name data.
--		
-- Releases Supported:
--		CM6.3.100 and greater
-- Polling Type:
--		Inventory
-- Polling Interval:
--		No more than once a day.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. list node-names v4
-- Form/Report Name:
--		1. NODE NAMES
-- Reference Document:
--		1. Information about NODE NAMES can be
--		   found in document referenced by REF_DOC_5 in the
--		   DOCUMENT REFERENCE SECTION.
-- Command Permission/User-profile:
--		1. No special permissions needed.

avCmListNodeNamesV4	OBJECT IDENTIFIER ::= { avCmObjects 52 }

avCmListNodeNamesV4Table	OBJECT-TYPE
    SYNTAX	SEQUENCE OF AvCmListNodeNamesV4Entry
    MAX-ACCESS	not-accessible
    STATUS	current
    DESCRIPTION
	"
	Fld OID Name:	avCmListNodeNamesV4Entry
	Fld OID:	enterprises.6889.2.73.8.1.52.1
	Fld Form/Rpt:	NA
	Fld Format:	NA
	Fld(s) Name:	NA
	Fld Descr:	A list of the avCmListNodeNamesV4 entries
	"
    ::= { avCmListNodeNamesV4 1 }

avCmListNodeNamesV4Entry	OBJECT-TYPE
    SYNTAX	AvCmListNodeNamesV4Entry
    MAX-ACCESS	not-accessible
    STATUS	current
    DESCRIPTION
	"
	Fld OID Name:	avCmListNodeNamesV4Entry
	Fld OID:	enterprises.6889.2.73.8.1.52.1.1
	Fld Form/Rpt:	NA
	Fld Format:	NA
	Fld(s) Name:	NA
	Fld Descr:	A avCmListNodeNamesV4 entry containing objects of the
			avCmListNodeNamesV4 information sent by the switch.
	"
    INDEX    { avCmListNodeNamesV4NameIdx }
    ::= { avCmListNodeNamesV4Table 1 }

AvCmListNodeNamesV4Entry ::= SEQUENCE {
		avCmListNodeNamesV4NameIdx
		    SnmpAdminString,
		avCmListNodeNamesV4Name
		    SnmpAdminString,
		avCmListNodeNamesV4Type
		    SnmpAdminString,
		avCmListNodeNamesV4IPAddress
		    SnmpAdminString
		}

avCmListNodeNamesV4NameIdx	OBJECT-TYPE
    SYNTAX	SnmpAdminString (SIZE (0..16))
    MAX-ACCESS	not-accessible
    STATUS	current
    DESCRIPTION
	"
	Fld OID Name:	avCmListNodeNamesV4NameIdx
	Fld OID:	enterprises.6889.2.73.8.1.52.1.1.1
	Fld Format:	NA
	Fld(s) Name:	NA
	Fld Descr:	An object that uniquely identifies each Increment of 
			data.
	"
    ::= { avCmListNodeNamesV4Entry 1 }

avCmListNodeNamesV4Name	OBJECT-TYPE
    SYNTAX	SnmpAdminString (SIZE (0..16))
    MAX-ACCESS	read-only
    STATUS	current
    DESCRIPTION
	"
	Fld OID Name:	avCmListNodeNamesV4Extension
	Fld OID:	enterprises.6889.2.73.8.1.52.1.1.2
	Fld Form/Rpt:	NODE NAMES
	Fld Format:	Single Field
	Fld(s) Name:	Name
	Fld Descr:	An object containing the Name of the node.
	"
    ::= { avCmListNodeNamesV4Entry 2 }

avCmListNodeNamesV4Type	OBJECT-TYPE
    SYNTAX	SnmpAdminString (SIZE (0..6))
    MAX-ACCESS	read-only
    STATUS	current
    DESCRIPTION
	"
	Fld OID Name:	avCmListNodeNamesV4Type
	Fld OID:	enterprises.6889.2.73.8.1.52.1.1.3
	Fld Form/Rpt:	NODE NAMES
	Fld Format:	Single Field
	Fld(s) Name:	Type
	Fld Descr:	An object containing the type of node name.
	"
    ::= { avCmListNodeNamesV4Entry 3 }

avCmListNodeNamesV4IPAddress   OBJECT-TYPE
    SYNTAX	SnmpAdminString (SIZE (0..41))
    MAX-ACCESS  read-only
    STATUS      current
    DESCRIPTION
        "
        Fld OID Name:   avCmListNodeNamesV4IPAddress
        Fld OID:        enterprises.6889.2.73.8.1.52.1.1.4
        Fld Form/Rpt:   NODE NAMES
        Fld Format:     Single Field
        Fld(s) Name:    IP Address
        Fld Descr:      An object containing an IPV4
			IP Address.
	"
    ::= { avCmListNodeNamesV4Entry 4 }

-- ******************** avCmListNodeNamesV6 Group *************************

-- MIB GROUP DESCRIPTION

-- MIB Group Name:
--		avCmListNodeNamesV6 Group
-- OID:
--		enterprises.6889.2.73.8.1.53
-- Description:
--		The avCmListNodeNamesV6 MIB Group uses the 
--		"list node-names v6" command to 
-- 		retrieve  IPV6 address node name data.
--		
-- Releases Supported:
--		CM6.3.100 and greater
-- Polling Type:
--		Inventory
-- Polling Interval:
--		No more than once a day.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. list node-names v6
-- Form/Report Name:
--		1. NODE NAMES
-- Reference Document:
--		1. Information about NODE NAMES can be
--		   found in document referenced by REF_DOC_5 in the
--		   DOCUMENT REFERENCE SECTION.
-- Command Permission/User-profile:
--		1. No special permissions needed.

avCmListNodeNamesV6	OBJECT IDENTIFIER ::= { avCmObjects 53 }

avCmListNodeNamesV6Table	OBJECT-TYPE
    SYNTAX	SEQUENCE OF AvCmListNodeNamesV6Entry
    MAX-ACCESS	not-accessible
    STATUS	current
    DESCRIPTION
	"
	Fld OID Name:	avCmListNodeNamesV6Entry
	Fld OID:	enterprises.6889.2.73.8.1.53.1
	Fld Form/Rpt:	NA
	Fld Format:	NA
	Fld(s) Name:	NA
	Fld Descr:	A list of the avCmListNodeNamesV6 entries
	"
    ::= { avCmListNodeNamesV6 1 }

avCmListNodeNamesV6Entry	OBJECT-TYPE
    SYNTAX	AvCmListNodeNamesV6Entry
    MAX-ACCESS	not-accessible
    STATUS	current
    DESCRIPTION
	"
	Fld OID Name:	avCmListNodeNamesV6Entry
	Fld OID:	enterprises.6889.2.73.8.1.53.1.1
	Fld Form/Rpt:	NA
	Fld Format:	NA
	Fld(s) Name:	NA
	Fld Descr:	A avCmListNodeNamesV6 entry containing objects of the
			avCmListNodeNamesV6 information sent by the switch.
	"
    INDEX    { avCmListNodeNamesV6NameIdx }
    ::= { avCmListNodeNamesV6Table 1 }

AvCmListNodeNamesV6Entry ::= SEQUENCE {
		avCmListNodeNamesV6NameIdx
		    SnmpAdminString,
		avCmListNodeNamesV6Name
		    SnmpAdminString,
		avCmListNodeNamesV6Type
		    SnmpAdminString,
		avCmListNodeNamesV6IPAddress
		    SnmpAdminString
		}

avCmListNodeNamesV6NameIdx	OBJECT-TYPE
    SYNTAX	SnmpAdminString (SIZE (0..16))
    MAX-ACCESS	not-accessible
    STATUS	current
    DESCRIPTION
	"
	Fld OID Name:	avCmListNodeNamesV6NameIdx
	Fld OID:	enterprises.6889.2.73.8.1.53.1.1.1
	Fld Format:	NA
	Fld(s) Name:	NA
	Fld Descr:	An object that uniquely identifies each Increment of 
			data.
	"
    ::= { avCmListNodeNamesV6Entry 1 }

avCmListNodeNamesV6Name	OBJECT-TYPE
    SYNTAX	SnmpAdminString (SIZE (0..16))
    MAX-ACCESS	read-only
    STATUS	current
    DESCRIPTION
	"
	Fld OID Name:	avCmListNodeNamesV6Extension
	Fld OID:	enterprises.6889.2.73.8.1.53.1.1.2
	Fld Form/Rpt:	NODE NAMES
	Fld Format:	Single Field
	Fld(s) Name:	Name
	Fld Descr:	An object containing the Name of the node.
	"
    ::= { avCmListNodeNamesV6Entry 2 }

avCmListNodeNamesV6Type	OBJECT-TYPE
    SYNTAX	SnmpAdminString (SIZE (0..6))
    MAX-ACCESS	read-only
    STATUS	current
    DESCRIPTION
	"
	Fld OID Name:	avCmListNodeNamesV6Type
	Fld OID:	enterprises.6889.2.73.8.1.53.1.1.3
	Fld Form/Rpt:	NODE NAMES
	Fld Format:	Single Field
	Fld(s) Name:	Type
	Fld Descr:	An object containing the type of node name.
	"
    ::= { avCmListNodeNamesV6Entry 3 }

avCmListNodeNamesV6IPAddress   OBJECT-TYPE
    SYNTAX	SnmpAdminString (SIZE (0..41))
    MAX-ACCESS  read-only
    STATUS      current
    DESCRIPTION
        "
        Fld OID Name:   avCmListNodeNamesV6IPAddress
        Fld OID:        enterprises.6889.2.73.8.1.53.1.1.4
        Fld Form/Rpt:   NODE NAMES
        Fld Format:     Single Field
        Fld(s) Name:    IP Address
        Fld Descr:      An object containing an IPV6
			IP Address.
	"
    ::= { avCmListNodeNamesV6Entry 4 }


-- ******************** avCmListAnn Group *************************

-- MIB GROUP DESCRIPTION

-- MIB Group Name:
--		avCmListAnn Group
-- OID:
--		enterprises.6889.2.73.8.1.54
-- Description:
--		The avCmListAnn MIB Group uses the 
--		"list announcement" command to 
-- 		retrieve announcement data.
--		
-- Releases Supported:
--		CM6.3.100 and greater
-- Polling Type:
--		Inventory
-- Polling Interval:
--		No more than once a day.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. list announcement
-- Form/Report Name:
--		1. ANNOUNCEMENTS/AUDIO SOURCES
-- Reference Document:
--		1. A detailed description of the command and form can be
--		   found in document referenced by REF_DOC_1 in the
--		   DOCUMENT REFERENCE SECTION.
-- Command Permission/User-profile:
--		1. No special permissions needed.

avCmListAnn	OBJECT IDENTIFIER ::= { avCmObjects 54 }

avCmListAnnTable	OBJECT-TYPE
    SYNTAX	SEQUENCE OF AvCmListAnnEntry
    MAX-ACCESS	not-accessible
    STATUS	current
    DESCRIPTION
	"
	Fld OID Name:	avCmListAnnEntry
	Fld OID:	enterprises.6889.2.73.8.1.54.1
	Fld Form/Rpt:	NA
	Fld Format:	NA
	Fld(s) Name:	NA
	Fld Descr:	A list of the avCmListAnn entries
	"
    ::= { avCmListAnn 1 }

avCmListAnnEntry	OBJECT-TYPE
    SYNTAX	AvCmListAnnEntry
    MAX-ACCESS	not-accessible
    STATUS	current
    DESCRIPTION
	"
	Fld OID Name:	avCmListAnnEntry
	Fld OID:	enterprises.6889.2.73.8.1.54.1.1
	Fld Form/Rpt:	NA
	Fld Format:	NA
	Fld(s) Name:	NA
	Fld Descr:	A avCmListAnn entry containing objects of the
			avCmListAnn information sent by the switch.
	"
    INDEX    { avCmListAnnExtIdx }
    ::= { avCmListAnnTable 1 }

AvCmListAnnEntry ::= SEQUENCE {
		avCmListAnnExtIdx
		    SnmpAdminString,
		avCmListAnnExtension
		    SnmpAdminString,
		avCmListAnnType
		    SnmpAdminString,
		avCmListAnnName
		    SnmpAdminString,
		avCmListAnnSource
		    SnmpAdminString,
		avCmListAnnNumFiles
		    Integer32
		}

avCmListAnnExtIdx	OBJECT-TYPE
    SYNTAX	SnmpAdminString (SIZE (0..17))
    MAX-ACCESS	not-accessible
    STATUS	current
    DESCRIPTION
	"
	Fld OID Name:	avCmListAnnExtIdx
	Fld OID:	enterprises.6889.2.73.8.1.54.1.1.1
	Fld Format:	NA
	Fld(s) Name:	NA
	Fld Descr:	An object that uniquely identifies each Increment of 
			data.
	"
    ::= { avCmListAnnEntry 1 }

avCmListAnnExtension	OBJECT-TYPE
    SYNTAX	SnmpAdminString (SIZE (0..17))
    MAX-ACCESS	read-only
    STATUS	current
    DESCRIPTION
	"
	Fld OID Name:	avCmListAnnExtension
	Fld OID:	enterprises.6889.2.73.8.1.54.1.1.2
	Fld Form/Rpt:	ANNOUNCEMENTS/AUDIO SOURCES
	Fld Format:	Single Field
	Fld(s) Name:	Extension
	Fld Descr:	An object containing the extension of the announcement.
	"
    ::= { avCmListAnnEntry 2 }

avCmListAnnType	OBJECT-TYPE
    SYNTAX	SnmpAdminString (SIZE (0..11))
    MAX-ACCESS	read-only
    STATUS	current
    DESCRIPTION
	"
	Fld OID Name:	avCmListAnnType
	Fld OID:	enterprises.6889.2.73.8.1.54.1.1.3
	Fld Form/Rpt:	ANNOUNCEMENTS/AUDIO SOURCES
	Fld Format:	Single Field
	Fld(s) Name:	Type
	Fld Descr:	An object containing the type of announcement.
	"
    ::= { avCmListAnnEntry 3 }

avCmListAnnName   OBJECT-TYPE
    SYNTAX	SnmpAdminString (SIZE (0..28))
    MAX-ACCESS  read-only
    STATUS      current
    DESCRIPTION
        "
        Fld OID Name:   avCmListAnnName
        Fld OID:        enterprises.6889.2.73.8.1.54.1.1.4
        Fld Form/Rpt:   ANNOUNCEMENTS/AUDIO SOURCES
        Fld Format:     Single Field
        Fld(s) Name:    Name
        Fld Descr:      An object containing the name of the announcement.
	"
    ::= { avCmListAnnEntry 4 }

avCmListAnnSource   OBJECT-TYPE
    SYNTAX	SnmpAdminString (SIZE (0..6))
    MAX-ACCESS  read-only
    STATUS      current
    DESCRIPTION
        "
        Fld OID Name:   avCmListAnnSource
        Fld OID:        enterprises.6889.2.73.8.1.54.1.1.5
        Fld Form/Rpt:   ANNOUNCEMENTS/AUDIO SOURCES
        Fld Format:     Single Field
        Fld(s) Name:    Source
        Fld Descr:      An object containing the source of the announcement.
			Either a port, board or group.
	"
    ::= { avCmListAnnEntry 5 }

avCmListAnnNumFiles   OBJECT-TYPE
    SYNTAX      Integer32 (0..999)
    MAX-ACCESS  read-only
    STATUS      current
    DESCRIPTION
        "
        Fld OID Name:   avCmListAnnNumFiles
        Fld OID:        enterprises.6889.2.73.8.1.54.1.1.6
        Fld Form/Rpt:   ANNOUNCEMENTS/AUDIO SOURCES
        Fld Format:     Single Field
        Fld(s) Name:    Num of Files
        Fld Descr:      An object containing the number of files.
        "
    ::= { avCmListAnnEntry 6 }


--   ***********	  avCmListIpUnregisteredRange Group       **************

-- MIB Group Name:
--		avCmListIpUnregisteredRange
-- OID:
--		enterprises.6889.2.73.8.1.55
-- Description:
--		The avCmListIpUnregisteredRange MIB group displays the output 
--		of the list multimedia ip-unregistered xxxx count xx command. 
--		This MIB Group  should be used instead of the 
--		avCmListIpUnregistered MIB Group on systems
--		with over 100 stations.
-- Releases Supported:
--		CM6.3.100 and greater
-- Polling Type:
--		Inventory and Performance/Utilization
-- Polling Interval:
--		No more than once a day or when stations are added.
-- Default Caching Interval
-- 		600 seconds
-- Timeout Interval:
--		Initial Timeout should be set to 15 seconds.
-- Retry Interval:
--		Initial Retry should be set to 3.
-- Limitations:
--		Yellow/Medium - The data collected by this MIB Group
--		may have some impact on the system.
-- Command Type:
--		1. SAT
-- Command:
--		1. list multimedia ip-unregistered xxxxx count x
-- Form/Report Name:
--		1. UNREGISTERED IP TELEPHONES
-- Reference Document:
--		1. A detailed description of the command and form can be
--		   found in REF_DOC_3 and REF_DOC_5 in the DOCUMENT REFERENCE 
--		   SECTION.
-- Command Permission/User-profile:
--		1. No special permissions needed. Default customer super-user
--		   profile can access this command.

avCmListIpUnregisteredRange	OBJECT IDENTIFIER ::= { avCmObjects 55 }

avCmListIpUnregisteredRangeStartExt	OBJECT-TYPE
    SYNTAX	SnmpAdminString (SIZE (0..17))
    MAX-ACCESS	read-write
    STATUS	current
    DESCRIPTION
	"
	Fld OID Name:	avCmSationRangeStartExt
	Fld OID:	enterprises.6889.2.73.8.1.55.1
	Fld Form/Rpt:	NA
	Fld Format:	NA
	Fld(s) Name:	NA
	Fld Descr:	An object containing the starting Extension location
	"
    ::= { avCmListIpUnregisteredRange 1 }

avCmListIpUnregisteredRangeCount	OBJECT-TYPE
    SYNTAX	Integer32 (1..100)
    MAX-ACCESS	read-write
    STATUS	current
    DESCRIPTION
	"
	Fld OID Name:	avCmIpUnregisteredRangeCount
	Fld OID:	enterprises.6889.2.73.8.1.55.2
	Fld Form/Rpt:	NA
	Fld Format:	NA
	Fld(s) Name:	NA
	Fld Descr:	An object containing the number of unregistered
			stations to list.
	"
    DEFVAL	{ 10 }
    ::= { avCmListIpUnregisteredRange 2 }

avCmListIpUnregisteredRangeTable	OBJECT-TYPE
    SYNTAX	SEQUENCE OF AvCmListIpUnregisteredRangeEntry
    MAX-ACCESS	not-accessible
    STATUS	current
    DESCRIPTION
	"
	Fld OID Name:	avCmListIpUnregisteredRangeTable
	Fld OID:	enterprises.6889.2.73.8.1.55.3
	Fld Form/Rpt:	NA
	Fld Format:	NA
	Fld(s) Name:	NA
	Fld Descr:	A list of the avCmIpUnregisteredRange entries.
	"
    ::= { avCmListIpUnregisteredRange 3 }

avCmListIpUnregisteredRangeEntry	OBJECT-TYPE
    SYNTAX	AvCmListIpUnregisteredRangeEntry
    MAX-ACCESS	not-accessible
    STATUS	current
    DESCRIPTION
	"
	Fld OID Name:	avCmListIpUnregisteredRangeEntry
	Fld OID:	enterprises.6889.2.73.8.1.55.3.1
	Fld Form/Rpt:	NA
	Fld Format:	NA
	Fld(s) Name:	NA
	Fld Descr:	A avCmListIpUnregisteredRange entry containing objects 
			of the avCmListIpUnregisteredRange information sent by 
			the switch.
	"
    INDEX    { avCmListIpUnregisteredRangeIdx }
    ::= { avCmListIpUnregisteredRangeTable 1 }

AvCmListIpUnregisteredRangeEntry ::= SEQUENCE {
		avCmListIpUnregisteredRangeIdx
		    SnmpAdminString,
		avCmListIpUnregisteredRangeExtension
		    SnmpAdminString,
		avCmListIpUnregisteredRangePort
		    SnmpAdminString,
		avCmListIpUnregisteredRangeRegistered
		    SnmpAdminString
		}

avCmListIpUnregisteredRangeIdx	OBJECT-TYPE
    SYNTAX	SnmpAdminString (SIZE (0..17))
    MAX-ACCESS	not-accessible
    STATUS	current
    DESCRIPTION
	"
	Fld OID Name:	avCmListIpUnregisteredRangeIdx
	Fld OID:	enterprises.6889.2.73.8.1.55.3.1.1
	Fld Form/Rpt:	NA
	Fld Format:	NA
	Fld(s) Name:	NA
	Fld Descr:	An object that uniquely identifies each Record.
	"
    ::= { avCmListIpUnregisteredRangeEntry 1 }

avCmListIpUnregisteredRangeExtension	OBJECT-TYPE
    SYNTAX	SnmpAdminString (SIZE (0..17))
    MAX-ACCESS	read-only
    STATUS	current
    DESCRIPTION
	"
	Fld OID Name:	avCmIpUnregisteredRangeExtension
	Fld OID:	enterprises.6889.2.73.8.1.55.3.1.2
	Fld Form/Rpt:	UNREGISTERED IP TELEPHONES
	Fld Format:	Single
	Fld(s) Name:	Ext
	Fld Descr:	An object the uniquely identifies an administered
			station.
	"
    ::= { avCmListIpUnregisteredRangeEntry 2 }

avCmListIpUnregisteredRangePort	OBJECT-TYPE
    SYNTAX	SnmpAdminString (SIZE (0..9))
    MAX-ACCESS	read-only
    STATUS	current
    DESCRIPTION
	"
	Fld OID Name:	avCmIpUnregisteredRangePort
	Fld OID:	enterprises.6889.2.73.8.1.55.3.1.3
	Fld Form/Rpt:	UNREGISTERED IP TELEPHONES
	Fld Format:	Single
	Fld(s) Name:	Port
	Fld Descr:	An object containing the station Port.
	"
    ::= { avCmListIpUnregisteredRangeEntry 3 }

avCmListIpUnregisteredRangeRegistered	OBJECT-TYPE
    SYNTAX	SnmpAdminString (SIZE (0..2))
    MAX-ACCESS	read-only
    STATUS	current
    DESCRIPTION
	"
	Fld OID Name:	avCmIpUnregisteredRangeRegistered 
	Fld OID:	enterprises.6889.2.73.8.1.55.3.1.4
	Fld Form/Rpt:	UNREGISTERED IP TELEPHONES
	Fld Format:	Single
	Fld(s) Name:	Registered
	Fld Descr:	An object containing whether or not the station is 
			registered.
	"
    ::= { avCmListIpUnregisteredRangeEntry 4 }


-- ******************** avCmDispTime Group *************************

-- MIB GROUP DESCRIPTION

-- MIB Group Name:
--              avCmDispTime
-- OID:
--              enterprises.6889.2.73.8.1.56
-- Description:
--              The avCmDispTime MIB Group uses the "display
--              time" command to retrieve time information.
--
-- Releases Supported:
--              CM6.3.100 and greater
-- Polling Type:
--              Performance/Utilization
-- Polling Interval:
--              None
-- Default Caching Interval
-- 		0 seconds
-- Timeout Interval:
--              Initial Timeout should be set to 15 seconds.
-- Retry Interval:
--              Initial Retry should be set to 3.
-- Limitations:
--              Green/Low - The data collected by this MIB Group
--              is minimal and therefore has a low impact on the system.
-- Command Type:
--              1. SAT
-- Command:
--              1. display time
-- Form/Report Name:
--              1. DATE AND TIME
-- Reference Document:
--              1. A detailed description of the command and form can be
--                 found in document referenced by REF_DOC_1 in the
--                 DOCUMENT REFERENCE SECTION.
-- Command Permission/User-profile:
--              1. No special permissions needed.

avCmDispTime        OBJECT IDENTIFIER ::= { avCmObjects 56 }

avCmDispTimeDayOfWeek OBJECT-TYPE
    SYNTAX      SnmpAdminString (SIZE (0..10))
    MAX-ACCESS  read-only
    STATUS      current
    DESCRIPTION
        "
        Fld OID Name:   avCmDispTimeDayOfWeek
        Fld OID:        enterprises.6889.2.73.8.1.56.1
        Fld Form/Rpt:   DATE AND TIME
        Fld Format:     Single
        Fld(s) Name:    Day of the Week
        Fld Descr:      An object that contains the day of the week
        "
    ::= { avCmDispTime 1 }

avCmDispTimeMonth OBJECT-TYPE
    SYNTAX      SnmpAdminString (SIZE (0..10))
    MAX-ACCESS  read-only
    STATUS      current
    DESCRIPTION
        "
        Fld OID Name:   avCmDispTimeDayOfWeek
        Fld OID:        enterprises.6889.2.73.8.1.56.1
        Fld Form/Rpt:   DATE AND TIME
        Fld Format:     Single
        Fld(s) Name:    Month
        Fld Descr:      An object that contains the month of the year.
        "
    ::= { avCmDispTime 2 }

avCmDispTimeDayOfTheMonth OBJECT-TYPE
    SYNTAX      Integer32 (0..99)
    MAX-ACCESS  read-only
    STATUS      current
    DESCRIPTION
        "
        Fld OID Name:   avCmDispTimeDayOfTheMonth
        Fld OID:        enterprises.6889.2.73.8.1.56.3
        Fld Form/Rpt:   DATE AND TIME
        Fld Format:     Single Field
        Fld(s) Name:    Day of the Month
        Fld Descr:      An object that contains the day of the month.
        "
    ::= { avCmDispTime 3 }


avCmDispTimeYear OBJECT-TYPE
    SYNTAX      Integer32 (0..9999)
    MAX-ACCESS  read-only
    STATUS      current
    DESCRIPTION
        "
        Fld OID Name:   avCmDispTimeYear
        Fld OID:        enterprises.6889.2.73.8.1.56.4
        Fld Form/Rpt:   DATE AND TIME
        Fld Format:     Single Field
        Fld(s) Name:    Year
        Fld Descr:      An object that contains the Year.
        "
    ::= { avCmDispTime 4 }

avCmDispTimeHour OBJECT-TYPE
    SYNTAX      Integer32 (0..99)
    MAX-ACCESS  read-only
    STATUS      current
    DESCRIPTION
        "
        Fld OID Name:   avCmDispTimeHour
        Fld OID:        enterprises.6889.2.73.8.1.56.5
        Fld Form/Rpt:   DATE AND TIME
        Fld Format:     Single Field
        Fld(s) Name:    Hour
        Fld Descr:      An object that contains the Hour in 24 hour format.
        "
    ::= { avCmDispTime 5 }

avCmDispTimeMinute OBJECT-TYPE
    SYNTAX      Integer32 (0..99)
    MAX-ACCESS  read-only
    STATUS      current
    DESCRIPTION
        "
        Fld OID Name:   avCmDispTimeMinute
        Fld OID:        enterprises.6889.2.73.8.1.56.6
        Fld Form/Rpt:   DATE AND TIME
        Fld Format:     Single Field
        Fld(s) Name:    Minute
        Fld Descr:      An object that contains the minute.
        "
    ::= { avCmDispTime 6 }

avCmDispTimeSecond OBJECT-TYPE
    SYNTAX      Integer32 (0..99)
    MAX-ACCESS  read-only
    STATUS      current
    DESCRIPTION
        "
        Fld OID Name:   avCmDispTimeSecond
        Fld OID:        enterprises.6889.2.73.8.1.56.7
        Fld Form/Rpt:   DATE AND TIME
        Fld Format:     Single Field
        Fld(s) Name:    Second
        Fld Descr:      An object that contains the second.
        "
    ::= { avCmDispTime 7 }

avCmDispTimeType OBJECT-TYPE
    SYNTAX      SnmpAdminString (SIZE (0..17))
    MAX-ACCESS  read-only
    STATUS      current
    DESCRIPTION
        "
        Fld OID Name:   avCmDispTimeType
        Fld OID:        enterprises.6889.2.73.8.1.56.8
        Fld Form/Rpt:   DATE AND TIME
        Fld Format:     Single
        Fld(s) Name:    Type
        Fld Descr:      An object that contains whether standard time or 
			daylight savings time is in effect.
        "
    ::= { avCmDispTime 8 }

avCmDispTimeDSTRule OBJECT-TYPE
    SYNTAX      Integer32 (0..99)
    MAX-ACCESS  read-only
    STATUS      current
    DESCRIPTION
        "
        Fld OID Name:   avCmDispTimeDSTRule
        Fld OID:        enterprises.6889.2.73.8.1.56.9
        Fld Form/Rpt:   DATE AND TIME
        Fld Format:     Single Field
        Fld(s) Name:    Daylight Saving Rule
        Fld Descr:      An object that contains the daylight savings rule.
        "
    ::= { avCmDispTime 9 }

--   ***********	 avCmMessagingAlarm Group       **************

-- MIB GROUP DESCRIPTION

-- MIB Group Name:
--		avCmMessagingAlarm
-- OID:
--		enterprises.6889.2.73.8.1.57
-- Description:
--		The avCmMessagingAlarm MIB Group displays the output of the
--		"almdisplay -chia -w" command.  The "almdisplay -chia -w"
--		displays all messaging alarms.
-- Releases Supported:
--		CM6.3.100 and greater
-- Polling Type:
--		Fault
-- Polling Interval:
--		No more than every 20 minutes.
-- Default Caching Interval
-- 		90 seconds
-- Timeout Interval:
--		Initial Timeout should be set to 15 seconds.
-- Retry Interval:
--		Initial Retry should be set to 3.
-- Limitations:
--		Yellow/Medium - The data collected by this MIB Group
--		may have some impact on the system.
-- Command Type:
--		1. BASH
-- Command:
--		1. almdisplay -chia -w
-- Form/Report Name:
--		1. Messaging Alarms
-- Reference Document:
--		1. A detailed description of the command and form can be
--		   found in REF_DOC_1 in the DOCUMENT REFERENCE SECTION.
--		   Note, no reference to "-chia" option because it is messaging.
-- Command Permission/User-profile:
--		1. No special permissions needed.

avCmMessagingAlarm		OBJECT IDENTIFIER ::= { avCmObjects 57 }

avCmMessagingAlarmTable	OBJECT-TYPE
    SYNTAX	SEQUENCE OF AvCmMessagingAlarmEntry
    MAX-ACCESS	not-accessible
    STATUS	current
    DESCRIPTION
	"
	Fld OID Name:	avCmMessagingAlarmEntry
	Fld OID:	enterprises.6889.2.73.8.1.57.1
	Fld Form/Rpt:	NA
	Fld Format:	NA
	Fld(s) Name:	NA
	Fld Descr:	A list of the avCmMessagingAlarms entries
	"
    ::= { avCmMessagingAlarm 1 }

avCmMessagingAlarmEntry	OBJECT-TYPE
    SYNTAX	AvCmMessagingAlarmEntry
    MAX-ACCESS	not-accessible
    STATUS	current
    DESCRIPTION
	"
	Fld OID Name:	avCmMessagingAlarmEntry
	Fld OID:	enterprises.6889.2.73.8.1.57.1.1
	Fld Form/Rpt:	NA
	Fld Format:	NA
	Fld(s) Name:	NA
	Fld Descr:	A avCmMessagingAlarm entry containing objects of the
			avCmMessagingAlarm information sent by the switch.
	"
    INDEX    { avCmMessagingAlarmIdx }
    ::= { avCmMessagingAlarmTable 1 }

AvCmMessagingAlarmEntry ::= SEQUENCE {
		avCmMessagingAlarmIdx
		    Integer32,
		avCmMessagingAlarmID
		    Integer32,
		avCmMessagingAlarmApp
		    SnmpAdminString,
		avCmMessagingAlarmSource
		    SnmpAdminString,
		avCmMessagingAlarmEventID
		    SnmpAdminString,
		avCmMessagingAlarmLevel
		    SnmpAdminString,
		avCmMessagingAlarmAck
		    SnmpAdminString,
		avCmMessagingAlarmLoc
		    SnmpAdminString,
		avCmMessagingAlarmDate
		    SnmpAdminString,
		avCmMessagingAlarmDescription
		    SnmpAdminString
		}
avCmMessagingAlarmIdx	OBJECT-TYPE
    SYNTAX	Integer32 (0..400)
    MAX-ACCESS	not-accessible
    STATUS	current
    DESCRIPTION
	"
	Fld OID Name:	avCmMessagingAlarmIdx
	Fld OID:	enterprises.6889.2.73.8.1.57.1.1.1
	Fld Format:	NA
	Fld(s) Name:	NA
	Fld Descr:	An object that uniquely identifies each Messaging Alarm.
	"
    ::= { avCmMessagingAlarmEntry 1 }

avCmMessagingAlarmID	OBJECT-TYPE
    SYNTAX	Integer32 (0..400)
    MAX-ACCESS	read-only
    STATUS	current
    DESCRIPTION
	"
	Fld OID Name:	avCmMessagingAlarmID
	Fld OID:	enterprises.6889.2.73.8.1.57.1.1.2
	Fld Form/Rpt:	Messaging Alarms
	Fld Format:	Single
	Fld(s) Name:	ID
	Fld Descr:	An object that uniquely identifies each Messaging Alarm.
	"
    ::= { avCmMessagingAlarmEntry 2 }

avCmMessagingAlarmApp	OBJECT-TYPE
    SYNTAX	SnmpAdminString (SIZE (0..12))
    MAX-ACCESS	read-only
    STATUS	current
    DESCRIPTION
	"
	Fld OID Name:	avCmMessagingAlarmApp
	Fld OID:	enterprises.6889.2.73.8.1.57.1.1.3
	Fld Form/Rpt:	Messaging Alarms
	Fld Format:	Single
	Fld(s) Name:	APP
	Fld Descr:	An object that displays the application name
			associated with the alarm. 
	"
    ::= { avCmMessagingAlarmEntry 3 }

avCmMessagingAlarmSource	OBJECT-TYPE
    SYNTAX	SnmpAdminString (SIZE (0..7))
    MAX-ACCESS	read-only
    STATUS	current
    DESCRIPTION
	"
	Fld OID Name:	avCmMessagingAlarmSource
	Fld OID:	enterprises.6889.2.73.8.1.57.1.1.4
	Fld Form/Rpt:	Messaging Alarms
	Fld Format:	Single
	Fld(s) Name:	Source
	Fld Descr:	An object that displays the abbreviated name of
			the Source which generated the alarm.
	"
    ::= { avCmMessagingAlarmEntry 4 }

avCmMessagingAlarmEventID	OBJECT-TYPE
    SYNTAX	SnmpAdminString (SIZE (0..6))
    MAX-ACCESS	read-only
    STATUS	current
    DESCRIPTION
	"
	Fld OID Name:	avCmMessagingAlarmEventID
	Fld OID:	enterprises.6889.2.73.8.1.57.1.1.5
	Fld Form/Rpt:	Messaging Alarms
	Fld Format:	Single
	Fld(s) Name:	EvtID
	Fld Descr:	An object that displays the Event ID of the alarm.
			The Event ID is a unique number that identifies an
			alarm event on a per Source basis.
	"
    ::= { avCmMessagingAlarmEntry 5 }

avCmMessagingAlarmLevel	OBJECT-TYPE
    SYNTAX	SnmpAdminString (SIZE (0..6))
    MAX-ACCESS	read-only
    STATUS	current
    DESCRIPTION
	"
	Fld OID Name:	avCmMessagingAlarmLevel
	Fld OID:	enterprises.6889.2.73.8.1.57.1.1.6
	Fld Form/Rpt:	Messaging Alarms
	Fld Format:	Single
	Fld(s) Name:	Lvl
	Fld Descr:	An object that contains the severity level the alarm:
			Warning (WRN), Minor (MIN), or Major (MAJ).
	"
    ::= { avCmMessagingAlarmEntry 6 }

avCmMessagingAlarmAck	OBJECT-TYPE
    SYNTAX	SnmpAdminString (SIZE (0..4))
    MAX-ACCESS	read-only
    STATUS	current
    DESCRIPTION
	"
	Fld OID Name:	avCmMessagingAlarmAck
	Fld OID:	enterprises.6889.2.73.8.1.57.1.1.7
	Fld Form/Rpt:	Messaging Alarms
	Fld Format:	Single
	Fld(s) Name:	Ack
	Fld Descr:	An object that displays Y or N, indicating whether or
			not the alarm has been acknowledged by INADS.
	"
    ::= { avCmMessagingAlarmEntry 7 }

avCmMessagingAlarmLoc	OBJECT-TYPE
    SYNTAX	SnmpAdminString (SIZE (0..11))
    MAX-ACCESS	read-only
    STATUS	current
    DESCRIPTION
	"
	Fld OID Name:	avCmMessagingAlarmLoc
	Fld OID:	enterprises.6889.2.73.8.1.57.1.1.8
	Fld Form/Rpt:	Messaging Alarms
	Fld Format:	Single
	Fld(s) Name:	Location
	Fld Descr:	An object that displays the location of the alarm
			origination.
	"
    ::= { avCmMessagingAlarmEntry 8 }

avCmMessagingAlarmDate	OBJECT-TYPE
    SYNTAX	SnmpAdminString (SIZE (0..35))
    MAX-ACCESS	read-only
    STATUS	current
    DESCRIPTION
	"
	Fld OID Name:	avCmMessagingAlarmDate
	Fld OID:	enterprises.6889.2.73.8.1.57.1.1.9
	Fld Form/Rpt:	Messaging Alarms
	Fld Format:	Single
	Fld(s) Name:	Date
	Fld Descr:	An object that contains the date the Messaging Alarm
			was generated.
	"
    ::= { avCmMessagingAlarmEntry 9 }

avCmMessagingAlarmDescription	OBJECT-TYPE
    SYNTAX	SnmpAdminString (SIZE (0..120))
    MAX-ACCESS	read-only
    STATUS	current
    DESCRIPTION
	"
	Fld OID Name:	avCmMessagingAlarmDescription
	Fld OID:	enterprises.6889.2.73.8.1.57.1.1.10
	Fld Form/Rpt:	Messaging Alarms
	Fld Format:	Single
	Fld(s) Name:	Description
	Fld Descr:	An object that contains a description of the
			Messaging Alarm.
	"
    ::= { avCmMessagingAlarmEntry 10 }


-- ******************** avCmInitCauses Group *************************

-- MIB GROUP DESCRIPTION

-- MIB Group Name:
--		avCmInitCauses Group
-- OID:
--		enterprises.6889.2.73.8.1.58
-- Description:
--		The avCmInitCauses MIB Group uses the 
--		"display initcauses" command to 
--		retrieve restart information.
--		
-- Releases Supported:
--		CM6.3.100 and greater
-- Polling Type:
--		Performance/Utilization
-- Polling Interval:
--		Once a minute.
-- Default Caching Interval
-- 		60 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. display initcauses
-- Form/Report Name:
--		1. INITIALIZATION CAUSES
-- Reference Document:
--		1. A detailed description of the command and form can be
--		   found in document referenced by REF_DOC_1 in the
--		   DOCUMENT REFERENCE SECTION.
-- Command Permission/User-profile:
--		1. No special permissions needed.

avCmInitCauses	OBJECT IDENTIFIER ::= { avCmObjects 58 }

avCmInitCausesTable	OBJECT-TYPE
    SYNTAX	SEQUENCE OF AvCmInitCausesEntry
    MAX-ACCESS	not-accessible
    STATUS	current
    DESCRIPTION
	"
	Fld OID Name:	AvCmInitCausesEntry
	Fld OID:	enterprises.6889.2.73.8.1.58.1
	Fld Form/Rpt:	NA
	Fld Format:	NA
	Fld(s) Name:	NA
	Fld Descr:	A list of the avCmInitCauses entries
	"
    ::= { avCmInitCauses 1 }

avCmInitCausesEntry	OBJECT-TYPE
    SYNTAX	AvCmInitCausesEntry
    MAX-ACCESS	not-accessible
    STATUS	current
    DESCRIPTION
	"
	Fld OID Name:	avCmInitCausesEntry
	Fld OID:	enterprises.6889.2.73.8.1.58.1.1
	Fld Form/Rpt:	NA
	Fld Format:	NA
	Fld(s) Name:	NA
	Fld Descr:	A avCmInitCausesEntry entry containing objects of the
			avCmInitCauses information sent by the switch.
	"
    INDEX    { avCmInitCausesTimeIdx, avCmInitCausesIdx  }
    ::= { avCmInitCausesTable 1 }

AvCmInitCausesEntry ::= SEQUENCE {
		avCmInitCausesTimeIdx
		    SnmpAdminString,
		avCmInitCausesIdx
		    Integer32,
		avCmInitCausesTime
		    SnmpAdminString,
		avCmInitCausesCause
		    SnmpAdminString,
		avCmInitCausesAction
		    Integer32,
		avCmInitCausesEscalated
		    SnmpAdminString,
		avCmInitCausesMode
		    SnmpAdminString
		}

avCmInitCausesTimeIdx	OBJECT-TYPE
    SYNTAX	SnmpAdminString (SIZE (0..13))
    MAX-ACCESS	not-accessible
    STATUS	current
    DESCRIPTION
	"
	Fld OID Name:	avCmInitCausesTimeIdx
	Fld OID:	enterprises.6889.2.73.8.1.58.1.1.1
	Fld Format:	NA
	Fld(s) Name:	NA
	Fld Descr:	An object that uniquely identifies each Increment of 
			data.
	"
    ::= { avCmInitCausesEntry 1 }

avCmInitCausesIdx         OBJECT-TYPE
    SYNTAX      Integer32 (0..400)
    MAX-ACCESS  not-accessible
    STATUS      current
    DESCRIPTION
        "
        Fld OID Name:   avCmInitCausesIdx
        Fld OID:        enterprises.6889.2.73.8.1.58.1.1.2
        Fld Form/Rpt:   NA
        Fld Format:     NA
        Fld(s) Name:    NA
        Fld Descr:      An Integer32 object containing an index that numbers
                        the alarm entry for the avCmInitCausesIdx.  This
                        object along with avCmInitCausesTimeIdx serves as the
                        instance identifier for avCmInitCausesEntry.
        "
    ::= { avCmInitCausesEntry 2 }

avCmInitCausesTime	OBJECT-TYPE
    SYNTAX	SnmpAdminString (SIZE (0..13))
    MAX-ACCESS	read-only
    STATUS	current
    DESCRIPTION
	"
	Fld OID Name:	avCmInitCausesTime
	Fld OID:	enterprises.6889.2.73.8.1.58.1.1.3
	Fld Form/Rpt:	INITIALIZATION CAUSES
	Fld Format:	Single Field
	Fld(s) Name:	Time
	Fld Descr:	An object containing the time of the event.
	"
    ::= { avCmInitCausesEntry 3 }

avCmInitCausesCause	OBJECT-TYPE
    SYNTAX	SnmpAdminString (SIZE (0..25))
    MAX-ACCESS	read-only
    STATUS	current
    DESCRIPTION
	"
	Fld OID Name:	avCmInitCausesCause
	Fld OID:	enterprises.6889.2.73.8.1.58.1.1.4
	Fld Form/Rpt:	INITIALIZATION CAUSES
	Fld Format:	Single Field
	Fld(s) Name:	Cause
	Fld Descr:	An object containing the cause of the event.
	"
    ::= { avCmInitCausesEntry 4 }

avCmInitCausesAction	OBJECT-TYPE
    SYNTAX      Integer32 (0..9)
    MAX-ACCESS  read-only
    STATUS      current
    DESCRIPTION
        "
        Fld OID Name:   avCmInitCausesAction
        Fld OID:        enterprises.6889.2.73.8.1.59.1.1.5
        Fld Form/Rpt:   INITIALIZATION CAUSES
        Fld Format:     Single Field
        Fld(s) Name:    Action
        Fld Descr:      An object containing the reset level of the vent.
        "
    ::= { avCmInitCausesEntry 5 }



avCmInitCausesEscalated   OBJECT-TYPE
    SYNTAX	SnmpAdminString (SIZE (0..6))
    MAX-ACCESS  read-only
    STATUS      current
    DESCRIPTION
        "
        Fld OID Name:   avCmInitCausesEscalated
        Fld OID:        enterprises.6889.2.73.8.1.58.1.1.6
        Fld Form/Rpt:   INITIALIZATION CAUSES
        Fld Format:     Single Field
        Fld(s) Name:    Escalated
        Fld Descr:      An object containing whether or not event escalated.
			
        "
    ::= { avCmInitCausesEntry 6 }


avCmInitCausesMode	OBJECT-TYPE
    SYNTAX	SnmpAdminString (SIZE (0..9))
    MAX-ACCESS	read-only
    STATUS	current
    DESCRIPTION
	"
	Fld OID Name:	avCmInitCausesMode
	Fld OID:	enterprises.6889.2.73.8.1.58.1.1.7
        Fld Form/Rpt:   INITIALIZATION CAUSES
	Fld Format:	Single Field
	Fld(s) Name:	Mode
	Fld Descr:	An object containing the mode.
	"
    ::= { avCmInitCausesEntry 7 }

-- ******************** avCmMeasAnnIntegAllLstHr Group *************************

-- MIB GROUP DESCRIPTION

-- MIB Group Name:
--		avCmMeasAnnIntegAllLstHr Group
-- OID:
--		enterprises.6889.2.73.8.1.59
-- Description:
--		The avCmMeasAnnIntegAllLstHr MIB Group uses the 
--		"list measurements announcement  integ-all  last-hour" command 
--		to retrieve measurements information for all integrated
--		announcements for the last hour.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements announcement integ-all last-hour
-- Form/Report Name:
--		1. VOICE ANNOUNCEMENT MEASUREMENTS
-- Reference Document:
--		1. A detailed description of the command and form can be
--		   found in document referenced by REF_DOC_4 in the
--		   DOCUMENT REFERENCE SECTION.
-- Command Permission/User-profile:
--		1. No special permissions needed.

avCmMeasAnnIntegAllLstHr	OBJECT IDENTIFIER ::= { avCmObjects 59 }

avCmMeasAnnIntegAllLstHrTable	OBJECT-TYPE
    SYNTAX	SEQUENCE OF AvCmMeasAnnIntegAllLstHrEntry
    MAX-ACCESS	not-accessible
    STATUS	current
    DESCRIPTION
	"
	Fld OID Name:	avCmMeasAnnIntegAllLstHrEntry
	Fld OID:	enterprises.6889.2.73.8.1.59.1
	Fld Form/Rpt:	NA
	Fld Format:	NA
	Fld(s) Name:	NA
	Fld Descr:	A list of the avCmMeasAnnIntegAllLstHr entries
	"
    ::= { avCmMeasAnnIntegAllLstHr 1 }

avCmMeasAnnIntegAllLstHrEntry	OBJECT-TYPE
    SYNTAX	AvCmMeasAnnIntegAllLstHrEntry
    MAX-ACCESS	not-accessible
    STATUS	current
    DESCRIPTION
	"
	Fld OID Name:	avCmMeasAnnIntegAllLstHrEntry
	Fld OID:	enterprises.6889.2.73.8.1.59.1.1
	Fld Form/Rpt:	NA
	Fld Format:	NA
	Fld(s) Name:	NA
	Fld Descr:	A avCmMeasAnnIntegAllLstHr entry containing objects of the
			avCmMeasAnnIntegAllLstHr information sent by the switch.
	"
    INDEX    { avCmMeasAnnIntegAllLstHrIdx }
    ::= { avCmMeasAnnIntegAllLstHrTable 1 }

AvCmMeasAnnIntegAllLstHrEntry ::= SEQUENCE {
		avCmMeasAnnIntegAllLstHrIdx
		    SnmpAdminString,
		avCmMeasAnnIntegAllLstHrExtension
		    SnmpAdminString,
		avCmMeasAnnIntegAllLstHrRunDate
		    SnmpAdminString,
		avCmMeasAnnIntegAllLstHrSource
		    SnmpAdminString,
		avCmMeasAnnIntegAllLstHrPlayPorts
		    Integer32,
		avCmMeasAnnIntegAllLstHrMaxCallrsPeriod
		    Integer32,
		avCmMeasAnnIntegAllLstHrAllPortsBusyPeriod
		    Integer32,
		avCmMeasAnnIntegAllLstHrName
		    SnmpAdminString,
		avCmMeasAnnIntegAllLstHrMeasHour
		    Integer32,
		avCmMeasAnnIntegAllLstHrPlayRequests
		    Integer32,
		avCmMeasAnnIntegAllLstHrCallsQueued
		    Integer32,
		avCmMeasAnnIntegAllLstHrASP
		    Integer32,
		avCmMeasAnnIntegAllLstHrPSP
		    Integer32,
		avCmMeasAnnIntegAllLstHrQueueDrops
		    Integer32,
		avCmMeasAnnIntegAllLstHrMportPlays
		    Integer32,
		avCmMeasAnnIntegAllLstHrMxPorts
		    Integer32,
		avCmMeasAnnIntegAllLstHrMaxCallers
		    Integer32
		}

avCmMeasAnnIntegAllLstHrIdx	OBJECT-TYPE
    SYNTAX	SnmpAdminString (SIZE (0..17))
    MAX-ACCESS	not-accessible
    STATUS	current
    DESCRIPTION
	"
	Fld OID Name:	avCmMeasAnnIntegAllLstHrIdx
	Fld OID:	enterprises.6889.2.73.8.1.59.1.1.1
	Fld Format:	NA
	Fld(s) Name:	NA
	Fld Descr:	An object that uniquely identifies each Increment of 
			data.
	"
    ::= { avCmMeasAnnIntegAllLstHrEntry 1 }

avCmMeasAnnIntegAllLstHrExtension	OBJECT-TYPE
    SYNTAX	SnmpAdminString (SIZE (0..17))
    MAX-ACCESS	read-only
    STATUS	current
    DESCRIPTION
	"
	Fld OID Name:	avCmMeasAnnIntegAllLstHrExtension
	Fld OID:	enterprises.6889.2.73.8.1.59.1.1.2
	Fld Form/Rpt:	VOICE ANNOUNCEMENT MEASUREMENTS
	Fld Format:	Single Field
	Fld(s) Name:	Extension
	Fld Descr:	An object containing the announcement extension.
	"
    ::= { avCmMeasAnnIntegAllLstHrEntry 2 }

avCmMeasAnnIntegAllLstHrRunDate	OBJECT-TYPE
    SYNTAX	SnmpAdminString (SIZE (0..28))
    MAX-ACCESS	read-only
    STATUS	current
    DESCRIPTION
	"
	Fld OID Name:	avCmMeasAnnIntegAllLstHrRunDate
	Fld OID:	enterprises.6889.2.73.8.1.59.1.1.3
	Fld Form/Rpt:	VOICE ANNOUNCEMENT MEASUREMENTS
	Fld Format:	Single Field
	Fld(s) Name:	Date
	Fld Descr:	An object containing the Date the command was executed.
	"
    ::= { avCmMeasAnnIntegAllLstHrEntry 3 }

avCmMeasAnnIntegAllLstHrSource OBJECT-TYPE
    SYNTAX      SnmpAdminString (SIZE (0..6))
    MAX-ACCESS  read-only
    STATUS      current
    DESCRIPTION
        "
        Fld OID Name:   avCmMeasAnnIntegAllLstHrSource
        Fld OID:        enterprises.6889.2.73.8.1.59.1.1.4
        Fld Form/Rpt:   VOICE ANNOUNCEMENT MEASUREMENTS
        Fld Format:     Single Field
        Fld(s) Name:    Source
        Fld Descr:      An object containing the Source board or media module.
        "
    ::= { avCmMeasAnnIntegAllLstHrEntry 4 }

avCmMeasAnnIntegAllLstHrPlayPorts OBJECT-TYPE
    SYNTAX	Integer32 (0..99999)
    MAX-ACCESS  read-only
    STATUS      current
    DESCRIPTION
        "
        Fld OID Name:   avCmMeasAnnIntegAllLstHrPlayPorts
        Fld OID:        enterprises.6889.2.73.8.1.59.1.1.5
        Fld Form/Rpt:   VOICE ANNOUNCEMENT MEASUREMENTS
        Fld Format:     Single Field
        Fld(s) Name:    Play Ports
        Fld Descr:      An object containing the number of play ports for the 
			source.
        "
    ::= { avCmMeasAnnIntegAllLstHrEntry 5 }

avCmMeasAnnIntegAllLstHrMaxCallrsPeriod OBJECT-TYPE
    SYNTAX	Integer32 (0..99999)
    MAX-ACCESS  read-only
    STATUS      current
    DESCRIPTION
        "
        Fld OID Name:   avCmMeasAnnIntegAllLstHrMaxCallrsPeriod
        Fld OID:        enterprises.6889.2.73.8.1.59.1.1.6
        Fld Form/Rpt:   VOICE ANNOUNCEMENT MEASUREMENTS
        Fld Format:     Single Field
        Fld(s) Name:    Max Callers on Source in Period
        Fld Descr:      An object containing the maximum callers using the
			source in the period.
        "
    ::= { avCmMeasAnnIntegAllLstHrEntry 6 }


avCmMeasAnnIntegAllLstHrAllPortsBusyPeriod OBJECT-TYPE
    SYNTAX      Integer32 (0..99999)
    MAX-ACCESS  read-only
    STATUS      current
    DESCRIPTION
        "
        Fld OID Name:   avCmMeasAnnIntegAllLstHrAllPortsBusyPeriod
        Fld OID:        enterprises.6889.2.73.8.1.59.1.1.7
        Fld Form/Rpt:   VOICE ANNOUNCEMENT MEASUREMENTS
        Fld Format:     Single Field
        Fld(s) Name:    All Ports Busy in Period
        Fld Descr:      An object containing the number of time all the ports
                        on the source were busy during the period.
        "
    ::= { avCmMeasAnnIntegAllLstHrEntry 7 }

avCmMeasAnnIntegAllLstHrName   OBJECT-TYPE
    SYNTAX	SnmpAdminString (SIZE (0..25))
    MAX-ACCESS  read-only
    STATUS      current
    DESCRIPTION
        "
        Fld OID Name:   avCmMeasAnnIntegAllLstHrName
        Fld OID:        enterprises.6889.2.73.8.1.59.1.1.8
        Fld Form/Rpt:   VOICE ANNOUNCEMENT MEASUREMENTS
        Fld Format:     Single Field
        Fld(s) Name:    Name
        Fld Descr:      An object containing the 24 characters of the 
			announcement name.
        "
    ::= { avCmMeasAnnIntegAllLstHrEntry 8 }


avCmMeasAnnIntegAllLstHrMeasHour	OBJECT-TYPE
    SYNTAX	Integer32 (0..9999)
    MAX-ACCESS	read-only
    STATUS	current
    DESCRIPTION
	"
	Fld OID Name:	avCmMeasAnnIntegAllLstHrMeasHour
	Fld OID:	enterprises.6889.2.73.8.1.59.1.1.9
	Fld Form/Rpt:	VOICE ANNOUNCEMENT MEASUREMENTS
	Fld Format:	Single Field
	Fld(s) Name:	Meas Hour
	Fld Descr:	An object containing the measurement hour.
	"
    ::= { avCmMeasAnnIntegAllLstHrEntry 9 }

avCmMeasAnnIntegAllLstHrPlayRequests	OBJECT-TYPE
    SYNTAX	Integer32 (0..99999)
    MAX-ACCESS	read-only
    STATUS	current
    DESCRIPTION
	"
	Fld OID Name:	avCmMeasAnnIntegAllLstHrPlayRequests
	Fld OID:	enterprises.6889.2.73.8.1.59.1.1.10
	Fld Form/Rpt:	VOICE ANNOUNCEMENT MEASUREMENTS
	Fld Format:	Single Field
	Fld(s) Name:	Play Reqts
	Fld Descr:	An object containing the number of play requests
			for the announcement.
	"
    ::= { avCmMeasAnnIntegAllLstHrEntry 10 }

avCmMeasAnnIntegAllLstHrCallsQueued OBJECT-TYPE
    SYNTAX      Integer32 (0..99999)
    MAX-ACCESS  read-only
    STATUS      current
    DESCRIPTION
        "
        Fld OID Name:   avCmMeasAnnIntegAllLstHrCallsQueued
        Fld OID:        enterprises.6889.2.73.8.1.59.1.1.11
        Fld Form/Rpt:   VOICE ANNOUNCEMENT MEASUREMENTS
        Fld Format:     Single Field
        Fld(s) Name:    Calls Que
        Fld Descr:      An object containing the number of calls for an 
			announcement that had to queue waiting for a port 
			during the period.
        "
    ::= { avCmMeasAnnIntegAllLstHrEntry 11 }


avCmMeasAnnIntegAllLstHrASP OBJECT-TYPE
    SYNTAX      Integer32 (0..9999)
    MAX-ACCESS  read-only
    STATUS      current
    DESCRIPTION
        "
        Fld OID Name:   avCmMeasAnnIntegAllLstHrASP
        Fld OID:        enterprises.6889.2.73.8.1.59.1.1.12
        Fld Form/Rpt:   VOICE ANNOUNCEMENT MEASUREMENTS
        Fld Format:     Single Field
        Fld(s) Name:    ASP
        Fld Descr:      An object containing from time waiting for announcement
			to play to when it starts playing in seconds averaged 
			over the period.  Calls abandoned while in the waiting 
			for announcement port queue are not to be included.
        "
    ::= { avCmMeasAnnIntegAllLstHrEntry 12 }

avCmMeasAnnIntegAllLstHrPSP OBJECT-TYPE
    SYNTAX      Integer32 (0..9999)
    MAX-ACCESS  read-only
    STATUS      current
    DESCRIPTION
        "
        Fld OID Name:   avCmMeasAnnIntegAllLstHrPSP
        Fld OID:        enterprises.6889.2.73.8.1.59.1.1.13
        Fld Form/Rpt:   VOICE ANNOUNCEMENT MEASUREMENTS
        Fld Format:     Single Field
        Fld(s) Name:    PSP
        Fld Descr:      An object containing the peak speed to play an 
			announcement.
        "
    ::= { avCmMeasAnnIntegAllLstHrEntry 13 }


avCmMeasAnnIntegAllLstHrQueueDrops OBJECT-TYPE
    SYNTAX      Integer32 (0..99999)
    MAX-ACCESS  read-only
    STATUS      current
    DESCRIPTION
        "
        Fld OID Name:   avCmMeasAnnIntegAllLstHrQueueDrops
        Fld OID:        enterprises.6889.2.73.8.1.59.1.1.14
        Fld Form/Rpt:   VOICE ANNOUNCEMENT MEASUREMENTS
        Fld Format:     Single Field
        Fld(s) Name:    Queue Drops
        Fld Descr:      An object containing - count of the individual calls 
			that had to queue but dropped while waiting during the 
			period - this includes calls abandoned by the caller 
			and VOA (VDN of origin Announcements) aborts but should 
			exclude calls that were waiting but answered by an 
			agent.
        "
    ::= { avCmMeasAnnIntegAllLstHrEntry 14 }


avCmMeasAnnIntegAllLstHrMportPlays OBJECT-TYPE
    SYNTAX      Integer32 (0..99999)
    MAX-ACCESS  read-only
    STATUS      current
    DESCRIPTION
        "
        Fld OID Name:   avCmMeasAnnIntegAllLstHrMportPlays
        Fld OID:        enterprises.6889.2.73.8.1.59.1.1.15
        Fld Form/Rpt:   VOICE ANNOUNCEMENT MEASUREMENTS
        Fld Format:     Single Field
        Fld(s) Name:    Mport Plays
        Fld Descr:      An object containing - count of how many times the 
			announcement is being played out of more than one port 
			at the same time during the period.
        "
    ::= { avCmMeasAnnIntegAllLstHrEntry 15 }


avCmMeasAnnIntegAllLstHrMxPorts OBJECT-TYPE
    SYNTAX      Integer32 (0..99)
    MAX-ACCESS  read-only
    STATUS      current
    DESCRIPTION
        "
        Fld OID Name:   avCmMeasAnnIntegAllLstHrMxPorts
        Fld OID:        enterprises.6889.2.73.8.1.59.1.1.16
        Fld Form/Rpt:   VOICE ANNOUNCEMENT MEASUREMENTS
        Fld Format:     Single Field
        Fld(s) Name:    Mx Pt
        Fld Descr:      An object containing the peak number of ports used for 
			the announcement during the period.
        "
    ::= { avCmMeasAnnIntegAllLstHrEntry 16 }


avCmMeasAnnIntegAllLstHrMaxCallers OBJECT-TYPE
    SYNTAX      Integer32 (0..999)
    MAX-ACCESS  read-only
    STATUS      current
    DESCRIPTION
        "
        Fld OID Name:   avCmMeasAnnIntegAllLstHrMaxCallers
        Fld OID:        enterprises.6889.2.73.8.1.59.1.1.17
        Fld Form/Rpt:   VOICE ANNOUNCEMENT MEASUREMENTS
        Fld Format:     Single Field
        Fld(s) Name:    Max Cls
        Fld Descr:      An object containing the peak number callers connected 
			to a port at the same time for this announcement during
			the period
        "
    ::= { avCmMeasAnnIntegAllLstHrEntry 17 }

-- ******************** avCmMeasAnnIntegAllToday Group *************************

-- MIB GROUP DESCRIPTION

-- MIB Group Name:
--		avCmMeasAnnIntegAllToday Group
-- OID:
--		enterprises.6889.2.73.8.1.60
-- Description:
--		The avCmMeasAnnIntegAllToday MIB Group uses the 
--		"list measurements announcement  integ-all  today-peak" command 
--		to retrieve measurements information for all integrated
--		announcements for today.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements announcement integ-all today-peak
-- Form/Report Name:
--		1. VOICE ANNOUNCEMENT MEASUREMENTS
-- Reference Document:
--		1. A detailed description of the command and form can be
--		   found in document referenced by REF_DOC_4 in the
--		   DOCUMENT REFERENCE SECTION.
-- Command Permission/User-profile:
--		1. No special permissions needed.

avCmMeasAnnIntegAllToday	OBJECT IDENTIFIER ::= { avCmObjects 60 }

avCmMeasAnnIntegAllTodayTable	OBJECT-TYPE
    SYNTAX	SEQUENCE OF AvCmMeasAnnIntegAllTodayEntry
    MAX-ACCESS	not-accessible
    STATUS	current
    DESCRIPTION
	"
	Fld OID Name:	avCmMeasAnnIntegAllTodayEntry
	Fld OID:	enterprises.6889.2.73.8.1.60.1
	Fld Form/Rpt:	NA
	Fld Format:	NA
	Fld(s) Name:	NA
	Fld Descr:	A list of the avCmMeasAnnIntegAllToday entries
	"
    ::= { avCmMeasAnnIntegAllToday 1 }

avCmMeasAnnIntegAllTodayEntry	OBJECT-TYPE
    SYNTAX	AvCmMeasAnnIntegAllTodayEntry
    MAX-ACCESS	not-accessible
    STATUS	current
    DESCRIPTION
	"
	Fld OID Name:	avCmMeasAnnIntegAllTodayEntry
	Fld OID:	enterprises.6889.2.73.8.1.60.1.1
	Fld Form/Rpt:	NA
	Fld Format:	NA
	Fld(s) Name:	NA
	Fld Descr:	A avCmMeasAnnIntegAllToday entry containing objects of the
			avCmMeasAnnIntegAllToday information sent by the switch.
	"
    INDEX    { avCmMeasAnnIntegAllTodayIdx }
    ::= { avCmMeasAnnIntegAllTodayTable 1 }

AvCmMeasAnnIntegAllTodayEntry ::= SEQUENCE {
		avCmMeasAnnIntegAllTodayIdx
		    SnmpAdminString,
		avCmMeasAnnIntegAllTodayExtension
		    SnmpAdminString,
		avCmMeasAnnIntegAllTodayRunDate
		    SnmpAdminString,
		avCmMeasAnnIntegAllTodaySource
		    SnmpAdminString,
		avCmMeasAnnIntegAllTodayPlayPorts
		    Integer32,
		avCmMeasAnnIntegAllTodayMaxCallrsPeriod
		    Integer32,
		avCmMeasAnnIntegAllTodayAllPortsBusyPeriod
		    Integer32,
		avCmMeasAnnIntegAllTodayName
		    SnmpAdminString,
		avCmMeasAnnIntegAllTodayMeasHour
		    Integer32,
		avCmMeasAnnIntegAllTodayPlayRequests
		    Integer32,
		avCmMeasAnnIntegAllTodayCallsQueued
		    Integer32,
		avCmMeasAnnIntegAllTodayASP
		    Integer32,
		avCmMeasAnnIntegAllTodayPSP
		    Integer32,
		avCmMeasAnnIntegAllTodayQueueDrops
		    Integer32,
		avCmMeasAnnIntegAllTodayMportPlays
		    Integer32,
		avCmMeasAnnIntegAllTodayMxPorts
		    Integer32,
		avCmMeasAnnIntegAllTodayMaxCallers
		    Integer32
		}

avCmMeasAnnIntegAllTodayIdx	OBJECT-TYPE
    SYNTAX	SnmpAdminString (SIZE (0..17))
    MAX-ACCESS	not-accessible
    STATUS	current
    DESCRIPTION
	"
	Fld OID Name:	avCmMeasAnnIntegAllTodayIdx
	Fld OID:	enterprises.6889.2.73.8.1.60.1.1.1
	Fld Format:	NA
	Fld(s) Name:	NA
	Fld Descr:	An object that uniquely identifies each Increment of 
			data.
	"
    ::= { avCmMeasAnnIntegAllTodayEntry 1 }

avCmMeasAnnIntegAllTodayExtension	OBJECT-TYPE
    SYNTAX	SnmpAdminString (SIZE (0..17))
    MAX-ACCESS	read-only
    STATUS	current
    DESCRIPTION
	"
	Fld OID Name:	avCmMeasAnnIntegAllTodayExtension
	Fld OID:	enterprises.6889.2.73.8.1.60.1.1.2
	Fld Form/Rpt:	VOICE ANNOUNCEMENT MEASUREMENTS
	Fld Format:	Single Field
	Fld(s) Name:	Extension
	Fld Descr:	An object containing the announcement extension.
	"
    ::= { avCmMeasAnnIntegAllTodayEntry 2 }

avCmMeasAnnIntegAllTodayRunDate	OBJECT-TYPE
    SYNTAX	SnmpAdminString (SIZE (0..28))
    MAX-ACCESS	read-only
    STATUS	current
    DESCRIPTION
	"
	Fld OID Name:	avCmMeasAnnIntegAllTodayRunDate
	Fld OID:	enterprises.6889.2.73.8.1.60.1.1.3
	Fld Form/Rpt:	VOICE ANNOUNCEMENT MEASUREMENTS
	Fld Format:	Single Field
	Fld(s) Name:	Date
	Fld Descr:	An object containing the Date the command was executed.
	"
    ::= { avCmMeasAnnIntegAllTodayEntry 3 }

avCmMeasAnnIntegAllTodaySource OBJECT-TYPE
    SYNTAX      SnmpAdminString (SIZE (0..6))
    MAX-ACCESS  read-only
    STATUS      current
    DESCRIPTION
        "
        Fld OID Name:   avCmMeasAnnIntegAllTodaySource
        Fld OID:        enterprises.6889.2.73.8.1.60.1.1.4
        Fld Form/Rpt:   VOICE ANNOUNCEMENT MEASUREMENTS
        Fld Format:     Single Field
        Fld(s) Name:    Source
        Fld Descr:      An object containing the Source board or media module.
        "
    ::= { avCmMeasAnnIntegAllTodayEntry 4 }

avCmMeasAnnIntegAllTodayPlayPorts OBJECT-TYPE
    SYNTAX	Integer32 (0..99999)
    MAX-ACCESS  read-only
    STATUS      current
    DESCRIPTION
        "
        Fld OID Name:   avCmMeasAnnIntegAllTodayPlayPorts
        Fld OID:        enterprises.6889.2.73.8.1.60.1.1.5
        Fld Form/Rpt:   VOICE ANNOUNCEMENT MEASUREMENTS
        Fld Format:     Single Field
        Fld(s) Name:    Play Ports
        Fld Descr:      An object containing the number of play ports for the 
			source.
        "
    ::= { avCmMeasAnnIntegAllTodayEntry 5 }

avCmMeasAnnIntegAllTodayMaxCallrsPeriod OBJECT-TYPE
    SYNTAX	Integer32 (0..99999)
    MAX-ACCESS  read-only
    STATUS      current
    DESCRIPTION
        "
        Fld OID Name:   avCmMeasAnnIntegAllTodayMaxCallrsPeriod
        Fld OID:        enterprises.6889.2.73.8.1.60.1.1.6
        Fld Form/Rpt:   VOICE ANNOUNCEMENT MEASUREMENTS
        Fld Format:     Single Field
        Fld(s) Name:    Max Callers on Source in Period
        Fld Descr:      An object containing the maximum callers using the
			source in the period.
        "
    ::= { avCmMeasAnnIntegAllTodayEntry 6 }


avCmMeasAnnIntegAllTodayAllPortsBusyPeriod OBJECT-TYPE
    SYNTAX      Integer32 (0..99999)
    MAX-ACCESS  read-only
    STATUS      current
    DESCRIPTION
        "
        Fld OID Name:   avCmMeasAnnIntegAllTodayAllPortsBusyPeriod
        Fld OID:        enterprises.6889.2.73.8.1.60.1.1.7
        Fld Form/Rpt:   VOICE ANNOUNCEMENT MEASUREMENTS
        Fld Format:     Single Field
        Fld(s) Name:    All Ports Busy in Period
        Fld Descr:      An object containing the number of time all the ports
                        on the source were busy during the period.
        "
    ::= { avCmMeasAnnIntegAllTodayEntry 7 }

avCmMeasAnnIntegAllTodayName   OBJECT-TYPE
    SYNTAX	SnmpAdminString (SIZE (0..25))
    MAX-ACCESS  read-only
    STATUS      current
    DESCRIPTION
        "
        Fld OID Name:   avCmMeasAnnIntegAllTodayName
        Fld OID:        enterprises.6889.2.73.8.1.60.1.1.8
        Fld Form/Rpt:   VOICE ANNOUNCEMENT MEASUREMENTS
        Fld Format:     Single Field
        Fld(s) Name:    Name
        Fld Descr:      An object containing the 24 characters of the 
			announcement name.
        "
    ::= { avCmMeasAnnIntegAllTodayEntry 8 }


avCmMeasAnnIntegAllTodayMeasHour	OBJECT-TYPE
    SYNTAX	Integer32 (0..9999)
    MAX-ACCESS	read-only
    STATUS	current
    DESCRIPTION
	"
	Fld OID Name:	avCmMeasAnnIntegAllTodayMeasHour
	Fld OID:	enterprises.6889.2.73.8.1.60.1.1.9
	Fld Form/Rpt:	VOICE ANNOUNCEMENT MEASUREMENTS
	Fld Format:	Single Field
	Fld(s) Name:	Meas Hour
	Fld Descr:	An object containing the measurement hour.
	"
    ::= { avCmMeasAnnIntegAllTodayEntry 9 }

avCmMeasAnnIntegAllTodayPlayRequests	OBJECT-TYPE
    SYNTAX	Integer32 (0..99999)
    MAX-ACCESS	read-only
    STATUS	current
    DESCRIPTION
	"
	Fld OID Name:	avCmMeasAnnIntegAllTodayPlayRequests
	Fld OID:	enterprises.6889.2.73.8.1.60.1.1.10
	Fld Form/Rpt:	VOICE ANNOUNCEMENT MEASUREMENTS
	Fld Format:	Single Field
	Fld(s) Name:	Play Reqts
	Fld Descr:	An object containing the number of play requests
			for the announcement.
	"
    ::= { avCmMeasAnnIntegAllTodayEntry 10 }

avCmMeasAnnIntegAllTodayCallsQueued OBJECT-TYPE
    SYNTAX      Integer32 (0..99999)
    MAX-ACCESS  read-only
    STATUS      current
    DESCRIPTION
        "
        Fld OID Name:   avCmMeasAnnIntegAllTodayCallsQueued
        Fld OID:        enterprises.6889.2.73.8.1.60.1.1.11
        Fld Form/Rpt:   VOICE ANNOUNCEMENT MEASUREMENTS
        Fld Format:     Single Field
        Fld(s) Name:    Calls Que
        Fld Descr:      An object containing the number of calls for an 
			announcement that had to queue waiting for a port 
			during the period.
        "
    ::= { avCmMeasAnnIntegAllTodayEntry 11 }


avCmMeasAnnIntegAllTodayASP OBJECT-TYPE
    SYNTAX      Integer32 (0..9999)
    MAX-ACCESS  read-only
    STATUS      current
    DESCRIPTION
        "
        Fld OID Name:   avCmMeasAnnIntegAllTodayASP
        Fld OID:        enterprises.6889.2.73.8.1.60.1.1.12
        Fld Form/Rpt:   VOICE ANNOUNCEMENT MEASUREMENTS
        Fld Format:     Single Field
        Fld(s) Name:    ASP
        Fld Descr:      An object containing from time waiting for announcement
			to play to when it starts playing in seconds averaged 
			over the period.  Calls abandoned while in the waiting 
			for announcement port queue are not to be included.
        "
    ::= { avCmMeasAnnIntegAllTodayEntry 12 }

avCmMeasAnnIntegAllTodayPSP OBJECT-TYPE
    SYNTAX      Integer32 (0..9999)
    MAX-ACCESS  read-only
    STATUS      current
    DESCRIPTION
        "
        Fld OID Name:   avCmMeasAnnIntegAllTodayPSP
        Fld OID:        enterprises.6889.2.73.8.1.60.1.1.13
        Fld Form/Rpt:   VOICE ANNOUNCEMENT MEASUREMENTS
        Fld Format:     Single Field
        Fld(s) Name:    PSP
        Fld Descr:      An object containing the peak speed to play an 
			announcement.
        "
    ::= { avCmMeasAnnIntegAllTodayEntry 13 }


avCmMeasAnnIntegAllTodayQueueDrops OBJECT-TYPE
    SYNTAX      Integer32 (0..99999)
    MAX-ACCESS  read-only
    STATUS      current
    DESCRIPTION
        "
        Fld OID Name:   avCmMeasAnnIntegAllTodayQueueDrops
        Fld OID:        enterprises.6889.2.73.8.1.60.1.1.14
        Fld Form/Rpt:   VOICE ANNOUNCEMENT MEASUREMENTS
        Fld Format:     Single Field
        Fld(s) Name:    Queue Drops
        Fld Descr:      An object containing - count of the individual calls 
			that had to queue but dropped while waiting during the 
			period - this includes calls abandoned by the caller 
			and VOA (VDN of origin Announcements) aborts but should 
			exclude calls that were waiting but answered by an 
			agent.
        "
    ::= { avCmMeasAnnIntegAllTodayEntry 14 }


avCmMeasAnnIntegAllTodayMportPlays OBJECT-TYPE
    SYNTAX      Integer32 (0..99999)
    MAX-ACCESS  read-only
    STATUS      current
    DESCRIPTION
        "
        Fld OID Name:   avCmMeasAnnIntegAllTodayMportPlays
        Fld OID:        enterprises.6889.2.73.8.1.60.1.1.15
        Fld Form/Rpt:   VOICE ANNOUNCEMENT MEASUREMENTS
        Fld Format:     Single Field
        Fld(s) Name:    Mport Plays
        Fld Descr:      An object containing - count of how many times the 
			announcement is being played out of more than one port 
			at the same time during the period.
        "
    ::= { avCmMeasAnnIntegAllTodayEntry 15 }


avCmMeasAnnIntegAllTodayMxPorts OBJECT-TYPE
    SYNTAX      Integer32 (0..99)
    MAX-ACCESS  read-only
    STATUS      current
    DESCRIPTION
        "
        Fld OID Name:   avCmMeasAnnIntegAllTodayMxPorts
        Fld OID:        enterprises.6889.2.73.8.1.60.1.1.16
        Fld Form/Rpt:   VOICE ANNOUNCEMENT MEASUREMENTS
        Fld Format:     Single Field
        Fld(s) Name:    Mx Pt
        Fld Descr:      An object containing the peak number of ports used for 
			the announcement during the period.
        "
    ::= { avCmMeasAnnIntegAllTodayEntry 16 }


avCmMeasAnnIntegAllTodayMaxCallers OBJECT-TYPE
    SYNTAX      Integer32 (0..999)
    MAX-ACCESS  read-only
    STATUS      current
    DESCRIPTION
        "
        Fld OID Name:   avCmMeasAnnIntegAllTodayMaxCallers
        Fld OID:        enterprises.6889.2.73.8.1.60.1.1.17
        Fld Form/Rpt:   VOICE ANNOUNCEMENT MEASUREMENTS
        Fld Format:     Single Field
        Fld(s) Name:    Max Cls
        Fld Descr:      An object containing the peak number callers connected 
			to a port at the same time for this announcement during
			the period
        "
    ::= { avCmMeasAnnIntegAllTodayEntry 17 }


-- ******************** avCmMeasAnnIntegAllYest Group *************************

-- MIB GROUP DESCRIPTION

-- MIB Group Name:
--		avCmMeasAnnIntegAllYest Group
-- OID:
--		enterprises.6889.2.73.8.1.61
-- Description:
--		The avCmMeasAnnIntegAllYest MIB Group uses the 
--		"list measurements announcement  integ-all  yesterday-peak" command 
--		to retrieve measurements information for all integrated
--		announcements for yesterday.
--		
-- Releases Supported:
--		CM6.3.100 and greater
-- Polling Type:
--		Performance/Utilization
-- Polling Interval:
--		No more than once a day because the data is only updated
--		after the beginning of the new day.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements announcement integ-all yesterday-peak
-- Form/Report Name:
--		1. VOICE ANNOUNCEMENT MEASUREMENTS
-- Reference Document:
--		1. A detailed description of the command and form can be
--		   found in document referenced by REF_DOC_4 in the
--		   DOCUMENT REFERENCE SECTION.
-- Command Permission/User-profile:
--		1. No special permissions needed.

avCmMeasAnnIntegAllYest	OBJECT IDENTIFIER ::= { avCmObjects 61 }

avCmMeasAnnIntegAllYestTable	OBJECT-TYPE
    SYNTAX	SEQUENCE OF AvCmMeasAnnIntegAllYestEntry
    MAX-ACCESS	not-accessible
    STATUS	current
    DESCRIPTION
	"
	Fld OID Name:	avCmMeasAnnIntegAllYestEntry
	Fld OID:	enterprises.6889.2.73.8.1.61.1
	Fld Form/Rpt:	NA
	Fld Format:	NA
	Fld(s) Name:	NA
	Fld Descr:	A list of the avCmMeasAnnIntegAllYest entries
	"
    ::= { avCmMeasAnnIntegAllYest 1 }

avCmMeasAnnIntegAllYestEntry	OBJECT-TYPE
    SYNTAX	AvCmMeasAnnIntegAllYestEntry
    MAX-ACCESS	not-accessible
    STATUS	current
    DESCRIPTION
	"
	Fld OID Name:	avCmMeasAnnIntegAllYestEntry
	Fld OID:	enterprises.6889.2.73.8.1.61.1.1
	Fld Form/Rpt:	NA
	Fld Format:	NA
	Fld(s) Name:	NA
	Fld Descr:	A avCmMeasAnnIntegAllYest entry containing objects of the
			avCmMeasAnnIntegAllYest information sent by the switch.
	"
    INDEX    { avCmMeasAnnIntegAllYestIdx }
    ::= { avCmMeasAnnIntegAllYestTable 1 }

AvCmMeasAnnIntegAllYestEntry ::= SEQUENCE {
		avCmMeasAnnIntegAllYestIdx
		    SnmpAdminString,
		avCmMeasAnnIntegAllYestExtension
		    SnmpAdminString,
		avCmMeasAnnIntegAllYestRunDate
		    SnmpAdminString,
		avCmMeasAnnIntegAllYestSource
		    SnmpAdminString,
		avCmMeasAnnIntegAllYestPlayPorts
		    Integer32,
		avCmMeasAnnIntegAllYestMaxCallrsPeriod
		    Integer32,
		avCmMeasAnnIntegAllYestAllPortsBusyPeriod
		    Integer32,
		avCmMeasAnnIntegAllYestName
		    SnmpAdminString,
		avCmMeasAnnIntegAllYestMeasHour
		    Integer32,
		avCmMeasAnnIntegAllYestPlayRequests
		    Integer32,
		avCmMeasAnnIntegAllYestCallsQueued
		    Integer32,
		avCmMeasAnnIntegAllYestASP
		    Integer32,
		avCmMeasAnnIntegAllYestPSP
		    Integer32,
		avCmMeasAnnIntegAllYestQueueDrops
		    Integer32,
		avCmMeasAnnIntegAllYestMportPlays
		    Integer32,
		avCmMeasAnnIntegAllYestMxPorts
		    Integer32,
		avCmMeasAnnIntegAllYestMaxCallers
		    Integer32
		}

avCmMeasAnnIntegAllYestIdx	OBJECT-TYPE
    SYNTAX	SnmpAdminString (SIZE (0..17))
    MAX-ACCESS	not-accessible
    STATUS	current
    DESCRIPTION
	"
	Fld OID Name:	avCmMeasAnnIntegAllYestIdx
	Fld OID:	enterprises.6889.2.73.8.1.61.1.1.1
	Fld Format:	NA
	Fld(s) Name:	NA
	Fld Descr:	An object that uniquely identifies each Increment of 
			data.
	"
    ::= { avCmMeasAnnIntegAllYestEntry 1 }

avCmMeasAnnIntegAllYestExtension	OBJECT-TYPE
    SYNTAX	SnmpAdminString (SIZE (0..17))
    MAX-ACCESS	read-only
    STATUS	current
    DESCRIPTION
	"
	Fld OID Name:	avCmMeasAnnIntegAllYestExtension
	Fld OID:	enterprises.6889.2.73.8.1.61.1.1.2
	Fld Form/Rpt:	VOICE ANNOUNCEMENT MEASUREMENTS
	Fld Format:	Single Field
	Fld(s) Name:	Extension
	Fld Descr:	An object containing the announcement extension.
	"
    ::= { avCmMeasAnnIntegAllYestEntry 2 }

avCmMeasAnnIntegAllYestRunDate	OBJECT-TYPE
    SYNTAX	SnmpAdminString (SIZE (0..28))
    MAX-ACCESS	read-only
    STATUS	current
    DESCRIPTION
	"
	Fld OID Name:	avCmMeasAnnIntegAllYestRunDate
	Fld OID:	enterprises.6889.2.73.8.1.61.1.1.3
	Fld Form/Rpt:	VOICE ANNOUNCEMENT MEASUREMENTS
	Fld Format:	Single Field
	Fld(s) Name:	Date
	Fld Descr:	An object containing the Date the command was executed.
	"
    ::= { avCmMeasAnnIntegAllYestEntry 3 }

avCmMeasAnnIntegAllYestSource OBJECT-TYPE
    SYNTAX      SnmpAdminString (SIZE (0..6))
    MAX-ACCESS  read-only
    STATUS      current
    DESCRIPTION
        "
        Fld OID Name:   avCmMeasAnnIntegAllYestSource
        Fld OID:        enterprises.6889.2.73.8.1.61.1.1.4
        Fld Form/Rpt:   VOICE ANNOUNCEMENT MEASUREMENTS
        Fld Format:     Single Field
        Fld(s) Name:    Source
        Fld Descr:      An object containing the Source board or media module.
        "
    ::= { avCmMeasAnnIntegAllYestEntry 4 }

avCmMeasAnnIntegAllYestPlayPorts OBJECT-TYPE
    SYNTAX	Integer32 (0..99999)
    MAX-ACCESS  read-only
    STATUS      current
    DESCRIPTION
        "
        Fld OID Name:   avCmMeasAnnIntegAllYestPlayPorts
        Fld OID:        enterprises.6889.2.73.8.1.61.1.1.5
        Fld Form/Rpt:   VOICE ANNOUNCEMENT MEASUREMENTS
        Fld Format:     Single Field
        Fld(s) Name:    Play Ports
        Fld Descr:      An object containing the number of play ports for the 
			source.
        "
    ::= { avCmMeasAnnIntegAllYestEntry 5 }

avCmMeasAnnIntegAllYestMaxCallrsPeriod OBJECT-TYPE
    SYNTAX	Integer32 (0..99999)
    MAX-ACCESS  read-only
    STATUS      current
    DESCRIPTION
        "
        Fld OID Name:   avCmMeasAnnIntegAllYestMaxCallrsPeriod
        Fld OID:        enterprises.6889.2.73.8.1.61.1.1.6
        Fld Form/Rpt:   VOICE ANNOUNCEMENT MEASUREMENTS
        Fld Format:     Single Field
        Fld(s) Name:    Max Callers on Source in Period
        Fld Descr:      An object containing the maximum callers using the
			source in the period.
        "
    ::= { avCmMeasAnnIntegAllYestEntry 6 }


avCmMeasAnnIntegAllYestAllPortsBusyPeriod OBJECT-TYPE
    SYNTAX      Integer32 (0..99999)
    MAX-ACCESS  read-only
    STATUS      current
    DESCRIPTION
        "
        Fld OID Name:   avCmMeasAnnIntegAllYestAllPortsBusyPeriod
        Fld OID:        enterprises.6889.2.73.8.1.61.1.1.7
        Fld Form/Rpt:   VOICE ANNOUNCEMENT MEASUREMENTS
        Fld Format:     Single Field
        Fld(s) Name:    All Ports Busy in Period
        Fld Descr:      An object containing the number of time all the ports
                        on the source were busy during the period.
        "
    ::= { avCmMeasAnnIntegAllYestEntry 7 }

avCmMeasAnnIntegAllYestName   OBJECT-TYPE
    SYNTAX	SnmpAdminString (SIZE (0..25))
    MAX-ACCESS  read-only
    STATUS      current
    DESCRIPTION
        "
        Fld OID Name:   avCmMeasAnnIntegAllYestName
        Fld OID:        enterprises.6889.2.73.8.1.61.1.1.8
        Fld Form/Rpt:   VOICE ANNOUNCEMENT MEASUREMENTS
        Fld Format:     Single Field
        Fld(s) Name:    Name
        Fld Descr:      An object containing the 24 characters of the 
			announcement name.
        "
    ::= { avCmMeasAnnIntegAllYestEntry 8 }


avCmMeasAnnIntegAllYestMeasHour	OBJECT-TYPE
    SYNTAX	Integer32 (0..9999)
    MAX-ACCESS	read-only
    STATUS	current
    DESCRIPTION
	"
	Fld OID Name:	avCmMeasAnnIntegAllYestMeasHour
	Fld OID:	enterprises.6889.2.73.8.1.61.1.1.9
	Fld Form/Rpt:	VOICE ANNOUNCEMENT MEASUREMENTS
	Fld Format:	Single Field
	Fld(s) Name:	Meas Hour
	Fld Descr:	An object containing the measurement hour.
	"
    ::= { avCmMeasAnnIntegAllYestEntry 9 }

avCmMeasAnnIntegAllYestPlayRequests	OBJECT-TYPE
    SYNTAX	Integer32 (0..99999)
    MAX-ACCESS	read-only
    STATUS	current
    DESCRIPTION
	"
	Fld OID Name:	avCmMeasAnnIntegAllYestPlayRequests
	Fld OID:	enterprises.6889.2.73.8.1.61.1.1.10
	Fld Form/Rpt:	VOICE ANNOUNCEMENT MEASUREMENTS
	Fld Format:	Single Field
	Fld(s) Name:	Play Reqts
	Fld Descr:	An object containing the number of play requests
			for the announcement.
	"
    ::= { avCmMeasAnnIntegAllYestEntry 10 }

avCmMeasAnnIntegAllYestCallsQueued OBJECT-TYPE
    SYNTAX      Integer32 (0..99999)
    MAX-ACCESS  read-only
    STATUS      current
    DESCRIPTION
        "
        Fld OID Name:   avCmMeasAnnIntegAllYestCallsQueued
        Fld OID:        enterprises.6889.2.73.8.1.61.1.1.11
        Fld Form/Rpt:   VOICE ANNOUNCEMENT MEASUREMENTS
        Fld Format:     Single Field
        Fld(s) Name:    Calls Que
        Fld Descr:      An object containing the number of calls for an 
			announcement that had to queue waiting for a port 
			during the period.
        "
    ::= { avCmMeasAnnIntegAllYestEntry 11 }


avCmMeasAnnIntegAllYestASP OBJECT-TYPE
    SYNTAX      Integer32 (0..9999)
    MAX-ACCESS  read-only
    STATUS      current
    DESCRIPTION
        "
        Fld OID Name:   avCmMeasAnnIntegAllYestASP
        Fld OID:        enterprises.6889.2.73.8.1.61.1.1.12
        Fld Form/Rpt:   VOICE ANNOUNCEMENT MEASUREMENTS
        Fld Format:     Single Field
        Fld(s) Name:    ASP
        Fld Descr:      An object containing from time waiting for announcement
			to play to when it starts playing in seconds averaged 
			over the period.  Calls abandoned while in the waiting 
			for announcement port queue are not to be included.
        "
    ::= { avCmMeasAnnIntegAllYestEntry 12 }

avCmMeasAnnIntegAllYestPSP OBJECT-TYPE
    SYNTAX      Integer32 (0..9999)
    MAX-ACCESS  read-only
    STATUS      current
    DESCRIPTION
        "
        Fld OID Name:   avCmMeasAnnIntegAllYestPSP
        Fld OID:        enterprises.6889.2.73.8.1.61.1.1.13
        Fld Form/Rpt:   VOICE ANNOUNCEMENT MEASUREMENTS
        Fld Format:     Single Field
        Fld(s) Name:    PSP
        Fld Descr:      An object containing the peak speed to play an 
			announcement.
        "
    ::= { avCmMeasAnnIntegAllYestEntry 13 }


avCmMeasAnnIntegAllYestQueueDrops OBJECT-TYPE
    SYNTAX      Integer32 (0..99999)
    MAX-ACCESS  read-only
    STATUS      current
    DESCRIPTION
        "
        Fld OID Name:   avCmMeasAnnIntegAllYestQueueDrops
        Fld OID:        enterprises.6889.2.73.8.1.61.1.1.14
        Fld Form/Rpt:   VOICE ANNOUNCEMENT MEASUREMENTS
        Fld Format:     Single Field
        Fld(s) Name:    Queue Drops
        Fld Descr:      An object containing - count of the individual calls 
			that had to queue but dropped while waiting during the 
			period - this includes calls abandoned by the caller 
			and VOA (VDN of origin Announcements) aborts but should 
			exclude calls that were waiting but answered by an 
			agent.
        "
    ::= { avCmMeasAnnIntegAllYestEntry 14 }


avCmMeasAnnIntegAllYestMportPlays OBJECT-TYPE
    SYNTAX      Integer32 (0..99999)
    MAX-ACCESS  read-only
    STATUS      current
    DESCRIPTION
        "
        Fld OID Name:   avCmMeasAnnIntegAllYestMportPlays
        Fld OID:        enterprises.6889.2.73.8.1.61.1.1.15
        Fld Form/Rpt:   VOICE ANNOUNCEMENT MEASUREMENTS
        Fld Format:     Single Field
        Fld(s) Name:    Mport Plays
        Fld Descr:      An object containing - count of how many times the 
			announcement is being played out of more than one port 
			at the same time during the period.
        "
    ::= { avCmMeasAnnIntegAllYestEntry 15 }


avCmMeasAnnIntegAllYestMxPorts OBJECT-TYPE
    SYNTAX      Integer32 (0..99)
    MAX-ACCESS  read-only
    STATUS      current
    DESCRIPTION
        "
        Fld OID Name:   avCmMeasAnnIntegAllYestMxPorts
        Fld OID:        enterprises.6889.2.73.8.1.61.1.1.16
        Fld Form/Rpt:   VOICE ANNOUNCEMENT MEASUREMENTS
        Fld Format:     Single Field
        Fld(s) Name:    Mx Pt
        Fld Descr:      An object containing the peak number of ports used for 
			the announcement during the period.
        "
    ::= { avCmMeasAnnIntegAllYestEntry 16 }


avCmMeasAnnIntegAllYestMaxCallers OBJECT-TYPE
    SYNTAX      Integer32 (0..999)
    MAX-ACCESS  read-only
    STATUS      current
    DESCRIPTION
        "
        Fld OID Name:   avCmMeasAnnIntegAllYestMaxCallers
        Fld OID:        enterprises.6889.2.73.8.1.61.1.1.17
        Fld Form/Rpt:   VOICE ANNOUNCEMENT MEASUREMENTS
        Fld Format:     Single Field
        Fld(s) Name:    Max Cls
        Fld Descr:      An object containing the peak number callers connected 
			to a port at the same time for this announcement during
			the period
        "
    ::= { avCmMeasAnnIntegAllYestEntry 17 }

-- ******************** avCmStatusMGAnn Group *************************

-- MIB GROUP DESCRIPTION

-- MIB Group Name:
--		avCmStatusMGAnn Group
-- OID:
--		enterprises.6889.2.73.8.1.62
-- Description:
--		The avCmStatusMGAnn MIB Group uses the 
--		"status mg-announcements" command 
--		to retrieve status information for all media-gateway
--		announcements.
--		
-- Releases Supported:
--		CM6.3.100 and greater
-- Polling Type:
--		Performance/Utilization
-- Polling Interval:
--		No more than once a day because the data is only updated
--		after the beginning of the day.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. status mg-announcements
-- Form/Report Name:
--		1. MEDIA GATEWAY ANNOUNCEMENT STATUS
-- Reference Document:
--		1. A detailed description of the command and form can be
--		   found in document referenced by REF_DOC_1 in the
--		   DOCUMENT REFERENCE SECTION.
-- Command Permission/User-profile:
--		1. No special permissions needed.

avCmStatusMGAnn	OBJECT IDENTIFIER ::= { avCmObjects 62 }

avCmStatusMGAnnTable	OBJECT-TYPE
    SYNTAX	SEQUENCE OF AvCmStatusMGAnnEntry
    MAX-ACCESS	not-accessible
    STATUS	current
    DESCRIPTION
	"
	Fld OID Name:	avCmStatusMGAnnEntry
	Fld OID:	enterprises.6889.2.73.8.1.62.1
	Fld Form/Rpt:	NA
	Fld Format:	NA
	Fld(s) Name:	NA
	Fld Descr:	A list of the avCmStatusMGAnn entries
	"
    ::= { avCmStatusMGAnn 1 }

avCmStatusMGAnnEntry	OBJECT-TYPE
    SYNTAX	AvCmStatusMGAnnEntry
    MAX-ACCESS	not-accessible
    STATUS	current
    DESCRIPTION
	"
	Fld OID Name:	avCmStatusMGAnnEntry
	Fld OID:	enterprises.6889.2.73.8.1.62.1.1
	Fld Form/Rpt:	NA
	Fld Format:	NA
	Fld(s) Name:	NA
	Fld Descr:	A avCmStatusMGAnn entry containing objects of the
			avCmStatusMGAnn information sent by the switch.
	"
    INDEX    { avCmStatusMGAnnIdx }
    ::= { avCmStatusMGAnnTable 1 }

AvCmStatusMGAnnEntry ::= SEQUENCE {
		avCmStatusMGAnnIdx
		    Integer32,
		avCmStatusMGAnnMGNum
		    Integer32,
		avCmStatusMGAnnMGType
		    SnmpAdminString,
		avCmStatusMGAnnEnabled
		    SnmpAdminString,
		avCmStatusMGAnnStorUsedTotal
		    SnmpAdminString,
		avCmStatusMGAnnStorUsedUsed
		    SnmpAdminString,
		avCmStatusMGAnnStorUsedAvail
		    SnmpAdminString,
		avCmStatusMGAnnCfStatIns
		    SnmpAdminString,
		avCmStatusMGAnnCfStatAct
		    SnmpAdminString,
		avCmStatusMGAnnCfStatErr
		    SnmpAdminString
		}

avCmStatusMGAnnIdx	OBJECT-TYPE
    SYNTAX	Integer32 (0..9999)
    MAX-ACCESS	not-accessible
    STATUS	current
    DESCRIPTION
	"
	Fld OID Name:	avCmStatusMGAnnIdx
	Fld OID:	enterprises.6889.2.73.8.1.62.1.1.1
	Fld Format:	NA
	Fld(s) Name:	NA
	Fld Descr:	An object that uniquely identifies each Increment of 
			data.
	"
    ::= { avCmStatusMGAnnEntry 1 }

avCmStatusMGAnnMGNum	OBJECT-TYPE
    SYNTAX	Integer32 (0..9999)
    MAX-ACCESS	read-only
    STATUS	current
    DESCRIPTION
	"
	Fld OID Name:	avCmStatusMGAnnMGNum
	Fld OID:	enterprises.6889.2.73.8.1.62.1.1.2
	Fld Form/Rpt:	MEDIA GATEWAY ANNOUNCEMENT STATUS
	Fld Format:	Single Field
	Fld(s) Name:	MG Num
	Fld Descr:	An object containing the media-gateway number.
	"
    ::= { avCmStatusMGAnnEntry 2 }

avCmStatusMGAnnMGType	OBJECT-TYPE
    SYNTAX	SnmpAdminString (SIZE (0..9))
    MAX-ACCESS	read-only
    STATUS	current
    DESCRIPTION
	"
	Fld OID Name:	avCmStatusMGAnnMGType
	Fld OID:	enterprises.6889.2.73.8.1.62.1.1.3
	Fld Form/Rpt:	MEDIA GATEWAY ANNOUNCEMENT STATUS
	Fld Format:	Single Field
	Fld(s) Name:	MG Type
	Fld Descr:	An object containing the media-gateway type.
	"
    ::= { avCmStatusMGAnnEntry 3 }

avCmStatusMGAnnEnabled OBJECT-TYPE
    SYNTAX      SnmpAdminString (SIZE (0..2))
    MAX-ACCESS  read-only
    STATUS      current
    DESCRIPTION
        "
        Fld OID Name:   avCmStatusMGAnnEnabled
        Fld OID:        enterprises.6889.2.73.8.1.62.1.1.4
        Fld Form/Rpt:   MEDIA GATEWAY ANNOUNCEMENT STATUS
        Fld Format:     Single Field
        Fld(s) Name:    Announcement Enabled
        Fld Descr:      An object containing whether the announcement is 
			enabled.
        "
    ::= { avCmStatusMGAnnEntry 4 }

avCmStatusMGAnnStorUsedTotal OBJECT-TYPE
    SYNTAX      SnmpAdminString (SIZE (0..5))
    MAX-ACCESS  read-only
    STATUS      current
    DESCRIPTION
        "
        Fld OID Name:   avCmStatusMGAnnStorUsedTotal
        Fld OID:        enterprises.6889.2.73.8.1.62.1.1.5
        Fld Form/Rpt:   MEDIA GATEWAY ANNOUNCEMENT STATUS
        Fld Format:     Single Field
        Fld(s) Name:    CF Storage Usage(MB) Total/Annc /Avail
        Fld Descr:      An object containing the amount of storage available.
			source.
        "
    ::= { avCmStatusMGAnnEntry 5 }

avCmStatusMGAnnStorUsedUsed OBJECT-TYPE
    SYNTAX      SnmpAdminString (SIZE (0..5))
    MAX-ACCESS  read-only
    STATUS      current
    DESCRIPTION
        "
        Fld OID Name:   avCmStatusMGAnnStorUsedUsed
        Fld OID:        enterprises.6889.2.73.8.1.62.1.1.6
        Fld Form/Rpt:   MEDIA GATEWAY ANNOUNCEMENT STATUS
        Fld Format:     Single Field
        Fld(s) Name:    CF Storage Usage(MB) Total/Annc /Avail
        Fld Descr:      An object containing the amount of storage available.
                        source.
        "
    ::= { avCmStatusMGAnnEntry 6 }


avCmStatusMGAnnStorUsedAvail OBJECT-TYPE
    SYNTAX      SnmpAdminString (SIZE (0..5))
    MAX-ACCESS  read-only
    STATUS      current
    DESCRIPTION
        "
        Fld OID Name:   avCmStatusMGAnnStorUsedAvail
        Fld OID:        enterprises.6889.2.73.8.1.62.1.1.7
        Fld Form/Rpt:   MEDIA GATEWAY ANNOUNCEMENT STATUS
        Fld Format:     Single Field
        Fld(s) Name:    CF Storage Usage(MB) Total/Annc /Avail
        Fld Descr:      An object containing the amount of storage available.
                        source.
        "
    ::= { avCmStatusMGAnnEntry 7 }

avCmStatusMGAnnCfStatIns OBJECT-TYPE
    SYNTAX      SnmpAdminString (SIZE (0..4))
    MAX-ACCESS  read-only
    STATUS      current
    DESCRIPTION
        "
        Fld OID Name:   avCmStatusMGAnnCfStatIns
        Fld OID:        enterprises.6889.2.73.8.1.62.1.1.8
        Fld Form/Rpt:   MEDIA GATEWAY ANNOUNCEMENT STATUS
        Fld Format:     Single Field
        Fld(s) Name:    CF Status Ins
        Fld Descr:      An object containing the announcement status.
        "
    ::= { avCmStatusMGAnnEntry 8 }

avCmStatusMGAnnCfStatAct OBJECT-TYPE
    SYNTAX      SnmpAdminString (SIZE (0..4))
    MAX-ACCESS  read-only
    STATUS      current
    DESCRIPTION
        "
        Fld OID Name:   avCmStatusMGAnnCfStatAct
        Fld OID:        enterprises.6889.2.73.8.1.62.1.1.9
        Fld Form/Rpt:   MEDIA GATEWAY ANNOUNCEMENT STATUS
        Fld Format:     Single Field
        Fld(s) Name:    CF Status Act
        Fld Descr:      An object containing the announcement status.
        "
    ::= { avCmStatusMGAnnEntry 9 }

avCmStatusMGAnnCfStatErr OBJECT-TYPE
    SYNTAX      SnmpAdminString (SIZE (0..4))
    MAX-ACCESS  read-only
    STATUS      current
    DESCRIPTION
        "
        Fld OID Name:   avCmStatusMGAnnCfStatErr
        Fld OID:        enterprises.6889.2.73.8.1.62.1.1.10
        Fld Form/Rpt:   MEDIA GATEWAY ANNOUNCEMENT STATUS
        Fld Format:     Single Field
        Fld(s) Name:    CF Status Err
        Fld Descr:      An object containing the announcement status.
        "
    ::= { avCmStatusMGAnnEntry 10 }


-- ******************** avCmListIntegAnn Group *************************

-- MIB GROUP DESCRIPTION

-- MIB Group Name:
--		avCmListIntegAnn Group
-- OID:
--		enterprises.6889.2.73.8.1.63
-- Description:
--		The avCmListIntegAnn MIB Group uses the 
--		"list integrated-annc-boards" command 
--		to retrieve information for all integrated announcements.
--		
-- Releases Supported:
--		CM6.3.100 and greater
-- Polling Type:
--		Inventory and Configuration
-- Polling Interval:
--              No more than once a day or after announcement changes.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. list integrated-annc-boards
-- Form/Report Name:
--		1. INTEGRATED ANNOUNCEMENTS
-- Reference Document:
--		1. Informations about INTEGRATED ANNOUNCEMENTS can be
--		   found in document referenced by REF_DOC_5 in the
--		   DOCUMENT REFERENCE SECTION.
--
-- Command Permission/User-profile:
--		1. No special permissions needed.

avCmListIntegAnn	OBJECT IDENTIFIER ::= { avCmObjects 63 }

avCmListIntegAnnTable	OBJECT-TYPE
    SYNTAX	SEQUENCE OF AvCmListIntegAnnEntry
    MAX-ACCESS	not-accessible
    STATUS	current
    DESCRIPTION
	"
	Fld OID Name:	avCmListIntegAnnEntry
	Fld OID:	enterprises.6889.2.73.8.1.63.1
	Fld Form/Rpt:	NA
	Fld Format:	NA
	Fld(s) Name:	NA
	Fld Descr:	A list of the avCmListIntegAnn entries
	"
    ::= { avCmListIntegAnn 1 }

avCmListIntegAnnEntry	OBJECT-TYPE
    SYNTAX	AvCmListIntegAnnEntry
    MAX-ACCESS	not-accessible
    STATUS	current
    DESCRIPTION
	"
	Fld OID Name:	avCmListIntegAnnEntry
	Fld OID:	enterprises.6889.2.73.8.1.63.1.1
	Fld Form/Rpt:	NA
	Fld Format:	NA
	Fld(s) Name:	NA
	Fld Descr:	A avCmListIntegAnn entry containing objects of the
			avCmListIntegAnn information sent by the switch.
	"
    INDEX    { avCmListIntegAnnIdx, avCmListIntegAnnIntIdx  }
    ::= { avCmListIntegAnnTable 1 }

AvCmListIntegAnnEntry ::= SEQUENCE {
		avCmListIntegAnnIdx
		    SnmpAdminString,
		avCmListIntegAnnIntIdx
		    SnmpAdminString,
		avCmListIntegAnnSource
		    SnmpAdminString,
		avCmListIntegAnnTimeRem
		    SnmpAdminString,
		avCmListIntegAnnKbps
		    SnmpAdminString,
		avCmListIntegAnnIntNum
		    SnmpAdminString,
		avCmListIntegAnnGrpNum
		    SnmpAdminString,
		avCmListIntegAnnExtension
		    SnmpAdminString,
		avCmListIntegAnnName
		    SnmpAdminString,
		avCmListIntegAnnLength
		    Integer32,
		avCmListIntegAnnSize
		    Integer32
		}

avCmListIntegAnnIdx	OBJECT-TYPE
    SYNTAX	SnmpAdminString (SIZE (0..6))
    MAX-ACCESS	not-accessible
    STATUS	current
    DESCRIPTION
	"
	Fld OID Name:	avCmListIntegAnnIdx
	Fld OID:	enterprises.6889.2.73.8.1.63.1.1.1
	Fld Format:	NA
	Fld(s) Name:	NA
	Fld Descr:	An object that uniquely identifies each Increment of 
			data.
	"
    ::= { avCmListIntegAnnEntry 1 }

avCmListIntegAnnIntIdx     OBJECT-TYPE
    SYNTAX      SnmpAdminString (SIZE (0..4))
    MAX-ACCESS  not-accessible
    STATUS      current
    DESCRIPTION
        "
        Fld OID Name:   avCmListIntegAnnIntIdx
        Fld OID:        enterprises.6889.2.73.8.1.63.1.1.2
        Fld Format:     NA
        Fld(s) Name:    NA
        Fld Descr:      An object that uniquely identifies each Increment of
                        data.
        "
    ::= { avCmListIntegAnnEntry 2 }


avCmListIntegAnnSource       OBJECT-TYPE
    SYNTAX      SnmpAdminString (SIZE (0..6))
    MAX-ACCESS  read-only
    STATUS      current
    DESCRIPTION
        "
        Fld OID Name:   avCmListIntegAnnSource
        Fld OID:        enterprises.6889.2.73.8.1.63.1.1.3
        Fld Form/Rpt:   INTEGRATED ANNOUNCEMENTS
        Fld Format:     Single Field
        Fld(s) Name:    Source
        Fld Descr:      An object containing the announcement source location.
        "
    ::= { avCmListIntegAnnEntry 3 }

avCmListIntegAnnTimeRem       OBJECT-TYPE
    SYNTAX	SnmpAdminString (SIZE (0..3))
    MAX-ACCESS  read-only
    STATUS      current
    DESCRIPTION
        "
        Fld OID Name:   avCmListIntegAnnTimeRem
        Fld OID:        enterprises.6889.2.73.8.1.63.1.1.4
        Fld Form/Rpt:   INTEGRATED ANNOUNCEMENTS
        Fld Format:     Single Field
        Fld(s) Name:    Time Remaining at
        Fld Descr:      An object containing the run rate of the announcements.
        "
    ::= { avCmListIntegAnnEntry 4 }

avCmListIntegAnnKbps       OBJECT-TYPE
    SYNTAX	SnmpAdminString (SIZE (0..6))
    MAX-ACCESS  read-only
    STATUS      current
    DESCRIPTION
        "
        Fld OID Name:   avCmListIntegAnnTimeRem
        Fld OID:        enterprises.6889.2.73.8.1.63.1.1.5
        Fld Form/Rpt:   INTEGRATED ANNOUNCEMENTS
        Fld Format:     Single Field
        Fld(s) Name:    kbps
        Fld Descr:      An object containing the kilobytes per second of
			the announcements.
        "
    ::= { avCmListIntegAnnEntry 5 }

avCmListIntegAnnIntNum       OBJECT-TYPE
    SYNTAX      SnmpAdminString (SIZE (0..4))
    MAX-ACCESS  read-only
    STATUS      current
    DESCRIPTION
        "
        Fld OID Name:   avCmListIntegAnnIntNum
        Fld OID:        enterprises.6889.2.73.8.1.63.1.1.6
        Fld Form/Rpt:   INTEGRATED ANNOUNCEMENTS
        Fld Format:     Single Field
        Fld(s) Name:    Internal Number
        Fld Descr:      An object containing the internal number of
                        the announcements.
        "
    ::= { avCmListIntegAnnEntry 6 }

avCmListIntegAnnGrpNum       OBJECT-TYPE
    SYNTAX      SnmpAdminString (SIZE (0..3))
    MAX-ACCESS  read-only
    STATUS      current
    DESCRIPTION
        "
        Fld OID Name:   avCmListIntegAnnGrpNum
        Fld OID:        enterprises.6889.2.73.8.1.63.1.1.7
        Fld Form/Rpt:   INTEGRATED ANNOUNCEMENTS
        Fld Format:     Single Field
        Fld(s) Name:    Group Number
        Fld Descr:      An object containing the audio group number of
                        the announcement.
        "
    ::= { avCmListIntegAnnEntry 7 }


avCmListIntegAnnExtension	OBJECT-TYPE
    SYNTAX	SnmpAdminString (SIZE (0..17))
    MAX-ACCESS	read-only
    STATUS	current
    DESCRIPTION
	"
	Fld OID Name:	avCmListIntegAnnExtension
	Fld OID:	enterprises.6889.2.73.8.1.63.1.1.8
	Fld Form/Rpt:	INTEGRATED ANNOUNCEMENTS
	Fld Format:	Single Field
	Fld(s) Name:	Extension
	Fld Descr:	An object containing the announcement extension.
	"
    ::= { avCmListIntegAnnEntry 8 }

avCmListIntegAnnName	OBJECT-TYPE
    SYNTAX	SnmpAdminString (SIZE (0..29))
    MAX-ACCESS	read-only
    STATUS	current
    DESCRIPTION
	"
	Fld OID Name:	avCmListIntegAnnName
	Fld OID:	enterprises.6889.2.73.8.1.63.1.1.9
	Fld Form/Rpt:	INTEGRATED ANNOUNCEMENTS
	Fld Format:	Single Field
	Fld(s) Name:	Name
	Fld Descr:	An object containing the name of the announcement.
	"
    ::= { avCmListIntegAnnEntry 9 }


avCmListIntegAnnLength	OBJECT-TYPE
    SYNTAX	Integer32 (0..9999)
    MAX-ACCESS	read-only
    STATUS	current
    DESCRIPTION
	"
	Fld OID Name:	avCmListIntegAnnLength
	Fld OID:	enterprises.6889.2.73.8.1.63.1.1.10
	Fld Form/Rpt:	INTEGRATED ANNOUNCEMENTS
	Fld Format:	Single Field
	Fld(s) Name:	Length
	Fld Descr:	An object containing the length in seconds of the
			announcement.
	"
    ::= { avCmListIntegAnnEntry 10 }

avCmListIntegAnnSize	OBJECT-TYPE
    SYNTAX	Integer32 (0..99999)
    MAX-ACCESS	read-only
    STATUS	current
    DESCRIPTION
	"
	Fld OID Name:	avCmListIntegAnnSize
	Fld OID:	enterprises.6889.2.73.8.1.63.1.1.11
	Fld Form/Rpt:	INTEGRATED ANNOUNCEMENTS
	Fld Format:	Single Field
	Fld(s) Name:	Size
	Fld Descr:	An object containing the size in kilobytes of the
			announcement.
	"
    ::= { avCmListIntegAnnEntry 11 }


--   *********** avCmMeasIpVoStatHrJitter Group **************

-- MIB Group Name:
--		avCmMeasIpVoStatHrJitter
-- OID:
--		enterprises.6889.2.73.8.1.64
-- Description:
--		The avCmMeasIpVoStatHrJitter MIB group displays the output of 
--		the list measurements ip voice-stats hourly jitter command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats hourly jitter
-- Form/Report Name:
--		1. IP VOICE STATISTICS NETWORK REGION JITTER REPORT
-- Reference Document:
--		1. A detailed description of the command and form can be
--		   found in REF_DOC_4 in the DOCUMENT REFERENCE SECTION.
-- Command Permission/User-profile:
--		1. No special permissions needed. Default customer super-user
--		   profile can access this command.

avCmMeasIpVoStatHrJitter	OBJECT IDENTIFIER ::= { avCmObjects 64 }

avCmMeasIpVoStatHrJitterTable	OBJECT-TYPE
    SYNTAX	SEQUENCE OF AvCmMeasIpVoStatHrJitterEntry
    MAX-ACCESS	not-accessible
    STATUS	current
    DESCRIPTION
	"
	Fld OID Name:	avCmMeasIpVoStatHrJitterTable
	Fld OID:	enterprises.6889.2.73.8.1.64.1
	Fld Form/Rpt:	NA
	Fld Format:	NA
	Fld(s) Name:	NA
	Fld Descr:	A list of the avCmMeasIpVoStatHrJitter entries.
	"
    ::= { avCmMeasIpVoStatHrJitter 1 }

avCmMeasIpVoStatHrJitterEntry	OBJECT-TYPE
    SYNTAX	AvCmMeasIpVoStatHrJitterEntry
    MAX-ACCESS	not-accessible
    STATUS	current
    DESCRIPTION
	"
	Fld OID Name:	avCmMeasIpVoStatHrJitterEntry
	Fld OID:	enterprises.6889.2.73.8.1.64.1.1
	Fld Form/Rpt:	NA
	Fld Format:	NA
	Fld(s) Name:	NA
	Fld Descr:	A avCmMeasIpVoStatHrJitter entry containing objects of 
			the avCmMeasIpVoStatHrJitter information sent by the 
			switch.
	"
    INDEX    { avCmMeasIpVoStatHrJitterRegIdx, avCmMeasIpVoStatHrJitterHourIdx,
		avCmMeasIpVoStatHrJitterIdx }
    ::= { avCmMeasIpVoStatHrJitterTable 1 }

AvCmMeasIpVoStatHrJitterEntry ::= SEQUENCE {
		avCmMeasIpVoStatHrJitterRegIdx
		    Integer32,
                avCmMeasIpVoStatHrJitterHourIdx
                    Integer32,
                avCmMeasIpVoStatHrJitterIdx
                    Integer32,
                avCmMeasIpVoStatHrJitterRegion
                    Integer32,
                avCmMeasIpVoStatHrJitterMeasHour
                    Integer32,
                avCmMeasIpVoStatHrJitterRunTime
                    SnmpAdminString,
                avCmMeasIpVoStatHrJitterBoardLoc
                    SnmpAdminString,
                avCmMeasIpVoStatHrJitterCallingNum
                    SnmpAdminString,
                avCmMeasIpVoStatHrJitterCalledNum
                    SnmpAdminString,
                avCmMeasIpVoStatHrJitterCodec
                    SnmpAdminString,
                avCmMeasIpVoStatHrJitterPktSize
                    Integer32,
                avCmMeasIpVoStatHrJitterTimeCall
                    SnmpAdminString,
                avCmMeasIpVoStatHrJitterBufSize
                    SnmpAdminString,
                avCmMeasIpVoStatHrJitterBufOrn
                    SnmpAdminString,
                avCmMeasIpVoStatHrJitterBufUrn
                    SnmpAdminString,
                avCmMeasIpVoStatHrJitterAvgJitter
                    SnmpAdminString,
                avCmMeasIpVoStatHrJitterPeakJitter
                    SnmpAdminString,
                avCmMeasIpVoStatHrJitterFarIpAddr
                    SnmpAdminString
		}

avCmMeasIpVoStatHrJitterRegIdx	OBJECT-TYPE
    SYNTAX	Integer32 (1..2000)
    MAX-ACCESS	not-accessible
    STATUS	current
    DESCRIPTION
	"
	Fld OID Name:	avCmMeasIpVoStatHrJitterRegIdx
	Fld OID:	enterprises.6889.2.73.8.1.64.1.1.1
	Fld Form/Rpt:	NA
	Fld Format:	NA
	Fld(s) Name:	NA
	Fld Descr:	An index into the network region.
	"
    ::= { avCmMeasIpVoStatHrJitterEntry 1 }

avCmMeasIpVoStatHrJitterHourIdx        OBJECT-TYPE
    SYNTAX      Integer32 (0..2300)
    MAX-ACCESS	not-accessible
    STATUS      current
    DESCRIPTION
        "
        Fld OID Name:   avCmMeasIpVoStatHrJitterHourIdx
        Fld OID:        enterprises.6889.2.73.8.1.64.1.1.2
        Fld Form/Rpt:   NA
        Fld Format:     NA
        Fld(s) Name:    NA
        Fld Descr:      An index that contains the measurement hour for the
                        jitter voice statistics.
        "
    ::= { avCmMeasIpVoStatHrJitterEntry 2 }

avCmMeasIpVoStatHrJitterIdx        OBJECT-TYPE
    SYNTAX      Integer32 (0..9999)
    MAX-ACCESS  not-accessible
    STATUS      current
    DESCRIPTION
        "
        Fld OID Name:   avCmMeasIpVoStatHrJitterIdx
        Fld OID:        enterprises.6889.2.73.8.1.64.1.1.3
        Fld Form/Rpt:   NA
        Fld Format:     NA
        Fld(s) Name:    NA
        Fld Descr:      An unique index for the jitter voice statistics.
        "
    ::= { avCmMeasIpVoStatHrJitterEntry 3 }



avCmMeasIpVoStatHrJitterRegion        OBJECT-TYPE
    SYNTAX      Integer32 (0..2000)
    MAX-ACCESS  read-only
    STATUS      current
    DESCRIPTION
        "
        Fld OID Name:   avCmMeasIpVoStatHrJitterRegion
        Fld OID:        enterprises.6889.2.73.8.1.64.1.1.4
        Fld Form/Rpt:   IP VOICE STATISTICS NETWORK REGION JITTER REPORT
        Fld Format:     Single Field
        Fld(s) Name:    List Command: Region
        Fld Descr:      An object that contains the Network Region.
        "
    ::= { avCmMeasIpVoStatHrJitterEntry 4 }

avCmMeasIpVoStatHrJitterMeasHour	OBJECT-TYPE
    SYNTAX      Integer32 (0..2300)
    MAX-ACCESS	read-only
    STATUS	current
    DESCRIPTION
	"
	Fld OID Name:	avCmMeasIpVoStatHrJitterMeasHour
	Fld OID:	enterprises.6889.2.73.8.1.64.1.1.5
	Fld Form/Rpt:	IP VOICE STATISTICS NETWORK REGION JITTER REPORT
	Fld Format:	Single
	Fld(s) Name:	Measurement Hour
	Fld Descr:	An object containing the measurement hour.
	"
    ::= { avCmMeasIpVoStatHrJitterEntry 5 }

avCmMeasIpVoStatHrJitterRunTime	OBJECT-TYPE
    SYNTAX	SnmpAdminString (SIZE (0..28))
    MAX-ACCESS	read-only
    STATUS	current
    DESCRIPTION
	"
	Fld OID Name:	avCmMeasIpVoStatHrJitterRunTime
	Fld OID:	enterprises.6889.2.73.8.1.64.1.1.6
	Fld Form/Rpt:	IP VOICE STATISTICS NETWORK REGION JITTER REPORT
	Fld Format:	Single
	Fld(s) Name:	Date
	Fld Descr:	An object containing the Date.
	"
    ::= { avCmMeasIpVoStatHrJitterEntry 6 }

avCmMeasIpVoStatHrJitterBoardLoc	OBJECT-TYPE
    SYNTAX	SnmpAdminString (SIZE (0..6))
    MAX-ACCESS	read-only
    STATUS	current
    DESCRIPTION
	"
	Fld OID Name:	avCmMeasIpVoStatHrJitterBoardLoc
	Fld OID:	enterprises.6889.2.73.8.1.64.1.1.7
	Fld Form/Rpt:	IP VOICE STATISTICS NETWORK REGION JITTER REPORT
	Fld Format:	Single
	Fld(s) Name:	Board Loc
	Fld Descr:	An object containing the Board location.
	"
    ::= { avCmMeasIpVoStatHrJitterEntry 7 }

avCmMeasIpVoStatHrJitterCallingNum	OBJECT-TYPE
    SYNTAX	SnmpAdminString (SIZE (0..17))
    MAX-ACCESS	read-only
    STATUS	current
    DESCRIPTION
	"
	Fld OID Name:	avCmMeasIpVoStatHrJitterCallingNum
	Fld OID:	enterprises.6889.2.73.8.1.64.1.1.8
	Fld Form/Rpt:	IP VOICE STATISTICS NETWORK REGION JITTER REPORT
	Fld Format:	Single
	Fld(s) Name:	Calling Number
	Fld Descr:	An object containing the Calling Number.
	"
    ::= { avCmMeasIpVoStatHrJitterEntry 8 }

avCmMeasIpVoStatHrJitterCalledNum      OBJECT-TYPE
    SYNTAX      SnmpAdminString (SIZE (0..17))
    MAX-ACCESS  read-only
    STATUS      current
    DESCRIPTION
        "
        Fld OID Name:   avCmMeasIpVoStatHrJitterCalledNum
        Fld OID:        enterprises.6889.2.73.8.1.64.1.1.9
        Fld Form/Rpt:   IP VOICE STATISTICS NETWORK REGION JITTER REPORT
        Fld Format:     Single
        Fld(s) Name:    Called Number
        Fld Descr:      An object containing the Called Number.
        "
    ::= { avCmMeasIpVoStatHrJitterEntry 9 }

avCmMeasIpVoStatHrJitterCodec      OBJECT-TYPE
    SYNTAX      SnmpAdminString (SIZE (0..8))
    MAX-ACCESS  read-only
    STATUS      current
    DESCRIPTION
        "
        Fld OID Name:   avCmMeasIpVoStatHrJitterCodec
        Fld OID:        enterprises.6889.2.73.8.1.64.1.1.10
        Fld Form/Rpt:   IP VOICE STATISTICS NETWORK REGION JITTER REPORT
        Fld Format:     Single
        Fld(s) Name:    Codec
        Fld Descr:      An object containing the Codec.
        "
    ::= { avCmMeasIpVoStatHrJitterEntry 10 }



avCmMeasIpVoStatHrJitterPktSize      OBJECT-TYPE
    SYNTAX      Integer32 (0..999)
    MAX-ACCESS  read-only
    STATUS      current
    DESCRIPTION
        "
        Fld OID Name:   avCmMeasIpVoStatHrJitterPktSize
        Fld OID:        enterprises.6889.2.73.8.1.64.1.1.11
        Fld Form/Rpt:   IP VOICE STATISTICS NETWORK REGION JITTER REPORT
        Fld Format:     Single
        Fld(s) Name:    Pkt Size
        Fld Descr:      An object containing the Packet Size.
        "
    ::= { avCmMeasIpVoStatHrJitterEntry 11 }

avCmMeasIpVoStatHrJitterTimeCall      OBJECT-TYPE
    SYNTAX      SnmpAdminString (SIZE (0..5))
    MAX-ACCESS  read-only
    STATUS      current
    DESCRIPTION
        "
        Fld OID Name:   avCmMeasIpVoStatHrJitterTimeCall
        Fld OID:        enterprises.6889.2.73.8.1.64.1.1.12
        Fld Form/Rpt:   IP VOICE STATISTICS NETWORK REGION JITTER REPORT
        Fld Format:     Single
        Fld(s) Name:    Time of Call
        Fld Descr:      An object containing the time of the call.
        "
    ::= { avCmMeasIpVoStatHrJitterEntry 12 }


avCmMeasIpVoStatHrJitterBufSize      OBJECT-TYPE
    SYNTAX      SnmpAdminString (SIZE (0..4))
    MAX-ACCESS  read-only
    STATUS      current
    DESCRIPTION
        "
        Fld OID Name:   avCmMeasIpVoStatHrJitterBufSize
        Fld OID:        enterprises.6889.2.73.8.1.64.1.1.13
        Fld Form/Rpt:   IP VOICE STATISTICS NETWORK REGION JITTER REPORT
        Fld Format:     Single
        Fld(s) Name:    Jitter-Buffer Size
        Fld Descr:      An object containing the Jitter buffer size.
        "
    ::= { avCmMeasIpVoStatHrJitterEntry 13 }


avCmMeasIpVoStatHrJitterBufOrn      OBJECT-TYPE
    SYNTAX      SnmpAdminString (SIZE (0..4))
    MAX-ACCESS  read-only
    STATUS      current
    DESCRIPTION
        "
        Fld OID Name:   avCmMeasIpVoStatHrJitterBufOrn
        Fld OID:        enterprises.6889.2.73.8.1.64.1.1.14
        Fld Form/Rpt:   IP VOICE STATISTICS NETWORK REGION JITTER REPORT
        Fld Format:     Single
        Fld(s) Name:    Jitter-Buffer Orn
        Fld Descr:      An object containing the Jitter buffer Orn.
        "
    ::= { avCmMeasIpVoStatHrJitterEntry 14 }

avCmMeasIpVoStatHrJitterBufUrn      OBJECT-TYPE
    SYNTAX      SnmpAdminString (SIZE (0..4))
    MAX-ACCESS  read-only
    STATUS      current
    DESCRIPTION
        "
        Fld OID Name:   avCmMeasIpVoStatHrJitterBufUrn
        Fld OID:        enterprises.6889.2.73.8.1.64.1.1.15
        Fld Form/Rpt:   IP VOICE STATISTICS NETWORK REGION JITTER REPORT
        Fld Format:     Single
        Fld(s) Name:    Jitter-Buffer Urn
        Fld Descr:      An object containing the Jitter buffer Urn.
        "
    ::= { avCmMeasIpVoStatHrJitterEntry 15 }


avCmMeasIpVoStatHrJitterAvgJitter      OBJECT-TYPE
    SYNTAX      SnmpAdminString (SIZE (0..5))
    MAX-ACCESS  read-only
    STATUS      current
    DESCRIPTION
        "
        Fld OID Name:   avCmMeasIpVoStatHrJitterAvgJitter
        Fld OID:        enterprises.6889.2.73.8.1.64.1.1.16
        Fld Form/Rpt:   IP VOICE STATISTICS NETWORK REGION JITTER REPORT
        Fld Format:     Single
        Fld(s) Name:    Jitter  Avg
        Fld Descr:      An object containing the Jitter average.
        "
    ::= { avCmMeasIpVoStatHrJitterEntry 16 }

avCmMeasIpVoStatHrJitterPeakJitter      OBJECT-TYPE
    SYNTAX      SnmpAdminString (SIZE (0..5))
    MAX-ACCESS  read-only
    STATUS      current
    DESCRIPTION
        "
        Fld OID Name:   avCmMeasIpVoStatHrJitterPeakJitter
        Fld OID:        enterprises.6889.2.73.8.1.64.1.1.17
        Fld Form/Rpt:   IP VOICE STATISTICS NETWORK REGION JITTER REPORT
        Fld Format:     Single
        Fld(s) Name:    Jitter  Peak
        Fld Descr:      An object containing the Jitter Peak.
        "
    ::= { avCmMeasIpVoStatHrJitterEntry 17 }

avCmMeasIpVoStatHrJitterFarIpAddr      OBJECT-TYPE
    SYNTAX      SnmpAdminString (SIZE (0..41))
    MAX-ACCESS  read-only
    STATUS      current
    DESCRIPTION
        "
        Fld OID Name:   avCmMeasIpVoStatHrJitterFarIpAddr
        Fld OID:        enterprises.6889.2.73.8.1.64.1.1.18
        Fld Form/Rpt:   IP VOICE STATISTICS NETWORK REGION JITTER REPORT
        Fld Format:     Single
        Fld(s) Name:    Farend IP-Addr
        Fld Descr:      An object containing the far-end ip-address.
        "
    ::= { avCmMeasIpVoStatHrJitterEntry 18 }

--   *********** avCmMeasIpVoStatHrPkLos Group **************

-- MIB Group Name:
--		avCmMeasIpVoStatHrPkLos
-- OID:
--		enterprises.6889.2.73.8.1.65
-- Description:
--		The avCmMeasIpVoStatHrPkLos MIB group displays the output of 
--		the list measurements ip voice-stats hourly pktloss command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats hourly pktloss
-- Form/Report Name:
--		1. IP VOICE STATISTICS NETWORK REGION PKTLOSS REPORT
-- Reference Document:
--		1. A detailed description of the command and form can be
--		   found in REF_DOC_4 in the DOCUMENT REFERENCE SECTION.
-- Command Permission/User-profile:
--		1. No special permissions needed. Default customer super-user
--		   profile can access this command.

avCmMeasIpVoStatHrPkLos	OBJECT IDENTIFIER ::= { avCmObjects 65 }

avCmMeasIpVoStatHrPkLosTable	OBJECT-TYPE
    SYNTAX	SEQUENCE OF AvCmMeasIpVoStatHrPkLosEntry
    MAX-ACCESS	not-accessible
    STATUS	current
    DESCRIPTION
	"
	Fld OID Name:	avCmMeasIpVoStatHrPkLosTable
	Fld OID:	enterprises.6889.2.73.8.1.65.1
	Fld Form/Rpt:	NA
	Fld Format:	NA
	Fld(s) Name:	NA
	Fld Descr:	A list of the AvCmMeasIpVoStatHrPkLos entries.
	"
    ::= { avCmMeasIpVoStatHrPkLos 1 }

avCmMeasIpVoStatHrPkLosEntry	OBJECT-TYPE
    SYNTAX	AvCmMeasIpVoStatHrPkLosEntry
    MAX-ACCESS	not-accessible
    STATUS	current
    DESCRIPTION
	"
	Fld OID Name:	avCmMeasIpVoStatHrPkLosEntry
	Fld OID:	enterprises.6889.2.73.8.1.65.1.1
	Fld Form/Rpt:	NA
	Fld Format:	NA
	Fld(s) Name:	NA
	Fld Descr:	A avCmMeasIpVoStatHrPkLos entry containing objects of 
			the avCmMeasIpVoStatHrPkLos information sent by the 
			switch.
	"
    INDEX    { avCmMeasIpVoStatHrPkLosRegIdx, avCmMeasIpVoStatHrPkLosHourIdx,
		avCmMeasIpVoStatHrPkLosIdx }
    ::= { avCmMeasIpVoStatHrPkLosTable 1 }

AvCmMeasIpVoStatHrPkLosEntry ::= SEQUENCE {
		avCmMeasIpVoStatHrPkLosRegIdx
		    Integer32,
                avCmMeasIpVoStatHrPkLosHourIdx
                    Integer32,
                avCmMeasIpVoStatHrPkLosIdx
                    Integer32,
                avCmMeasIpVoStatHrPkLosRegion
                    Integer32,
                avCmMeasIpVoStatHrPkLosMeasHour
                    Integer32,
                avCmMeasIpVoStatHrPkLosRunTime
                    SnmpAdminString,
                avCmMeasIpVoStatHrPkLosBoardLoc
                    SnmpAdminString,
                avCmMeasIpVoStatHrPkLosCallingNum
                    SnmpAdminString,
                avCmMeasIpVoStatHrPkLosCalledNum
                    SnmpAdminString,
                avCmMeasIpVoStatHrPkLosCodec
                    SnmpAdminString,
                avCmMeasIpVoStatHrPkLosDstReg
                    Integer32,
                avCmMeasIpVoStatHrPkLosTimeCall
                    SnmpAdminString,
                avCmMeasIpVoStatHrPkLosUDPPort
                    SnmpAdminString,
                avCmMeasIpVoStatHrPkLosPktSize
                    Integer32,
                avCmMeasIpVoStatHrPkLosTotnumLosPkts
                    Integer32,
                avCmMeasIpVoStatHrPkLosPktLossPerc
                    SnmpAdminString,
                avCmMeasIpVoStatHrPkLosSilSup
                    SnmpAdminString,
                avCmMeasIpVoStatHrPkLosFEAddr
                    SnmpAdminString
		}

avCmMeasIpVoStatHrPkLosRegIdx	OBJECT-TYPE
    SYNTAX	Integer32 (1..2000)
    MAX-ACCESS	not-accessible
    STATUS	current
    DESCRIPTION
	"
	Fld OID Name:	avCmMeasIpVoStatHrPkLosRegIdx
	Fld OID:	enterprises.6889.2.73.8.1.65.1.1.1
	Fld Form/Rpt:	NA
	Fld Format:	NA
	Fld(s) Name:	NA
	Fld Descr:	An index into the network region.
	"
    ::= { avCmMeasIpVoStatHrPkLosEntry 1 }

avCmMeasIpVoStatHrPkLosHourIdx        OBJECT-TYPE
    SYNTAX      Integer32 (0..2300)
    MAX-ACCESS	not-accessible
    STATUS      current
    DESCRIPTION
        "
        Fld OID Name:   avCmMeasIpVoStatHrPkLosHourIdx
        Fld OID:        enterprises.6889.2.73.8.1.65.1.1.2
        Fld Form/Rpt:   NA
        Fld Format:     NA
        Fld(s) Name:    NA
        Fld Descr:      An index that contains the measurement hour in military
			time for the packet loss voice statistics.
        "
    ::= { avCmMeasIpVoStatHrPkLosEntry 2 }

avCmMeasIpVoStatHrPkLosIdx        OBJECT-TYPE
    SYNTAX      Integer32 (0..9999)
    MAX-ACCESS	not-accessible
    STATUS      current
    DESCRIPTION
        "
        Fld OID Name:   avCmMeasIpVoStatHrPkLosIdx
        Fld OID:        enterprises.6889.2.73.8.1.65.1.1.3
        Fld Form/Rpt:   NA
        Fld Format:     NA
        Fld(s) Name:    NA
        Fld Descr:      An unique index for the packet loss voice statistics.
        "
    ::= { avCmMeasIpVoStatHrPkLosEntry 3 }

avCmMeasIpVoStatHrPkLosRegion        OBJECT-TYPE
    SYNTAX      Integer32 (0..2000)
    MAX-ACCESS  read-only
    STATUS      current
    DESCRIPTION
        "
        Fld OID Name:   avCmMeasIpVoStatHrPkLosRegion
        Fld OID:        enterprises.6889.2.73.8.1.65.1.1.4
        Fld Form/Rpt:   IP VOICE STATISTICS NETWORK REGION PKTLOSS REPORT
        Fld Format:     Single Field
        Fld(s) Name:    List Command: Region
        Fld Descr:      An object that contains the Network Region.
        "
    ::= { avCmMeasIpVoStatHrPkLosEntry 4 }

avCmMeasIpVoStatHrPkLosMeasHour	OBJECT-TYPE
    SYNTAX      Integer32 (0..2300)
    MAX-ACCESS	read-only
    STATUS	current
    DESCRIPTION
	"
	Fld OID Name:	avCmMeasIpVoStatHrPkLosMeasHour
	Fld OID:	enterprises.6889.2.73.8.1.65.1.1.5
	Fld Form/Rpt:	IP VOICE STATISTICS NETWORK REGION PKTLOSS REPORT
	Fld Format:	Single
	Fld(s) Name:	Measurement Hour
	Fld Descr:	An object containing the measurement hour.
	"
    ::= { avCmMeasIpVoStatHrPkLosEntry 5 }

avCmMeasIpVoStatHrPkLosRunTime	OBJECT-TYPE
    SYNTAX	SnmpAdminString (SIZE (0..28))
    MAX-ACCESS	read-only
    STATUS	current
    DESCRIPTION
	"
	Fld OID Name:	avCmMeasIpVoStatHrPkLosRunTime
	Fld OID:	enterprises.6889.2.73.8.1.65.1.1.6
	Fld Form/Rpt:	IP VOICE STATISTICS NETWORK REGION PKTLOSS REPORT
	Fld Format:	Single
	Fld(s) Name:	Date
	Fld Descr:	An object containing the Date.
	"
    ::= { avCmMeasIpVoStatHrPkLosEntry 6 }

avCmMeasIpVoStatHrPkLosBoardLoc	OBJECT-TYPE
    SYNTAX	SnmpAdminString (SIZE (0..6))
    MAX-ACCESS	read-only
    STATUS	current
    DESCRIPTION
	"
	Fld OID Name:	avCmMeasIpVoStatHrPkLosBoardLoc
	Fld OID:	enterprises.6889.2.73.8.1.65.1.1.7
	Fld Form/Rpt:	IP VOICE STATISTICS NETWORK REGION PKTLOSS REPORT
	Fld Format:	Single
	Fld(s) Name:	Board Loc
	Fld Descr:	An object containing the Board location.
	"
    ::= { avCmMeasIpVoStatHrPkLosEntry 7 }

avCmMeasIpVoStatHrPkLosCallingNum	OBJECT-TYPE
    SYNTAX	SnmpAdminString (SIZE (0..17))
    MAX-ACCESS	read-only
    STATUS	current
    DESCRIPTION
	"
	Fld OID Name:	avCmMeasIpVoStatHrPkLosCallingNum
	Fld OID:	enterprises.6889.2.73.8.1.65.1.1.8
	Fld Form/Rpt:	IP VOICE STATISTICS NETWORK REGION PKTLOSS REPORT
	Fld Format:	Single
	Fld(s) Name:	Calling Number
	Fld Descr:	An object containing the Calling Number.
	"
    ::= { avCmMeasIpVoStatHrPkLosEntry 8 }

avCmMeasIpVoStatHrPkLosCalledNum      OBJECT-TYPE
    SYNTAX      SnmpAdminString (SIZE (0..17))
    MAX-ACCESS  read-only
    STATUS      current
    DESCRIPTION
        "
        Fld OID Name:   avCmMeasIpVoStatHrPkLosCalledNum
        Fld OID:        enterprises.6889.2.73.8.1.65.1.1.9
        Fld Form/Rpt:   IP VOICE STATISTICS NETWORK REGION PKTLOSS REPORT
        Fld Format:     Single
        Fld(s) Name:    Called Number
        Fld Descr:      An object containing the Called Number.
        "
    ::= { avCmMeasIpVoStatHrPkLosEntry 9 }

avCmMeasIpVoStatHrPkLosCodec      OBJECT-TYPE
    SYNTAX      SnmpAdminString (SIZE (0..8))
    MAX-ACCESS  read-only
    STATUS      current
    DESCRIPTION
        "
        Fld OID Name:   avCmMeasIpVoStatHrPkLosCodec
        Fld OID:        enterprises.6889.2.73.8.1.65.1.1.10
        Fld Form/Rpt:   IP VOICE STATISTICS NETWORK REGION PKTLOSS REPORT
        Fld Format:     Single
        Fld(s) Name:    Codec
        Fld Descr:      An object containing the Codec used for the call.
        "
    ::= { avCmMeasIpVoStatHrPkLosEntry 10 }



avCmMeasIpVoStatHrPkLosDstReg      OBJECT-TYPE
    SYNTAX      Integer32 (0..9999)
    MAX-ACCESS  read-only
    STATUS      current
    DESCRIPTION
        "
        Fld OID Name:   avCmMeasIpVoStatHrPkLosDstReg
        Fld OID:        enterprises.6889.2.73.8.1.65.1.1.11
        Fld Form/Rpt:   IP VOICE STATISTICS NETWORK REGION PKTLOSS REPORT
        Fld Format:     Single
        Fld(s) Name:    Dst Reg
        Fld Descr:      The network region where the destination
			media processor is located.
        "
    ::= { avCmMeasIpVoStatHrPkLosEntry 11 }

avCmMeasIpVoStatHrPkLosTimeCall      OBJECT-TYPE
    SYNTAX      SnmpAdminString (SIZE (0..5))
    MAX-ACCESS  read-only
    STATUS      current
    DESCRIPTION
        "
        Fld OID Name:   avCmMeasIpVoStatHrPkLosTimeCall
        Fld OID:        enterprises.6889.2.73.8.1.65.1.1.12
        Fld Form/Rpt:   IP VOICE STATISTICS NETWORK REGION PKTLOSS REPORT
        Fld Format:     Single
        Fld(s) Name:    Time of Call
        Fld Descr:      A time stamp when threshold was first
			exceeded for the associated call, shown in MMSS 
			(minutes seconds).
        "
    ::= { avCmMeasIpVoStatHrPkLosEntry 12 }


avCmMeasIpVoStatHrPkLosUDPPort      OBJECT-TYPE
    SYNTAX      SnmpAdminString (SIZE (0..6))
    MAX-ACCESS  read-only
    STATUS      current
    DESCRIPTION
        "
        Fld OID Name:   avCmMeasIpVoStatHrPkLosUDPPort
        Fld OID:        enterprises.6889.2.73.8.1.65.1.1.13
        Fld Form/Rpt:   IP VOICE STATISTICS NETWORK REGION PKTLOSS REPORT
        Fld Format:     Single
        Fld(s) Name:    UDP Port
        Fld Descr:      The UDP port used by the media processor
			for this call.
        "
    ::= { avCmMeasIpVoStatHrPkLosEntry 13 }


avCmMeasIpVoStatHrPkLosPktSize      OBJECT-TYPE
    SYNTAX      Integer32 (0..999)
    MAX-ACCESS  read-only
    STATUS      current
    DESCRIPTION
        "
        Fld OID Name:   avCmMeasIpVoStatHrPkLosPktSize
        Fld OID:        enterprises.6889.2.73.8.1.65.1.1.14
        Fld Form/Rpt:   IP VOICE STATISTICS NETWORK REGION PKTLOSS REPORT
        Fld Format:     Single
        Fld(s) Name:    Pkt Size
        Fld Descr:      The packet size for each steam of data for
			the associated call, measured in milliseconds.
        "
    ::= { avCmMeasIpVoStatHrPkLosEntry 14 }

avCmMeasIpVoStatHrPkLosTotnumLosPkts      OBJECT-TYPE
    SYNTAX      Integer32 (0..9999)
    MAX-ACCESS  read-only
    STATUS      current
    DESCRIPTION
        "
        Fld OID Name:   avCmMeasIpVoStatHrPkLosTotnumLosPkts
        Fld OID:        enterprises.6889.2.73.8.1.65.1.1.15
        Fld Form/Rpt:   IP VOICE STATISTICS NETWORK REGION PKTLOSS REPORT
        Fld Format:     Single
        Fld(s) Name:    Total #lost Pkts
        Fld Descr:      An object containing the total number of lost packets				for the call.
        "
    ::= { avCmMeasIpVoStatHrPkLosEntry 15 }


avCmMeasIpVoStatHrPkLosPktLossPerc      OBJECT-TYPE
    SYNTAX      SnmpAdminString (SIZE (0..3))
    MAX-ACCESS  read-only
    STATUS      current
    DESCRIPTION
        "
        Fld OID Name:   avCmMeasIpVoStatHrPkLosPktLossPerc
        Fld OID:        enterprises.6889.2.73.8.1.65.1.1.16
        Fld Form/Rpt:   IP VOICE STATISTICS NETWORK REGION PKTLOSS REPORT
        Fld Format:     Single
        Fld(s) Name:    Packet loss %
        Fld Descr:      The peak packet loss for the call. The packet
			loss percentage is calculated at 10-second
			intervals.
        "
    ::= { avCmMeasIpVoStatHrPkLosEntry 16 }

avCmMeasIpVoStatHrPkLosSilSup      OBJECT-TYPE
    SYNTAX      SnmpAdminString (SIZE (0..2))
    MAX-ACCESS  read-only
    STATUS      current
    DESCRIPTION
        "
        Fld OID Name:   avCmMeasIpVoStatHrPkLosSilSup
        Fld OID:        enterprises.6889.2.73.8.1.65.1.1.17
        Fld Form/Rpt:   IP VOICE STATISTICS NETWORK REGION PKTLOSS REPORT
        Fld Format:     Single
        Fld(s) Name:    Sil Sup
        Fld Descr:      Indicates whether the silence suppression
			was used for the call.
        "
    ::= { avCmMeasIpVoStatHrPkLosEntry 17 }

avCmMeasIpVoStatHrPkLosFEAddr      OBJECT-TYPE
    SYNTAX      SnmpAdminString (SIZE (0..41))
    MAX-ACCESS  read-only
    STATUS      current
    DESCRIPTION
        "
        Fld OID Name:   avCmMeasIpVoStatHrPkLosFEAddr
        Fld OID:        enterprises.6889.2.73.8.1.65.1.1.18
        Fld Form/Rpt:   IP VOICE STATISTICS NETWORK REGION PKTLOSS REPORT
        Fld Format:     Single
        Fld(s) Name:    FEAddr
        Fld Descr:      An object containing the far-end ip-address.
        "
    ::= { avCmMeasIpVoStatHrPkLosEntry 18 }

--   *********** avCmMeasIpVoStatHrRtdel Group **************
-- MIB Group Name:
--		avCmMeasIpVoStatHrRtdel
-- OID:
--		enterprises.6889.2.73.8.1.66
-- Description:
--		The avCmMeasIpVoStatHrRtdel MIB group displays the output of 
--		the list measurements ip voice-stats hourly rtdelay command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats hourly rtdelay
-- Form/Report Name:
--		1. IP VOICE STATISTICS NETWORK REGION RTDELAY REPORT
-- Reference Document:
--		1. A detailed description of the command and form can be
--		   found in REF_DOC_4 in the DOCUMENT REFERENCE SECTION.
-- Command Permission/User-profile:
--		1. No special permissions needed. Default customer super-user
--		   profile can access this command.

avCmMeasIpVoStatHrRtdel	OBJECT IDENTIFIER ::= { avCmObjects 66 }

avCmMeasIpVoStatHrRtdelTable	OBJECT-TYPE
    SYNTAX	SEQUENCE OF AvCmMeasIpVoStatHrRtdelEntry
    MAX-ACCESS	not-accessible
    STATUS	current
    DESCRIPTION
	"
	Fld OID Name:	avCmMeasIpVoStatHrRtdelTable
	Fld OID:	enterprises.6889.2.73.8.1.66.1
	Fld Form/Rpt:	NA
	Fld Format:	NA
	Fld(s) Name:	NA
	Fld Descr:	A list of the AvCmMeasIpVoStatHrRtdel entries.
	"
    ::= { avCmMeasIpVoStatHrRtdel 1 }

avCmMeasIpVoStatHrRtdelEntry	OBJECT-TYPE
    SYNTAX	AvCmMeasIpVoStatHrRtdelEntry
    MAX-ACCESS	not-accessible
    STATUS	current
    DESCRIPTION
	"
	Fld OID Name:	avCmMeasIpVoStatHrRtdelEntry
	Fld OID:	enterprises.6889.2.73.8.1.66.1.1
	Fld Form/Rpt:	NA
	Fld Format:	NA
	Fld(s) Name:	NA
	Fld Descr:	A avCmMeasIpVoStatHrRtdel entry containing objects of 
			the avCmMeasIpVoStatHrRtdel information sent by the 
			switch.
	"
    INDEX    { avCmMeasIpVoStatHrRtdelRegIdx, avCmMeasIpVoStatHrRtdelHourIdx,
		avCmMeasIpVoStatHrRtdelIdx }
    ::= { avCmMeasIpVoStatHrRtdelTable 1 }

AvCmMeasIpVoStatHrRtdelEntry ::= SEQUENCE {
		avCmMeasIpVoStatHrRtdelRegIdx
		    Integer32,
                avCmMeasIpVoStatHrRtdelHourIdx
                    Integer32,
                avCmMeasIpVoStatHrRtdelIdx
                    Integer32,
                avCmMeasIpVoStatHrRtdelRegion
                    Integer32,
                avCmMeasIpVoStatHrRtdelMeasHour
                    Integer32,
                avCmMeasIpVoStatHrRtdelRunTime
                    SnmpAdminString,
                avCmMeasIpVoStatHrRtdelBoardLoc
                    SnmpAdminString,
                avCmMeasIpVoStatHrRtdelCallingNum
                    SnmpAdminString,
                avCmMeasIpVoStatHrRtdelCalledNum
                    SnmpAdminString,
                avCmMeasIpVoStatHrRtdelCodec
                    SnmpAdminString,
                avCmMeasIpVoStatHrRtdelPktSize
                    Integer32,
                avCmMeasIpVoStatHrRtdelDstReg
                    Integer32,
                avCmMeasIpVoStatHrRtdelAvg
                    Integer32,
                avCmMeasIpVoStatHrRtdelPeak
                    Integer32,
                avCmMeasIpVoStatHrRtdelTimeCall
                    SnmpAdminString,
                avCmMeasIpVoStatHrRtdelDataCall
                    SnmpAdminString,
                avCmMeasIpVoStatHrRtdelEncryp
                    SnmpAdminString,
                avCmMeasIpVoStatHrRtdelEC
                    SnmpAdminString,
                avCmMeasIpVoStatHrRtdelFEAddr
                    SnmpAdminString
		}

avCmMeasIpVoStatHrRtdelRegIdx	OBJECT-TYPE
    SYNTAX	Integer32 (1..2000)
    MAX-ACCESS	not-accessible
    STATUS	current
    DESCRIPTION
	"
	Fld OID Name:	avCmMeasIpVoStatHrRtdelRegIdx
	Fld OID:	enterprises.6889.2.73.8.1.66.1.1.1
	Fld Form/Rpt:	NA
	Fld Format:	NA
	Fld(s) Name:	NA
	Fld Descr:	An index into the network region.
	"
    ::= { avCmMeasIpVoStatHrRtdelEntry 1 }

avCmMeasIpVoStatHrRtdelHourIdx        OBJECT-TYPE
    SYNTAX      Integer32 (0..2300)
    MAX-ACCESS	not-accessible
    STATUS      current
    DESCRIPTION
        "
        Fld OID Name:   avCmMeasIpVoStatHrRtdelHourIdx
        Fld OID:        enterprises.6889.2.73.8.1.66.1.1.2
        Fld Form/Rpt:   NA
        Fld Format:     NA
        Fld(s) Name:    NA
        Fld Descr:      An index that contains the measurement hour in military
			time for the packet loss voice statistics.
        "
    ::= { avCmMeasIpVoStatHrRtdelEntry 2 }

avCmMeasIpVoStatHrRtdelIdx        OBJECT-TYPE
    SYNTAX      Integer32 (0..9999)
    MAX-ACCESS	not-accessible
    STATUS      current
    DESCRIPTION
        "
        Fld OID Name:   avCmMeasIpVoStatHrRtdelIdx
        Fld OID:        enterprises.6889.2.73.8.1.66.1.1.3
        Fld Form/Rpt:   NA
        Fld Format:     NA
        Fld(s) Name:    NA
        Fld Descr:      A  unique index for the packet loss voice statistics.
        "
    ::= { avCmMeasIpVoStatHrRtdelEntry 3 }

avCmMeasIpVoStatHrRtdelRegion        OBJECT-TYPE
    SYNTAX      Integer32 (0..2000)
    MAX-ACCESS  read-only
    STATUS      current
    DESCRIPTION
        "
        Fld OID Name:   avCmMeasIpVoStatHrRtdelRegion
        Fld OID:        enterprises.6889.2.73.8.1.66.1.1.4
        Fld Form/Rpt:   IP VOICE STATISTICS NETWORK REGION RTDELAY REPORT
        Fld Format:     Single Field
        Fld(s) Name:    List Command: Region
        Fld Descr:      An object that contains the Network Region.
        "
    ::= { avCmMeasIpVoStatHrRtdelEntry 4 }

avCmMeasIpVoStatHrRtdelMeasHour	OBJECT-TYPE
    SYNTAX      Integer32 (0..2300)
    MAX-ACCESS	read-only
    STATUS	current
    DESCRIPTION
	"
	Fld OID Name:	avCmMeasIpVoStatHrRtdelMeasHour
	Fld OID:	enterprises.6889.2.73.8.1.66.1.1.5
	Fld Form/Rpt:	IP VOICE STATISTICS NETWORK REGION RTDELAY REPORT
	Fld Format:	Single
	Fld(s) Name:	Measurement Hour
	Fld Descr:	An object containing the measurement hour.
	"
    ::= { avCmMeasIpVoStatHrRtdelEntry 5 }

avCmMeasIpVoStatHrRtdelRunTime	OBJECT-TYPE
    SYNTAX	SnmpAdminString (SIZE (0..28))
    MAX-ACCESS	read-only
    STATUS	current
    DESCRIPTION
	"
	Fld OID Name:	avCmMeasIpVoStatHrRtdelRunTime
	Fld OID:	enterprises.6889.2.73.8.1.66.1.1.6
	Fld Form/Rpt:	IP VOICE STATISTICS NETWORK REGION RTDELAY REPORT
	Fld Format:	Single
	Fld(s) Name:	Date
	Fld Descr:	An object containing the Date.
	"
    ::= { avCmMeasIpVoStatHrRtdelEntry 6 }

avCmMeasIpVoStatHrRtdelBoardLoc	OBJECT-TYPE
    SYNTAX	SnmpAdminString (SIZE (0..6))
    MAX-ACCESS	read-only
    STATUS	current
    DESCRIPTION
	"
	Fld OID Name:	avCmMeasIpVoStatHrRtdelBoardLoc
	Fld OID:	enterprises.6889.2.73.8.1.66.1.1.7
	Fld Form/Rpt:	IP VOICE STATISTICS NETWORK REGION RTDELAY REPORT
	Fld Format:	Single
	Fld(s) Name:	Board Loc
	Fld Descr:	An object containing the Board location.
	"
    ::= { avCmMeasIpVoStatHrRtdelEntry 7 }

avCmMeasIpVoStatHrRtdelCallingNum	OBJECT-TYPE
    SYNTAX	SnmpAdminString (SIZE (0..17))
    MAX-ACCESS	read-only
    STATUS	current
    DESCRIPTION
	"
	Fld OID Name:	avCmMeasIpVoStatHrRtdelCallingNum
	Fld OID:	enterprises.6889.2.73.8.1.66.1.1.8
	Fld Form/Rpt:	IP VOICE STATISTICS NETWORK REGION RTDELAY REPORT
	Fld Format:	Single
	Fld(s) Name:	Calling Number
	Fld Descr:	An object containing the Calling Number.
	"
    ::= { avCmMeasIpVoStatHrRtdelEntry 8 }

avCmMeasIpVoStatHrRtdelCalledNum      OBJECT-TYPE
    SYNTAX      SnmpAdminString (SIZE (0..17))
    MAX-ACCESS  read-only
    STATUS      current
    DESCRIPTION
        "
        Fld OID Name:   avCmMeasIpVoStatHrRtdelCalledNum
        Fld OID:        enterprises.6889.2.73.8.1.66.1.1.9
        Fld Form/Rpt:   IP VOICE STATISTICS NETWORK REGION RTDELAY REPORT
        Fld Format:     Single
        Fld(s) Name:    Called Number
        Fld Descr:      An object containing the Called Number.
        "
    ::= { avCmMeasIpVoStatHrRtdelEntry 9 }

avCmMeasIpVoStatHrRtdelCodec      OBJECT-TYPE
    SYNTAX      SnmpAdminString (SIZE (0..8))
    MAX-ACCESS  read-only
    STATUS      current
    DESCRIPTION
        "
        Fld OID Name:   avCmMeasIpVoStatHrRtdelCodec
        Fld OID:        enterprises.6889.2.73.8.1.66.1.1.10
        Fld Form/Rpt:   IP VOICE STATISTICS NETWORK REGION RTDELAY REPORT
        Fld Format:     Single
        Fld(s) Name:    Codec
        Fld Descr:      An object containing the Codec used for the call.
        "
    ::= { avCmMeasIpVoStatHrRtdelEntry 10 }


avCmMeasIpVoStatHrRtdelPktSize      OBJECT-TYPE
    SYNTAX      Integer32 (0..999)
    MAX-ACCESS  read-only
    STATUS      current
    DESCRIPTION
        "
        Fld OID Name:   avCmMeasIpVoStatHrRtdelPktSize
        Fld OID:        enterprises.6889.2.73.8.1.66.1.1.11
        Fld Form/Rpt:   IP VOICE STATISTICS NETWORK REGION RTDELAY REPORT
        Fld Format:     Single
        Fld(s) Name:    Pkt Size
        Fld Descr:      The packet size for each steam of data for
			the associated call, measured in milliseconds.
        "
    ::= { avCmMeasIpVoStatHrRtdelEntry 11 }


avCmMeasIpVoStatHrRtdelDstReg      OBJECT-TYPE
    SYNTAX      Integer32 (0..9999)
    MAX-ACCESS  read-only
    STATUS      current
    DESCRIPTION
        "
        Fld OID Name:   avCmMeasIpVoStatHrRtdelDstReg
        Fld OID:        enterprises.6889.2.73.8.1.66.1.1.12
        Fld Form/Rpt:   IP VOICE STATISTICS NETWORK REGION RTDELAY REPORT
        Fld Format:     Single
        Fld(s) Name:    Dst Reg
        Fld Descr:      The network region where the destination
			media processor is located.
        "
    ::= { avCmMeasIpVoStatHrRtdelEntry 12 }

avCmMeasIpVoStatHrRtdelAvg      OBJECT-TYPE
    SYNTAX      Integer32 (0..9999)
    MAX-ACCESS  read-only
    STATUS      current
    DESCRIPTION
        "
        Fld OID Name:   avCmMeasIpVoStatHrRtdelAvg
        Fld OID:        enterprises.6889.2.73.8.1.66.1.1.13
        Fld Form/Rpt:   IP VOICE STATISTICS NETWORK REGION RTDELAY REPORT
        Fld Format:     Single
        Fld(s) Name:    RT-Delay Avg
        Fld Descr:      The average round trip delay of packets,
			measured in milliseconds.
			
        "
    ::= { avCmMeasIpVoStatHrRtdelEntry 13 }

avCmMeasIpVoStatHrRtdelPeak      OBJECT-TYPE
    SYNTAX      Integer32 (0..9999)
    MAX-ACCESS  read-only
    STATUS      current
    DESCRIPTION
        "
        Fld OID Name:   avCmMeasIpVoStatHrRtdelPeak
        Fld OID:        enterprises.6889.2.73.8.1.66.1.1.14
        Fld Form/Rpt:   IP VOICE STATISTICS NETWORK REGION RTDELAY REPORT
        Fld Format:     Single
        Fld(s) Name:    RT-Delay Peak
        Fld Descr:      The peak round trip delay recorded for the call.
        "
    ::= { avCmMeasIpVoStatHrRtdelEntry 14 }

avCmMeasIpVoStatHrRtdelTimeCall      OBJECT-TYPE
    SYNTAX      SnmpAdminString (SIZE (0..5))
    MAX-ACCESS  read-only
    STATUS      current
    DESCRIPTION
        "
        Fld OID Name:   avCmMeasIpVoStatHrRtdelTimeCall
        Fld OID:        enterprises.6889.2.73.8.1.66.1.1.15
        Fld Form/Rpt:   IP VOICE STATISTICS NETWORK REGION RTDELAY REPORT
        Fld Format:     Single
        Fld(s) Name:    Time of Call
        Fld Descr:      A time stamp when threshold was first
			exceeded for the associated call, shown in MMSS 
			(minutes seconds).
        "
    ::= { avCmMeasIpVoStatHrRtdelEntry 15 }


avCmMeasIpVoStatHrRtdelDataCall      OBJECT-TYPE
    SYNTAX      SnmpAdminString (SIZE (0..2))
    MAX-ACCESS  read-only
    STATUS      current
    DESCRIPTION
        "
        Fld OID Name:   avCmMeasIpVoStatHrRtdelDataCall
        Fld OID:        enterprises.6889.2.73.8.1.66.1.1.16
        Fld Form/Rpt:   IP VOICE STATISTICS NETWORK REGION RTDELAY REPORT
        Fld Format:     Single
        Fld(s) Name:    Data Call
        Fld Descr:      Indicates whether the call is a data call.
        "
    ::= { avCmMeasIpVoStatHrRtdelEntry 16 }

avCmMeasIpVoStatHrRtdelEncryp      OBJECT-TYPE
    SYNTAX      SnmpAdminString (SIZE (0..2))
    MAX-ACCESS  read-only
    STATUS      current
    DESCRIPTION
        "
        Fld OID Name:   avCmMeasIpVoStatHrRtdelEncryp
        Fld OID:        enterprises.6889.2.73.8.1.66.1.1.17
        Fld Form/Rpt:   IP VOICE STATISTICS NETWORK REGION RTDELAY REPORT
        Fld Format:     Single
        Fld(s) Name:    Encryp
        Fld Descr:      Indicates whether media encryption was used for the 
			call.
        "
    ::= { avCmMeasIpVoStatHrRtdelEntry 17 }

avCmMeasIpVoStatHrRtdelEC      OBJECT-TYPE
    SYNTAX      SnmpAdminString (SIZE (0..2))
    MAX-ACCESS  read-only
    STATUS      current
    DESCRIPTION
        "
        Fld OID Name:   avCmMeasIpVoStatHrRtdelEncryp
        Fld OID:        enterprises.6889.2.73.8.1.66.1.1.18
        Fld Form/Rpt:   IP VOICE STATISTICS NETWORK REGION RTDELAY REPORT
        Fld Format:     Single
        Fld(s) Name:    EC
        Fld Descr:      Indicates whether the echo cancellation is on/off for 
			the call.
        "
    ::= { avCmMeasIpVoStatHrRtdelEntry 18 }

avCmMeasIpVoStatHrRtdelFEAddr      OBJECT-TYPE
    SYNTAX      SnmpAdminString (SIZE (0..41))
    MAX-ACCESS  read-only
    STATUS      current
    DESCRIPTION
        "
        Fld OID Name:   avCmMeasIpVoStatHrRtdelFEAddr
        Fld OID:        enterprises.6889.2.73.8.1.66.1.1.19
        Fld Form/Rpt:   IP VOICE STATISTICS NETWORK REGION RTDELAY REPORT
        Fld Format:     Single
        Fld(s) Name:    FE-Addr
        Fld Descr:      An object containing the far-end ip-address.
        "
    ::= { avCmMeasIpVoStatHrRtdelEntry 19 }

--   *********** avCmMeasIpVoStatHrData Group **************

-- MIB Group Name:
--		avCmMeasIpVoStatHrData
-- OID:
--		enterprises.6889.2.73.8.1.67
-- Description:
--		The avCmMeasIpVoStatHrData MIB group displays the output of 
--		the list measurements ip voice-stats hourly data command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats hourly data
-- Form/Report Name:
--		1. IP VOICE STATISTICS NETWORK REGION DATA REPORT
-- Reference Document:
--		1. A detailed description of the command and form can be
--		   found in REF_DOC_4 in the DOCUMENT REFERENCE SECTION.
-- Command Permission/User-profile:
--		1. No special permissions needed. Default customer super-user
--		   profile can access this command.

avCmMeasIpVoStatHrData	OBJECT IDENTIFIER ::= { avCmObjects 67 }

avCmMeasIpVoStatHrDataTable	OBJECT-TYPE
    SYNTAX	SEQUENCE OF AvCmMeasIpVoStatHrDataEntry
    MAX-ACCESS	not-accessible
    STATUS	current
    DESCRIPTION
	"
	Fld OID Name:	avCmMeasIpVoStatHrDataTable
	Fld OID:	enterprises.6889.2.73.8.1.67.1
	Fld Form/Rpt:	NA
	Fld Format:	NA
	Fld(s) Name:	NA
	Fld Descr:	A list of the avCmMeasIpVoStatHrData entries.
	"
    ::= { avCmMeasIpVoStatHrData 1 }

avCmMeasIpVoStatHrDataEntry	OBJECT-TYPE
    SYNTAX	AvCmMeasIpVoStatHrDataEntry
    MAX-ACCESS	not-accessible
    STATUS	current
    DESCRIPTION
	"
	Fld OID Name:	avCmMeasIpVoStatHrDataEntry
	Fld OID:	enterprises.6889.2.73.8.1.67.1.1
	Fld Form/Rpt:	NA
	Fld Format:	NA
	Fld(s) Name:	NA
	Fld Descr:	A avCmMeasIpVoStatHrData entry containing objects of 
			the avCmMeasIpVoStatHrData information sent by the 
			switch.
	"
    INDEX    { avCmMeasIpVoStatHrDataRegIdx, avCmMeasIpVoStatHrDataHourIdx,
		avCmMeasIpVoStatHrDataIdx }
    ::= { avCmMeasIpVoStatHrDataTable 1 }

AvCmMeasIpVoStatHrDataEntry ::= SEQUENCE {
		avCmMeasIpVoStatHrDataRegIdx
		    Integer32,
                avCmMeasIpVoStatHrDataHourIdx
                    Integer32,
                avCmMeasIpVoStatHrDataIdx
                    Integer32,
                avCmMeasIpVoStatHrDataRegion
                    Integer32,
                avCmMeasIpVoStatHrDataMeasHour
                    Integer32,
                avCmMeasIpVoStatHrDataRunTime
                    SnmpAdminString,
                avCmMeasIpVoStatHrDataBoardLoc
                    SnmpAdminString,
                avCmMeasIpVoStatHrDataCallingNum
                    SnmpAdminString,
                avCmMeasIpVoStatHrDataCalledNum
                    SnmpAdminString,
                avCmMeasIpVoStatHrDataCodec
                    SnmpAdminString,
                avCmMeasIpVoStatHrDataDataType
                    SnmpAdminString,
                avCmMeasIpVoStatHrDataPktSize
                    Integer32,
                avCmMeasIpVoStatHrDataLossPerc
                    SnmpAdminString,
                avCmMeasIpVoStatHrDataPeakJitter
                    Integer32,
                avCmMeasIpVoStatHrDataPeakDly
                    Integer32,
                avCmMeasIpVoStatHrDataEC
                    SnmpAdminString,
                avCmMeasIpVoStatHrDataFarIpAddr
                    SnmpAdminString
		}

avCmMeasIpVoStatHrDataRegIdx	OBJECT-TYPE
    SYNTAX	Integer32 (1..2000)
    MAX-ACCESS	not-accessible
    STATUS	current
    DESCRIPTION
	"
	Fld OID Name:	avCmMeasIpVoStatHrDataRegIdx
	Fld OID:	enterprises.6889.2.73.8.1.67.1.1.1
	Fld Form/Rpt:	NA
	Fld Format:	NA
	Fld(s) Name:	NA
	Fld Descr:	An index into the network region.
	"
    ::= { avCmMeasIpVoStatHrDataEntry 1 }

avCmMeasIpVoStatHrDataHourIdx        OBJECT-TYPE
    SYNTAX      Integer32 (0..2300)
    MAX-ACCESS	not-accessible
    STATUS      current
    DESCRIPTION
        "
        Fld OID Name:   avCmMeasIpVoStatHrDataHourIdx
        Fld OID:        enterprises.6889.2.73.8.1.67.1.1.2
        Fld Form/Rpt:   NA
        Fld Format:     NA
        Fld(s) Name:    NA
        Fld Descr:      An index that contains the measurement hour for the
                        data voice statistics.
        "
    ::= { avCmMeasIpVoStatHrDataEntry 2 }

avCmMeasIpVoStatHrDataIdx        OBJECT-TYPE
    SYNTAX      Integer32 (0..9999)
    MAX-ACCESS	not-accessible
    STATUS      current
    DESCRIPTION
        "
        Fld OID Name:   avCmMeasIpVoStatHrDataIdx
        Fld OID:        enterprises.6889.2.73.8.1.67.1.1.3
        Fld Form/Rpt:   NA
        Fld Format:     NA
        Fld(s) Name:    NA
        Fld Descr:      A unique index for the data voice statistics.
        "
    ::= { avCmMeasIpVoStatHrDataEntry 3 }

avCmMeasIpVoStatHrDataRegion        OBJECT-TYPE
    SYNTAX      Integer32 (0..2000)
    MAX-ACCESS  read-only
    STATUS      current
    DESCRIPTION
        "
        Fld OID Name:   avCmMeasIpVoStatHrDataRegion
        Fld OID:        enterprises.6889.2.73.8.1.67.1.1.4
        Fld Form/Rpt:   IP VOICE STATISTICS NETWORK REGION DATA REPORT
        Fld Format:     Single Field
        Fld(s) Name:    List Command: Region
        Fld Descr:      An object that contains the Network Region.
        "
    ::= { avCmMeasIpVoStatHrDataEntry 4 }

avCmMeasIpVoStatHrDataMeasHour	OBJECT-TYPE
    SYNTAX      Integer32 (0..2300)
    MAX-ACCESS	read-only
    STATUS	current
    DESCRIPTION
	"
	Fld OID Name:	avCmMeasIpVoStatHrDataMeasHour
	Fld OID:	enterprises.6889.2.73.8.1.67.1.1.5
	Fld Form/Rpt:	IP VOICE STATISTICS NETWORK REGION DATA REPORT
	Fld Format:	Single
	Fld(s) Name:	Measurement Hour
	Fld Descr:	An object containing the measurement hour.
	"
    ::= { avCmMeasIpVoStatHrDataEntry 5 }

avCmMeasIpVoStatHrDataRunTime	OBJECT-TYPE
    SYNTAX	SnmpAdminString (SIZE (0..28))
    MAX-ACCESS	read-only
    STATUS	current
    DESCRIPTION
	"
	Fld OID Name:	avCmMeasIpVoStatHrDataRunTime
	Fld OID:	enterprises.6889.2.73.8.1.67.1.1.6
	Fld Form/Rpt:	IP VOICE STATISTICS NETWORK REGION DATA REPORT
	Fld Format:	Single
	Fld(s) Name:	Date
	Fld Descr:	An object containing the Date.
	"
    ::= { avCmMeasIpVoStatHrDataEntry 6 }

avCmMeasIpVoStatHrDataBoardLoc	OBJECT-TYPE
    SYNTAX	SnmpAdminString (SIZE (0..6))
    MAX-ACCESS	read-only
    STATUS	current
    DESCRIPTION
	"
	Fld OID Name:	avCmMeasIpVoStatHrDataBoardLoc
	Fld OID:	enterprises.6889.2.73.8.1.67.1.1.7
	Fld Form/Rpt:	IP VOICE STATISTICS NETWORK REGION DATA REPORT
	Fld Format:	Single
	Fld(s) Name:	Board Loc
	Fld Descr:	An object containing the Board location.
	"
    ::= { avCmMeasIpVoStatHrDataEntry 7 }

avCmMeasIpVoStatHrDataCallingNum	OBJECT-TYPE
    SYNTAX	SnmpAdminString (SIZE (0..17))
    MAX-ACCESS	read-only
    STATUS	current
    DESCRIPTION
	"
	Fld OID Name:	avCmMeasIpVoStatHrDataCallingNum
	Fld OID:	enterprises.6889.2.73.8.1.67.1.1.8
	Fld Form/Rpt:	IP VOICE STATISTICS NETWORK REGION DATA REPORT
	Fld Format:	Single
	Fld(s) Name:	Calling Number
	Fld Descr:	An object containing the Calling Number.
	"
    ::= { avCmMeasIpVoStatHrDataEntry 8 }

avCmMeasIpVoStatHrDataCalledNum      OBJECT-TYPE
    SYNTAX      SnmpAdminString (SIZE (0..17))
    MAX-ACCESS  read-only
    STATUS      current
    DESCRIPTION
        "
        Fld OID Name:   avCmMeasIpVoStatHrDataCalledNum
        Fld OID:        enterprises.6889.2.73.8.1.67.1.1.9
        Fld Form/Rpt:   IP VOICE STATISTICS NETWORK REGION DATA REPORT
        Fld Format:     Single
        Fld(s) Name:    Called Number
        Fld Descr:      An object containing the Called Number.
        "
    ::= { avCmMeasIpVoStatHrDataEntry 9 }

avCmMeasIpVoStatHrDataCodec      OBJECT-TYPE
    SYNTAX      SnmpAdminString (SIZE (0..8))
    MAX-ACCESS  read-only
    STATUS      current
    DESCRIPTION
        "
        Fld OID Name:   avCmMeasIpVoStatHrDataCodec
        Fld OID:        enterprises.6889.2.73.8.1.67.1.1.10
        Fld Form/Rpt:   IP VOICE STATISTICS NETWORK REGION DATA REPORT
        Fld Format:     Single
        Fld(s) Name:    Codec
        Fld Descr:      An object containing the Codec.
        "
    ::= { avCmMeasIpVoStatHrDataEntry 10 }

avCmMeasIpVoStatHrDataDataType      OBJECT-TYPE
    SYNTAX      SnmpAdminString (SIZE (0..7))
    MAX-ACCESS  read-only
    STATUS      current
    DESCRIPTION
        "
        Fld OID Name:   avCmMeasIpVoStatHrDataDataType
        Fld OID:        enterprises.6889.2.73.8.1.67.1.1.11
        Fld Form/Rpt:   IP VOICE STATISTICS NETWORK REGION DATA REPORT
        Fld Format:     Single
        Fld(s) Name:    Data Type
        Fld Descr:      Indicates the type of data call. Valid options
			include:
			~ ttyrel (TTY Relay)
			~ mod-pt (Modem pass-through)
			~ fax-pt (FAX pass-through)
			~ tty-pt (TTY pass-through)
			~ t38fax (T.38 FAX)
			~ faxrel (FAX relay)
			~ modrel (Modem relay)
        "
    ::= { avCmMeasIpVoStatHrDataEntry 11 }

avCmMeasIpVoStatHrDataPktSize      OBJECT-TYPE
    SYNTAX      Integer32 (0..999)
    MAX-ACCESS  read-only
    STATUS      current
    DESCRIPTION
        "
        Fld OID Name:   avCmMeasIpVoStatHrDataPktSize
        Fld OID:        enterprises.6889.2.73.8.1.67.1.1.12
        Fld Form/Rpt:   IP VOICE STATISTICS NETWORK REGION DATA REPORT
        Fld Format:     Single
        Fld(s) Name:    Pkt Size
        Fld Descr:      The packet size for each steam of data for
			the associated call, measured in
			milliseconds.
        "
    ::= { avCmMeasIpVoStatHrDataEntry 12 }

avCmMeasIpVoStatHrDataLossPerc      OBJECT-TYPE
    SYNTAX      SnmpAdminString (SIZE (0..4))
    MAX-ACCESS  read-only
    STATUS      current
    DESCRIPTION
        "
        Fld OID Name:   avCmMeasIpVoStatHrDataLossPerc
        Fld OID:        enterprises.6889.2.73.8.1.67.1.1.13
        Fld Form/Rpt:   IP VOICE STATISTICS NETWORK REGION DATA REPORT
        Fld Format:     Single
        Fld(s) Name:    Loss %
        Fld Descr:      The packet Loss for the call. The Packet loss
			percentage is calculated at 10-second
			intervals.
        "
    ::= { avCmMeasIpVoStatHrDataEntry 13 }


avCmMeasIpVoStatHrDataPeakJitter      OBJECT-TYPE
    SYNTAX      Integer32 (0..9999)
    MAX-ACCESS  read-only
    STATUS      current
    DESCRIPTION
        "
        Fld OID Name:   avCmMeasIpVoStatHrDataPeakJitter
        Fld OID:        enterprises.6889.2.73.8.1.67.1.1.14
        Fld Form/Rpt:   IP VOICE STATISTICS NETWORK REGION DATA REPORT
        Fld Format:     Single
        Fld(s) Name:    Peak Jit
        Fld Descr:      The peak amount of jitter recorded for the
			call, measured in milliseconds.
        "
    ::= { avCmMeasIpVoStatHrDataEntry 14 }

avCmMeasIpVoStatHrDataPeakDly      OBJECT-TYPE
    SYNTAX      Integer32 (0..9999)
    MAX-ACCESS  read-only
    STATUS      current
    DESCRIPTION
        "
        Fld OID Name:   avCmMeasIpVoStatHrDataPeakDly
        Fld OID:        enterprises.6889.2.73.8.1.67.1.1.15
        Fld Form/Rpt:   IP VOICE STATISTICS NETWORK REGION DATA REPORT
        Fld Format:     Single
        Fld(s) Name:    Dly
        Fld Descr:      The peak round trip delay recorded for the
			call, measured in milliseconds.
        "
    ::= { avCmMeasIpVoStatHrDataEntry 15 }


avCmMeasIpVoStatHrDataEC      OBJECT-TYPE
    SYNTAX      SnmpAdminString (SIZE (0..2))
    MAX-ACCESS  read-only
    STATUS      current
    DESCRIPTION
        "
        Fld OID Name:   avCmMeasIpVoStatHrDataEC
        Fld OID:        enterprises.6889.2.73.8.1.67.1.1.16
        Fld Form/Rpt:   IP VOICE STATISTICS NETWORK REGION DATA REPORT
        Fld Format:     Single
        Fld(s) Name:    EC
        Fld Descr:      Indicates whether the echo cancellation is
			turned on/off for the call.
        "
    ::= { avCmMeasIpVoStatHrDataEntry 16 }

avCmMeasIpVoStatHrDataFarIpAddr      OBJECT-TYPE
    SYNTAX      SnmpAdminString (SIZE (0..41))
    MAX-ACCESS  read-only
    STATUS      current
    DESCRIPTION
        "
        Fld OID Name:   avCmMeasIpVoStatHrDataFarIpAddr
        Fld OID:        enterprises.6889.2.73.8.1.67.1.1.17
        Fld Form/Rpt:   IP VOICE STATISTICS NETWORK REGION DATA REPORT
        Fld Format:     Single
        Fld(s) Name:    Farend IPAddr
        Fld Descr:      An object containing the far-end ip-address.
        "
    ::= { avCmMeasIpVoStatHrDataEntry 17 }

--   *********** avCmMeasIpVoStatSumJitterLstHr Group **************

-- MIB Group Name:
--		avCmMeasIpVoStatSumJitterLstHr
-- OID:
--		enterprises.6889.2.73.8.1.68
-- Description:
--		The avCmMeasIpVoStatSumJitterLstHr MIB group displays the 
--		output of the "list measurements ip voice-stats summary jitter 
--		last-hour" command  for each network-region administered on the 
--		NETWORK REGION MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary jitter last-hour
-- Form/Report Name:
--		1. IP VOICE STATISTICS SUMMARY JITTER REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumJitterLstHr	OBJECT IDENTIFIER ::= { avCmObjects 68 }

avCmMeasIpVoStatSumJitterLstHrTable	OBJECT-TYPE
    SYNTAX	SEQUENCE OF AvCmMeasIpVoStatSumJitterLstHrEntry
    MAX-ACCESS	not-accessible
    STATUS	current
    DESCRIPTION
	"
	Fld OID Name:	avCmMeasIpVoStatSumJitterLstHrTable
	Fld OID:	enterprises.6889.2.73.8.1.68.1
	Fld Form/Rpt:	NA
	Fld Format:	NA
	Fld(s) Name:	NA
	Fld Descr:	A list of the avCmMemTrunk entries.
	"
    ::= { avCmMeasIpVoStatSumJitterLstHr 1 }

avCmMeasIpVoStatSumJitterLstHrEntry	OBJECT-TYPE
    SYNTAX	AvCmMeasIpVoStatSumJitterLstHrEntry
    MAX-ACCESS	not-accessible
    STATUS	current
    DESCRIPTION
	"
	Fld OID Name:	avCmMeasIpVoStatSumJitterLstHrEntry
	Fld OID:	enterprises.6889.2.73.8.1.68.1.1
	Fld Form/Rpt:	NA
	Fld Format:	NA
	Fld(s) Name:	NA
	Fld Descr:	A avCmMeasIpVoStatSumJitterLstHr entry containing 
			objects of the avCmMeasIpVoStatSumJitterLstHr 
			information sent by the switch.
	"
    INDEX {avCmMeasIpVoStatSumJitterLstHrRegIdx, 
				avCmMeasIpVoStatSumJitterLstHrHourIdx,
					avCmMeasIpVoStatSumJitterLstHrIdx }
    ::= { avCmMeasIpVoStatSumJitterLstHrTable 1 }

AvCmMeasIpVoStatSumJitterLstHrEntry ::= SEQUENCE {
		avCmMeasIpVoStatSumJitterLstHrRegIdx
		    Integer32,
                avCmMeasIpVoStatSumJitterLstHrHourIdx
                    Integer32,
                avCmMeasIpVoStatSumJitterLstHrIdx
                    Integer32,
                avCmMeasIpVoStatSumJitterLstHrRegion
                    Integer32,
                avCmMeasIpVoStatSumJitterLstHrMeasHour
                    Integer32,
                avCmMeasIpVoStatSumJitterLstHrRunTime
                    SnmpAdminString,
                avCmMeasIpVoStatSumJitterLstHrBoardLoc
                    SnmpAdminString,
                avCmMeasIpVoStatSumJitterLstHrCallingNum
                    SnmpAdminString,
                avCmMeasIpVoStatSumJitterLstHrCalledNum
                    SnmpAdminString,
                avCmMeasIpVoStatSumJitterLstHrDstReg
                    Integer32,
                avCmMeasIpVoStatSumJitterLstHrCodec
                    SnmpAdminString,
                avCmMeasIpVoStatSumJitterLstHrPktSize
                    Integer32,
                avCmMeasIpVoStatSumJitterLstHrTimeCall
                    SnmpAdminString,
                avCmMeasIpVoStatSumJitterLstHrBufSize
                    SnmpAdminString,
                avCmMeasIpVoStatSumJitterLstHrBufOrn
                    SnmpAdminString,
                avCmMeasIpVoStatSumJitterLstHrBufUrn
                    SnmpAdminString,
                avCmMeasIpVoStatSumJitterLstHrAvgJitter
                    SnmpAdminString,
                avCmMeasIpVoStatSumJitterLstHrPeakJitter
                    SnmpAdminString,
                avCmMeasIpVoStatSumJitterLstHrFarIpAddr
                    SnmpAdminString
		}

avCmMeasIpVoStatSumJitterLstHrRegIdx	OBJECT-TYPE
    SYNTAX	Integer32 (1..2000)
    MAX-ACCESS	not-accessible
    STATUS	current
    DESCRIPTION
	"
	Fld OID Name:	avCmMeasIpVoStatSumJitterLstHrRegIdx
	Fld OID:	enterprises.6889.2.73.8.1.68.1.1.1
	Fld Form/Rpt:	NA
	Fld Format:	NA
	Fld(s) Name:	NA
	Fld Descr:	An index into the network region.
	"
    ::= { avCmMeasIpVoStatSumJitterLstHrEntry 1 }

avCmMeasIpVoStatSumJitterLstHrHourIdx        OBJECT-TYPE
    SYNTAX      Integer32 (0..2300)
    MAX-ACCESS	not-accessible
    STATUS      current
    DESCRIPTION
        "
        Fld OID Name:   avCmMeasIpVoStatSumJitterLstHrHourIdx
        Fld OID:        enterprises.6889.2.73.8.1.68.1.1.2
        Fld Form/Rpt:   NA
        Fld Format:     NA
        Fld(s) Name:    NA
        Fld Descr:      An index that contains the measurement hour for the
                        jitter voice statistics.
        "
    ::= { avCmMeasIpVoStatSumJitterLstHrEntry 2 }

avCmMeasIpVoStatSumJitterLstHrIdx        OBJECT-TYPE
    SYNTAX      Integer32 (0..9999)
    MAX-ACCESS  not-accessible
    STATUS      current
    DESCRIPTION
        "
        Fld OID Name:   avCmMeasIpVoStatSumJitterLstHrIdx
        Fld OID:        enterprises.6889.2.73.8.1.68.1.1.3
        Fld Form/Rpt:   NA
        Fld Format:     NA
        Fld(s) Name:    NA
        Fld Descr:      A  unique index for the jitter voice statistics.
        "
    ::= { avCmMeasIpVoStatSumJitterLstHrEntry 3 }


avCmMeasIpVoStatSumJitterLstHrRegion        OBJECT-TYPE
    SYNTAX      Integer32 (0..2000)
    MAX-ACCESS  read-only
    STATUS      current
    DESCRIPTION
        "
        Fld OID Name:   avCmMeasIpVoStatSumJitterLstHrRegion
        Fld OID:        enterprises.6889.2.73.8.1.68.1.1.4
        Fld Form/Rpt:   IP VOICE STATISTICS SUMMARY JITTER REPORT
        Fld Format:     Single Field
        Fld(s) Name:    List Command: Region
        Fld Descr:      An object that contains the Network Region.
        "
    ::= { avCmMeasIpVoStatSumJitterLstHrEntry 4 }

avCmMeasIpVoStatSumJitterLstHrMeasHour	OBJECT-TYPE
    SYNTAX      Integer32 (0..2300)
    MAX-ACCESS	read-only
    STATUS	current
    DESCRIPTION
	"
	Fld OID Name:	avCmMeasIpVoStatSumJitterLstHrMeasHour
	Fld OID:	enterprises.6889.2.73.8.1.68.1.1.5
	Fld Form/Rpt:	IP VOICE STATISTICS SUMMARY JITTER REPORT
	Fld Format:	Single
	Fld(s) Name:	Measurement Hour
	Fld Descr:	An object containing the measurement hour.
	"
    ::= { avCmMeasIpVoStatSumJitterLstHrEntry 5 }

avCmMeasIpVoStatSumJitterLstHrRunTime	OBJECT-TYPE
    SYNTAX	SnmpAdminString (SIZE (0..28))
    MAX-ACCESS	read-only
    STATUS	current
    DESCRIPTION
	"
	Fld OID Name:	avCmMeasIpVoStatSumJitterLstHrRunTime
	Fld OID:	enterprises.6889.2.73.8.1.68.1.1.6
	Fld Form/Rpt:	IP VOICE STATISTICS SUMMARY JITTER REPORT
	Fld Format:	Single
	Fld(s) Name:	Date
	Fld Descr:	An object containing the Date.
	"
    ::= { avCmMeasIpVoStatSumJitterLstHrEntry 6 }

avCmMeasIpVoStatSumJitterLstHrBoardLoc	OBJECT-TYPE
    SYNTAX	SnmpAdminString (SIZE (0..6))
    MAX-ACCESS	read-only
    STATUS	current
    DESCRIPTION
	"
	Fld OID Name:	avCmMeasIpVoStatSumJitterLstHrBoardLoc
	Fld OID:	enterprises.6889.2.73.8.1.68.1.1.7
	Fld Form/Rpt:	IP VOICE STATISTICS SUMMARY JITTER REPORT
	Fld Format:	Single
	Fld(s) Name:	Board Loc
	Fld Descr:	An object containing the Board location.
	"
    ::= { avCmMeasIpVoStatSumJitterLstHrEntry 7 }

avCmMeasIpVoStatSumJitterLstHrCallingNum	OBJECT-TYPE
    SYNTAX	SnmpAdminString (SIZE (0..17))
    MAX-ACCESS	read-only
    STATUS	current
    DESCRIPTION
	"
	Fld OID Name:	avCmMeasIpVoStatSumJitterLstHrCallingNum
	Fld OID:	enterprises.6889.2.73.8.1.68.1.1.8
	Fld Form/Rpt:	IP VOICE STATISTICS SUMMARY JITTER REPORT
	Fld Format:	Single
	Fld(s) Name:	Calling Number
	Fld Descr:	An object containing the Calling Number.
	"
    ::= { avCmMeasIpVoStatSumJitterLstHrEntry 8 }

avCmMeasIpVoStatSumJitterLstHrCalledNum      OBJECT-TYPE
    SYNTAX      SnmpAdminString (SIZE (0..17))
    MAX-ACCESS  read-only
    STATUS      current
    DESCRIPTION
        "
        Fld OID Name:   avCmMeasIpVoStatSumJitterLstHrCalledNum
        Fld OID:        enterprises.6889.2.73.8.1.68.1.1.9
        Fld Form/Rpt:   IP VOICE STATISTICS SUMMARY JITTER REPORT
        Fld Format:     Single
        Fld(s) Name:    Called Number
        Fld Descr:      An object containing the Called Number.
        "
    ::= { avCmMeasIpVoStatSumJitterLstHrEntry 9 }

avCmMeasIpVoStatSumJitterLstHrDstReg	OBJECT-TYPE
    SYNTAX      Integer32 (0..9999)
    MAX-ACCESS	read-only
    STATUS	current
    DESCRIPTION
	"
	Fld OID Name:	avCmMeasIpVoStatSumJitterLstHrDstReg
	Fld OID:	enterprises.6889.2.73.8.1.68.1.1.10
	Fld Form/Rpt:	IP VOICE STATISTICS SUMMARY JITTER REPORT
	Fld Format:	Single
	Fld(s) Name:	Dst Reg
	Fld Descr:	An object containing the destination region.
	"
    ::= { avCmMeasIpVoStatSumJitterLstHrEntry 10 }

avCmMeasIpVoStatSumJitterLstHrCodec      OBJECT-TYPE
    SYNTAX      SnmpAdminString (SIZE (0..8))
    MAX-ACCESS  read-only
    STATUS      current
    DESCRIPTION
        "
        Fld OID Name:   avCmMeasIpVoStatSumJitterLstHrCodec
        Fld OID:        enterprises.6889.2.73.8.1.68.1.1.11
        Fld Form/Rpt:   IP VOICE STATISTICS SUMMARY JITTER REPORT
        Fld Format:     Single
        Fld(s) Name:    Codec
        Fld Descr:      An object containing the Codec.
        "
    ::= { avCmMeasIpVoStatSumJitterLstHrEntry 11 }

avCmMeasIpVoStatSumJitterLstHrPktSize      OBJECT-TYPE
    SYNTAX      Integer32 (0..999)
    MAX-ACCESS  read-only
    STATUS      current
    DESCRIPTION
        "
        Fld OID Name:   avCmMeasIpVoStatSumJitterLstHrPktSize
        Fld OID:        enterprises.6889.2.73.8.1.68.1.1.12
        Fld Form/Rpt:   IP VOICE STATISTICS SUMMARY JITTER REPORT
        Fld Format:     Single
        Fld(s) Name:    Pkt Size
        Fld Descr:      An object containing the Packet Size.
        "
    ::= { avCmMeasIpVoStatSumJitterLstHrEntry 12 }

avCmMeasIpVoStatSumJitterLstHrTimeCall      OBJECT-TYPE
    SYNTAX      SnmpAdminString (SIZE (0..5))
    MAX-ACCESS  read-only
    STATUS      current
    DESCRIPTION
        "
        Fld OID Name:   avCmMeasIpVoStatSumJitterLstHrTimeCall
        Fld OID:        enterprises.6889.2.73.8.1.68.1.1.13
        Fld Form/Rpt:   IP VOICE STATISTICS SUMMARY JITTER REPORT
        Fld Format:     Single
        Fld(s) Name:    Time of Call
        Fld Descr:      An object containing the time of the call.
        "
    ::= { avCmMeasIpVoStatSumJitterLstHrEntry 13 }


avCmMeasIpVoStatSumJitterLstHrBufSize      OBJECT-TYPE
    SYNTAX      SnmpAdminString (SIZE (0..4))
    MAX-ACCESS  read-only
    STATUS      current
    DESCRIPTION
        "
        Fld OID Name:   avCmMeasIpVoStatSumJitterLstHrBufSize
        Fld OID:        enterprises.6889.2.73.8.1.68.1.1.14
        Fld Form/Rpt:   IP VOICE STATISTICS SUMMARY JITTER REPORT
        Fld Format:     Single
        Fld(s) Name:    Jitter-Buffer Size
        Fld Descr:      An object containing the Jitter buffer size.
        "
    ::= { avCmMeasIpVoStatSumJitterLstHrEntry 14 }


avCmMeasIpVoStatSumJitterLstHrBufOrn      OBJECT-TYPE
    SYNTAX      SnmpAdminString (SIZE (0..4))
    MAX-ACCESS  read-only
    STATUS      current
    DESCRIPTION
        "
        Fld OID Name:   avCmMeasIpVoStatSumJitterLstHrBufOrn
        Fld OID:        enterprises.6889.2.73.8.1.68.1.1.15
        Fld Form/Rpt:   IP VOICE STATISTICS SUMMARY JITTER REPORT
        Fld Format:     Single
        Fld(s) Name:    Jitter-Buffer Orn
        Fld Descr:      An object containing the Jitter buffer Orn.
        "
    ::= { avCmMeasIpVoStatSumJitterLstHrEntry 15 }

avCmMeasIpVoStatSumJitterLstHrBufUrn      OBJECT-TYPE
    SYNTAX      SnmpAdminString (SIZE (0..4))
    MAX-ACCESS  read-only
    STATUS      current
    DESCRIPTION
        "
        Fld OID Name:   avCmMeasIpVoStatSumJitterLstHrBufUrn
        Fld OID:        enterprises.6889.2.73.8.1.68.1.1.16
        Fld Form/Rpt:   IP VOICE STATISTICS SUMMARY JITTER REPORT
        Fld Format:     Single
        Fld(s) Name:    Jitter-Buffer Urn
        Fld Descr:      An object containing the Jitter buffer Urn.
        "
    ::= { avCmMeasIpVoStatSumJitterLstHrEntry 16 }


avCmMeasIpVoStatSumJitterLstHrAvgJitter      OBJECT-TYPE
    SYNTAX      SnmpAdminString (SIZE (0..5))
    MAX-ACCESS  read-only
    STATUS      current
    DESCRIPTION
        "
        Fld OID Name:   avCmMeasIpVoStatSumJitterLstHrAvgJitter
        Fld OID:        enterprises.6889.2.73.8.1.68.1.1.17
        Fld Form/Rpt:   IP VOICE STATISTICS SUMMARY JITTER REPORT
        Fld Format:     Single
        Fld(s) Name:    Jitter  Avg
        Fld Descr:      An object containing the Jitter average.
        "
    ::= { avCmMeasIpVoStatSumJitterLstHrEntry 17 }

avCmMeasIpVoStatSumJitterLstHrPeakJitter      OBJECT-TYPE
    SYNTAX      SnmpAdminString (SIZE (0..5))
    MAX-ACCESS  read-only
    STATUS      current
    DESCRIPTION
        "
        Fld OID Name:   avCmMeasIpVoStatSumJitterLstHrPeakJitter
        Fld OID:        enterprises.6889.2.73.8.1.68.1.1.18
        Fld Form/Rpt:   IP VOICE STATISTICS SUMMARY JITTER REPORT
        Fld Format:     Single
        Fld(s) Name:    Jitter  Peak
        Fld Descr:      An object containing the Jitter Peak.
        "
    ::= { avCmMeasIpVoStatSumJitterLstHrEntry 18 }

avCmMeasIpVoStatSumJitterLstHrFarIpAddr      OBJECT-TYPE
    SYNTAX      SnmpAdminString (SIZE (0..41))
    MAX-ACCESS  read-only
    STATUS      current
    DESCRIPTION
        "
        Fld OID Name:   avCmMeasIpVoStatSumJitterLstHrFarIpAddr
        Fld OID:        enterprises.6889.2.73.8.1.68.1.1.19
        Fld Form/Rpt:   IP VOICE STATISTICS SUMMARY JITTER REPORT
        Fld Format:     Single
        Fld(s) Name:    FEAddr
        Fld Descr:      An object containing the far-end ip-address.
        "
    ::= { avCmMeasIpVoStatSumJitterLstHrEntry 19 }


--   *********** avCmMeasIpVoStatSumJitterToday Group **************

-- MIB Group Name:
--		avCmMeasIpVoStatSumJitterToday
-- OID:
--		enterprises.6889.2.73.8.1.69
-- Description:
--		The avCmMeasIpVoStatSumJitterToday MIB group displays the 
--		output of the "list measurements ip voice-stats summary jitter 
--		today" command  for each network-region administered on the 
--		NETWORK REGION MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary jitter today
-- Form/Report Name:
--		1. IP VOICE STATISTICS SUMMARY JITTER REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumJitterToday	OBJECT IDENTIFIER ::= { avCmObjects 69 }

avCmMeasIpVoStatSumJitterTodayTable	OBJECT-TYPE
    SYNTAX	SEQUENCE OF AvCmMeasIpVoStatSumJitterTodayEntry
    MAX-ACCESS	not-accessible
    STATUS	current
    DESCRIPTION
	"
	Fld OID Name:	avCmMeasIpVoStatSumJitterTodayTable
	Fld OID:	enterprises.6889.2.73.8.1.69.1
	Fld Form/Rpt:	NA
	Fld Format:	NA
	Fld(s) Name:	NA
	Fld Descr:	A list of the avCmMemTrunk entries.
	"
    ::= { avCmMeasIpVoStatSumJitterToday 1 }

avCmMeasIpVoStatSumJitterTodayEntry	OBJECT-TYPE
    SYNTAX	AvCmMeasIpVoStatSumJitterTodayEntry
    MAX-ACCESS	not-accessible
    STATUS	current
    DESCRIPTION
	"
	Fld OID Name:	avCmMeasIpVoStatSumJitterTodayEntry
	Fld OID:	enterprises.6889.2.73.8.1.69.1.1
	Fld Form/Rpt:	NA
	Fld Format:	NA
	Fld(s) Name:	NA
	Fld Descr:	A avCmMeasIpVoStatSumJitterToday entry containing 
			objects of the avCmMeasIpVoStatSumJitterToday 
			information sent by the switch.
	"
    INDEX {avCmMeasIpVoStatSumJitterTodayRegIdx, 
			avCmMeasIpVoStatSumJitterTodayHourIdx,
				avCmMeasIpVoStatSumJitterTodayIdx }
    ::= { avCmMeasIpVoStatSumJitterTodayTable 1 }

AvCmMeasIpVoStatSumJitterTodayEntry ::= SEQUENCE {
		avCmMeasIpVoStatSumJitterTodayRegIdx
		    Integer32,
                avCmMeasIpVoStatSumJitterTodayHourIdx
                    Integer32,
                avCmMeasIpVoStatSumJitterTodayIdx
                    Integer32,
                avCmMeasIpVoStatSumJitterTodayRegion
                    Integer32,
                avCmMeasIpVoStatSumJitterTodayMeasHour
                    Integer32,
                avCmMeasIpVoStatSumJitterTodayRunTime
                    SnmpAdminString,
                avCmMeasIpVoStatSumJitterTodayBoardLoc
                    SnmpAdminString,
                avCmMeasIpVoStatSumJitterTodayCallingNum
                    SnmpAdminString,
                avCmMeasIpVoStatSumJitterTodayCalledNum
                    SnmpAdminString,
                avCmMeasIpVoStatSumJitterTodayDstReg
                    Integer32,
                avCmMeasIpVoStatSumJitterTodayCodec
                    SnmpAdminString,
                avCmMeasIpVoStatSumJitterTodayPktSize
                    Integer32,
                avCmMeasIpVoStatSumJitterTodayTimeCall
                    SnmpAdminString,
                avCmMeasIpVoStatSumJitterTodayBufSize
                    SnmpAdminString,
                avCmMeasIpVoStatSumJitterTodayBufOrn
                    SnmpAdminString,
                avCmMeasIpVoStatSumJitterTodayBufUrn
                    SnmpAdminString,
                avCmMeasIpVoStatSumJitterTodayAvgJitter
                    SnmpAdminString,
                avCmMeasIpVoStatSumJitterTodayPeakJitter
                    SnmpAdminString,
                avCmMeasIpVoStatSumJitterTodayFarIpAddr
                    SnmpAdminString
		}

avCmMeasIpVoStatSumJitterTodayRegIdx	OBJECT-TYPE
    SYNTAX	Integer32 (1..2000)
    MAX-ACCESS	not-accessible
    STATUS	current
    DESCRIPTION
	"
	Fld OID Name:	avCmMeasIpVoStatSumJitterTodayRegIdx
	Fld OID:	enterprises.6889.2.73.8.1.69.1.1.1
	Fld Form/Rpt:	NA
	Fld Format:	NA
	Fld(s) Name:	NA
	Fld Descr:	An index into the network region.
	"
    ::= { avCmMeasIpVoStatSumJitterTodayEntry 1 }

avCmMeasIpVoStatSumJitterTodayHourIdx        OBJECT-TYPE
    SYNTAX      Integer32 (0..2300)
    MAX-ACCESS	not-accessible
    STATUS      current
    DESCRIPTION
        "
        Fld OID Name:   avCmMeasIpVoStatSumJitterTodayHourIdx
        Fld OID:        enterprises.6889.2.73.8.1.69.1.1.2
        Fld Form/Rpt:   NA
        Fld Format:     NA
        Fld(s) Name:    NA
        Fld Descr:      An index that contains the measurement hour for the
                        jitter voice statistics.
        "
    ::= { avCmMeasIpVoStatSumJitterTodayEntry 2 }


avCmMeasIpVoStatSumJitterTodayIdx        OBJECT-TYPE
    SYNTAX      Integer32 (0..9999)
    MAX-ACCESS  not-accessible
    STATUS      current
    DESCRIPTION
        "
        Fld OID Name:   avCmMeasIpVoStatSumJitterTodayHourIdx
        Fld OID:        enterprises.6889.2.73.8.1.69.1.1.3
        Fld Form/Rpt:   NA
        Fld Format:     NA
        Fld(s) Name:    NA
        Fld Descr:      An index that contains the measurement hour for the
                        jitter voice statistics.
        "
    ::= { avCmMeasIpVoStatSumJitterTodayEntry 3 }


avCmMeasIpVoStatSumJitterTodayRegion        OBJECT-TYPE
    SYNTAX      Integer32 (0..2000)
    MAX-ACCESS  read-only
    STATUS      current
    DESCRIPTION
        "
        Fld OID Name:   avCmMeasIpVoStatSumJitterTodayRegion
        Fld OID:        enterprises.6889.2.73.8.1.69.1.1.4
        Fld Form/Rpt:   IP VOICE STATISTICS SUMMARY JITTER REPORT
        Fld Format:     Single Field
        Fld(s) Name:    List Command: Region
        Fld Descr:      An object that contains the Network Region.
        "
    ::= { avCmMeasIpVoStatSumJitterTodayEntry 4 }

avCmMeasIpVoStatSumJitterTodayMeasHour	OBJECT-TYPE
    SYNTAX      Integer32 (0..2300)
    MAX-ACCESS	read-only
    STATUS	current
    DESCRIPTION
	"
	Fld OID Name:	avCmMeasIpVoStatSumJitterTodayMeasHour
	Fld OID:	enterprises.6889.2.73.8.1.69.1.1.5
	Fld Form/Rpt:	IP VOICE STATISTICS SUMMARY JITTER REPORT
	Fld Format:	Single
	Fld(s) Name:	Measurement Hour
	Fld Descr:	An object containing the measurement hour.
	"
    ::= { avCmMeasIpVoStatSumJitterTodayEntry 5 }

avCmMeasIpVoStatSumJitterTodayRunTime	OBJECT-TYPE
    SYNTAX	SnmpAdminString (SIZE (0..28))
    MAX-ACCESS	read-only
    STATUS	current
    DESCRIPTION
	"
	Fld OID Name:	avCmMeasIpVoStatSumJitterTodayRunTime
	Fld OID:	enterprises.6889.2.73.8.1.69.1.1.6
	Fld Form/Rpt:	IP VOICE STATISTICS SUMMARY JITTER REPORT
	Fld Format:	Single
	Fld(s) Name:	Date
	Fld Descr:	An object containing the Date.
	"
    ::= { avCmMeasIpVoStatSumJitterTodayEntry 6 }

avCmMeasIpVoStatSumJitterTodayBoardLoc	OBJECT-TYPE
    SYNTAX	SnmpAdminString (SIZE (0..6))
    MAX-ACCESS	read-only
    STATUS	current
    DESCRIPTION
	"
	Fld OID Name:	avCmMeasIpVoStatSumJitterTodayBoardLoc
	Fld OID:	enterprises.6889.2.73.8.1.69.1.1.7
	Fld Form/Rpt:	IP VOICE STATISTICS SUMMARY JITTER REPORT
	Fld Format:	Single
	Fld(s) Name:	Board Loc
	Fld Descr:	An object containing the Board location.
	"
    ::= { avCmMeasIpVoStatSumJitterTodayEntry 7 }

avCmMeasIpVoStatSumJitterTodayCallingNum	OBJECT-TYPE
    SYNTAX	SnmpAdminString (SIZE (0..17))
    MAX-ACCESS	read-only
    STATUS	current
    DESCRIPTION
	"
	Fld OID Name:	avCmMeasIpVoStatSumJitterTodayCallingNum
	Fld OID:	enterprises.6889.2.73.8.1.69.1.1.8
	Fld Form/Rpt:	IP VOICE STATISTICS SUMMARY JITTER REPORT
	Fld Format:	Single
	Fld(s) Name:	Calling Number
	Fld Descr:	An object containing the Calling Number.
	"
    ::= { avCmMeasIpVoStatSumJitterTodayEntry 8 }

avCmMeasIpVoStatSumJitterTodayCalledNum      OBJECT-TYPE
    SYNTAX      SnmpAdminString (SIZE (0..17))
    MAX-ACCESS  read-only
    STATUS      current
    DESCRIPTION
        "
        Fld OID Name:   avCmMeasIpVoStatSumJitterTodayCalledNum
        Fld OID:        enterprises.6889.2.73.8.1.69.1.1.9
        Fld Form/Rpt:   IP VOICE STATISTICS SUMMARY JITTER REPORT
        Fld Format:     Single
        Fld(s) Name:    Called Number
        Fld Descr:      An object containing the Called Number.
        "
    ::= { avCmMeasIpVoStatSumJitterTodayEntry 9 }

avCmMeasIpVoStatSumJitterTodayDstReg	OBJECT-TYPE
    SYNTAX      Integer32 (0..9999)
    MAX-ACCESS	read-only
    STATUS	current
    DESCRIPTION
	"
	Fld OID Name:	avCmMeasIpVoStatSumJitterTodayDstReg
	Fld OID:	enterprises.6889.2.73.8.1.69.1.1.10
	Fld Form/Rpt:	IP VOICE STATISTICS SUMMARY JITTER REPORT
	Fld Format:	Single
	Fld(s) Name:	Dst Reg
	Fld Descr:	An object containing the destination region.
	"
    ::= { avCmMeasIpVoStatSumJitterTodayEntry 10 }

avCmMeasIpVoStatSumJitterTodayCodec      OBJECT-TYPE
    SYNTAX      SnmpAdminString (SIZE (0..8))
    MAX-ACCESS  read-only
    STATUS      current
    DESCRIPTION
        "
        Fld OID Name:   avCmMeasIpVoStatSumJitterTodayCodec
        Fld OID:        enterprises.6889.2.73.8.1.69.1.1.11
        Fld Form/Rpt:   IP VOICE STATISTICS SUMMARY JITTER REPORT
        Fld Format:     Single
        Fld(s) Name:    Codec
        Fld Descr:      An object containing the Codec.
        "
    ::= { avCmMeasIpVoStatSumJitterTodayEntry 11 }

avCmMeasIpVoStatSumJitterTodayPktSize      OBJECT-TYPE
    SYNTAX      Integer32 (0..999)
    MAX-ACCESS  read-only
    STATUS      current
    DESCRIPTION
        "
        Fld OID Name:   avCmMeasIpVoStatSumJitterTodayPktSize
        Fld OID:        enterprises.6889.2.73.8.1.69.1.1.12
        Fld Form/Rpt:   IP VOICE STATISTICS SUMMARY JITTER REPORT
        Fld Format:     Single
        Fld(s) Name:    Pkt Size
        Fld Descr:      An object containing the Packet Size.
        "
    ::= { avCmMeasIpVoStatSumJitterTodayEntry 12 }

avCmMeasIpVoStatSumJitterTodayTimeCall      OBJECT-TYPE
    SYNTAX      SnmpAdminString (SIZE (0..5))
    MAX-ACCESS  read-only
    STATUS      current
    DESCRIPTION
        "
        Fld OID Name:   avCmMeasIpVoStatSumJitterTodayTimeCall
        Fld OID:        enterprises.6889.2.73.8.1.69.1.1.13
        Fld Form/Rpt:   IP VOICE STATISTICS SUMMARY JITTER REPORT
        Fld Format:     Single
        Fld(s) Name:    Time of Call
        Fld Descr:      An object containing the time of the call.
        "
    ::= { avCmMeasIpVoStatSumJitterTodayEntry 13 }


avCmMeasIpVoStatSumJitterTodayBufSize      OBJECT-TYPE
    SYNTAX      SnmpAdminString (SIZE (0..4))
    MAX-ACCESS  read-only
    STATUS      current
    DESCRIPTION
        "
        Fld OID Name:   avCmMeasIpVoStatSumJitterTodayBufSize
        Fld OID:        enterprises.6889.2.73.8.1.69.1.1.14
        Fld Form/Rpt:   IP VOICE STATISTICS SUMMARY JITTER REPORT
        Fld Format:     Single
        Fld(s) Name:    Jitter-Buffer Size
        Fld Descr:      An object containing the Jitter buffer size.
        "
    ::= { avCmMeasIpVoStatSumJitterTodayEntry 14 }


avCmMeasIpVoStatSumJitterTodayBufOrn      OBJECT-TYPE
    SYNTAX      SnmpAdminString (SIZE (0..4))
    MAX-ACCESS  read-only
    STATUS      current
    DESCRIPTION
        "
        Fld OID Name:   avCmMeasIpVoStatSumJitterTodayBufOrn
        Fld OID:        enterprises.6889.2.73.8.1.69.1.1.15
        Fld Form/Rpt:   IP VOICE STATISTICS SUMMARY JITTER REPORT
        Fld Format:     Single
        Fld(s) Name:    Jitter-Buffer Orn
        Fld Descr:      An object containing the Jitter buffer Orn.
        "
    ::= { avCmMeasIpVoStatSumJitterTodayEntry 15 }

avCmMeasIpVoStatSumJitterTodayBufUrn      OBJECT-TYPE
    SYNTAX      SnmpAdminString (SIZE (0..4))
    MAX-ACCESS  read-only
    STATUS      current
    DESCRIPTION
        "
        Fld OID Name:   avCmMeasIpVoStatSumJitterTodayBufUrn
        Fld OID:        enterprises.6889.2.73.8.1.69.1.1.16
        Fld Form/Rpt:   IP VOICE STATISTICS SUMMARY JITTER REPORT
        Fld Format:     Single
        Fld(s) Name:    Jitter-Buffer Urn
        Fld Descr:      An object containing the Jitter buffer Urn.
        "
    ::= { avCmMeasIpVoStatSumJitterTodayEntry 16 }


avCmMeasIpVoStatSumJitterTodayAvgJitter      OBJECT-TYPE
    SYNTAX      SnmpAdminString (SIZE (0..5))
    MAX-ACCESS  read-only
    STATUS      current
    DESCRIPTION
        "
        Fld OID Name:   avCmMeasIpVoStatSumJitterTodayAvgJitter
        Fld OID:        enterprises.6889.2.73.8.1.69.1.1.17
        Fld Form/Rpt:   IP VOICE STATISTICS SUMMARY JITTER REPORT
        Fld Format:     Single
        Fld(s) Name:    Jitter  Avg
        Fld Descr:      An object containing the Jitter average.
        "
    ::= { avCmMeasIpVoStatSumJitterTodayEntry 17 }

avCmMeasIpVoStatSumJitterTodayPeakJitter      OBJECT-TYPE
    SYNTAX      SnmpAdminString (SIZE (0..5))
    MAX-ACCESS  read-only
    STATUS      current
    DESCRIPTION
        "
        Fld OID Name:   avCmMeasIpVoStatSumJitterTodayPeakJitter
        Fld OID:        enterprises.6889.2.73.8.1.69.1.1.18
        Fld Form/Rpt:   IP VOICE STATISTICS SUMMARY JITTER REPORT
        Fld Format:     Single
        Fld(s) Name:    Jitter  Peak
        Fld Descr:      An object containing the Jitter Peak.
        "
    ::= { avCmMeasIpVoStatSumJitterTodayEntry 18 }

avCmMeasIpVoStatSumJitterTodayFarIpAddr      OBJECT-TYPE
    SYNTAX      SnmpAdminString (SIZE (0..41))
    MAX-ACCESS  read-only
    STATUS      current
    DESCRIPTION
        "
        Fld OID Name:   avCmMeasIpVoStatSumJitterTodayFarIpAddr
        Fld OID:        enterprises.6889.2.73.8.1.69.1.1.19
        Fld Form/Rpt:   IP VOICE STATISTICS SUMMARY JITTER REPORT
        Fld Format:     Single
        Fld(s) Name:    FEAddr
        Fld Descr:      An object containing the far-end ip-address.
        "
    ::= { avCmMeasIpVoStatSumJitterTodayEntry 19 }


--   *********** avCmMeasIpVoStatSumJitterYest Group **************

-- MIB Group Name:
--		avCmMeasIpVoStatSumJitterYest
-- OID:
--		enterprises.6889.2.73.8.1.70
-- Description:
--		The avCmMeasIpVoStatSumJitterYest MIB group displays the 
--		output of the "list measurements ip voice-stats summary jitter 
--		yesterday" command  for each network-region administered on the 
--		NETWORK REGION MEASUREMENT SELECTION form.
--
-- Releases Supported:
--		CM6.3.100 and greater
-- Polling Type:
--		Performance/Utilization
-- Polling Interval:
--              No more than once a day because the data is only updated
--              after the beginning of the day which is midnight.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary jitter yesterday
-- Form/Report Name:
--		1. IP VOICE STATISTICS SUMMARY JITTER REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumJitterYest	OBJECT IDENTIFIER ::= { avCmObjects 70 }

avCmMeasIpVoStatSumJitterYestTable	OBJECT-TYPE
    SYNTAX	SEQUENCE OF AvCmMeasIpVoStatSumJitterYestEntry
    MAX-ACCESS	not-accessible
    STATUS	current
    DESCRIPTION
	"
	Fld OID Name:	avCmMeasIpVoStatSumJitterYestTable
	Fld OID:	enterprises.6889.2.73.8.1.70.1
	Fld Form/Rpt:	NA
	Fld Format:	NA
	Fld(s) Name:	NA
	Fld Descr:	A list of the avCmMemTrunk entries.
	"
    ::= { avCmMeasIpVoStatSumJitterYest 1 }

avCmMeasIpVoStatSumJitterYestEntry	OBJECT-TYPE
    SYNTAX	AvCmMeasIpVoStatSumJitterYestEntry
    MAX-ACCESS	not-accessible
    STATUS	current
    DESCRIPTION
	"
	Fld OID Name:	avCmMeasIpVoStatSumJitterYestEntry
	Fld OID:	enterprises.6889.2.73.8.1.70.1.1
	Fld Form/Rpt:	NA
	Fld Format:	NA
	Fld(s) Name:	NA
	Fld Descr:	A avCmMeasIpVoStatSumJitterYest entry containing 
			objects of the avCmMeasIpVoStatSumJitterYest 
			information sent by the switch.
	"
    INDEX {avCmMeasIpVoStatSumJitterYestRegIdx, 
		avCmMeasIpVoStatSumJitterYestHourIdx,
			avCmMeasIpVoStatSumJitterYestIdx }
    ::= { avCmMeasIpVoStatSumJitterYestTable 1 }

AvCmMeasIpVoStatSumJitterYestEntry ::= SEQUENCE {
		avCmMeasIpVoStatSumJitterYestRegIdx
		    Integer32,
                avCmMeasIpVoStatSumJitterYestHourIdx
                    Integer32,
                avCmMeasIpVoStatSumJitterYestIdx
                    Integer32,
                avCmMeasIpVoStatSumJitterYestRegion
                    Integer32,
                avCmMeasIpVoStatSumJitterYestMeasHour
                    Integer32,
                avCmMeasIpVoStatSumJitterYestRunTime
                    SnmpAdminString,
                avCmMeasIpVoStatSumJitterYestBoardLoc
                    SnmpAdminString,
                avCmMeasIpVoStatSumJitterYestCallingNum
                    SnmpAdminString,
                avCmMeasIpVoStatSumJitterYestCalledNum
                    SnmpAdminString,
                avCmMeasIpVoStatSumJitterYestDstReg
                    Integer32,
                avCmMeasIpVoStatSumJitterYestCodec
                    SnmpAdminString,
                avCmMeasIpVoStatSumJitterYestPktSize
                    Integer32,
                avCmMeasIpVoStatSumJitterYestTimeCall
                    SnmpAdminString,
                avCmMeasIpVoStatSumJitterYestBufSize
                    SnmpAdminString,
                avCmMeasIpVoStatSumJitterYestBufOrn
                    SnmpAdminString,
                avCmMeasIpVoStatSumJitterYestBufUrn
                    SnmpAdminString,
                avCmMeasIpVoStatSumJitterYestAvgJitter
                    SnmpAdminString,
                avCmMeasIpVoStatSumJitterYestPeakJitter
                    SnmpAdminString,
                avCmMeasIpVoStatSumJitterYestFarIpAddr
                    SnmpAdminString
		}

avCmMeasIpVoStatSumJitterYestRegIdx	OBJECT-TYPE
    SYNTAX	Integer32 (1..2000)
    MAX-ACCESS	not-accessible
    STATUS	current
    DESCRIPTION
	"
	Fld OID Name:	avCmMeasIpVoStatSumJitterYestRegIdx
	Fld OID:	enterprises.6889.2.73.8.1.70.1.1.1
	Fld Form/Rpt:	NA
	Fld Format:	NA
	Fld(s) Name:	NA
	Fld Descr:	An index into the network region.
	"
    ::= { avCmMeasIpVoStatSumJitterYestEntry 1 }

avCmMeasIpVoStatSumJitterYestHourIdx        OBJECT-TYPE
    SYNTAX      Integer32 (0..2300)
    MAX-ACCESS	not-accessible
    STATUS      current
    DESCRIPTION
        "
        Fld OID Name:   avCmMeasIpVoStatSumJitterYestHourIdx
        Fld OID:        enterprises.6889.2.73.8.1.70.1.1.2
        Fld Form/Rpt:   NA
        Fld Format:     NA
        Fld(s) Name:    NA
        Fld Descr:      An index that contains the measurement hour for the
                        jitter voice statistics.
        "
    ::= { avCmMeasIpVoStatSumJitterYestEntry 2 }

avCmMeasIpVoStatSumJitterYestIdx        OBJECT-TYPE
    SYNTAX      Integer32 (0..9999)
    MAX-ACCESS  not-accessible
    STATUS      current
    DESCRIPTION
        "
        Fld OID Name:   avCmMeasIpVoStatSumJitterYestHourIdx
        Fld OID:        enterprises.6889.2.73.8.1.70.1.1.3
        Fld Form/Rpt:   NA
        Fld Format:     NA
        Fld(s) Name:    NA
        Fld Descr:      A unique index for the jitter voice statistics.
        "
    ::= { avCmMeasIpVoStatSumJitterYestEntry 3 }

avCmMeasIpVoStatSumJitterYestRegion        OBJECT-TYPE
    SYNTAX      Integer32 (0..2000)
    MAX-ACCESS  read-only
    STATUS      current
    DESCRIPTION
        "
        Fld OID Name:   avCmMeasIpVoStatSumJitterYestRegion
        Fld OID:        enterprises.6889.2.73.8.1.70.1.1.4
        Fld Form/Rpt:   IP VOICE STATISTICS SUMMARY JITTER REPORT
        Fld Format:     Single Field
        Fld(s) Name:    List Command: Region
        Fld Descr:      An object that contains the Network Region.
        "
    ::= { avCmMeasIpVoStatSumJitterYestEntry 4 }

avCmMeasIpVoStatSumJitterYestMeasHour	OBJECT-TYPE
    SYNTAX      Integer32 (0..2300)
    MAX-ACCESS	read-only
    STATUS	current
    DESCRIPTION
	"
	Fld OID Name:	avCmMeasIpVoStatSumJitterYestMeasHour
	Fld OID:	enterprises.6889.2.73.8.1.70.1.1.5
	Fld Form/Rpt:	IP VOICE STATISTICS SUMMARY JITTER REPORT
	Fld Format:	Single
	Fld(s) Name:	Measurement Hour
	Fld Descr:	An object containing the measurement hour.
	"
    ::= { avCmMeasIpVoStatSumJitterYestEntry 5 }

avCmMeasIpVoStatSumJitterYestRunTime	OBJECT-TYPE
    SYNTAX	SnmpAdminString (SIZE (0..28))
    MAX-ACCESS	read-only
    STATUS	current
    DESCRIPTION
	"
	Fld OID Name:	avCmMeasIpVoStatSumJitterYestRunTime
	Fld OID:	enterprises.6889.2.73.8.1.70.1.1.6
	Fld Form/Rpt:	IP VOICE STATISTICS SUMMARY JITTER REPORT
	Fld Format:	Single
	Fld(s) Name:	Date
	Fld Descr:	An object containing the Date.
	"
    ::= { avCmMeasIpVoStatSumJitterYestEntry 6 }

avCmMeasIpVoStatSumJitterYestBoardLoc	OBJECT-TYPE
    SYNTAX	SnmpAdminString (SIZE (0..6))
    MAX-ACCESS	read-only
    STATUS	current
    DESCRIPTION
	"
	Fld OID Name:	avCmMeasIpVoStatSumJitterYestBoardLoc
	Fld OID:	enterprises.6889.2.73.8.1.70.1.1.7
	Fld Form/Rpt:	IP VOICE STATISTICS SUMMARY JITTER REPORT
	Fld Format:	Single
	Fld(s) Name:	Board Loc
	Fld Descr:	An object containing the Board location.
	"
    ::= { avCmMeasIpVoStatSumJitterYestEntry 7 }

avCmMeasIpVoStatSumJitterYestCallingNum	OBJECT-TYPE
    SYNTAX	SnmpAdminString (SIZE (0..17))
    MAX-ACCESS	read-only
    STATUS	current
    DESCRIPTION
	"
	Fld OID Name:	avCmMeasIpVoStatSumJitterYestCallingNum
	Fld OID:	enterprises.6889.2.73.8.1.70.1.1.8
	Fld Form/Rpt:	IP VOICE STATISTICS SUMMARY JITTER REPORT
	Fld Format:	Single
	Fld(s) Name:	Calling Number
	Fld Descr:	An object containing the Calling Number.
	"
    ::= { avCmMeasIpVoStatSumJitterYestEntry 8 }

avCmMeasIpVoStatSumJitterYestCalledNum      OBJECT-TYPE
    SYNTAX      SnmpAdminString (SIZE (0..17))
    MAX-ACCESS  read-only
    STATUS      current
    DESCRIPTION
        "
        Fld OID Name:   avCmMeasIpVoStatSumJitterYestCalledNum
        Fld OID:        enterprises.6889.2.73.8.1.70.1.1.9
        Fld Form/Rpt:   IP VOICE STATISTICS SUMMARY JITTER REPORT
        Fld Format:     Single
        Fld(s) Name:    Called Number
        Fld Descr:      An object containing the Called Number.
        "
    ::= { avCmMeasIpVoStatSumJitterYestEntry 9 }

avCmMeasIpVoStatSumJitterYestDstReg	OBJECT-TYPE
    SYNTAX      Integer32 (0..9999)
    MAX-ACCESS	read-only
    STATUS	current
    DESCRIPTION
	"
	Fld OID Name:	avCmMeasIpVoStatSumJitterYestDstReg
	Fld OID:	enterprises.6889.2.73.8.1.70.1.1.10
	Fld Form/Rpt:	IP VOICE STATISTICS SUMMARY JITTER REPORT
	Fld Format:	Single
	Fld(s) Name:	Dst Reg
	Fld Descr:	An object containing the destination region.
	"
    ::= { avCmMeasIpVoStatSumJitterYestEntry 10 }

avCmMeasIpVoStatSumJitterYestCodec      OBJECT-TYPE
    SYNTAX      SnmpAdminString (SIZE (0..8))
    MAX-ACCESS  read-only
    STATUS      current
    DESCRIPTION
        "
        Fld OID Name:   avCmMeasIpVoStatSumJitterYestCodec
        Fld OID:        enterprises.6889.2.73.8.1.70.1.1.11
        Fld Form/Rpt:   IP VOICE STATISTICS SUMMARY JITTER REPORT
        Fld Format:     Single
        Fld(s) Name:    Codec
        Fld Descr:      An object containing the Codec.
        "
    ::= { avCmMeasIpVoStatSumJitterYestEntry 11 }

avCmMeasIpVoStatSumJitterYestPktSize      OBJECT-TYPE
    SYNTAX      Integer32 (0..999)
    MAX-ACCESS  read-only
    STATUS      current
    DESCRIPTION
        "
        Fld OID Name:   avCmMeasIpVoStatSumJitterYestPktSize
        Fld OID:        enterprises.6889.2.73.8.1.70.1.1.12
        Fld Form/Rpt:   IP VOICE STATISTICS SUMMARY JITTER REPORT
        Fld Format:     Single
        Fld(s) Name:    Pkt Size
        Fld Descr:      An object containing the Packet Size.
        "
    ::= { avCmMeasIpVoStatSumJitterYestEntry 12 }

avCmMeasIpVoStatSumJitterYestTimeCall      OBJECT-TYPE
    SYNTAX      SnmpAdminString (SIZE (0..5))
    MAX-ACCESS  read-only
    STATUS      current
    DESCRIPTION
        "
        Fld OID Name:   avCmMeasIpVoStatSumJitterYestTimeCall
        Fld OID:        enterprises.6889.2.73.8.1.70.1.1.13
        Fld Form/Rpt:   IP VOICE STATISTICS SUMMARY JITTER REPORT
        Fld Format:     Single
        Fld(s) Name:    Time of Call
        Fld Descr:      An object containing the time of the call.
        "
    ::= { avCmMeasIpVoStatSumJitterYestEntry 13 }


avCmMeasIpVoStatSumJitterYestBufSize      OBJECT-TYPE
    SYNTAX      SnmpAdminString (SIZE (0..4))
    MAX-ACCESS  read-only
    STATUS      current
    DESCRIPTION
        "
        Fld OID Name:   avCmMeasIpVoStatSumJitterYestBufSize
        Fld OID:        enterprises.6889.2.73.8.1.70.1.1.14
        Fld Form/Rpt:   IP VOICE STATISTICS SUMMARY JITTER REPORT
        Fld Format:     Single
        Fld(s) Name:    Jitter-Buffer Size
        Fld Descr:      An object containing the Jitter buffer size.
        "
    ::= { avCmMeasIpVoStatSumJitterYestEntry 14 }


avCmMeasIpVoStatSumJitterYestBufOrn      OBJECT-TYPE
    SYNTAX      SnmpAdminString (SIZE (0..4))
    MAX-ACCESS  read-only
    STATUS      current
    DESCRIPTION
        "
        Fld OID Name:   avCmMeasIpVoStatSumJitterYestBufOrn
        Fld OID:        enterprises.6889.2.73.8.1.70.1.1.15
        Fld Form/Rpt:   IP VOICE STATISTICS SUMMARY JITTER REPORT
        Fld Format:     Single
        Fld(s) Name:    Jitter-Buffer Orn
        Fld Descr:      An object containing the Jitter buffer Orn.
        "
    ::= { avCmMeasIpVoStatSumJitterYestEntry 15 }

avCmMeasIpVoStatSumJitterYestBufUrn      OBJECT-TYPE
    SYNTAX      SnmpAdminString (SIZE (0..4))
    MAX-ACCESS  read-only
    STATUS      current
    DESCRIPTION
        "
        Fld OID Name:   avCmMeasIpVoStatSumJitterYestBufUrn
        Fld OID:        enterprises.6889.2.73.8.1.70.1.1.16
        Fld Form/Rpt:   IP VOICE STATISTICS SUMMARY JITTER REPORT
        Fld Format:     Single
        Fld(s) Name:    Jitter-Buffer Urn
        Fld Descr:      An object containing the Jitter buffer Urn.
        "
    ::= { avCmMeasIpVoStatSumJitterYestEntry 16 }


avCmMeasIpVoStatSumJitterYestAvgJitter      OBJECT-TYPE
    SYNTAX      SnmpAdminString (SIZE (0..5))
    MAX-ACCESS  read-only
    STATUS      current
    DESCRIPTION
        "
        Fld OID Name:   avCmMeasIpVoStatSumJitterYestAvgJitter
        Fld OID:        enterprises.6889.2.73.8.1.70.1.1.17
        Fld Form/Rpt:   IP VOICE STATISTICS SUMMARY JITTER REPORT
        Fld Format:     Single
        Fld(s) Name:    Jitter  Avg
        Fld Descr:      An object containing the Jitter average.
        "
    ::= { avCmMeasIpVoStatSumJitterYestEntry 17 }

avCmMeasIpVoStatSumJitterYestPeakJitter      OBJECT-TYPE
    SYNTAX      SnmpAdminString (SIZE (0..5))
    MAX-ACCESS  read-only
    STATUS      current
    DESCRIPTION
        "
        Fld OID Name:   avCmMeasIpVoStatSumJitterYestPeakJitter
        Fld OID:        enterprises.6889.2.73.8.1.70.1.1.18
        Fld Form/Rpt:   IP VOICE STATISTICS SUMMARY JITTER REPORT
        Fld Format:     Single
        Fld(s) Name:    Jitter  Peak
        Fld Descr:      An object containing the Jitter Peak.
        "
    ::= { avCmMeasIpVoStatSumJitterYestEntry 18 }

avCmMeasIpVoStatSumJitterYestFarIpAddr      OBJECT-TYPE
    SYNTAX      SnmpAdminString (SIZE (0..41))
    MAX-ACCESS  read-only
    STATUS      current
    DESCRIPTION
        "
        Fld OID Name:   avCmMeasIpVoStatSumJitterYestFarIpAddr
        Fld OID:        enterprises.6889.2.73.8.1.70.1.1.19
        Fld Form/Rpt:   IP VOICE STATISTICS SUMMARY JITTER REPORT
        Fld Format:     Single
        Fld(s) Name:    FEAddr
        Fld Descr:      An object containing the far-end ip-address.
        "
    ::= { avCmMeasIpVoStatSumJitterYestEntry 19 }

--   *********** avCmMeasIpVoStatSumPkLosLstHr Group **************

-- MIB Group Name:
--		avCmMeasIpVoStatSumPkLosLstHr
-- OID:
--		enterprises.6889.2.73.8.1.71
-- Description:
--		The avCmMeasIpVoStatSumPkLosLstHr MIB group displays the 
--		output of the "list measurements ip voice-stats summary pktloss 
--		last-hour" command  for each network-region administered on the 
--		SUMMARY MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary pktloss last-hour
-- Form/Report Name:
--		1. IP VOICE STATISTICS SUMMARY PKTLOSS REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumPkLosLstHr	OBJECT IDENTIFIER ::= { avCmObjects 71 }

avCmMeasIpVoStatSumPkLosLstHrTable	OBJECT-TYPE
    SYNTAX	SEQUENCE OF AvCmMeasIpVoStatSumPkLosLstHrEntry
    MAX-ACCESS	not-accessible
    STATUS	current
    DESCRIPTION
	"
	Fld OID Name:	avCmMeasIpVoStatSumPkLosLstHrTable
	Fld OID:	enterprises.6889.2.73.8.1.71.1
	Fld Form/Rpt:	NA
	Fld Format:	NA
	Fld(s) Name:	NA
	Fld Descr:	A list of the avCmMemTrunk entries.
	"
    ::= { avCmMeasIpVoStatSumPkLosLstHr 1 }

avCmMeasIpVoStatSumPkLosLstHrEntry	OBJECT-TYPE
    SYNTAX	AvCmMeasIpVoStatSumPkLosLstHrEntry
    MAX-ACCESS	not-accessible
    STATUS	current
    DESCRIPTION
	"
	Fld OID Name:	avCmMeasIpVoStatSumPkLosLstHrEntry
	Fld OID:	enterprises.6889.2.73.8.1.71.1.1
	Fld Form/Rpt:	NA
	Fld Format:	NA
	Fld(s) Name:	NA
	Fld Descr:	A avCmMeasIpVoStatSumPkLosLstHr entry containing 
			objects of the avCmMeasIpVoStatSumPkLosLstHr 
			information sent by the switch.
	"
    INDEX {avCmMeasIpVoStatSumPkLosLstHrRegIdx, 
		avCmMeasIpVoStatSumPkLosLstHrHourIdx,
			avCmMeasIpVoStatSumPkLosLstHrIdx }
    ::= { avCmMeasIpVoStatSumPkLosLstHrTable 1 }

AvCmMeasIpVoStatSumPkLosLstHrEntry ::= SEQUENCE {
		avCmMeasIpVoStatSumPkLosLstHrRegIdx
		    Integer32,
                avCmMeasIpVoStatSumPkLosLstHrHourIdx
                    Integer32,
                avCmMeasIpVoStatSumPkLosLstHrIdx
                    Integer32,
                avCmMeasIpVoStatSumPkLosLstHrRegion
                    Integer32,
                avCmMeasIpVoStatSumPkLosLstHrMeasHour
                    Integer32,
                avCmMeasIpVoStatSumPkLosLstHrRunTime
                    SnmpAdminString,
                avCmMeasIpVoStatSumPkLosLstHrBoardLoc
                    SnmpAdminString,
                avCmMeasIpVoStatSumPkLosLstHrCallingNum
                    SnmpAdminString,
                avCmMeasIpVoStatSumPkLosLstHrCalledNum
                    SnmpAdminString,
                avCmMeasIpVoStatSumPkLosLstHrDstReg
                    Integer32,
                avCmMeasIpVoStatSumPkLosLstHrCodec
                    SnmpAdminString,
                avCmMeasIpVoStatSumPkLosLstHrTimeCall
                    SnmpAdminString,
                avCmMeasIpVoStatSumPkLosLstHrUDPPort
                    SnmpAdminString,
                avCmMeasIpVoStatSumPkLosLstHrPktSize
                    Integer32,
                avCmMeasIpVoStatSumPkLosLstHrTotnumLosPkts
                    Integer32,
                avCmMeasIpVoStatSumPkLosLstHrPktLossPerc
                    SnmpAdminString,
                avCmMeasIpVoStatSumPkLosLstHrSilSup
                    SnmpAdminString,
                avCmMeasIpVoStatSumPkLosLstHrFEAddr
                    SnmpAdminString

		}

avCmMeasIpVoStatSumPkLosLstHrRegIdx	OBJECT-TYPE
    SYNTAX	Integer32 (1..2000)
    MAX-ACCESS	not-accessible
    STATUS	current
    DESCRIPTION
	"
	Fld OID Name:	avCmMeasIpVoStatSumPkLosLstHrRegIdx
	Fld OID:	enterprises.6889.2.73.8.1.71.1.1.1
	Fld Form/Rpt:	NA
	Fld Format:	NA
	Fld(s) Name:	NA
	Fld Descr:	An index into the network region.
	"
    ::= { avCmMeasIpVoStatSumPkLosLstHrEntry 1 }

avCmMeasIpVoStatSumPkLosLstHrHourIdx        OBJECT-TYPE
    SYNTAX      Integer32 (0..2300)
    MAX-ACCESS	not-accessible
    STATUS      current
    DESCRIPTION
        "
        Fld OID Name:   avCmMeasIpVoStatSumPkLosLstHrHourIdx
        Fld OID:        enterprises.6889.2.73.8.1.71.1.1.2
        Fld Form/Rpt:   NA
        Fld Format:     NA
        Fld(s) Name:    NA
        Fld Descr:      An index that contains the measurement hour for the
                        pktloss voice statistics.
        "
    ::= { avCmMeasIpVoStatSumPkLosLstHrEntry 2 }

avCmMeasIpVoStatSumPkLosLstHrIdx        OBJECT-TYPE
    SYNTAX      Integer32 (0..9999)
    MAX-ACCESS  not-accessible
    STATUS      current
    DESCRIPTION
        "
        Fld OID Name:   avCmMeasIpVoStatSumPkLosLstHrIdx
        Fld OID:        enterprises.6889.2.73.8.1.71.1.1.3
        Fld Form/Rpt:   NA
        Fld Format:     NA
        Fld(s) Name:    NA
        Fld Descr:      A unique index for the pktloss voice statistics.
        "
    ::= { avCmMeasIpVoStatSumPkLosLstHrEntry 3 }


avCmMeasIpVoStatSumPkLosLstHrRegion        OBJECT-TYPE
    SYNTAX      Integer32 (0..2000)
    MAX-ACCESS  read-only
    STATUS      current
    DESCRIPTION
        "
        Fld OID Name:   avCmMeasIpVoStatSumPkLosLstHrRegion
        Fld OID:        enterprises.6889.2.73.8.1.71.1.1.4
        Fld Form/Rpt:   IP VOICE STATISTICS SUMMARY PKTLOSS REPORT
        Fld Format:     Single Field
        Fld(s) Name:    List Command: Region
        Fld Descr:      An object that contains the Network Region.
        "
    ::= { avCmMeasIpVoStatSumPkLosLstHrEntry 4 }

avCmMeasIpVoStatSumPkLosLstHrMeasHour	OBJECT-TYPE
    SYNTAX      Integer32 (0..2300)
    MAX-ACCESS	read-only
    STATUS	current
    DESCRIPTION
	"
	Fld OID Name:	avCmMeasIpVoStatSumPkLosLstHrMeasHour
	Fld OID:	enterprises.6889.2.73.8.1.71.1.1.5
	Fld Form/Rpt:	IP VOICE STATISTICS SUMMARY PKTLOSS REPORT
	Fld Format:	Single
	Fld(s) Name:	Measurement Hour
	Fld Descr:	An object containing the measurement hour.
	"
    ::= { avCmMeasIpVoStatSumPkLosLstHrEntry 5 }

avCmMeasIpVoStatSumPkLosLstHrRunTime	OBJECT-TYPE
    SYNTAX	SnmpAdminString (SIZE (0..28))
    MAX-ACCESS	read-only
    STATUS	current
    DESCRIPTION
	"
	Fld OID Name:	avCmMeasIpVoStatSumPkLosLstHrRunTime
	Fld OID:	enterprises.6889.2.73.8.1.71.1.1.6
	Fld Form/Rpt:	IP VOICE STATISTICS SUMMARY PKTLOSS REPORT
	Fld Format:	Single
	Fld(s) Name:	Date
	Fld Descr:	An object containing the Date.
	"
    ::= { avCmMeasIpVoStatSumPkLosLstHrEntry 6 }

avCmMeasIpVoStatSumPkLosLstHrBoardLoc	OBJECT-TYPE
    SYNTAX	SnmpAdminString (SIZE (0..6))
    MAX-ACCESS	read-only
    STATUS	current
    DESCRIPTION
	"
	Fld OID Name:	avCmMeasIpVoStatSumPkLosLstHrBoardLoc
	Fld OID:	enterprises.6889.2.73.8.1.71.1.1.7
	Fld Form/Rpt:	IP VOICE STATISTICS SUMMARY PKTLOSS REPORT
	Fld Format:	Single
	Fld(s) Name:	Board Loc
	Fld Descr:	An object containing the Board location.
	"
    ::= { avCmMeasIpVoStatSumPkLosLstHrEntry 7 }

avCmMeasIpVoStatSumPkLosLstHrCallingNum	OBJECT-TYPE
    SYNTAX	SnmpAdminString (SIZE (0..17))
    MAX-ACCESS	read-only
    STATUS	current
    DESCRIPTION
	"
	Fld OID Name:	avCmMeasIpVoStatSumPkLosLstHrCallingNum
	Fld OID:	enterprises.6889.2.73.8.1.71.1.1.8
	Fld Form/Rpt:	IP VOICE STATISTICS SUMMARY PKTLOSS REPORT
	Fld Format:	Single
	Fld(s) Name:	Calling Number
	Fld Descr:	An object containing the Calling Number.
	"
    ::= { avCmMeasIpVoStatSumPkLosLstHrEntry 8 }

avCmMeasIpVoStatSumPkLosLstHrCalledNum      OBJECT-TYPE
    SYNTAX      SnmpAdminString (SIZE (0..17))
    MAX-ACCESS  read-only
    STATUS      current
    DESCRIPTION
        "
        Fld OID Name:   avCmMeasIpVoStatSumPkLosLstHrCalledNum
        Fld OID:        enterprises.6889.2.73.8.1.71.1.1.9
        Fld Form/Rpt:   IP VOICE STATISTICS SUMMARY PKTLOSS REPORT
        Fld Format:     Single
        Fld(s) Name:    Called Number
        Fld Descr:      An object containing the Called Number.
        "
    ::= { avCmMeasIpVoStatSumPkLosLstHrEntry 9 }

avCmMeasIpVoStatSumPkLosLstHrDstReg	OBJECT-TYPE
    SYNTAX      Integer32 (0..9999)
    MAX-ACCESS	read-only
    STATUS	current
    DESCRIPTION
	"
	Fld OID Name:	avCmMeasIpVoStatSumPkLosLstHrDstReg
	Fld OID:	enterprises.6889.2.73.8.1.71.1.1.10
	Fld Form/Rpt:	IP VOICE STATISTICS SUMMARY PKTLOSS REPORT
	Fld Format:	Single
	Fld(s) Name:	Dst Reg
	Fld Descr:	An object containing the destination region.
	"
    ::= { avCmMeasIpVoStatSumPkLosLstHrEntry 10 }

avCmMeasIpVoStatSumPkLosLstHrCodec      OBJECT-TYPE
    SYNTAX      SnmpAdminString (SIZE (0..8))
    MAX-ACCESS  read-only
    STATUS      current
    DESCRIPTION
        "
        Fld OID Name:   avCmMeasIpVoStatSumPkLosLstHrCodec
        Fld OID:        enterprises.6889.2.73.8.1.71.1.1.11
        Fld Form/Rpt:   IP VOICE STATISTICS SUMMARY PKTLOSS REPORT
        Fld Format:     Single
        Fld(s) Name:    Codec
        Fld Descr:      An object containing the Codec.
        "
    ::= { avCmMeasIpVoStatSumPkLosLstHrEntry 11 }


avCmMeasIpVoStatSumPkLosLstHrTimeCall      OBJECT-TYPE
    SYNTAX      SnmpAdminString (SIZE (0..5))
    MAX-ACCESS  read-only
    STATUS      current
    DESCRIPTION
        "
        Fld OID Name:   avCmMeasIpVoStatSumPkLosLstHrTimeCall
        Fld OID:        enterprises.6889.2.73.8.1.71.1.1.12
        Fld Form/Rpt:   IP VOICE STATISTICS SUMMARY PKTLOSS REPORT
        Fld Format:     Single
        Fld(s) Name:    Time of Call
        Fld Descr:      A time stamp when threshold was first
			exceeded for the associated call, shown in MMSS 
			(minutes seconds).
        "
    ::= { avCmMeasIpVoStatSumPkLosLstHrEntry 12 }


avCmMeasIpVoStatSumPkLosLstHrUDPPort      OBJECT-TYPE
    SYNTAX      SnmpAdminString (SIZE (0..6))
    MAX-ACCESS  read-only
    STATUS      current
    DESCRIPTION
        "
        Fld OID Name:   avCmMeasIpVoStatSumPkLosLstHrUDPPort
        Fld OID:        enterprises.6889.2.73.8.1.71.1.1.13
        Fld Form/Rpt:   IP VOICE STATISTICS SUMMARY PKTLOSS REPORT
        Fld Format:     Single
        Fld(s) Name:    UDP Port
        Fld Descr:      The UDP port used by the media processor
			for this call.
        "
    ::= { avCmMeasIpVoStatSumPkLosLstHrEntry 13 }


avCmMeasIpVoStatSumPkLosLstHrPktSize      OBJECT-TYPE
    SYNTAX      Integer32 (0..999)
    MAX-ACCESS  read-only
    STATUS      current
    DESCRIPTION
        "
        Fld OID Name:   avCmMeasIpVoStatSumPkLosLstHrPktSize
        Fld OID:        enterprises.6889.2.73.8.1.71.1.1.14
        Fld Form/Rpt:   IP VOICE STATISTICS SUMMARY PKTLOSS REPORT
        Fld Format:     Single
        Fld(s) Name:    Pkt Size
        Fld Descr:      The packet size for each steam of data for
			the associated call, measured in milliseconds.
        "
    ::= { avCmMeasIpVoStatSumPkLosLstHrEntry 14 }

avCmMeasIpVoStatSumPkLosLstHrTotnumLosPkts      OBJECT-TYPE
    SYNTAX      Integer32 (0..9999)
    MAX-ACCESS  read-only
    STATUS      current
    DESCRIPTION
        "
        Fld OID Name:   avCmMeasIpVoStatSumPkLosLstHrTotnumLosPkts
        Fld OID:        enterprises.6889.2.73.8.1.71.1.1.15
        Fld Form/Rpt:   IP VOICE STATISTICS SUMMARY PKTLOSS REPORT
        Fld Format:     Single
        Fld(s) Name:    Total #lost Pkts
        Fld Descr:      An object containing the total number of lost packets				for the call.
        "
    ::= { avCmMeasIpVoStatSumPkLosLstHrEntry 15 }


avCmMeasIpVoStatSumPkLosLstHrPktLossPerc      OBJECT-TYPE
    SYNTAX      SnmpAdminString (SIZE (0..3))
    MAX-ACCESS  read-only
    STATUS      current
    DESCRIPTION
        "
        Fld OID Name:   avCmMeasIpVoStatSumPkLosPktLstHrLossPerc
        Fld OID:        enterprises.6889.2.73.8.1.71.1.1.16
        Fld Form/Rpt:   IP VOICE STATISTICS SUMMARY PKTLOSS REPORT
        Fld Format:     Single
        Fld(s) Name:    Packet loss %
        Fld Descr:      The peak packet loss for the call. The packet
			loss percentage is calculated at 10-second
			intervals.
        "
    ::= { avCmMeasIpVoStatSumPkLosLstHrEntry 16 }

avCmMeasIpVoStatSumPkLosLstHrSilSup      OBJECT-TYPE
    SYNTAX      SnmpAdminString (SIZE (0..2))
    MAX-ACCESS  read-only
    STATUS      current
    DESCRIPTION
        "
        Fld OID Name:   avCmMeasIpVoStatSumPkLosLstHrSilSup
        Fld OID:        enterprises.6889.2.73.8.1.71.1.1.17
        Fld Form/Rpt:   IP VOICE STATISTICS SUMMARY PKTLOSS REPORT
        Fld Format:     Single
        Fld(s) Name:    Sil Sup
        Fld Descr:      Indicates whether the silence suppression
			was used for the call.
        "
    ::= { avCmMeasIpVoStatSumPkLosLstHrEntry 17 }

avCmMeasIpVoStatSumPkLosLstHrFEAddr      OBJECT-TYPE
    SYNTAX      SnmpAdminString (SIZE (0..41))
    MAX-ACCESS  read-only
    STATUS      current
    DESCRIPTION
        "
        Fld OID Name:   avCmMeasIpVoStatSumPkLosLstHrFEAddr
        Fld OID:        enterprises.6889.2.73.8.1.71.1.1.18
        Fld Form/Rpt:   IP VOICE STATISTICS SUMMARY PKTLOSS REPORT
        Fld Format:     Single
        Fld(s) Name:    FEAddr
        Fld Descr:      An object containing the far-end ip-address.
        "
    ::= { avCmMeasIpVoStatSumPkLosLstHrEntry 18 }

--   *********** avCmMeasIpVoStatSumPkLosToday Group **************

-- MIB Group Name:
--		avCmMeasIpVoStatSumPkLosToday
-- OID:
--		enterprises.6889.2.73.8.1.72
-- Description:
--		The avCmMeasIpVoStatSumPkLosToday MIB group displays the 
--		output of the "list measurements ip voice-stats summary pktloss 
--		today" command  for each network-region administered on the 
--		SUMMARY MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary pktloss today
-- Form/Report Name:
--		1. IP VOICE STATISTICS SUMMARY PKTLOSS REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumPkLosToday	OBJECT IDENTIFIER ::= { avCmObjects 72 }

avCmMeasIpVoStatSumPkLosTodayTable	OBJECT-TYPE
    SYNTAX	SEQUENCE OF AvCmMeasIpVoStatSumPkLosTodayEntry
    MAX-ACCESS	not-accessible
    STATUS	current
    DESCRIPTION
	"
	Fld OID Name:	avCmMeasIpVoStatSumPkLosTodayTable
	Fld OID:	enterprises.6889.2.73.8.1.72.1
	Fld Form/Rpt:	NA
	Fld Format:	NA
	Fld(s) Name:	NA
	Fld Descr:	A list of the avCmMemTrunk entries.
	"
    ::= { avCmMeasIpVoStatSumPkLosToday 1 }

avCmMeasIpVoStatSumPkLosTodayEntry	OBJECT-TYPE
    SYNTAX	AvCmMeasIpVoStatSumPkLosTodayEntry
    MAX-ACCESS	not-accessible
    STATUS	current
    DESCRIPTION
	"
	Fld OID Name:	avCmMeasIpVoStatSumPkLosTodayEntry
	Fld OID:	enterprises.6889.2.73.8.1.72.1.1
	Fld Form/Rpt:	NA
	Fld Format:	NA
	Fld(s) Name:	NA
	Fld Descr:	A avCmMeasIpVoStatSumPkLosToday entry containing 
			objects of the avCmMeasIpVoStatSumPkLosToday 
			information sent by the switch.
	"
    INDEX {avCmMeasIpVoStatSumPkLosTodayRegIdx, 
		avCmMeasIpVoStatSumPkLosTodayHourIdx,
			avCmMeasIpVoStatSumPkLosTodayIdx }
    ::= { avCmMeasIpVoStatSumPkLosTodayTable 1 }

AvCmMeasIpVoStatSumPkLosTodayEntry ::= SEQUENCE {
		avCmMeasIpVoStatSumPkLosTodayRegIdx
		    Integer32,
                avCmMeasIpVoStatSumPkLosTodayHourIdx
                    Integer32,
                avCmMeasIpVoStatSumPkLosTodayIdx
                    Integer32,
                avCmMeasIpVoStatSumPkLosTodayRegion
                    Integer32,
                avCmMeasIpVoStatSumPkLosTodayMeasHour
                    Integer32,
                avCmMeasIpVoStatSumPkLosTodayRunTime
                    SnmpAdminString,
                avCmMeasIpVoStatSumPkLosTodayBoardLoc
                    SnmpAdminString,
                avCmMeasIpVoStatSumPkLosTodayCallingNum
                    SnmpAdminString,
                avCmMeasIpVoStatSumPkLosTodayCalledNum
                    SnmpAdminString,
                avCmMeasIpVoStatSumPkLosTodayDstReg
                    Integer32,
                avCmMeasIpVoStatSumPkLosTodayCodec
                    SnmpAdminString,
                avCmMeasIpVoStatSumPkLosTodayTimeCall
                    SnmpAdminString,
                avCmMeasIpVoStatSumPkLosTodayUDPPort
                    SnmpAdminString,
                avCmMeasIpVoStatSumPkLosTodayPktSize
                    Integer32,
                avCmMeasIpVoStatSumPkLosTodayTotnumLosPkts
                    Integer32,
                avCmMeasIpVoStatSumPkLosTodayPktLossPerc
                    SnmpAdminString,
                avCmMeasIpVoStatSumPkLosTodaySilSup
                    SnmpAdminString,
                avCmMeasIpVoStatSumPkLosTodayFEAddr
                    SnmpAdminString

		}

avCmMeasIpVoStatSumPkLosTodayRegIdx	OBJECT-TYPE
    SYNTAX	Integer32 (1..2000)
    MAX-ACCESS	not-accessible
    STATUS	current
    DESCRIPTION
	"
	Fld OID Name:	avCmMeasIpVoStatSumPkLosTodayRegIdx
	Fld OID:	enterprises.6889.2.73.8.1.72.1.1.1
	Fld Form/Rpt:	NA
	Fld Format:	NA
	Fld(s) Name:	NA
	Fld Descr:	An index into the network region.
	"
    ::= { avCmMeasIpVoStatSumPkLosTodayEntry 1 }

avCmMeasIpVoStatSumPkLosTodayHourIdx        OBJECT-TYPE
    SYNTAX      Integer32 (0..2300)
    MAX-ACCESS	not-accessible
    STATUS      current
    DESCRIPTION
        "
        Fld OID Name:   avCmMeasIpVoStatSumPkLosTodayHourIdx
        Fld OID:        enterprises.6889.2.73.8.1.72.1.1.2
        Fld Form/Rpt:   NA
        Fld Format:     NA
        Fld(s) Name:    NA
        Fld Descr:      An index that contains the measurement hour for the
                        pktloss voice statistics.
        "
    ::= { avCmMeasIpVoStatSumPkLosTodayEntry 2 }

avCmMeasIpVoStatSumPkLosTodayIdx        OBJECT-TYPE
    SYNTAX      Integer32 (0..9999)
    MAX-ACCESS  not-accessible
    STATUS      current
    DESCRIPTION
        "
        Fld OID Name:   avCmMeasIpVoStatSumPkLosTodayIdx
        Fld OID:        enterprises.6889.2.73.8.1.72.1.1.3
        Fld Form/Rpt:   NA
        Fld Format:     NA
        Fld(s) Name:    NA
        Fld Descr:      An index that contains the measurement hour for the
                        pktloss voice statistics.
        "
    ::= { avCmMeasIpVoStatSumPkLosTodayEntry 3 }


avCmMeasIpVoStatSumPkLosTodayRegion        OBJECT-TYPE
    SYNTAX      Integer32 (0..2000)
    MAX-ACCESS  read-only
    STATUS      current
    DESCRIPTION
        "
        Fld OID Name:   avCmMeasIpVoStatSumPkLosTodayRegion
        Fld OID:        enterprises.6889.2.73.8.1.72.1.1.4
        Fld Form/Rpt:   IP VOICE STATISTICS SUMMARY PKTLOSS REPORT
        Fld Format:     Single Field
        Fld(s) Name:    List Command: Region
        Fld Descr:      An object that contains the Network Region.
        "
    ::= { avCmMeasIpVoStatSumPkLosTodayEntry 4 }

avCmMeasIpVoStatSumPkLosTodayMeasHour	OBJECT-TYPE
    SYNTAX      Integer32 (0..2300)
    MAX-ACCESS	read-only
    STATUS	current
    DESCRIPTION
	"
	Fld OID Name:	avCmMeasIpVoStatSumPkLosTodayMeasHour
	Fld OID:	enterprises.6889.2.73.8.1.72.1.1.5
	Fld Form/Rpt:	IP VOICE STATISTICS SUMMARY PKTLOSS REPORT
	Fld Format:	Single
	Fld(s) Name:	Measurement Hour
	Fld Descr:	An object containing the measurement hour.
	"
    ::= { avCmMeasIpVoStatSumPkLosTodayEntry 5 }

avCmMeasIpVoStatSumPkLosTodayRunTime	OBJECT-TYPE
    SYNTAX	SnmpAdminString (SIZE (0..28))
    MAX-ACCESS	read-only
    STATUS	current
    DESCRIPTION
	"
	Fld OID Name:	avCmMeasIpVoStatSumPkLosTodayRunTime
	Fld OID:	enterprises.6889.2.73.8.1.72.1.1.6
	Fld Form/Rpt:	IP VOICE STATISTICS SUMMARY PKTLOSS REPORT
	Fld Format:	Single
	Fld(s) Name:	Date
	Fld Descr:	An object containing the Date.
	"
    ::= { avCmMeasIpVoStatSumPkLosTodayEntry 6 }

avCmMeasIpVoStatSumPkLosTodayBoardLoc	OBJECT-TYPE
    SYNTAX	SnmpAdminString (SIZE (0..6))
    MAX-ACCESS	read-only
    STATUS	current
    DESCRIPTION
	"
	Fld OID Name:	avCmMeasIpVoStatSumPkLosTodayBoardLoc
	Fld OID:	enterprises.6889.2.73.8.1.72.1.1.7
	Fld Form/Rpt:	IP VOICE STATISTICS SUMMARY PKTLOSS REPORT
	Fld Format:	Single
	Fld(s) Name:	Board Loc
	Fld Descr:	An object containing the Board location.
	"
    ::= { avCmMeasIpVoStatSumPkLosTodayEntry 7 }

avCmMeasIpVoStatSumPkLosTodayCallingNum	OBJECT-TYPE
    SYNTAX	SnmpAdminString (SIZE (0..17))
    MAX-ACCESS	read-only
    STATUS	current
    DESCRIPTION
	"
	Fld OID Name:	avCmMeasIpVoStatSumPkLosTodayCallingNum
	Fld OID:	enterprises.6889.2.73.8.1.72.1.1.8
	Fld Form/Rpt:	IP VOICE STATISTICS SUMMARY PKTLOSS REPORT
	Fld Format:	Single
	Fld(s) Name:	Calling Number
	Fld Descr:	An object containing the Calling Number.
	"
    ::= { avCmMeasIpVoStatSumPkLosTodayEntry 8 }

avCmMeasIpVoStatSumPkLosTodayCalledNum      OBJECT-TYPE
    SYNTAX      SnmpAdminString (SIZE (0..17))
    MAX-ACCESS  read-only
    STATUS      current
    DESCRIPTION
        "
        Fld OID Name:   avCmMeasIpVoStatSumPkLosTodayCalledNum
        Fld OID:        enterprises.6889.2.73.8.1.72.1.1.9
        Fld Form/Rpt:   IP VOICE STATISTICS SUMMARY PKTLOSS REPORT
        Fld Format:     Single
        Fld(s) Name:    Called Number
        Fld Descr:      An object containing the Called Number.
        "
    ::= { avCmMeasIpVoStatSumPkLosTodayEntry 9 }

avCmMeasIpVoStatSumPkLosTodayDstReg	OBJECT-TYPE
    SYNTAX      Integer32 (0..9999)
    MAX-ACCESS	read-only
    STATUS	current
    DESCRIPTION
	"
	Fld OID Name:	avCmMeasIpVoStatSumPkLosTodayDstReg
	Fld OID:	enterprises.6889.2.73.8.1.72.1.1.10
	Fld Form/Rpt:	IP VOICE STATISTICS SUMMARY PKTLOSS REPORT
	Fld Format:	Single
	Fld(s) Name:	Dst Reg
	Fld Descr:	An object containing the destination region.
	"
    ::= { avCmMeasIpVoStatSumPkLosTodayEntry 10 }

avCmMeasIpVoStatSumPkLosTodayCodec      OBJECT-TYPE
    SYNTAX      SnmpAdminString (SIZE (0..8))
    MAX-ACCESS  read-only
    STATUS      current
    DESCRIPTION
        "
        Fld OID Name:   avCmMeasIpVoStatSumPkLosTodayCodec
        Fld OID:        enterprises.6889.2.73.8.1.72.1.1.11
        Fld Form/Rpt:   IP VOICE STATISTICS SUMMARY PKTLOSS REPORT
        Fld Format:     Single
        Fld(s) Name:    Codec
        Fld Descr:      An object containing the Codec.
        "
    ::= { avCmMeasIpVoStatSumPkLosTodayEntry 11 }


avCmMeasIpVoStatSumPkLosTodayTimeCall      OBJECT-TYPE
    SYNTAX      SnmpAdminString (SIZE (0..5))
    MAX-ACCESS  read-only
    STATUS      current
    DESCRIPTION
        "
        Fld OID Name:   avCmMeasIpVoStatSumPkLosTodayTimeCall
        Fld OID:        enterprises.6889.2.73.8.1.72.1.1.12
        Fld Form/Rpt:   IP VOICE STATISTICS SUMMARY PKTLOSS REPORT
        Fld Format:     Single
        Fld(s) Name:    Time of Call
        Fld Descr:      A time stamp when threshold was first
			exceeded for the associated call, shown in MMSS 
			(minutes seconds).
        "
    ::= { avCmMeasIpVoStatSumPkLosTodayEntry 12 }


avCmMeasIpVoStatSumPkLosTodayUDPPort      OBJECT-TYPE
    SYNTAX      SnmpAdminString (SIZE (0..6))
    MAX-ACCESS  read-only
    STATUS      current
    DESCRIPTION
        "
        Fld OID Name:   avCmMeasIpVoStatSumPkLosTodayUDPPort
        Fld OID:        enterprises.6889.2.73.8.1.72.1.1.13
        Fld Form/Rpt:   IP VOICE STATISTICS SUMMARY PKTLOSS REPORT
        Fld Format:     Single
        Fld(s) Name:    UDP Port
        Fld Descr:      The UDP port used by the media processor
			for this call.
        "
    ::= { avCmMeasIpVoStatSumPkLosTodayEntry 13 }


avCmMeasIpVoStatSumPkLosTodayPktSize      OBJECT-TYPE
    SYNTAX      Integer32 (0..999)
    MAX-ACCESS  read-only
    STATUS      current
    DESCRIPTION
        "
        Fld OID Name:   avCmMeasIpVoStatSumPkLosTodayPktSize
        Fld OID:        enterprises.6889.2.73.8.1.72.1.1.14
        Fld Form/Rpt:   IP VOICE STATISTICS SUMMARY PKTLOSS REPORT
        Fld Format:     Single
        Fld(s) Name:    Pkt Size
        Fld Descr:      The packet size for each steam of data for
			the associated call, measured in milliseconds.
        "
    ::= { avCmMeasIpVoStatSumPkLosTodayEntry 14 }

avCmMeasIpVoStatSumPkLosTodayTotnumLosPkts      OBJECT-TYPE
    SYNTAX      Integer32 (0..9999)
    MAX-ACCESS  read-only
    STATUS      current
    DESCRIPTION
        "
        Fld OID Name:   avCmMeasIpVoStatSumPkLosTodayTotnumLosPkts
        Fld OID:        enterprises.6889.2.73.8.1.72.1.1.15
        Fld Form/Rpt:   IP VOICE STATISTICS SUMMARY PKTLOSS REPORT
        Fld Format:     Single
        Fld(s) Name:    Total #lost Pkts
        Fld Descr:      An object containing the total number of lost packets				for the call.
        "
    ::= { avCmMeasIpVoStatSumPkLosTodayEntry 15 }


avCmMeasIpVoStatSumPkLosTodayPktLossPerc      OBJECT-TYPE
    SYNTAX      SnmpAdminString (SIZE (0..3))
    MAX-ACCESS  read-only
    STATUS      current
    DESCRIPTION
        "
        Fld OID Name:   avCmMeasIpVoStatSumPkLosPktTodayLossPerc
        Fld OID:        enterprises.6889.2.73.8.1.72.1.1.16
        Fld Form/Rpt:   IP VOICE STATISTICS SUMMARY PKTLOSS REPORT
        Fld Format:     Single
        Fld(s) Name:    Packet loss %
        Fld Descr:      The peak packet loss for the call. The packet
			loss percentage is calculated at 10-second
			intervals.
        "
    ::= { avCmMeasIpVoStatSumPkLosTodayEntry 16 }

avCmMeasIpVoStatSumPkLosTodaySilSup      OBJECT-TYPE
    SYNTAX      SnmpAdminString (SIZE (0..2))
    MAX-ACCESS  read-only
    STATUS      current
    DESCRIPTION
        "
        Fld OID Name:   avCmMeasIpVoStatSumPkLosTodaySilSup
        Fld OID:        enterprises.6889.2.73.8.1.72.1.1.17
        Fld Form/Rpt:   IP VOICE STATISTICS SUMMARY PKTLOSS REPORT
        Fld Format:     Single
        Fld(s) Name:    Sil Sup
        Fld Descr:      Indicates whether the silence suppression
			was used for the call.
        "
    ::= { avCmMeasIpVoStatSumPkLosTodayEntry 17 }

avCmMeasIpVoStatSumPkLosTodayFEAddr      OBJECT-TYPE
    SYNTAX      SnmpAdminString (SIZE (0..41))
    MAX-ACCESS  read-only
    STATUS      current
    DESCRIPTION
        "
        Fld OID Name:   avCmMeasIpVoStatSumPkLosTodayFEAddr
        Fld OID:        enterprises.6889.2.73.8.1.72.1.1.18
        Fld Form/Rpt:   IP VOICE STATISTICS SUMMARY PKTLOSS REPORT
        Fld Format:     Single
        Fld(s) Name:    FEAddr
        Fld Descr:      An object containing the far-end ip-address.
        "
    ::= { avCmMeasIpVoStatSumPkLosTodayEntry 18 }

--   *********** avCmMeasIpVoStatSumPkLosYest Group **************

-- MIB Group Name:
--		avCmMeasIpVoStatSumPkLosYest
-- OID:
--		enterprises.6889.2.73.8.1.73
-- Description:
--		The avCmMeasIpVoStatSumPkLosYest MIB group displays the 
--		output of the "list measurements ip voice-stats summary pktloss 
--		yesterday" command  for each network-region administered on the 
--		SUMMARY MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary pktloss yesterday
-- Form/Report Name:
--		1. IP VOICE STATISTICS SUMMARY PKTLOSS REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumPkLosYest	OBJECT IDENTIFIER ::= { avCmObjects 73 }

avCmMeasIpVoStatSumPkLosYestTable	OBJECT-TYPE
    SYNTAX	SEQUENCE OF AvCmMeasIpVoStatSumPkLosYestEntry
    MAX-ACCESS	not-accessible
    STATUS	current
    DESCRIPTION
	"
	Fld OID Name:	avCmMeasIpVoStatSumPkLosYestTable
	Fld OID:	enterprises.6889.2.73.8.1.73.1
	Fld Form/Rpt:	NA
	Fld Format:	NA
	Fld(s) Name:	NA
	Fld Descr:	A list of the avCmMemTrunk entries.
	"
    ::= { avCmMeasIpVoStatSumPkLosYest 1 }

avCmMeasIpVoStatSumPkLosYestEntry	OBJECT-TYPE
    SYNTAX	AvCmMeasIpVoStatSumPkLosYestEntry
    MAX-ACCESS	not-accessible
    STATUS	current
    DESCRIPTION
	"
	Fld OID Name:	avCmMeasIpVoStatSumPkLosYestEntry
	Fld OID:	enterprises.6889.2.73.8.1.73.1.1
	Fld Form/Rpt:	NA
	Fld Format:	NA
	Fld(s) Name:	NA
	Fld Descr:	A avCmMeasIpVoStatSumPkLosYest entry containing 
			objects of the avCmMeasIpVoStatSumPkLosYest 
			information sent by the switch.
	"
    INDEX {avCmMeasIpVoStatSumPkLosYestRegIdx, 
		avCmMeasIpVoStatSumPkLosYestHourIdx,
			avCmMeasIpVoStatSumPkLosYestIdx }
    ::= { avCmMeasIpVoStatSumPkLosYestTable 1 }

AvCmMeasIpVoStatSumPkLosYestEntry ::= SEQUENCE {
		avCmMeasIpVoStatSumPkLosYestRegIdx
		    Integer32,
                avCmMeasIpVoStatSumPkLosYestHourIdx
                    Integer32,
                avCmMeasIpVoStatSumPkLosYestIdx
                    Integer32,
                avCmMeasIpVoStatSumPkLosYestRegion
                    Integer32,
                avCmMeasIpVoStatSumPkLosYestMeasHour
                    Integer32,
                avCmMeasIpVoStatSumPkLosYestRunTime
                    SnmpAdminString,
                avCmMeasIpVoStatSumPkLosYestBoardLoc
                    SnmpAdminString,
                avCmMeasIpVoStatSumPkLosYestCallingNum
                    SnmpAdminString,
                avCmMeasIpVoStatSumPkLosYestCalledNum
                    SnmpAdminString,
                avCmMeasIpVoStatSumPkLosYestDstReg
                    Integer32,
                avCmMeasIpVoStatSumPkLosYestCodec
                    SnmpAdminString,
                avCmMeasIpVoStatSumPkLosYestTimeCall
                    SnmpAdminString,
                avCmMeasIpVoStatSumPkLosYestUDPPort
                    SnmpAdminString,
                avCmMeasIpVoStatSumPkLosYestPktSize
                    Integer32,
                avCmMeasIpVoStatSumPkLosYestTotnumLosPkts
                    Integer32,
                avCmMeasIpVoStatSumPkLosYestPktLossPerc
                    SnmpAdminString,
                avCmMeasIpVoStatSumPkLosYestSilSup
                    SnmpAdminString,
                avCmMeasIpVoStatSumPkLosYestFEAddr
                    SnmpAdminString

		}

avCmMeasIpVoStatSumPkLosYestRegIdx	OBJECT-TYPE
    SYNTAX	Integer32 (1..2000)
    MAX-ACCESS	not-accessible
    STATUS	current
    DESCRIPTION
	"
	Fld OID Name:	avCmMeasIpVoStatSumPkLosYestRegIdx
	Fld OID:	enterprises.6889.2.73.8.1.73.1.1.1
	Fld Form/Rpt:	NA
	Fld Format:	NA
	Fld(s) Name:	NA
	Fld Descr:	An index into the network region.
	"
    ::= { avCmMeasIpVoStatSumPkLosYestEntry 1 }

avCmMeasIpVoStatSumPkLosYestHourIdx        OBJECT-TYPE
    SYNTAX      Integer32 (0..2300)
    MAX-ACCESS	not-accessible
    STATUS      current
    DESCRIPTION
        "
        Fld OID Name:   avCmMeasIpVoStatSumPkLosYestHourIdx
        Fld OID:        enterprises.6889.2.73.8.1.73.1.1.2
        Fld Form/Rpt:   NA
        Fld Format:     NA
        Fld(s) Name:    NA
        Fld Descr:      An index that contains the measurement hour for the
                        pktloss voice statistics.
        "
    ::= { avCmMeasIpVoStatSumPkLosYestEntry 2 }

avCmMeasIpVoStatSumPkLosYestIdx        OBJECT-TYPE
    SYNTAX      Integer32 (0..9999)
    MAX-ACCESS  not-accessible
    STATUS      current
    DESCRIPTION
        "
        Fld OID Name:   avCmMeasIpVoStatSumPkLosYestHourIdx
        Fld OID:        enterprises.6889.2.73.8.1.73.1.1.3
        Fld Form/Rpt:   NA
        Fld Format:     NA
        Fld(s) Name:    NA
        Fld Descr:      A unique index for the pktloss voice statistics.
        "
    ::= { avCmMeasIpVoStatSumPkLosYestEntry 3 }


avCmMeasIpVoStatSumPkLosYestRegion        OBJECT-TYPE
    SYNTAX      Integer32 (0..2000)
    MAX-ACCESS  read-only
    STATUS      current
    DESCRIPTION
        "
        Fld OID Name:   avCmMeasIpVoStatSumPkLosYestRegion
        Fld OID:        enterprises.6889.2.73.8.1.73.1.1.4
        Fld Form/Rpt:   IP VOICE STATISTICS SUMMARY PKTLOSS REPORT
        Fld Format:     Single Field
        Fld(s) Name:    List Command: Region
        Fld Descr:      An object that contains the Network Region.
        "
    ::= { avCmMeasIpVoStatSumPkLosYestEntry 4 }

avCmMeasIpVoStatSumPkLosYestMeasHour	OBJECT-TYPE
    SYNTAX      Integer32 (0..2300)
    MAX-ACCESS	read-only
    STATUS	current
    DESCRIPTION
	"
	Fld OID Name:	avCmMeasIpVoStatSumPkLosYestMeasHour
	Fld OID:	enterprises.6889.2.73.8.1.73.1.1.5
	Fld Form/Rpt:	IP VOICE STATISTICS SUMMARY PKTLOSS REPORT
	Fld Format:	Single
	Fld(s) Name:	Measurement Hour
	Fld Descr:	An object containing the measurement hour.
	"
    ::= { avCmMeasIpVoStatSumPkLosYestEntry 5 }

avCmMeasIpVoStatSumPkLosYestRunTime	OBJECT-TYPE
    SYNTAX	SnmpAdminString (SIZE (0..28))
    MAX-ACCESS	read-only
    STATUS	current
    DESCRIPTION
	"
	Fld OID Name:	avCmMeasIpVoStatSumPkLosYestRunTime
	Fld OID:	enterprises.6889.2.73.8.1.73.1.1.6
	Fld Form/Rpt:	IP VOICE STATISTICS SUMMARY PKTLOSS REPORT
	Fld Format:	Single
	Fld(s) Name:	Date
	Fld Descr:	An object containing the Date.
	"
    ::= { avCmMeasIpVoStatSumPkLosYestEntry 6 }

avCmMeasIpVoStatSumPkLosYestBoardLoc	OBJECT-TYPE
    SYNTAX	SnmpAdminString (SIZE (0..6))
    MAX-ACCESS	read-only
    STATUS	current
    DESCRIPTION
	"
	Fld OID Name:	avCmMeasIpVoStatSumPkLosYestBoardLoc
	Fld OID:	enterprises.6889.2.73.8.1.73.1.1.7
	Fld Form/Rpt:	IP VOICE STATISTICS SUMMARY PKTLOSS REPORT
	Fld Format:	Single
	Fld(s) Name:	Board Loc
	Fld Descr:	An object containing the Board location.
	"
    ::= { avCmMeasIpVoStatSumPkLosYestEntry 7 }

avCmMeasIpVoStatSumPkLosYestCallingNum	OBJECT-TYPE
    SYNTAX	SnmpAdminString (SIZE (0..17))
    MAX-ACCESS	read-only
    STATUS	current
    DESCRIPTION
	"
	Fld OID Name:	avCmMeasIpVoStatSumPkLosYestCallingNum
	Fld OID:	enterprises.6889.2.73.8.1.73.1.1.8
	Fld Form/Rpt:	IP VOICE STATISTICS SUMMARY PKTLOSS REPORT
	Fld Format:	Single
	Fld(s) Name:	Calling Number
	Fld Descr:	An object containing the Calling Number.
	"
    ::= { avCmMeasIpVoStatSumPkLosYestEntry 8 }

avCmMeasIpVoStatSumPkLosYestCalledNum      OBJECT-TYPE
    SYNTAX      SnmpAdminString (SIZE (0..17))
    MAX-ACCESS  read-only
    STATUS      current
    DESCRIPTION
        "
        Fld OID Name:   avCmMeasIpVoStatSumPkLosYestCalledNum
        Fld OID:        enterprises.6889.2.73.8.1.73.1.1.9
        Fld Form/Rpt:   IP VOICE STATISTICS SUMMARY PKTLOSS REPORT
        Fld Format:     Single
        Fld(s) Name:    Called Number
        Fld Descr:      An object containing the Called Number.
        "
    ::= { avCmMeasIpVoStatSumPkLosYestEntry 9 }

avCmMeasIpVoStatSumPkLosYestDstReg	OBJECT-TYPE
    SYNTAX      Integer32 (0..9999)
    MAX-ACCESS	read-only
    STATUS	current
    DESCRIPTION
	"
	Fld OID Name:	avCmMeasIpVoStatSumPkLosYestDstReg
	Fld OID:	enterprises.6889.2.73.8.1.73.1.1.10
	Fld Form/Rpt:	IP VOICE STATISTICS SUMMARY PKTLOSS REPORT
	Fld Format:	Single
	Fld(s) Name:	Dst Reg
	Fld Descr:	An object containing the destination region.
	"
    ::= { avCmMeasIpVoStatSumPkLosYestEntry 10 }

avCmMeasIpVoStatSumPkLosYestCodec      OBJECT-TYPE
    SYNTAX      SnmpAdminString (SIZE (0..8))
    MAX-ACCESS  read-only
    STATUS      current
    DESCRIPTION
        "
        Fld OID Name:   avCmMeasIpVoStatSumPkLosYestCodec
        Fld OID:        enterprises.6889.2.73.8.1.73.1.1.11
        Fld Form/Rpt:   IP VOICE STATISTICS SUMMARY PKTLOSS REPORT
        Fld Format:     Single
        Fld(s) Name:    Codec
        Fld Descr:      An object containing the Codec.
        "
    ::= { avCmMeasIpVoStatSumPkLosYestEntry 11 }


avCmMeasIpVoStatSumPkLosYestTimeCall      OBJECT-TYPE
    SYNTAX      SnmpAdminString (SIZE (0..5))
    MAX-ACCESS  read-only
    STATUS      current
    DESCRIPTION
        "
        Fld OID Name:   avCmMeasIpVoStatSumPkLosYestTimeCall
        Fld OID:        enterprises.6889.2.73.8.1.73.1.1.12
        Fld Form/Rpt:   IP VOICE STATISTICS SUMMARY PKTLOSS REPORT
        Fld Format:     Single
        Fld(s) Name:    Time of Call
        Fld Descr:      A time stamp when threshold was first
			exceeded for the associated call, shown in MMSS 
			(minutes seconds).
        "
    ::= { avCmMeasIpVoStatSumPkLosYestEntry 12 }


avCmMeasIpVoStatSumPkLosYestUDPPort      OBJECT-TYPE
    SYNTAX      SnmpAdminString (SIZE (0..6))
    MAX-ACCESS  read-only
    STATUS      current
    DESCRIPTION
        "
        Fld OID Name:   avCmMeasIpVoStatSumPkLosYestUDPPort
        Fld OID:        enterprises.6889.2.73.8.1.73.1.1.13
        Fld Form/Rpt:   IP VOICE STATISTICS SUMMARY PKTLOSS REPORT
        Fld Format:     Single
        Fld(s) Name:    UDP Port
        Fld Descr:      The UDP port used by the media processor
			for this call.
        "
    ::= { avCmMeasIpVoStatSumPkLosYestEntry 13 }


avCmMeasIpVoStatSumPkLosYestPktSize      OBJECT-TYPE
    SYNTAX      Integer32 (0..999)
    MAX-ACCESS  read-only
    STATUS      current
    DESCRIPTION
        "
        Fld OID Name:   avCmMeasIpVoStatSumPkLosYestPktSize
        Fld OID:        enterprises.6889.2.73.8.1.73.1.1.14
        Fld Form/Rpt:   IP VOICE STATISTICS SUMMARY PKTLOSS REPORT
        Fld Format:     Single
        Fld(s) Name:    Pkt Size
        Fld Descr:      The packet size for each steam of data for
			the associated call, measured in milliseconds.
        "
    ::= { avCmMeasIpVoStatSumPkLosYestEntry 14 }

avCmMeasIpVoStatSumPkLosYestTotnumLosPkts      OBJECT-TYPE
    SYNTAX      Integer32 (0..9999)
    MAX-ACCESS  read-only
    STATUS      current
    DESCRIPTION
        "
        Fld OID Name:   avCmMeasIpVoStatSumPkLosYestTotnumLosPkts
        Fld OID:        enterprises.6889.2.73.8.1.73.1.1.15
        Fld Form/Rpt:   IP VOICE STATISTICS SUMMARY PKTLOSS REPORT
        Fld Format:     Single
        Fld(s) Name:    Total #lost Pkts
        Fld Descr:      An object containing the total number of lost packets				for the call.
        "
    ::= { avCmMeasIpVoStatSumPkLosYestEntry 15 }


avCmMeasIpVoStatSumPkLosYestPktLossPerc      OBJECT-TYPE
    SYNTAX      SnmpAdminString (SIZE (0..3))
    MAX-ACCESS  read-only
    STATUS      current
    DESCRIPTION
        "
        Fld OID Name:   avCmMeasIpVoStatSumPkLosPktYestLossPerc
        Fld OID:        enterprises.6889.2.73.8.1.73.1.1.16
        Fld Form/Rpt:   IP VOICE STATISTICS SUMMARY PKTLOSS REPORT
        Fld Format:     Single
        Fld(s) Name:    Packet loss %
        Fld Descr:      The peak packet loss for the call. The packet
			loss percentage is calculated at 10-second
			intervals.
        "
    ::= { avCmMeasIpVoStatSumPkLosYestEntry 16 }

avCmMeasIpVoStatSumPkLosYestSilSup      OBJECT-TYPE
    SYNTAX      SnmpAdminString (SIZE (0..2))
    MAX-ACCESS  read-only
    STATUS      current
    DESCRIPTION
        "
        Fld OID Name:   avCmMeasIpVoStatSumPkLosYestSilSup
        Fld OID:        enterprises.6889.2.73.8.1.73.1.1.17
        Fld Form/Rpt:   IP VOICE STATISTICS SUMMARY PKTLOSS REPORT
        Fld Format:     Single
        Fld(s) Name:    Sil Sup
        Fld Descr:      Indicates whether the silence suppression
			was used for the call.
        "
    ::= { avCmMeasIpVoStatSumPkLosYestEntry 17 }

avCmMeasIpVoStatSumPkLosYestFEAddr      OBJECT-TYPE
    SYNTAX      SnmpAdminString (SIZE (0..41))
    MAX-ACCESS  read-only
    STATUS      current
    DESCRIPTION
        "
        Fld OID Name:   avCmMeasIpVoStatSumPkLosYestFEAddr
        Fld OID:        enterprises.6889.2.73.8.1.73.1.1.18
        Fld Form/Rpt:   IP VOICE STATISTICS SUMMARY PKTLOSS REPORT
        Fld Format:     Single
        Fld(s) Name:    FEAddr
        Fld Descr:      An object containing the far-end ip-address.
        "
    ::= { avCmMeasIpVoStatSumPkLosYestEntry 18 }

--   *********** avCmMeasIpVoStatSumRtdelLstHr Group **************
-- MIB Group Name:
--		avCmMeasIpVoStatSumRtdelLstHr
-- OID:
--		enterprises.6889.2.73.8.1.74
-- Description:
--		The avCmMeasIpVoStatSumRtdelLstHr MIB group displays the 
--		output of the list measurements ip voice-stats  summary rtdelay
--		last-hour command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary rtdelay last-hour
-- Form/Report Name:
--		1. IP VOICE STATISTICS NETWORK REGION RTDELAY REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumRtdelLstHr	OBJECT IDENTIFIER ::= { avCmObjects 74 }

avCmMeasIpVoStatSumRtdelLstHrTable	OBJECT-TYPE
    SYNTAX	SEQUENCE OF AvCmMeasIpVoStatSumRtdelLstHrEntry
    MAX-ACCESS	not-accessible
    STATUS	current
    DESCRIPTION
	"
	Fld OID Name:	avCmMeasIpVoStatSumRtdelLstHrTable
	Fld OID:	enterprises.6889.2.73.8.1.74.1
	Fld Form/Rpt:	NA
	Fld Format:	NA
	Fld(s) Name:	NA
	Fld Descr:	A list of the AvCmMeasIpVoStatSumRtdelLstHr entries.
	"
    ::= { avCmMeasIpVoStatSumRtdelLstHr 1 }

avCmMeasIpVoStatSumRtdelLstHrEntry	OBJECT-TYPE
    SYNTAX	AvCmMeasIpVoStatSumRtdelLstHrEntry
    MAX-ACCESS	not-accessible
    STATUS	current
    DESCRIPTION
	"
	Fld OID Name:	avCmMeasIpVoStatSumRtdelLstHrEntry
	Fld OID:	enterprises.6889.2.73.8.1.74.1.1
	Fld Form/Rpt:	NA
	Fld Format:	NA
	Fld(s) Name:	NA
	Fld Descr:	A avCmMeasIpVoStatSumRtdelLstHr entry containing 
			objects of the avCmMeasIpVoStatSumRtdelLstHr 
			information sent by the switch.
	"
    INDEX    { avCmMeasIpVoStatSumRtdelLstHrRegIdx, 
				avCmMeasIpVoStatSumRtdelLstHrHourIdx,
					avCmMeasIpVoStatSumRtdelLstHrIdx }
    ::= { avCmMeasIpVoStatSumRtdelLstHrTable 1 }

AvCmMeasIpVoStatSumRtdelLstHrEntry ::= SEQUENCE {
		avCmMeasIpVoStatSumRtdelLstHrRegIdx
		    Integer32,
                avCmMeasIpVoStatSumRtdelLstHrHourIdx
                    Integer32,
                avCmMeasIpVoStatSumRtdelLstHrIdx
                    Integer32,
                avCmMeasIpVoStatSumRtdelLstHrRegion
                    Integer32,
                avCmMeasIpVoStatSumRtdelLstHrMeasHour
                    Integer32,
                avCmMeasIpVoStatSumRtdelLstHrRunTime
                    SnmpAdminString,
                avCmMeasIpVoStatSumRtdelLstHrBoardLoc
                    SnmpAdminString,
                avCmMeasIpVoStatSumRtdelLstHrCallingNum
                    SnmpAdminString,
                avCmMeasIpVoStatSumRtdelLstHrCalledNum
                    SnmpAdminString,
                avCmMeasIpVoStatSumRtdelLstHrPktSize
                    Integer32,
                avCmMeasIpVoStatSumRtdelLstHrDstReg
                    Integer32,
                avCmMeasIpVoStatSumRtdelLstHrCodec
                    SnmpAdminString,
                avCmMeasIpVoStatSumRtdelLstHrAvg
                    Integer32,
                avCmMeasIpVoStatSumRtdelLstHrPeak
                    Integer32,
                avCmMeasIpVoStatSumRtdelLstHrTimeCall
                    SnmpAdminString,
                avCmMeasIpVoStatSumRtdelLstHrDataCall
                    SnmpAdminString,
                avCmMeasIpVoStatSumRtdelLstHrEncryp
                    SnmpAdminString,
                avCmMeasIpVoStatSumRtdelLstHrEC
                    SnmpAdminString,
                avCmMeasIpVoStatSumRtdelLstHrFEAddr
                    SnmpAdminString
		}

avCmMeasIpVoStatSumRtdelLstHrRegIdx	OBJECT-TYPE
    SYNTAX	Integer32 (1..2000)
    MAX-ACCESS	not-accessible
    STATUS	current
    DESCRIPTION
	"
	Fld OID Name:	avCmMeasIpVoStatSumRtdelLstHrRegIdx
	Fld OID:	enterprises.6889.2.73.8.1.74.1.1.1
	Fld Form/Rpt:	NA
	Fld Format:	NA
	Fld(s) Name:	NA
	Fld Descr:	An index into the network region.
	"
    ::= { avCmMeasIpVoStatSumRtdelLstHrEntry 1 }

avCmMeasIpVoStatSumRtdelLstHrHourIdx        OBJECT-TYPE
    SYNTAX      Integer32 (0..2300)
    MAX-ACCESS	not-accessible
    STATUS      current
    DESCRIPTION
        "
        Fld OID Name:   avCmMeasIpVoStatSumRtdelLstHrHourIdx
        Fld OID:        enterprises.6889.2.73.8.1.74.1.1.2
        Fld Form/Rpt:   NA
        Fld Format:     NA
        Fld(s) Name:    NA
        Fld Descr:      An index that contains the measurement hour in military
			time for the packet loss voice statistics.
        "
    ::= { avCmMeasIpVoStatSumRtdelLstHrEntry 2 }

avCmMeasIpVoStatSumRtdelLstHrIdx        OBJECT-TYPE
    SYNTAX      Integer32 (0..9999)
    MAX-ACCESS  not-accessible
    STATUS      current
    DESCRIPTION
        "
        Fld OID Name:   avCmMeasIpVoStatSumRtdelLstHrIdx
        Fld OID:        enterprises.6889.2.73.8.1.74.1.1.3
        Fld Form/Rpt:   NA
        Fld Format:     NA
        Fld(s) Name:    NA
        Fld Descr:      An index that contains the measurement hour in military
                        time for the packet loss voice statistics.
        "
    ::= { avCmMeasIpVoStatSumRtdelLstHrEntry 3 }


avCmMeasIpVoStatSumRtdelLstHrRegion        OBJECT-TYPE
    SYNTAX      Integer32 (0..2000)
    MAX-ACCESS  read-only
    STATUS      current
    DESCRIPTION
        "
        Fld OID Name:   avCmMeasIpVoStatSumRtdelLstHrRegion
        Fld OID:        enterprises.6889.2.73.8.1.74.1.1.4
        Fld Form/Rpt:   IP VOICE STATISTICS NETWORK REGION RTDELAY REPORT
        Fld Format:     Single Field
        Fld(s) Name:    List Command: Region
        Fld Descr:      An object that contains the Network Region.
        "
    ::= { avCmMeasIpVoStatSumRtdelLstHrEntry 4 }

avCmMeasIpVoStatSumRtdelLstHrMeasHour	OBJECT-TYPE
    SYNTAX      Integer32 (0..2300)
    MAX-ACCESS	read-only
    STATUS	current
    DESCRIPTION
	"
	Fld OID Name:	avCmMeasIpVoStatSumRtdelLstHrMeasHour
	Fld OID:	enterprises.6889.2.73.8.1.74.1.1.5
	Fld Form/Rpt:	IP VOICE STATISTICS NETWORK REGION RTDELAY REPORT
	Fld Format:	Single
	Fld(s) Name:	Measurement Hour
	Fld Descr:	An object containing the measurement hour.
	"
    ::= { avCmMeasIpVoStatSumRtdelLstHrEntry 5 }

avCmMeasIpVoStatSumRtdelLstHrRunTime	OBJECT-TYPE
    SYNTAX	SnmpAdminString (SIZE (0..28))
    MAX-ACCESS	read-only
    STATUS	current
    DESCRIPTION
	"
	Fld OID Name:	avCmMeasIpVoStatSumRtdelLstHrRunTime
	Fld OID:	enterprises.6889.2.73.8.1.74.1.1.6
	Fld Form/Rpt:	IP VOICE STATISTICS NETWORK REGION RTDELAY REPORT
	Fld Format:	Single
	Fld(s) Name:	Date
	Fld Descr:	An object containing the Date.
	"
    ::= { avCmMeasIpVoStatSumRtdelLstHrEntry 6 }

avCmMeasIpVoStatSumRtdelLstHrBoardLoc	OBJECT-TYPE
    SYNTAX	SnmpAdminString (SIZE (0..6))
    MAX-ACCESS	read-only
    STATUS	current
    DESCRIPTION
	"
	Fld OID Name:	avCmMeasIpVoStatSumRtdelLstHrBoardLoc
	Fld OID:	enterprises.6889.2.73.8.1.74.1.1.7
	Fld Form/Rpt:	IP VOICE STATISTICS NETWORK REGION RTDELAY REPORT
	Fld Format:	Single
	Fld(s) Name:	Board Loc
	Fld Descr:	An object containing the Board location.
	"
    ::= { avCmMeasIpVoStatSumRtdelLstHrEntry 7 }

avCmMeasIpVoStatSumRtdelLstHrCallingNum	OBJECT-TYPE
    SYNTAX	SnmpAdminString (SIZE (0..17))
    MAX-ACCESS	read-only
    STATUS	current
    DESCRIPTION
	"
	Fld OID Name:	avCmMeasIpVoStatSumRtdelLstHrCallingNum
	Fld OID:	enterprises.6889.2.73.8.1.74.1.1.8
	Fld Form/Rpt:	IP VOICE STATISTICS NETWORK REGION RTDELAY REPORT
	Fld Format:	Single
	Fld(s) Name:	Calling Number
	Fld Descr:	An object containing the Calling Number.
	"
    ::= { avCmMeasIpVoStatSumRtdelLstHrEntry 8 }

avCmMeasIpVoStatSumRtdelLstHrCalledNum      OBJECT-TYPE
    SYNTAX      SnmpAdminString (SIZE (0..17))
    MAX-ACCESS  read-only
    STATUS      current
    DESCRIPTION
        "
        Fld OID Name:   avCmMeasIpVoStatSumRtdelLstHrCalledNum
        Fld OID:        enterprises.6889.2.73.8.1.74.1.1.9
        Fld Form/Rpt:   IP VOICE STATISTICS NETWORK REGION RTDELAY REPORT
        Fld Format:     Single
        Fld(s) Name:    Called Number
        Fld Descr:      An object containing the Called Number.
        "
    ::= { avCmMeasIpVoStatSumRtdelLstHrEntry 9 }

avCmMeasIpVoStatSumRtdelLstHrPktSize      OBJECT-TYPE
    SYNTAX      Integer32 (0..999)
    MAX-ACCESS  read-only
    STATUS      current
    DESCRIPTION
        "
        Fld OID Name:   avCmMeasIpVoStatSumRtdelLstHrPktSize
        Fld OID:        enterprises.6889.2.73.8.1.74.1.1.10
        Fld Form/Rpt:   IP VOICE STATISTICS NETWORK REGION RTDELAY REPORT
        Fld Format:     Single
        Fld(s) Name:    Pkt Size
        Fld Descr:      The packet size for each steam of data for
			the associated call, measured in milliseconds.
        "
    ::= { avCmMeasIpVoStatSumRtdelLstHrEntry 10 }


avCmMeasIpVoStatSumRtdelLstHrDstReg      OBJECT-TYPE
    SYNTAX      Integer32 (0..9999)
    MAX-ACCESS  read-only
    STATUS      current
    DESCRIPTION
        "
        Fld OID Name:   avCmMeasIpVoStatSumRtdelLstHrDstReg
        Fld OID:        enterprises.6889.2.73.8.1.74.1.1.11
        Fld Form/Rpt:   IP VOICE STATISTICS NETWORK REGION RTDELAY REPORT
        Fld Format:     Single
        Fld(s) Name:    Dst Reg
        Fld Descr:      The network region where the destination
			media processor is located.
        "
    ::= { avCmMeasIpVoStatSumRtdelLstHrEntry 11 }

avCmMeasIpVoStatSumRtdelLstHrCodec      OBJECT-TYPE
    SYNTAX      SnmpAdminString (SIZE (0..8))
    MAX-ACCESS  read-only
    STATUS      current
    DESCRIPTION
        "
        Fld OID Name:   avCmMeasIpVoStatSumRtdelLstHrCodec
        Fld OID:        enterprises.6889.2.73.8.1.74.1.1.12
        Fld Form/Rpt:   IP VOICE STATISTICS NETWORK REGION RTDELAY REPORT
        Fld Format:     Single
        Fld(s) Name:    Codec
        Fld Descr:      An object containing the Codec used for the call.
        "
    ::= { avCmMeasIpVoStatSumRtdelLstHrEntry 12 }

avCmMeasIpVoStatSumRtdelLstHrAvg      OBJECT-TYPE
    SYNTAX      Integer32 (0..9999)
    MAX-ACCESS  read-only
    STATUS      current
    DESCRIPTION
        "
        Fld OID Name:   avCmMeasIpVoStatSumRtdelLstHrAvg
        Fld OID:        enterprises.6889.2.73.8.1.74.1.1.13
        Fld Form/Rpt:   IP VOICE STATISTICS NETWORK REGION RTDELAY REPORT
        Fld Format:     Single
        Fld(s) Name:    RT-Delay Avg
        Fld Descr:      The average round trip delay of packets,
			measured in milliseconds.
			
        "
    ::= { avCmMeasIpVoStatSumRtdelLstHrEntry 13 }

avCmMeasIpVoStatSumRtdelLstHrPeak      OBJECT-TYPE
    SYNTAX      Integer32 (0..9999)
    MAX-ACCESS  read-only
    STATUS      current
    DESCRIPTION
        "
        Fld OID Name:   avCmMeasIpVoStatSumRtdelLstHrPeak
        Fld OID:        enterprises.6889.2.73.8.1.74.1.1.14
        Fld Form/Rpt:   IP VOICE STATISTICS NETWORK REGION RTDELAY REPORT
        Fld Format:     Single
        Fld(s) Name:    RT-Delay Peak
        Fld Descr:      The peak round trip delay recorded for the call.
        "
    ::= { avCmMeasIpVoStatSumRtdelLstHrEntry 14 }

avCmMeasIpVoStatSumRtdelLstHrTimeCall      OBJECT-TYPE
    SYNTAX      SnmpAdminString (SIZE (0..5))
    MAX-ACCESS  read-only
    STATUS      current
    DESCRIPTION
        "
        Fld OID Name:   avCmMeasIpVoStatSumRtdelLstHrTimeCall
        Fld OID:        enterprises.6889.2.73.8.1.74.1.1.15
        Fld Form/Rpt:   IP VOICE STATISTICS NETWORK REGION RTDELAY REPORT
        Fld Format:     Single
        Fld(s) Name:    Time of Call
        Fld Descr:      A time stamp when threshold was first
			exceeded for the associated call, shown in MMSS 
			(minutes seconds).
        "
    ::= { avCmMeasIpVoStatSumRtdelLstHrEntry 15 }


avCmMeasIpVoStatSumRtdelLstHrDataCall      OBJECT-TYPE
    SYNTAX      SnmpAdminString (SIZE (0..2))
    MAX-ACCESS  read-only
    STATUS      current
    DESCRIPTION
        "
        Fld OID Name:   avCmMeasIpVoStatSumRtdelLstHrDataCall
        Fld OID:        enterprises.6889.2.73.8.1.74.1.1.16
        Fld Form/Rpt:   IP VOICE STATISTICS NETWORK REGION RTDELAY REPORT
        Fld Format:     Single
        Fld(s) Name:    Data Call
        Fld Descr:      Indicates whether the call is a data call.
        "
    ::= { avCmMeasIpVoStatSumRtdelLstHrEntry 16 }

avCmMeasIpVoStatSumRtdelLstHrEncryp      OBJECT-TYPE
    SYNTAX      SnmpAdminString (SIZE (0..2))
    MAX-ACCESS  read-only
    STATUS      current
    DESCRIPTION
        "
        Fld OID Name:   avCmMeasIpVoStatSumRtdelLstHrEncryp
        Fld OID:        enterprises.6889.2.73.8.1.74.1.1.17
        Fld Form/Rpt:   IP VOICE STATISTICS NETWORK REGION RTDELAY REPORT
        Fld Format:     Single
        Fld(s) Name:    Encryp
        Fld Descr:      Indicates whether media encryption was used for the 
			call.
        "
    ::= { avCmMeasIpVoStatSumRtdelLstHrEntry 17 }

avCmMeasIpVoStatSumRtdelLstHrEC      OBJECT-TYPE
    SYNTAX      SnmpAdminString (SIZE (0..2))
    MAX-ACCESS  read-only
    STATUS      current
    DESCRIPTION
        "
        Fld OID Name:   avCmMeasIpVoStatSumRtdelLstHrEncryp
        Fld OID:        enterprises.6889.2.73.8.1.74.1.1.18
        Fld Form/Rpt:   IP VOICE STATISTICS NETWORK REGION RTDELAY REPORT
        Fld Format:     Single
        Fld(s) Name:    EC
        Fld Descr:      Indicates whether the echo cancellation is on/off for 
			the call.
        "
    ::= { avCmMeasIpVoStatSumRtdelLstHrEntry 18 }

avCmMeasIpVoStatSumRtdelLstHrFEAddr      OBJECT-TYPE
    SYNTAX      SnmpAdminString (SIZE (0..41))
    MAX-ACCESS  read-only
    STATUS      current
    DESCRIPTION
        "
        Fld OID Name:   avCmMeasIpVoStatSumRtdelLstHrFEAddr
        Fld OID:        enterprises.6889.2.73.8.1.74.1.1.19
        Fld Form/Rpt:   IP VOICE STATISTICS NETWORK REGION RTDELAY REPORT
        Fld Format:     Single
        Fld(s) Name:    FE-Addr
        Fld Descr:      An object containing the far-end ip-address.
        "
    ::= { avCmMeasIpVoStatSumRtdelLstHrEntry 19 }

--   *********** avCmMeasIpVoStatSumRtdelToday Group **************
-- MIB Group Name:
--		avCmMeasIpVoStatSumRtdelToday
-- OID:
--		enterprises.6889.2.73.8.1.75
-- Description:
--		The avCmMeasIpVoStatSumRtdelToday MIB group displays the 
--		output of the list measurements ip voice-stats  summary rtdelay
--		today command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary rtdelay today
-- Form/Report Name:
--		1. IP VOICE STATISTICS NETWORK REGION RTDELAY REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumRtdelToday	OBJECT IDENTIFIER ::= { avCmObjects 75 }

avCmMeasIpVoStatSumRtdelTodayTable	OBJECT-TYPE
    SYNTAX	SEQUENCE OF AvCmMeasIpVoStatSumRtdelTodayEntry
    MAX-ACCESS	not-accessible
    STATUS	current
    DESCRIPTION
	"
	Fld OID Name:	avCmMeasIpVoStatSumRtdelTodayTable
	Fld OID:	enterprises.6889.2.73.8.1.75.1
	Fld Form/Rpt:	NA
	Fld Format:	NA
	Fld(s) Name:	NA
	Fld Descr:	A list of the AvCmMeasIpVoStatSumRtdelToday entries.
	"
    ::= { avCmMeasIpVoStatSumRtdelToday 1 }

avCmMeasIpVoStatSumRtdelTodayEntry	OBJECT-TYPE
    SYNTAX	AvCmMeasIpVoStatSumRtdelTodayEntry
    MAX-ACCESS	not-accessible
    STATUS	current
    DESCRIPTION
	"
	Fld OID Name:	avCmMeasIpVoStatSumRtdelTodayEntry
	Fld OID:	enterprises.6889.2.73.8.1.75.1.1
	Fld Form/Rpt:	NA
	Fld Format:	NA
	Fld(s) Name:	NA
	Fld Descr:	A avCmMeasIpVoStatSumRtdelToday entry containing objects of 
			the avCmMeasIpVoStatSumRtdelToday information sent by the 
			switch.
	"
    INDEX    { avCmMeasIpVoStatSumRtdelTodayRegIdx, 
				avCmMeasIpVoStatSumRtdelTodayHourIdx,
					avCmMeasIpVoStatSumRtdelTodayIdx }
    ::= { avCmMeasIpVoStatSumRtdelTodayTable 1 }

AvCmMeasIpVoStatSumRtdelTodayEntry ::= SEQUENCE {
		avCmMeasIpVoStatSumRtdelTodayRegIdx
		    Integer32,
                avCmMeasIpVoStatSumRtdelTodayHourIdx
                    Integer32,
                avCmMeasIpVoStatSumRtdelTodayIdx
                    Integer32,
                avCmMeasIpVoStatSumRtdelTodayRegion
                    Integer32,
                avCmMeasIpVoStatSumRtdelTodayMeasHour
                    Integer32,
                avCmMeasIpVoStatSumRtdelTodayRunTime
                    SnmpAdminString,
                avCmMeasIpVoStatSumRtdelTodayBoardLoc
                    SnmpAdminString,
                avCmMeasIpVoStatSumRtdelTodayCallingNum
                    SnmpAdminString,
                avCmMeasIpVoStatSumRtdelTodayCalledNum
                    SnmpAdminString,
                avCmMeasIpVoStatSumRtdelTodayPktSize
                    Integer32,
                avCmMeasIpVoStatSumRtdelTodayDstReg
                    Integer32,
                avCmMeasIpVoStatSumRtdelTodayCodec
                    SnmpAdminString,
                avCmMeasIpVoStatSumRtdelTodayAvg
                    Integer32,
                avCmMeasIpVoStatSumRtdelTodayPeak
                    Integer32,
                avCmMeasIpVoStatSumRtdelTodayTimeCall
                    SnmpAdminString,
                avCmMeasIpVoStatSumRtdelTodayDataCall
                    SnmpAdminString,
                avCmMeasIpVoStatSumRtdelTodayEncryp
                    SnmpAdminString,
                avCmMeasIpVoStatSumRtdelTodayEC
                    SnmpAdminString,
                avCmMeasIpVoStatSumRtdelTodayFEAddr
                    SnmpAdminString
		}

avCmMeasIpVoStatSumRtdelTodayRegIdx	OBJECT-TYPE
    SYNTAX	Integer32 (1..2000)
    MAX-ACCESS	not-accessible
    STATUS	current
    DESCRIPTION
	"
	Fld OID Name:	avCmMeasIpVoStatSumRtdelTodayRegIdx
	Fld OID:	enterprises.6889.2.73.8.1.75.1.1.1
	Fld Form/Rpt:	NA
	Fld Format:	NA
	Fld(s) Name:	NA
	Fld Descr:	An index into the network region.
	"
    ::= { avCmMeasIpVoStatSumRtdelTodayEntry 1 }

avCmMeasIpVoStatSumRtdelTodayHourIdx        OBJECT-TYPE
    SYNTAX      Integer32 (0..2300)
    MAX-ACCESS	not-accessible
    STATUS      current
    DESCRIPTION
        "
        Fld OID Name:   avCmMeasIpVoStatSumRtdelTodayHourIdx
        Fld OID:        enterprises.6889.2.73.8.1.75.1.1.2
        Fld Form/Rpt:   NA
        Fld Format:     NA
        Fld(s) Name:    NA
        Fld Descr:      An index that contains the measurement hour in military
			time for the packet loss voice statistics.
        "
    ::= { avCmMeasIpVoStatSumRtdelTodayEntry 2 }

avCmMeasIpVoStatSumRtdelTodayIdx        OBJECT-TYPE
    SYNTAX      Integer32 (0..9999)
    MAX-ACCESS  not-accessible
    STATUS      current
    DESCRIPTION
        "
        Fld OID Name:   avCmMeasIpVoStatSumRtdelTodayIdx
        Fld OID:        enterprises.6889.2.73.8.1.75.1.1.3
        Fld Form/Rpt:   NA
        Fld Format:     NA
        Fld(s) Name:    NA
        Fld Descr:      A unique index for packet loss voice statistics.
        "
    ::= { avCmMeasIpVoStatSumRtdelTodayEntry 3 }


avCmMeasIpVoStatSumRtdelTodayRegion        OBJECT-TYPE
    SYNTAX      Integer32 (0..2000)
    MAX-ACCESS  read-only
    STATUS      current
    DESCRIPTION
        "
        Fld OID Name:   avCmMeasIpVoStatSumRtdelTodayRegion
        Fld OID:        enterprises.6889.2.73.8.1.75.1.1.4
        Fld Form/Rpt:   IP VOICE STATISTICS NETWORK REGION RTDELAY REPORT
        Fld Format:     Single Field
        Fld(s) Name:    List Command: Region
        Fld Descr:      An object that contains the Network Region.
        "
    ::= { avCmMeasIpVoStatSumRtdelTodayEntry 4 }

avCmMeasIpVoStatSumRtdelTodayMeasHour	OBJECT-TYPE
    SYNTAX      Integer32 (0..2300)
    MAX-ACCESS	read-only
    STATUS	current
    DESCRIPTION
	"
	Fld OID Name:	avCmMeasIpVoStatSumRtdelTodayMeasHour
	Fld OID:	enterprises.6889.2.73.8.1.75.1.1.5
	Fld Form/Rpt:	IP VOICE STATISTICS NETWORK REGION RTDELAY REPORT
	Fld Format:	Single
	Fld(s) Name:	Measurement Hour
	Fld Descr:	An object containing the measurement hour.
	"
    ::= { avCmMeasIpVoStatSumRtdelTodayEntry 5 }

avCmMeasIpVoStatSumRtdelTodayRunTime	OBJECT-TYPE
    SYNTAX	SnmpAdminString (SIZE (0..28))
    MAX-ACCESS	read-only
    STATUS	current
    DESCRIPTION
	"
	Fld OID Name:	avCmMeasIpVoStatSumRtdelTodayRunTime
	Fld OID:	enterprises.6889.2.73.8.1.75.1.1.6
	Fld Form/Rpt:	IP VOICE STATISTICS NETWORK REGION RTDELAY REPORT
	Fld Format:	Single
	Fld(s) Name:	Date
	Fld Descr:	An object containing the Date.
	"
    ::= { avCmMeasIpVoStatSumRtdelTodayEntry 6 }

avCmMeasIpVoStatSumRtdelTodayBoardLoc	OBJECT-TYPE
    SYNTAX	SnmpAdminString (SIZE (0..6))
    MAX-ACCESS	read-only
    STATUS	current
    DESCRIPTION
	"
	Fld OID Name:	avCmMeasIpVoStatSumRtdelTodayBoardLoc
	Fld OID:	enterprises.6889.2.73.8.1.75.1.1.7
	Fld Form/Rpt:	IP VOICE STATISTICS NETWORK REGION RTDELAY REPORT
	Fld Format:	Single
	Fld(s) Name:	Board Loc
	Fld Descr:	An object containing the Board location.
	"
    ::= { avCmMeasIpVoStatSumRtdelTodayEntry 7 }

avCmMeasIpVoStatSumRtdelTodayCallingNum	OBJECT-TYPE
    SYNTAX	SnmpAdminString (SIZE (0..17))
    MAX-ACCESS	read-only
    STATUS	current
    DESCRIPTION
	"
	Fld OID Name:	avCmMeasIpVoStatSumRtdelTodayCallingNum
	Fld OID:	enterprises.6889.2.73.8.1.75.1.1.8
	Fld Form/Rpt:	IP VOICE STATISTICS NETWORK REGION RTDELAY REPORT
	Fld Format:	Single
	Fld(s) Name:	Calling Number
	Fld Descr:	An object containing the Calling Number.
	"
    ::= { avCmMeasIpVoStatSumRtdelTodayEntry 8 }

avCmMeasIpVoStatSumRtdelTodayCalledNum      OBJECT-TYPE
    SYNTAX      SnmpAdminString (SIZE (0..17))
    MAX-ACCESS  read-only
    STATUS      current
    DESCRIPTION
        "
        Fld OID Name:   avCmMeasIpVoStatSumRtdelTodayCalledNum
        Fld OID:        enterprises.6889.2.73.8.1.75.1.1.9
        Fld Form/Rpt:   IP VOICE STATISTICS NETWORK REGION RTDELAY REPORT
        Fld Format:     Single
        Fld(s) Name:    Called Number
        Fld Descr:      An object containing the Called Number.
        "
    ::= { avCmMeasIpVoStatSumRtdelTodayEntry 9 }

avCmMeasIpVoStatSumRtdelTodayPktSize      OBJECT-TYPE
    SYNTAX      Integer32 (0..999)
    MAX-ACCESS  read-only
    STATUS      current
    DESCRIPTION
        "
        Fld OID Name:   avCmMeasIpVoStatSumRtdelTodayPktSize
        Fld OID:        enterprises.6889.2.73.8.1.75.1.1.10
        Fld Form/Rpt:   IP VOICE STATISTICS NETWORK REGION RTDELAY REPORT
        Fld Format:     Single
        Fld(s) Name:    Pkt Size
        Fld Descr:      The packet size for each steam of data for
			the associated call, measured in milliseconds.
        "
    ::= { avCmMeasIpVoStatSumRtdelTodayEntry 10 }


avCmMeasIpVoStatSumRtdelTodayDstReg      OBJECT-TYPE
    SYNTAX      Integer32 (0..9999)
    MAX-ACCESS  read-only
    STATUS      current
    DESCRIPTION
        "
        Fld OID Name:   avCmMeasIpVoStatSumRtdelTodayDstReg
        Fld OID:        enterprises.6889.2.73.8.1.75.1.1.11
        Fld Form/Rpt:   IP VOICE STATISTICS NETWORK REGION RTDELAY REPORT
        Fld Format:     Single
        Fld(s) Name:    Dst Reg
        Fld Descr:      The network region where the destination
			media processor is located.
        "
    ::= { avCmMeasIpVoStatSumRtdelTodayEntry 11 }

avCmMeasIpVoStatSumRtdelTodayCodec      OBJECT-TYPE
    SYNTAX      SnmpAdminString (SIZE (0..8))
    MAX-ACCESS  read-only
    STATUS      current
    DESCRIPTION
        "
        Fld OID Name:   avCmMeasIpVoStatSumRtdelTodayCodec
        Fld OID:        enterprises.6889.2.73.8.1.75.1.1.12
        Fld Form/Rpt:   IP VOICE STATISTICS NETWORK REGION RTDELAY REPORT
        Fld Format:     Single
        Fld(s) Name:    Codec
        Fld Descr:      An object containing the Codec used for the call.
        "
    ::= { avCmMeasIpVoStatSumRtdelTodayEntry 12 }

avCmMeasIpVoStatSumRtdelTodayAvg      OBJECT-TYPE
    SYNTAX      Integer32 (0..9999)
    MAX-ACCESS  read-only
    STATUS      current
    DESCRIPTION
        "
        Fld OID Name:   avCmMeasIpVoStatSumRtdelTodayAvg
        Fld OID:        enterprises.6889.2.73.8.1.75.1.1.13
        Fld Form/Rpt:   IP VOICE STATISTICS NETWORK REGION RTDELAY REPORT
        Fld Format:     Single
        Fld(s) Name:    RT-Delay Avg
        Fld Descr:      The average round trip delay of packets,
			measured in milliseconds.
			
        "
    ::= { avCmMeasIpVoStatSumRtdelTodayEntry 13 }

avCmMeasIpVoStatSumRtdelTodayPeak      OBJECT-TYPE
    SYNTAX      Integer32 (0..9999)
    MAX-ACCESS  read-only
    STATUS      current
    DESCRIPTION
        "
        Fld OID Name:   avCmMeasIpVoStatSumRtdelTodayPeak
        Fld OID:        enterprises.6889.2.73.8.1.75.1.1.14
        Fld Form/Rpt:   IP VOICE STATISTICS NETWORK REGION RTDELAY REPORT
        Fld Format:     Single
        Fld(s) Name:    RT-Delay Peak
        Fld Descr:      The peak round trip delay recorded for the call.
        "
    ::= { avCmMeasIpVoStatSumRtdelTodayEntry 14 }

avCmMeasIpVoStatSumRtdelTodayTimeCall      OBJECT-TYPE
    SYNTAX      SnmpAdminString (SIZE (0..5))
    MAX-ACCESS  read-only
    STATUS      current
    DESCRIPTION
        "
        Fld OID Name:   avCmMeasIpVoStatSumRtdelTodayTimeCall
        Fld OID:        enterprises.6889.2.73.8.1.75.1.1.15
        Fld Form/Rpt:   IP VOICE STATISTICS NETWORK REGION RTDELAY REPORT
        Fld Format:     Single
        Fld(s) Name:    Time of Call
        Fld Descr:      A time stamp when threshold was first
			exceeded for the associated call, shown in MMSS 
			(minutes seconds).
        "
    ::= { avCmMeasIpVoStatSumRtdelTodayEntry 15 }


avCmMeasIpVoStatSumRtdelTodayDataCall      OBJECT-TYPE
    SYNTAX      SnmpAdminString (SIZE (0..2))
    MAX-ACCESS  read-only
    STATUS      current
    DESCRIPTION
        "
        Fld OID Name:   avCmMeasIpVoStatSumRtdelTodayDataCall
        Fld OID:        enterprises.6889.2.73.8.1.75.1.1.16
        Fld Form/Rpt:   IP VOICE STATISTICS NETWORK REGION RTDELAY REPORT
        Fld Format:     Single
        Fld(s) Name:    Data Call
        Fld Descr:      Indicates whether the call is a data call.
        "
    ::= { avCmMeasIpVoStatSumRtdelTodayEntry 16 }

avCmMeasIpVoStatSumRtdelTodayEncryp      OBJECT-TYPE
    SYNTAX      SnmpAdminString (SIZE (0..2))
    MAX-ACCESS  read-only
    STATUS      current
    DESCRIPTION
        "
        Fld OID Name:   avCmMeasIpVoStatSumRtdelTodayEncryp
        Fld OID:        enterprises.6889.2.73.8.1.75.1.1.17
        Fld Form/Rpt:   IP VOICE STATISTICS NETWORK REGION RTDELAY REPORT
        Fld Format:     Single
        Fld(s) Name:    Encryp
        Fld Descr:      Indicates whether media encryption was used for the 
			call.
        "
    ::= { avCmMeasIpVoStatSumRtdelTodayEntry 17 }

avCmMeasIpVoStatSumRtdelTodayEC      OBJECT-TYPE
    SYNTAX      SnmpAdminString (SIZE (0..2))
    MAX-ACCESS  read-only
    STATUS      current
    DESCRIPTION
        "
        Fld OID Name:   avCmMeasIpVoStatSumRtdelTodayEncryp
        Fld OID:        enterprises.6889.2.73.8.1.75.1.1.18
        Fld Form/Rpt:   IP VOICE STATISTICS NETWORK REGION RTDELAY REPORT
        Fld Format:     Single
        Fld(s) Name:    EC
        Fld Descr:      Indicates whether the echo cancellation is on/off for 
			the call.
        "
    ::= { avCmMeasIpVoStatSumRtdelTodayEntry 18 }

avCmMeasIpVoStatSumRtdelTodayFEAddr      OBJECT-TYPE
    SYNTAX      SnmpAdminString (SIZE (0..41))
    MAX-ACCESS  read-only
    STATUS      current
    DESCRIPTION
        "
        Fld OID Name:   avCmMeasIpVoStatSumRtdelTodayFEAddr
        Fld OID:        enterprises.6889.2.73.8.1.75.1.1.19
        Fld Form/Rpt:   IP VOICE STATISTICS NETWORK REGION RTDELAY REPORT
        Fld Format:     Single
        Fld(s) Name:    FE-Addr
        Fld Descr:      An object containing the far-end ip-address.
        "
    ::= { avCmMeasIpVoStatSumRtdelTodayEntry 19 }


--   *********** avCmMeasIpVoStatSumRtdelYest Group **************
-- MIB Group Name:
--		avCmMeasIpVoStatSumRtdelYest
-- OID:
--		enterprises.6889.2.73.8.1.76
-- Description:
--		The avCmMeasIpVoStatSumRtdelYest MIB group displays the 
--		output of the list measurements ip voice-stats  summary rtdelay
--		yesterday command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary rtdelay yesterday
-- Form/Report Name:
--		1. IP VOICE STATISTICS NETWORK REGION RTDELAY REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumRtdelYest	OBJECT IDENTIFIER ::= { avCmObjects 76 }

avCmMeasIpVoStatSumRtdelYestTable	OBJECT-TYPE
    SYNTAX	SEQUENCE OF AvCmMeasIpVoStatSumRtdelYestEntry
    MAX-ACCESS	not-accessible
    STATUS	current
    DESCRIPTION
	"
	Fld OID Name:	avCmMeasIpVoStatSumRtdelYestTable
	Fld OID:	enterprises.6889.2.73.8.1.76.1
	Fld Form/Rpt:	NA
	Fld Format:	NA
	Fld(s) Name:	NA
	Fld Descr:	A list of the AvCmMeasIpVoStatSumRtdelYest entries.
	"
    ::= { avCmMeasIpVoStatSumRtdelYest 1 }

avCmMeasIpVoStatSumRtdelYestEntry	OBJECT-TYPE
    SYNTAX	AvCmMeasIpVoStatSumRtdelYestEntry
    MAX-ACCESS	not-accessible
    STATUS	current
    DESCRIPTION
	"
	Fld OID Name:	avCmMeasIpVoStatSumRtdelYestEntry
	Fld OID:	enterprises.6889.2.73.8.1.76.1.1
	Fld Form/Rpt:	NA
	Fld Format:	NA
	Fld(s) Name:	NA
	Fld Descr:	A avCmMeasIpVoStatSumRtdelYest entry containing objects of 
			the avCmMeasIpVoStatSumRtdelYest information sent by the 
			switch.
	"
    INDEX    { avCmMeasIpVoStatSumRtdelYestRegIdx, 
				avCmMeasIpVoStatSumRtdelYestHourIdx,
					avCmMeasIpVoStatSumRtdelYestIdx }
    ::= { avCmMeasIpVoStatSumRtdelYestTable 1 }

AvCmMeasIpVoStatSumRtdelYestEntry ::= SEQUENCE {
		avCmMeasIpVoStatSumRtdelYestRegIdx
		    Integer32,
                avCmMeasIpVoStatSumRtdelYestHourIdx
                    Integer32,
                avCmMeasIpVoStatSumRtdelYestIdx
                    Integer32,
                avCmMeasIpVoStatSumRtdelYestRegion
                    Integer32,
                avCmMeasIpVoStatSumRtdelYestMeasHour
                    Integer32,
                avCmMeasIpVoStatSumRtdelYestRunTime
                    SnmpAdminString,
                avCmMeasIpVoStatSumRtdelYestBoardLoc
                    SnmpAdminString,
                avCmMeasIpVoStatSumRtdelYestCallingNum
                    SnmpAdminString,
                avCmMeasIpVoStatSumRtdelYestCalledNum
                    SnmpAdminString,
                avCmMeasIpVoStatSumRtdelYestPktSize
                    Integer32,
                avCmMeasIpVoStatSumRtdelYestDstReg
                    Integer32,
                avCmMeasIpVoStatSumRtdelYestCodec
                    SnmpAdminString,
                avCmMeasIpVoStatSumRtdelYestAvg
                    Integer32,
                avCmMeasIpVoStatSumRtdelYestPeak
                    Integer32,
                avCmMeasIpVoStatSumRtdelYestTimeCall
                    SnmpAdminString,
                avCmMeasIpVoStatSumRtdelYestDataCall
                    SnmpAdminString,
                avCmMeasIpVoStatSumRtdelYestEncryp
                    SnmpAdminString,
                avCmMeasIpVoStatSumRtdelYestEC
                    SnmpAdminString,
                avCmMeasIpVoStatSumRtdelYestFEAddr
                    SnmpAdminString
		}

avCmMeasIpVoStatSumRtdelYestRegIdx	OBJECT-TYPE
    SYNTAX	Integer32 (1..2000)
    MAX-ACCESS	not-accessible
    STATUS	current
    DESCRIPTION
	"
	Fld OID Name:	avCmMeasIpVoStatSumRtdelYestRegIdx
	Fld OID:	enterprises.6889.2.73.8.1.76.1.1.1
	Fld Form/Rpt:	NA
	Fld Format:	NA
	Fld(s) Name:	NA
	Fld Descr:	An index into the network region.
	"
    ::= { avCmMeasIpVoStatSumRtdelYestEntry 1 }

avCmMeasIpVoStatSumRtdelYestHourIdx        OBJECT-TYPE
    SYNTAX      Integer32 (0..2300)
    MAX-ACCESS	not-accessible
    STATUS      current
    DESCRIPTION
        "
        Fld OID Name:   avCmMeasIpVoStatSumRtdelYestHourIdx
        Fld OID:        enterprises.6889.2.73.8.1.76.1.1.2
        Fld Form/Rpt:   NA
        Fld Format:     NA
        Fld(s) Name:    NA
        Fld Descr:      An index that contains the measurement hour in military
			time for the packet loss voice statistics.
        "
    ::= { avCmMeasIpVoStatSumRtdelYestEntry 2 }

avCmMeasIpVoStatSumRtdelYestIdx        OBJECT-TYPE
    SYNTAX      Integer32 (0..9999)
    MAX-ACCESS	not-accessible
    STATUS      current
    DESCRIPTION
        "
        Fld OID Name:   avCmMeasIpVoStatSumRtdelYestIdx
        Fld OID:        enterprises.6889.2.73.8.1.76.1.1.3
        Fld Form/Rpt:   NA
        Fld Format:     NA
        Fld(s) Name:    NA
        Fld Descr:      A unique index for the round trip delay voice 
			statistics.
        "
    ::= { avCmMeasIpVoStatSumRtdelYestEntry 3 }

avCmMeasIpVoStatSumRtdelYestRegion        OBJECT-TYPE
    SYNTAX      Integer32 (0..2000)
    MAX-ACCESS  read-only
    STATUS      current
    DESCRIPTION
        "
        Fld OID Name:   avCmMeasIpVoStatSumRtdelYestRegion
        Fld OID:        enterprises.6889.2.73.8.1.76.1.1.4
        Fld Form/Rpt:   IP VOICE STATISTICS NETWORK REGION RTDELAY REPORT
        Fld Format:     Single Field
        Fld(s) Name:    List Command: Region
        Fld Descr:      An object that contains the Network Region.
        "
    ::= { avCmMeasIpVoStatSumRtdelYestEntry 4 }

avCmMeasIpVoStatSumRtdelYestMeasHour	OBJECT-TYPE
    SYNTAX      Integer32 (0..2300)
    MAX-ACCESS	read-only
    STATUS	current
    DESCRIPTION
	"
	Fld OID Name:	avCmMeasIpVoStatSumRtdelYestMeasHour
	Fld OID:	enterprises.6889.2.73.8.1.76.1.1.5
	Fld Form/Rpt:	IP VOICE STATISTICS NETWORK REGION RTDELAY REPORT
	Fld Format:	Single
	Fld(s) Name:	Measurement Hour
	Fld Descr:	An object containing the measurement hour.
	"
    ::= { avCmMeasIpVoStatSumRtdelYestEntry 5 }

avCmMeasIpVoStatSumRtdelYestRunTime	OBJECT-TYPE
    SYNTAX	SnmpAdminString (SIZE (0..28))
    MAX-ACCESS	read-only
    STATUS	current
    DESCRIPTION
	"
	Fld OID Name:	avCmMeasIpVoStatSumRtdelYestRunTime
	Fld OID:	enterprises.6889.2.73.8.1.76.1.1.6
	Fld Form/Rpt:	IP VOICE STATISTICS NETWORK REGION RTDELAY REPORT
	Fld Format:	Single
	Fld(s) Name:	Date
	Fld Descr:	An object containing the Date.
	"
    ::= { avCmMeasIpVoStatSumRtdelYestEntry 6 }

avCmMeasIpVoStatSumRtdelYestBoardLoc	OBJECT-TYPE
    SYNTAX	SnmpAdminString (SIZE (0..6))
    MAX-ACCESS	read-only
    STATUS	current
    DESCRIPTION
	"
	Fld OID Name:	avCmMeasIpVoStatSumRtdelYestBoardLoc
	Fld OID:	enterprises.6889.2.73.8.1.76.1.1.7
	Fld Form/Rpt:	IP VOICE STATISTICS NETWORK REGION RTDELAY REPORT
	Fld Format:	Single
	Fld(s) Name:	Board Loc
	Fld Descr:	An object containing the Board location.
	"
    ::= { avCmMeasIpVoStatSumRtdelYestEntry 7 }

avCmMeasIpVoStatSumRtdelYestCallingNum	OBJECT-TYPE
    SYNTAX	SnmpAdminString (SIZE (0..17))
    MAX-ACCESS	read-only
    STATUS	current
    DESCRIPTION
	"
	Fld OID Name:	avCmMeasIpVoStatSumRtdelYestCallingNum
	Fld OID:	enterprises.6889.2.73.8.1.76.1.1.8
	Fld Form/Rpt:	IP VOICE STATISTICS NETWORK REGION RTDELAY REPORT
	Fld Format:	Single
	Fld(s) Name:	Calling Number
	Fld Descr:	An object containing the Calling Number.
	"
    ::= { avCmMeasIpVoStatSumRtdelYestEntry 8 }

avCmMeasIpVoStatSumRtdelYestCalledNum      OBJECT-TYPE
    SYNTAX      SnmpAdminString (SIZE (0..17))
    MAX-ACCESS  read-only
    STATUS      current
    DESCRIPTION
        "
        Fld OID Name:   avCmMeasIpVoStatSumRtdelYestCalledNum
        Fld OID:        enterprises.6889.2.73.8.1.76.1.1.9
        Fld Form/Rpt:   IP VOICE STATISTICS NETWORK REGION RTDELAY REPORT
        Fld Format:     Single
        Fld(s) Name:    Called Number
        Fld Descr:      An object containing the Called Number.
        "
    ::= { avCmMeasIpVoStatSumRtdelYestEntry 9 }

avCmMeasIpVoStatSumRtdelYestPktSize      OBJECT-TYPE
    SYNTAX      Integer32 (0..999)
    MAX-ACCESS  read-only
    STATUS      current
    DESCRIPTION
        "
        Fld OID Name:   avCmMeasIpVoStatSumRtdelYestPktSize
        Fld OID:        enterprises.6889.2.73.8.1.76.1.1.10
        Fld Form/Rpt:   IP VOICE STATISTICS NETWORK REGION RTDELAY REPORT
        Fld Format:     Single
        Fld(s) Name:    Pkt Size
        Fld Descr:      The packet size for each steam of data for
			the associated call, measured in milliseconds.
        "
    ::= { avCmMeasIpVoStatSumRtdelYestEntry 10 }


avCmMeasIpVoStatSumRtdelYestDstReg      OBJECT-TYPE
    SYNTAX      Integer32 (0..9999)
    MAX-ACCESS  read-only
    STATUS      current
    DESCRIPTION
        "
        Fld OID Name:   avCmMeasIpVoStatSumRtdelYestDstReg
        Fld OID:        enterprises.6889.2.73.8.1.76.1.1.11
        Fld Form/Rpt:   IP VOICE STATISTICS NETWORK REGION RTDELAY REPORT
        Fld Format:     Single
        Fld(s) Name:    Dst Reg
        Fld Descr:      The network region where the destination
			media processor is located.
        "
    ::= { avCmMeasIpVoStatSumRtdelYestEntry 11 }

avCmMeasIpVoStatSumRtdelYestCodec      OBJECT-TYPE
    SYNTAX      SnmpAdminString (SIZE (0..8))
    MAX-ACCESS  read-only
    STATUS      current
    DESCRIPTION
        "
        Fld OID Name:   avCmMeasIpVoStatSumRtdelYestCodec
        Fld OID:        enterprises.6889.2.73.8.1.76.1.1.12
        Fld Form/Rpt:   IP VOICE STATISTICS NETWORK REGION RTDELAY REPORT
        Fld Format:     Single
        Fld(s) Name:    Codec
        Fld Descr:      An object containing the Codec used for the call.
        "
    ::= { avCmMeasIpVoStatSumRtdelYestEntry 12 }

avCmMeasIpVoStatSumRtdelYestAvg      OBJECT-TYPE
    SYNTAX      Integer32 (0..9999)
    MAX-ACCESS  read-only
    STATUS      current
    DESCRIPTION
        "
        Fld OID Name:   avCmMeasIpVoStatSumRtdelYestAvg
        Fld OID:        enterprises.6889.2.73.8.1.76.1.1.13
        Fld Form/Rpt:   IP VOICE STATISTICS NETWORK REGION RTDELAY REPORT
        Fld Format:     Single
        Fld(s) Name:    RT-Delay Avg
        Fld Descr:      The average round trip delay of packets,
			measured in milliseconds.
			
        "
    ::= { avCmMeasIpVoStatSumRtdelYestEntry 13 }

avCmMeasIpVoStatSumRtdelYestPeak      OBJECT-TYPE
    SYNTAX      Integer32 (0..9999)
    MAX-ACCESS  read-only
    STATUS      current
    DESCRIPTION
        "
        Fld OID Name:   avCmMeasIpVoStatSumRtdelYestPeak
        Fld OID:        enterprises.6889.2.73.8.1.76.1.1.14
        Fld Form/Rpt:   IP VOICE STATISTICS NETWORK REGION RTDELAY REPORT
        Fld Format:     Single
        Fld(s) Name:    RT-Delay Peak
        Fld Descr:      The peak round trip delay recorded for the call.
        "
    ::= { avCmMeasIpVoStatSumRtdelYestEntry 14 }

avCmMeasIpVoStatSumRtdelYestTimeCall      OBJECT-TYPE
    SYNTAX      SnmpAdminString (SIZE (0..5))
    MAX-ACCESS  read-only
    STATUS      current
    DESCRIPTION
        "
        Fld OID Name:   avCmMeasIpVoStatSumRtdelYestTimeCall
        Fld OID:        enterprises.6889.2.73.8.1.76.1.1.15
        Fld Form/Rpt:   IP VOICE STATISTICS NETWORK REGION RTDELAY REPORT
        Fld Format:     Single
        Fld(s) Name:    Time of Call
        Fld Descr:      A time stamp when threshold was first
			exceeded for the associated call, shown in MMSS 
			(minutes seconds).
        "
    ::= { avCmMeasIpVoStatSumRtdelYestEntry 15 }


avCmMeasIpVoStatSumRtdelYestDataCall      OBJECT-TYPE
    SYNTAX      SnmpAdminString (SIZE (0..2))
    MAX-ACCESS  read-only
    STATUS      current
    DESCRIPTION
        "
        Fld OID Name:   avCmMeasIpVoStatSumRtdelYestDataCall
        Fld OID:        enterprises.6889.2.73.8.1.76.1.1.16
        Fld Form/Rpt:   IP VOICE STATISTICS NETWORK REGION RTDELAY REPORT
        Fld Format:     Single
        Fld(s) Name:    Data Call
        Fld Descr:      Indicates whether the call is a data call.
        "
    ::= { avCmMeasIpVoStatSumRtdelYestEntry 16 }

avCmMeasIpVoStatSumRtdelYestEncryp      OBJECT-TYPE
    SYNTAX      SnmpAdminString (SIZE (0..2))
    MAX-ACCESS  read-only
    STATUS      current
    DESCRIPTION
        "
        Fld OID Name:   avCmMeasIpVoStatSumRtdelYestEncryp
        Fld OID:        enterprises.6889.2.73.8.1.76.1.1.17
        Fld Form/Rpt:   IP VOICE STATISTICS NETWORK REGION RTDELAY REPORT
        Fld Format:     Single
        Fld(s) Name:    Encryp
        Fld Descr:      Indicates whether media encryption was used for the 
			call.
        "
    ::= { avCmMeasIpVoStatSumRtdelYestEntry 17 }

avCmMeasIpVoStatSumRtdelYestEC      OBJECT-TYPE
    SYNTAX      SnmpAdminString (SIZE (0..2))
    MAX-ACCESS  read-only
    STATUS      current
    DESCRIPTION
        "
        Fld OID Name:   avCmMeasIpVoStatSumRtdelYestEncryp
        Fld OID:        enterprises.6889.2.73.8.1.76.1.1.18
        Fld Form/Rpt:   IP VOICE STATISTICS NETWORK REGION RTDELAY REPORT
        Fld Format:     Single
        Fld(s) Name:    EC
        Fld Descr:      Indicates whether the echo cancellation is on/off for 
			the call.
        "
    ::= { avCmMeasIpVoStatSumRtdelYestEntry 18 }

avCmMeasIpVoStatSumRtdelYestFEAddr      OBJECT-TYPE
    SYNTAX      SnmpAdminString (SIZE (0..41))
    MAX-ACCESS  read-only
    STATUS      current
    DESCRIPTION
        "
        Fld OID Name:   avCmMeasIpVoStatSumRtdelYestFEAddr
        Fld OID:        enterprises.6889.2.73.8.1.76.1.1.19
        Fld Form/Rpt:   IP VOICE STATISTICS NETWORK REGION RTDELAY REPORT
        Fld Format:     Single
        Fld(s) Name:    FE-Addr
        Fld Descr:      An object containing the far-end ip-address.
        "
    ::= { avCmMeasIpVoStatSumRtdelYestEntry 19 }


--   *********** avCmMeasIpVoStatSumDataLstHr Group **************
-- MIB Group Name:
--		avCmMeasIpVoStatSumDataLstHr
-- OID:
--		enterprises.6889.2.73.8.1.77
-- Description:
--		The avCmMeasIpVoStatSumDataLstHr MIB group displays the 
--		output of the list measurements ip voice-stats  summary data
--		last-hour command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary data last-hour
-- Form/Report Name:
--		1. IP VOICE STATISTICS SUMMARY DATA REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumDataLstHr	OBJECT IDENTIFIER ::= { avCmObjects 77 }

avCmMeasIpVoStatSumDataLstHrTable	OBJECT-TYPE
    SYNTAX	SEQUENCE OF AvCmMeasIpVoStatSumDataLstHrEntry
    MAX-ACCESS	not-accessible
    STATUS	current
    DESCRIPTION
	"
	Fld OID Name:	avCmMeasIpVoStatSumDataLstHrTable
	Fld OID:	enterprises.6889.2.73.8.1.77.1
	Fld Form/Rpt:	NA
	Fld Format:	NA
	Fld(s) Name:	NA
	Fld Descr:	A list of the AvCmMeasIpVoStatSumDataLstHr entries.
	"
    ::= { avCmMeasIpVoStatSumDataLstHr 1 }

avCmMeasIpVoStatSumDataLstHrEntry	OBJECT-TYPE
    SYNTAX	AvCmMeasIpVoStatSumDataLstHrEntry
    MAX-ACCESS	not-accessible
    STATUS	current
    DESCRIPTION
	"
	Fld OID Name:	avCmMeasIpVoStatSumDataLstHrEntry
	Fld OID:	enterprises.6889.2.73.8.1.77.1.1
	Fld Form/Rpt:	NA
	Fld Format:	NA
	Fld(s) Name:	NA
	Fld Descr:	A avCmMeasIpVoStatSumDataLstHr entry containing
			objects of the avCmMeasIpVoStatSumDataLstHr
			information sent by the switch.
	"
    INDEX    { avCmMeasIpVoStatSumDataLstHrRegIdx, 
				avCmMeasIpVoStatSumDataLstHrHourIdx,
					avCmMeasIpVoStatSumDataLstHrIdx }
    ::= { avCmMeasIpVoStatSumDataLstHrTable 1 }

AvCmMeasIpVoStatSumDataLstHrEntry ::= SEQUENCE {
		avCmMeasIpVoStatSumDataLstHrRegIdx
		    Integer32,
                avCmMeasIpVoStatSumDataLstHrHourIdx
                    Integer32,
                avCmMeasIpVoStatSumDataLstHrIdx
                    Integer32,
                avCmMeasIpVoStatSumDataLstHrRegion
                    Integer32,
                avCmMeasIpVoStatSumDataLstHrMeasHour
                    Integer32,
                avCmMeasIpVoStatSumDataLstHrRunTime
                    SnmpAdminString,
                avCmMeasIpVoStatSumDataLstHrBoardLoc
                    SnmpAdminString,
                avCmMeasIpVoStatSumDataLstHrCallingNum
                    SnmpAdminString,
                avCmMeasIpVoStatSumDataLstHrCalledNum
                    SnmpAdminString,
                avCmMeasIpVoStatSumDataLstHrDstReg
                    Integer32,
                avCmMeasIpVoStatSumDataLstHrCodec
                    SnmpAdminString,
                avCmMeasIpVoStatSumDataLstHrDataType
                    SnmpAdminString,
                avCmMeasIpVoStatSumDataLstHrPktSize
                    Integer32,
                avCmMeasIpVoStatSumDataLstHrLossPerc
                    SnmpAdminString,
                avCmMeasIpVoStatSumDataLstHrPeakJitter
                    Integer32,
                avCmMeasIpVoStatSumDataLstHrPeakDly
                    Integer32,
                avCmMeasIpVoStatSumDataLstHrEC
                    SnmpAdminString,
                avCmMeasIpVoStatSumDataLstHrFEAddr
                    SnmpAdminString
		}

avCmMeasIpVoStatSumDataLstHrRegIdx	OBJECT-TYPE
    SYNTAX	Integer32 (1..2000)
    MAX-ACCESS	not-accessible
    STATUS	current
    DESCRIPTION
	"
	Fld OID Name:	avCmMeasIpVoStatSumDataLstHrRegIdx
	Fld OID:	enterprises.6889.2.73.8.1.77.1.1.1
	Fld Form/Rpt:	NA
	Fld Format:	NA
	Fld(s) Name:	NA
	Fld Descr:	An index into the network region.
	"
    ::= { avCmMeasIpVoStatSumDataLstHrEntry 1 }

avCmMeasIpVoStatSumDataLstHrHourIdx        OBJECT-TYPE
    SYNTAX      Integer32 (0..2300)
    MAX-ACCESS	not-accessible
    STATUS      current
    DESCRIPTION
        "
        Fld OID Name:   avCmMeasIpVoStatSumDataLstHrHourIdx
        Fld OID:        enterprises.6889.2.73.8.1.77.1.1.2
        Fld Form/Rpt:   NA
        Fld Format:     NA
        Fld(s) Name:    NA
        Fld Descr:      An index that contains the measurement hour in military
			time for the packet loss voice statistics.
        "
    ::= { avCmMeasIpVoStatSumDataLstHrEntry 2 }

avCmMeasIpVoStatSumDataLstHrIdx        OBJECT-TYPE
    SYNTAX      Integer32 (0..9999)
    MAX-ACCESS	not-accessible
    STATUS      current
    DESCRIPTION
        "
        Fld OID Name:   avCmMeasIpVoStatSumDataLstHrHourIdx
        Fld OID:        enterprises.6889.2.73.8.1.77.1.1.3
        Fld Form/Rpt:   NA
        Fld Format:     NA
        Fld(s) Name:    NA
        Fld Descr:      An index that contains the measurement hour in military
			time for the packet loss voice statistics.
        "
    ::= { avCmMeasIpVoStatSumDataLstHrEntry 3 }

avCmMeasIpVoStatSumDataLstHrRegion        OBJECT-TYPE
    SYNTAX      Integer32 (0..2000)
    MAX-ACCESS  read-only
    STATUS      current
    DESCRIPTION
        "
        Fld OID Name:   avCmMeasIpVoStatSumDataLstHrRegion
        Fld OID:        enterprises.6889.2.73.8.1.77.1.1.4
        Fld Form/Rpt:   IP VOICE STATISTICS SUMMARY DATA REPORT
        Fld Format:     Single Field
        Fld(s) Name:    List Command: Region
        Fld Descr:      An object that contains the Network Region.
        "
    ::= { avCmMeasIpVoStatSumDataLstHrEntry 4 }

avCmMeasIpVoStatSumDataLstHrMeasHour	OBJECT-TYPE
    SYNTAX      Integer32 (0..2300)
    MAX-ACCESS	read-only
    STATUS	current
    DESCRIPTION
	"
	Fld OID Name:	avCmMeasIpVoStatSumDataLstHrMeasHour
	Fld OID:	enterprises.6889.2.73.8.1.77.1.1.5
	Fld Form/Rpt:	IP VOICE STATISTICS SUMMARY DATA REPORT
	Fld Format:	Single
	Fld(s) Name:	Measurement Hour
	Fld Descr:	An object containing the measurement hour.
	"
    ::= { avCmMeasIpVoStatSumDataLstHrEntry 5 }

avCmMeasIpVoStatSumDataLstHrRunTime	OBJECT-TYPE
    SYNTAX	SnmpAdminString (SIZE (0..28))
    MAX-ACCESS	read-only
    STATUS	current
    DESCRIPTION
	"
	Fld OID Name:	avCmMeasIpVoStatSumDataLstHrRunTime
	Fld OID:	enterprises.6889.2.73.8.1.77.1.1.6
	Fld Form/Rpt:	IP VOICE STATISTICS SUMMARY DATA REPORT
	Fld Format:	Single
	Fld(s) Name:	Date
	Fld Descr:	An object containing the Date.
	"
    ::= { avCmMeasIpVoStatSumDataLstHrEntry 6 }

avCmMeasIpVoStatSumDataLstHrBoardLoc	OBJECT-TYPE
    SYNTAX	SnmpAdminString (SIZE (0..6))
    MAX-ACCESS	read-only
    STATUS	current
    DESCRIPTION
	"
	Fld OID Name:	avCmMeasIpVoStatSumDataLstHrBoardLoc
	Fld OID:	enterprises.6889.2.73.8.1.77.1.1.7
	Fld Form/Rpt:	IP VOICE STATISTICS SUMMARY DATA REPORT
	Fld Format:	Single
	Fld(s) Name:	Board Loc
	Fld Descr:	An object containing the Board location.
	"
    ::= { avCmMeasIpVoStatSumDataLstHrEntry 7 }

avCmMeasIpVoStatSumDataLstHrCallingNum	OBJECT-TYPE
    SYNTAX	SnmpAdminString (SIZE (0..17))
    MAX-ACCESS	read-only
    STATUS	current
    DESCRIPTION
	"
	Fld OID Name:	avCmMeasIpVoStatSumDataLstHrCallingNum
	Fld OID:	enterprises.6889.2.73.8.1.77.1.1.8
	Fld Form/Rpt:	IP VOICE STATISTICS SUMMARY DATA REPORT
	Fld Format:	Single
	Fld(s) Name:	Calling Number
	Fld Descr:	An object containing the Calling Number.
	"
    ::= { avCmMeasIpVoStatSumDataLstHrEntry 8 }

avCmMeasIpVoStatSumDataLstHrCalledNum      OBJECT-TYPE
    SYNTAX      SnmpAdminString (SIZE (0..17))
    MAX-ACCESS  read-only
    STATUS      current
    DESCRIPTION
        "
        Fld OID Name:   avCmMeasIpVoStatSumDataLstHrCalledNum
        Fld OID:        enterprises.6889.2.73.8.1.77.1.1.9
        Fld Form/Rpt:   IP VOICE STATISTICS SUMMARY DATA REPORT
        Fld Format:     Single
        Fld(s) Name:    Called Number
        Fld Descr:      An object containing the Called Number.
        "
    ::= { avCmMeasIpVoStatSumDataLstHrEntry 9 }


avCmMeasIpVoStatSumDataLstHrDstReg      OBJECT-TYPE
    SYNTAX      Integer32 (0..9999)
    MAX-ACCESS  read-only
    STATUS      current
    DESCRIPTION
        "
        Fld OID Name:   avCmMeasIpVoStatSumDataLstHrDstReg
        Fld OID:        enterprises.6889.2.73.8.1.77.1.1.10
        Fld Form/Rpt:   IP VOICE STATISTICS SUMMARY DATA REPORT
        Fld Format:     Single
        Fld(s) Name:    Dst Reg
        Fld Descr:      The network region where the destination
			media processor is located.
        "
    ::= { avCmMeasIpVoStatSumDataLstHrEntry 10 }

avCmMeasIpVoStatSumDataLstHrCodec      OBJECT-TYPE
    SYNTAX      SnmpAdminString (SIZE (0..8))
    MAX-ACCESS  read-only
    STATUS      current
    DESCRIPTION
        "
        Fld OID Name:   avCmMeasIpVoStatSumDataLstHrCodec
        Fld OID:        enterprises.6889.2.73.8.1.77.1.1.11
        Fld Form/Rpt:   IP VOICE STATISTICS SUMMARY DATA REPORT
        Fld Format:     Single
        Fld(s) Name:    Codec
        Fld Descr:      An object containing the Codec used for the call.
        "
    ::= { avCmMeasIpVoStatSumDataLstHrEntry 11 }

avCmMeasIpVoStatSumDataLstHrDataType      OBJECT-TYPE
    SYNTAX      SnmpAdminString (SIZE (0..7))
    MAX-ACCESS  read-only
    STATUS      current
    DESCRIPTION
        "
        Fld OID Name:   avCmMeasIpVoStatSumDataLstHrDataType
        Fld OID:        enterprises.6889.2.73.8.1.77.1.1.12
        Fld Form/Rpt:   IP VOICE STATISTICS SUMMARY DATA REPORT
        Fld Format:     Single
        Fld(s) Name:    Data Type
        Fld Descr:      Indicates the type of data call. Valid options
                        include:
                        ~ ttyrel (TTY Relay)
                        ~ mod-pt (Modem pass-through)
                        ~ fax-pt (FAX pass-through)
                        ~ tty-pt (TTY pass-through)
                        ~ t38fax (T.38 FAX)
                        ~ faxrel (FAX relay)
                        ~ modrel (Modem relay)
        "
    ::= { avCmMeasIpVoStatSumDataLstHrEntry 12 }

avCmMeasIpVoStatSumDataLstHrPktSize      OBJECT-TYPE
    SYNTAX      Integer32 (0..999)
    MAX-ACCESS  read-only
    STATUS      current
    DESCRIPTION
        "
        Fld OID Name:   avCmMeasIpVoStatSumDatLstHraPktSize
        Fld OID:        enterprises.6889.2.73.8.1.77.1.1.13
        Fld Form/Rpt:   IP VOICE STATISTICS SUMMARY DATA REPORT
        Fld Format:     Single
        Fld(s) Name:    Pkt Size
        Fld Descr:      The packet size for each steam of data for
                        the associated call, measured in
                        milliseconds.
        "
    ::= { avCmMeasIpVoStatSumDataLstHrEntry 13 }


avCmMeasIpVoStatSumDataLstHrLossPerc      OBJECT-TYPE
    SYNTAX      SnmpAdminString (SIZE (0..4))
    MAX-ACCESS  read-only
    STATUS      current
    DESCRIPTION
        "
        Fld OID Name:   avCmMeasIpVoStatSumDataLstHrLossPerc
        Fld OID:        enterprises.6889.2.73.8.1.77.1.1.14
        Fld Form/Rpt:   IP VOICE STATISTICS SUMMARY DATA REPORT
        Fld Format:     Single
        Fld(s) Name:    Loss %
        Fld Descr:      The packet Loss for the call. The Packet loss
                        percentage is calculated at 10-second
                        intervals.
        "
    ::= { avCmMeasIpVoStatSumDataLstHrEntry 14 }

avCmMeasIpVoStatSumDataLstHrPeakJitter      OBJECT-TYPE
    SYNTAX      Integer32 (0..9999)
    MAX-ACCESS  read-only
    STATUS      current
    DESCRIPTION
        "
        Fld OID Name:   avCmMeasIpVoStatSumDataLstHrPeakJitter
        Fld OID:        enterprises.6889.2.73.8.1.77.1.1.15
        Fld Form/Rpt:   IP VOICE STATISTICS SUMMARY DATA REPORT
        Fld Format:     Single
        Fld(s) Name:    Peak Jit
        Fld Descr:      The peak amount of jitter recorded for the
                        call, measured in milliseconds.
        "
    ::= { avCmMeasIpVoStatSumDataLstHrEntry 15 }

avCmMeasIpVoStatSumDataLstHrPeakDly      OBJECT-TYPE
    SYNTAX      Integer32 (0..9999)
    MAX-ACCESS  read-only
    STATUS      current
    DESCRIPTION
        "
        Fld OID Name:   avCmMeasIpVoStatSumDataPeakDly
        Fld OID:        enterprises.6889.2.73.8.1.77.1.1.16
        Fld Form/Rpt:   IP VOICE STATISTICS SUMMARY DATA REPORT
        Fld Format:     Single
        Fld(s) Name:    Dly
        Fld Descr:      The peak round trip delay recorded for the
                        call, measured in milliseconds.
        "
    ::= { avCmMeasIpVoStatSumDataLstHrEntry 16 }

avCmMeasIpVoStatSumDataLstHrEC      OBJECT-TYPE
    SYNTAX      SnmpAdminString (SIZE (0..2))
    MAX-ACCESS  read-only
    STATUS      current
    DESCRIPTION
        "
        Fld OID Name:   avCmMeasIpVoStatSumDataLstHrEC
        Fld OID:        enterprises.6889.2.73.8.1.77.1.1.17
        Fld Form/Rpt:   IP VOICE STATISTICS SUMMARY DATA REPORT
        Fld Format:     Single
        Fld(s) Name:    EC
        Fld Descr:      Indicates whether the echo cancellation is on/off for 
			the call.
        "
    ::= { avCmMeasIpVoStatSumDataLstHrEntry 17 }

avCmMeasIpVoStatSumDataLstHrFEAddr      OBJECT-TYPE
    SYNTAX      SnmpAdminString (SIZE (0..41))
    MAX-ACCESS  read-only
    STATUS      current
    DESCRIPTION
        "
        Fld OID Name:   avCmMeasIpVoStatSumDataLstHrFEAddr
        Fld OID:        enterprises.6889.2.73.8.1.77.1.1.18
        Fld Form/Rpt:   IP VOICE STATISTICS SUMMARY DATA REPORT
        Fld Format:     Single
        Fld(s) Name:    FE-Addr
        Fld Descr:      An object containing the far-end ip-address.
        "
    ::= { avCmMeasIpVoStatSumDataLstHrEntry 18 }

--   *********** avCmMeasIpVoStatSumDataToday Group **************
-- MIB Group Name:
--		avCmMeasIpVoStatSumDataToday
-- OID:
--		enterprises.6889.2.73.8.1.78
-- Description:
--		The avCmMeasIpVoStatSumDataToday MIB group displays the 
--		output of the list measurements ip voice-stats  summary data
--		today command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary data today
-- Form/Report Name:
--		1. IP VOICE STATISTICS SUMMARY DATA REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumDataToday	OBJECT IDENTIFIER ::= { avCmObjects 78 }

avCmMeasIpVoStatSumDataTodayTable	OBJECT-TYPE
    SYNTAX	SEQUENCE OF AvCmMeasIpVoStatSumDataTodayEntry
    MAX-ACCESS	not-accessible
    STATUS	current
    DESCRIPTION
	"
	Fld OID Name:	avCmMeasIpVoStatSumDataTodayTable
	Fld OID:	enterprises.6889.2.73.8.1.78.1
	Fld Form/Rpt:	NA
	Fld Format:	NA
	Fld(s) Name:	NA
	Fld Descr:	A list of the AvCmMeasIpVoStatSumDataToday entries.
	"
    ::= { avCmMeasIpVoStatSumDataToday 1 }

avCmMeasIpVoStatSumDataTodayEntry	OBJECT-TYPE
    SYNTAX	AvCmMeasIpVoStatSumDataTodayEntry
    MAX-ACCESS	not-accessible
    STATUS	current
    DESCRIPTION
	"
	Fld OID Name:	avCmMeasIpVoStatSumDataTodayEntry
	Fld OID:	enterprises.6889.2.73.8.1.78.1.1
	Fld Form/Rpt:	NA
	Fld Format:	NA
	Fld(s) Name:	NA
	Fld Descr:	A avCmMeasIpVoStatSumDataToday entry containing objects of 
			the avCmMeasIpVoStatSumDataToday information sent by the 
			switch.
	"
    INDEX    { avCmMeasIpVoStatSumDataTodayRegIdx, 
				avCmMeasIpVoStatSumDataTodayHourIdx,
					avCmMeasIpVoStatSumDataTodayIdx }
    ::= { avCmMeasIpVoStatSumDataTodayTable 1 }

AvCmMeasIpVoStatSumDataTodayEntry ::= SEQUENCE {
		avCmMeasIpVoStatSumDataTodayRegIdx
		    Integer32,
                avCmMeasIpVoStatSumDataTodayHourIdx
                    Integer32,
                avCmMeasIpVoStatSumDataTodayIdx
                    Integer32,
                avCmMeasIpVoStatSumDataTodayRegion
                    Integer32,
                avCmMeasIpVoStatSumDataTodayMeasHour
                    Integer32,
                avCmMeasIpVoStatSumDataTodayRunTime
                    SnmpAdminString,
                avCmMeasIpVoStatSumDataTodayBoardLoc
                    SnmpAdminString,
                avCmMeasIpVoStatSumDataTodayCallingNum
                    SnmpAdminString,
                avCmMeasIpVoStatSumDataTodayCalledNum
                    SnmpAdminString,
                avCmMeasIpVoStatSumDataTodayDstReg
                    Integer32,
                avCmMeasIpVoStatSumDataTodayCodec
                    SnmpAdminString,
                avCmMeasIpVoStatSumDataTodayDataType
                    SnmpAdminString,
                avCmMeasIpVoStatSumDataTodayPktSize
                    Integer32,
                avCmMeasIpVoStatSumDataTodayLossPerc
                    SnmpAdminString,
                avCmMeasIpVoStatSumDataTodayPeakJitter
                    Integer32,
                avCmMeasIpVoStatSumDataTodayPeakDly
                    Integer32,
                avCmMeasIpVoStatSumDataTodayEC
                    SnmpAdminString,
                avCmMeasIpVoStatSumDataTodayFEAddr
                    SnmpAdminString
		}

avCmMeasIpVoStatSumDataTodayRegIdx	OBJECT-TYPE
    SYNTAX	Integer32 (1..2000)
    MAX-ACCESS	not-accessible
    STATUS	current
    DESCRIPTION
	"
	Fld OID Name:	avCmMeasIpVoStatSumDataTodayRegIdx
	Fld OID:	enterprises.6889.2.73.8.1.78.1.1.1
	Fld Form/Rpt:	NA
	Fld Format:	NA
	Fld(s) Name:	NA
	Fld Descr:	An index into the network region.
	"
    ::= { avCmMeasIpVoStatSumDataTodayEntry 1 }

avCmMeasIpVoStatSumDataTodayHourIdx        OBJECT-TYPE
    SYNTAX      Integer32 (0..2300)
    MAX-ACCESS	not-accessible
    STATUS      current
    DESCRIPTION
        "
        Fld OID Name:   avCmMeasIpVoStatSumDataTodayHourIdx
        Fld OID:        enterprises.6889.2.73.8.1.78.1.1.2
        Fld Form/Rpt:   NA
        Fld Format:     NA
        Fld(s) Name:    NA
        Fld Descr:      An index that contains the measurement hour in military
			time for the packet loss voice statistics.
        "
    ::= { avCmMeasIpVoStatSumDataTodayEntry 2 }

avCmMeasIpVoStatSumDataTodayIdx        OBJECT-TYPE
    SYNTAX      Integer32 (0..9999)
    MAX-ACCESS	not-accessible
    STATUS      current
    DESCRIPTION
        "
        Fld OID Name:   avCmMeasIpVoStatSumDataTodayIdx
        Fld OID:        enterprises.6889.2.73.8.1.78.1.1.3
        Fld Form/Rpt:   NA
        Fld Format:     NA
        Fld(s) Name:    NA
        Fld Descr:      An index that contains the measurement hour in military
			time for the packet loss voice statistics.
        "
    ::= { avCmMeasIpVoStatSumDataTodayEntry 3 }

avCmMeasIpVoStatSumDataTodayRegion        OBJECT-TYPE
    SYNTAX      Integer32 (0..2000)
    MAX-ACCESS  read-only
    STATUS      current
    DESCRIPTION
        "
        Fld OID Name:   avCmMeasIpVoStatSumDataTodayRegion
        Fld OID:        enterprises.6889.2.73.8.1.78.1.1.4
        Fld Form/Rpt:   IP VOICE STATISTICS SUMMARY DATA REPORT
        Fld Format:     Single Field
        Fld(s) Name:    List Command: Region
        Fld Descr:      An object that contains the Network Region.
        "
    ::= { avCmMeasIpVoStatSumDataTodayEntry 4 }

avCmMeasIpVoStatSumDataTodayMeasHour	OBJECT-TYPE
    SYNTAX      Integer32 (0..2300)
    MAX-ACCESS	read-only
    STATUS	current
    DESCRIPTION
	"
	Fld OID Name:	avCmMeasIpVoStatSumDataTodayMeasHour
	Fld OID:	enterprises.6889.2.73.8.1.78.1.1.5
	Fld Form/Rpt:	IP VOICE STATISTICS SUMMARY DATA REPORT
	Fld Format:	Single
	Fld(s) Name:	Measurement Hour
	Fld Descr:	An object containing the measurement hour.
	"
    ::= { avCmMeasIpVoStatSumDataTodayEntry 5 }

avCmMeasIpVoStatSumDataTodayRunTime	OBJECT-TYPE
    SYNTAX	SnmpAdminString (SIZE (0..28))
    MAX-ACCESS	read-only
    STATUS	current
    DESCRIPTION
	"
	Fld OID Name:	avCmMeasIpVoStatSumDataTodayRunTime
	Fld OID:	enterprises.6889.2.73.8.1.78.1.1.6
	Fld Form/Rpt:	IP VOICE STATISTICS SUMMARY DATA REPORT
	Fld Format:	Single
	Fld(s) Name:	Date
	Fld Descr:	An object containing the Date.
	"
    ::= { avCmMeasIpVoStatSumDataTodayEntry 6 }

avCmMeasIpVoStatSumDataTodayBoardLoc	OBJECT-TYPE
    SYNTAX	SnmpAdminString (SIZE (0..6))
    MAX-ACCESS	read-only
    STATUS	current
    DESCRIPTION
	"
	Fld OID Name:	avCmMeasIpVoStatSumDataTodayBoardLoc
	Fld OID:	enterprises.6889.2.73.8.1.78.1.1.7
	Fld Form/Rpt:	IP VOICE STATISTICS SUMMARY DATA REPORT
	Fld Format:	Single
	Fld(s) Name:	Board Loc
	Fld Descr:	An object containing the Board location.
	"
    ::= { avCmMeasIpVoStatSumDataTodayEntry 7 }

avCmMeasIpVoStatSumDataTodayCallingNum	OBJECT-TYPE
    SYNTAX	SnmpAdminString (SIZE (0..17))
    MAX-ACCESS	read-only
    STATUS	current
    DESCRIPTION
	"
	Fld OID Name:	avCmMeasIpVoStatSumDataTodayCallingNum
	Fld OID:	enterprises.6889.2.73.8.1.78.1.1.8
	Fld Form/Rpt:	IP VOICE STATISTICS SUMMARY DATA REPORT
	Fld Format:	Single
	Fld(s) Name:	Calling Number
	Fld Descr:	An object containing the Calling Number.
	"
    ::= { avCmMeasIpVoStatSumDataTodayEntry 8 }

avCmMeasIpVoStatSumDataTodayCalledNum      OBJECT-TYPE
    SYNTAX      SnmpAdminString (SIZE (0..17))
    MAX-ACCESS  read-only
    STATUS      current
    DESCRIPTION
        "
        Fld OID Name:   avCmMeasIpVoStatSumDataTodayCalledNum
        Fld OID:        enterprises.6889.2.73.8.1.78.1.1.9
        Fld Form/Rpt:   IP VOICE STATISTICS SUMMARY DATA REPORT
        Fld Format:     Single
        Fld(s) Name:    Called Number
        Fld Descr:      An object containing the Called Number.
        "
    ::= { avCmMeasIpVoStatSumDataTodayEntry 9 }


avCmMeasIpVoStatSumDataTodayDstReg      OBJECT-TYPE
    SYNTAX      Integer32 (0..9999)
    MAX-ACCESS  read-only
    STATUS      current
    DESCRIPTION
        "
        Fld OID Name:   avCmMeasIpVoStatSumDataTodayDstReg
        Fld OID:        enterprises.6889.2.73.8.1.78.1.1.10
        Fld Form/Rpt:   IP VOICE STATISTICS SUMMARY DATA REPORT
        Fld Format:     Single
        Fld(s) Name:    Dst Reg
        Fld Descr:      The network region where the destination
			media processor is located.
        "
    ::= { avCmMeasIpVoStatSumDataTodayEntry 10 }

avCmMeasIpVoStatSumDataTodayCodec      OBJECT-TYPE
    SYNTAX      SnmpAdminString (SIZE (0..8))
    MAX-ACCESS  read-only
    STATUS      current
    DESCRIPTION
        "
        Fld OID Name:   avCmMeasIpVoStatSumDataTodayCodec
        Fld OID:        enterprises.6889.2.73.8.1.78.1.1.11
        Fld Form/Rpt:   IP VOICE STATISTICS SUMMARY DATA REPORT
        Fld Format:     Single
        Fld(s) Name:    Codec
        Fld Descr:      An object containing the Codec used for the call.
        "
    ::= { avCmMeasIpVoStatSumDataTodayEntry 11 }

avCmMeasIpVoStatSumDataTodayDataType      OBJECT-TYPE
    SYNTAX      SnmpAdminString (SIZE (0..7))
    MAX-ACCESS  read-only
    STATUS      current
    DESCRIPTION
        "
        Fld OID Name:   avCmMeasIpVoStatSumDataTodayDataType
        Fld OID:        enterprises.6889.2.73.8.1.78.1.1.12
        Fld Form/Rpt:   IP VOICE STATISTICS SUMMARY DATA REPORT
        Fld Format:     Single
        Fld(s) Name:    Data Type
        Fld Descr:      Indicates the type of data call. Valid options
                        include:
                        ~ ttyrel (TTY Relay)
                        ~ mod-pt (Modem pass-through)
                        ~ fax-pt (FAX pass-through)
                        ~ tty-pt (TTY pass-through)
                        ~ t38fax (T.38 FAX)
                        ~ faxrel (FAX relay)
                        ~ modrel (Modem relay)
        "
    ::= { avCmMeasIpVoStatSumDataTodayEntry 12 }

avCmMeasIpVoStatSumDataTodayPktSize      OBJECT-TYPE
    SYNTAX      Integer32 (0..999)
    MAX-ACCESS  read-only
    STATUS      current
    DESCRIPTION
        "
        Fld OID Name:   avCmMeasIpVoStatSumDatTodayaPktSize
        Fld OID:        enterprises.6889.2.73.8.1.78.1.1.13
        Fld Form/Rpt:   IP VOICE STATISTICS SUMMARY DATA REPORT
        Fld Format:     Single
        Fld(s) Name:    Pkt Size
        Fld Descr:      The packet size for each steam of data for
                        the associated call, measured in
                        milliseconds.
        "
    ::= { avCmMeasIpVoStatSumDataTodayEntry 13 }


avCmMeasIpVoStatSumDataTodayLossPerc      OBJECT-TYPE
    SYNTAX      SnmpAdminString (SIZE (0..4))
    MAX-ACCESS  read-only
    STATUS      current
    DESCRIPTION
        "
        Fld OID Name:   avCmMeasIpVoStatSumDataTodayLossPerc
        Fld OID:        enterprises.6889.2.73.8.1.78.1.1.14
        Fld Form/Rpt:   IP VOICE STATISTICS SUMMARY DATA REPORT
        Fld Format:     Single
        Fld(s) Name:    Loss %
        Fld Descr:      The packet Loss for the call. The Packet loss
                        percentage is calculated at 10-second
                        intervals.
        "
    ::= { avCmMeasIpVoStatSumDataTodayEntry 14 }

avCmMeasIpVoStatSumDataTodayPeakJitter      OBJECT-TYPE
    SYNTAX      Integer32 (0..9999)
    MAX-ACCESS  read-only
    STATUS      current
    DESCRIPTION
        "
        Fld OID Name:   avCmMeasIpVoStatSumDataTodayPeakJitter
        Fld OID:        enterprises.6889.2.73.8.1.78.1.1.15
        Fld Form/Rpt:   IP VOICE STATISTICS SUMMARY DATA REPORT
        Fld Format:     Single
        Fld(s) Name:    Peak Jit
        Fld Descr:      The peak amount of jitter recorded for the
                        call, measured in milliseconds.
        "
    ::= { avCmMeasIpVoStatSumDataTodayEntry 15 }

avCmMeasIpVoStatSumDataTodayPeakDly      OBJECT-TYPE
    SYNTAX      Integer32 (0..9999)
    MAX-ACCESS  read-only
    STATUS      current
    DESCRIPTION
        "
        Fld OID Name:   avCmMeasIpVoStatSumDataPeakDly
        Fld OID:        enterprises.6889.2.73.8.1.78.1.1.16
        Fld Form/Rpt:   IP VOICE STATISTICS SUMMARY DATA REPORT
        Fld Format:     Single
        Fld(s) Name:    Dly
        Fld Descr:      The peak round trip delay recorded for the
                        call, measured in milliseconds.
        "
    ::= { avCmMeasIpVoStatSumDataTodayEntry 16 }

avCmMeasIpVoStatSumDataTodayEC      OBJECT-TYPE
    SYNTAX      SnmpAdminString (SIZE (0..2))
    MAX-ACCESS  read-only
    STATUS      current
    DESCRIPTION
        "
        Fld OID Name:   avCmMeasIpVoStatSumDataTodayEC
        Fld OID:        enterprises.6889.2.73.8.1.78.1.1.17
        Fld Form/Rpt:   IP VOICE STATISTICS SUMMARY DATA REPORT
        Fld Format:     Single
        Fld(s) Name:    EC
        Fld Descr:      Indicates whether the echo cancellation is on/off for 
			the call.
        "
    ::= { avCmMeasIpVoStatSumDataTodayEntry 17 }

avCmMeasIpVoStatSumDataTodayFEAddr      OBJECT-TYPE
    SYNTAX      SnmpAdminString (SIZE (0..41))
    MAX-ACCESS  read-only
    STATUS      current
    DESCRIPTION
        "
        Fld OID Name:   avCmMeasIpVoStatSumDataTodayFEAddr
        Fld OID:        enterprises.6889.2.73.8.1.78.1.1.18
        Fld Form/Rpt:   IP VOICE STATISTICS SUMMARY DATA REPORT
        Fld Format:     Single
        Fld(s) Name:    FE-Addr
        Fld Descr:      An object containing the far-end ip-address.
        "
    ::= { avCmMeasIpVoStatSumDataTodayEntry 18 }

--   *********** avCmMeasIpVoStatSumDataYest Group **************
-- MIB Group Name:
--		avCmMeasIpVoStatSumDataYest
-- OID:
--		enterprises.6889.2.73.8.1.79
-- Description:
--		The avCmMeasIpVoStatSumDataYest MIB group displays the 
--		output of the list measurements ip voice-stats  summary data
--		yesterday command 
--              for each network-region administered on the NETWORK REGION 
--		MEASUREMENT SELECTION form.
--
-- Releases Supported:
--		CM6.3.100 and greater
-- Polling Type:
--		Performance/Utilization
-- Polling Interval:
--		No more than once an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements ip voice-stats summary data yesterday
-- Form/Report Name:
--		1. IP VOICE STATISTICS SUMMARY DATA REPORT
-- Reference Document:
--		1. A detailed description of the command and form can be
--		   found in REF_DOC_4 in the DOCUMENT REFERENCE SECTION.
-- Command Permission/User-profile:
--		1. No special permissions needed. Default customer super-user
--		   profile can access this command.

avCmMeasIpVoStatSumDataYest	OBJECT IDENTIFIER ::= { avCmObjects 79 }

avCmMeasIpVoStatSumDataYestTable	OBJECT-TYPE
    SYNTAX	SEQUENCE OF AvCmMeasIpVoStatSumDataYestEntry
    MAX-ACCESS	not-accessible
    STATUS	current
    DESCRIPTION
	"
	Fld OID Name:	avCmMeasIpVoStatSumDataYestTable
	Fld OID:	enterprises.6889.2.73.8.1.79.1
	Fld Form/Rpt:	NA
	Fld Format:	NA
	Fld(s) Name:	NA
	Fld Descr:	A list of the AvCmMeasIpVoStatSumDataYest entries.
	"
    ::= { avCmMeasIpVoStatSumDataYest 1 }

avCmMeasIpVoStatSumDataYestEntry	OBJECT-TYPE
    SYNTAX	AvCmMeasIpVoStatSumDataYestEntry
    MAX-ACCESS	not-accessible
    STATUS	current
    DESCRIPTION
	"
	Fld OID Name:	avCmMeasIpVoStatSumDataYestEntry
	Fld OID:	enterprises.6889.2.73.8.1.79.1.1
	Fld Form/Rpt:	NA
	Fld Format:	NA
	Fld(s) Name:	NA
	Fld Descr:	A avCmMeasIpVoStatSumDataYest entry containing objects of 
			the avCmMeasIpVoStatSumDataYest information sent by the 
			switch.
	"
    INDEX    { avCmMeasIpVoStatSumDataYestRegIdx, 
				avCmMeasIpVoStatSumDataYestHourIdx,
					avCmMeasIpVoStatSumDataYestIdx }
    ::= { avCmMeasIpVoStatSumDataYestTable 1 }

AvCmMeasIpVoStatSumDataYestEntry ::= SEQUENCE {
		avCmMeasIpVoStatSumDataYestRegIdx
		    Integer32,
                avCmMeasIpVoStatSumDataYestHourIdx
                    Integer32,
                avCmMeasIpVoStatSumDataYestIdx
                    Integer32,
                avCmMeasIpVoStatSumDataYestRegion
                    Integer32,
                avCmMeasIpVoStatSumDataYestMeasHour
                    Integer32,
                avCmMeasIpVoStatSumDataYestRunTime
                    SnmpAdminString,
                avCmMeasIpVoStatSumDataYestBoardLoc
                    SnmpAdminString,
                avCmMeasIpVoStatSumDataYestCallingNum
                    SnmpAdminString,
                avCmMeasIpVoStatSumDataYestCalledNum
                    SnmpAdminString,
                avCmMeasIpVoStatSumDataYestDstReg
                    Integer32,
                avCmMeasIpVoStatSumDataYestCodec
                    SnmpAdminString,
                avCmMeasIpVoStatSumDataYestDataType
                    SnmpAdminString,
                avCmMeasIpVoStatSumDataYestPktSize
                    Integer32,
                avCmMeasIpVoStatSumDataYestLossPerc
                    SnmpAdminString,
                avCmMeasIpVoStatSumDataYestPeakJitter
                    Integer32,
                avCmMeasIpVoStatSumDataYestPeakDly
                    Integer32,
                avCmMeasIpVoStatSumDataYestEC
                    SnmpAdminString,
                avCmMeasIpVoStatSumDataYestFEAddr
                    SnmpAdminString
		}

avCmMeasIpVoStatSumDataYestRegIdx	OBJECT-TYPE
    SYNTAX	Integer32 (1..2000)
    MAX-ACCESS	not-accessible
    STATUS	current
    DESCRIPTION
	"
	Fld OID Name:	avCmMeasIpVoStatSumDataYestRegIdx
	Fld OID:	enterprises.6889.2.73.8.1.79.1.1.1
	Fld Form/Rpt:	NA
	Fld Format:	NA
	Fld(s) Name:	NA
	Fld Descr:	An index into the network region.
	"
    ::= { avCmMeasIpVoStatSumDataYestEntry 1 }

avCmMeasIpVoStatSumDataYestHourIdx        OBJECT-TYPE
    SYNTAX      Integer32 (0..2300)
    MAX-ACCESS	not-accessible
    STATUS      current
    DESCRIPTION
        "
        Fld OID Name:   avCmMeasIpVoStatSumDataYestHourIdx
        Fld OID:        enterprises.6889.2.73.8.1.79.1.1.2
        Fld Form/Rpt:   NA
        Fld Format:     NA
        Fld(s) Name:    NA
        Fld Descr:      An index that contains the measurement hour in military
			time for the data loss voice statistics.
        "
    ::= { avCmMeasIpVoStatSumDataYestEntry 2 }

avCmMeasIpVoStatSumDataYestIdx        OBJECT-TYPE
    SYNTAX      Integer32 (0..9999)
    MAX-ACCESS	not-accessible
    STATUS      current
    DESCRIPTION
        "
        Fld OID Name:   avCmMeasIpVoStatSumDataYestIdx
        Fld OID:        enterprises.6889.2.73.8.1.79.1.1.3
        Fld Form/Rpt:   NA
        Fld Format:     NA
        Fld(s) Name:    NA
        Fld Descr:      An index for the data loss voice statistics.
        "
    ::= { avCmMeasIpVoStatSumDataYestEntry 3 }

avCmMeasIpVoStatSumDataYestRegion        OBJECT-TYPE
    SYNTAX      Integer32 (0..2000)
    MAX-ACCESS  read-only
    STATUS      current
    DESCRIPTION
        "
        Fld OID Name:   avCmMeasIpVoStatSumDataYestRegion
        Fld OID:        enterprises.6889.2.73.8.1.79.1.1.4
        Fld Form/Rpt:   IP VOICE STATISTICS SUMMARY DATA REPORT
        Fld Format:     Single Field
        Fld(s) Name:    List Command: Region
        Fld Descr:      An object that contains the Network Region.
        "
    ::= { avCmMeasIpVoStatSumDataYestEntry 4 }

avCmMeasIpVoStatSumDataYestMeasHour	OBJECT-TYPE
    SYNTAX      Integer32 (0..2300)
    MAX-ACCESS	read-only
    STATUS	current
    DESCRIPTION
	"
	Fld OID Name:	avCmMeasIpVoStatSumDataYestMeasHour
	Fld OID:	enterprises.6889.2.73.8.1.79.1.1.5
	Fld Form/Rpt:	IP VOICE STATISTICS SUMMARY DATA REPORT
	Fld Format:	Single
	Fld(s) Name:	Measurement Hour
	Fld Descr:	An object containing the measurement hour.
	"
    ::= { avCmMeasIpVoStatSumDataYestEntry 5 }

avCmMeasIpVoStatSumDataYestRunTime	OBJECT-TYPE
    SYNTAX	SnmpAdminString (SIZE (0..28))
    MAX-ACCESS	read-only
    STATUS	current
    DESCRIPTION
	"
	Fld OID Name:	avCmMeasIpVoStatSumDataYestRunTime
	Fld OID:	enterprises.6889.2.73.8.1.79.1.1.6
	Fld Form/Rpt:	IP VOICE STATISTICS SUMMARY DATA REPORT
	Fld Format:	Single
	Fld(s) Name:	Date
	Fld Descr:	An object containing the Date.
	"
    ::= { avCmMeasIpVoStatSumDataYestEntry 6 }

avCmMeasIpVoStatSumDataYestBoardLoc	OBJECT-TYPE
    SYNTAX	SnmpAdminString (SIZE (0..6))
    MAX-ACCESS	read-only
    STATUS	current
    DESCRIPTION
	"
	Fld OID Name:	avCmMeasIpVoStatSumDataYestBoardLoc
	Fld OID:	enterprises.6889.2.73.8.1.79.1.1.7
	Fld Form/Rpt:	IP VOICE STATISTICS SUMMARY DATA REPORT
	Fld Format:	Single
	Fld(s) Name:	Board Loc
	Fld Descr:	An object containing the Board location.
	"
    ::= { avCmMeasIpVoStatSumDataYestEntry 7 }

avCmMeasIpVoStatSumDataYestCallingNum	OBJECT-TYPE
    SYNTAX	SnmpAdminString (SIZE (0..17))
    MAX-ACCESS	read-only
    STATUS	current
    DESCRIPTION
	"
	Fld OID Name:	avCmMeasIpVoStatSumDataYestCallingNum
	Fld OID:	enterprises.6889.2.73.8.1.79.1.1.8
	Fld Form/Rpt:	IP VOICE STATISTICS SUMMARY DATA REPORT
	Fld Format:	Single
	Fld(s) Name:	Calling Number
	Fld Descr:	An object containing the Calling Number.
	"
    ::= { avCmMeasIpVoStatSumDataYestEntry 8 }

avCmMeasIpVoStatSumDataYestCalledNum      OBJECT-TYPE
    SYNTAX      SnmpAdminString (SIZE (0..17))
    MAX-ACCESS  read-only
    STATUS      current
    DESCRIPTION
        "
        Fld OID Name:   avCmMeasIpVoStatSumDataYestCalledNum
        Fld OID:        enterprises.6889.2.73.8.1.79.1.1.9
        Fld Form/Rpt:   IP VOICE STATISTICS SUMMARY DATA REPORT
        Fld Format:     Single
        Fld(s) Name:    Called Number
        Fld Descr:      An object containing the Called Number.
        "
    ::= { avCmMeasIpVoStatSumDataYestEntry 9 }


avCmMeasIpVoStatSumDataYestDstReg      OBJECT-TYPE
    SYNTAX      Integer32 (0..9999)
    MAX-ACCESS  read-only
    STATUS      current
    DESCRIPTION
        "
        Fld OID Name:   avCmMeasIpVoStatSumDataYestDstReg
        Fld OID:        enterprises.6889.2.73.8.1.79.1.1.10
        Fld Form/Rpt:   IP VOICE STATISTICS SUMMARY DATA REPORT
        Fld Format:     Single
        Fld(s) Name:    Dst Reg
        Fld Descr:      The network region where the destination
			media processor is located.
        "
    ::= { avCmMeasIpVoStatSumDataYestEntry 10 }

avCmMeasIpVoStatSumDataYestCodec      OBJECT-TYPE
    SYNTAX      SnmpAdminString (SIZE (0..8))
    MAX-ACCESS  read-only
    STATUS      current
    DESCRIPTION
        "
        Fld OID Name:   avCmMeasIpVoStatSumDataYestCodec
        Fld OID:        enterprises.6889.2.73.8.1.79.1.1.11
        Fld Form/Rpt:   IP VOICE STATISTICS SUMMARY DATA REPORT
        Fld Format:     Single
        Fld(s) Name:    Codec
        Fld Descr:      An object containing the Codec used for the call.
        "
    ::= { avCmMeasIpVoStatSumDataYestEntry 11 }

avCmMeasIpVoStatSumDataYestDataType      OBJECT-TYPE
    SYNTAX      SnmpAdminString (SIZE (0..7))
    MAX-ACCESS  read-only
    STATUS      current
    DESCRIPTION
        "
        Fld OID Name:   avCmMeasIpVoStatSumDataYestDataType
        Fld OID:        enterprises.6889.2.73.8.1.79.1.1.12
        Fld Form/Rpt:   IP VOICE STATISTICS SUMMARY DATA REPORT
        Fld Format:     Single
        Fld(s) Name:    Data Type
        Fld Descr:      Indicates the type of data call. Valid options
                        include:
                        ~ ttyrel (TTY Relay)
                        ~ mod-pt (Modem pass-through)
                        ~ fax-pt (FAX pass-through)
                        ~ tty-pt (TTY pass-through)
                        ~ t38fax (T.38 FAX)
                        ~ faxrel (FAX relay)
                        ~ modrel (Modem relay)
        "
    ::= { avCmMeasIpVoStatSumDataYestEntry 12 }

avCmMeasIpVoStatSumDataYestPktSize      OBJECT-TYPE
    SYNTAX      Integer32 (0..999)
    MAX-ACCESS  read-only
    STATUS      current
    DESCRIPTION
        "
        Fld OID Name:   avCmMeasIpVoStatSumDataYestPktSize
        Fld OID:        enterprises.6889.2.73.8.1.79.1.1.13
        Fld Form/Rpt:   IP VOICE STATISTICS SUMMARY DATA REPORT
        Fld Format:     Single
        Fld(s) Name:    Pkt Size
        Fld Descr:      The packet size for each steam of data for
                        the associated call, measured in
                        milliseconds.
        "
    ::= { avCmMeasIpVoStatSumDataYestEntry 13 }


avCmMeasIpVoStatSumDataYestLossPerc      OBJECT-TYPE
    SYNTAX      SnmpAdminString (SIZE (0..4))
    MAX-ACCESS  read-only
    STATUS      current
    DESCRIPTION
        "
        Fld OID Name:   avCmMeasIpVoStatSumDataYestLossPerc
        Fld OID:        enterprises.6889.2.73.8.1.79.1.1.14
        Fld Form/Rpt:   IP VOICE STATISTICS SUMMARY DATA REPORT
        Fld Format:     Single
        Fld(s) Name:    Loss %
        Fld Descr:      The packet Loss for the call. The Packet loss
                        percentage is calculated at 10-second
                        intervals.
        "
    ::= { avCmMeasIpVoStatSumDataYestEntry 14 }

avCmMeasIpVoStatSumDataYestPeakJitter      OBJECT-TYPE
    SYNTAX      Integer32 (0..9999)
    MAX-ACCESS  read-only
    STATUS      current
    DESCRIPTION
        "
        Fld OID Name:   avCmMeasIpVoStatSumDataYestPeakJitter
        Fld OID:        enterprises.6889.2.73.8.1.79.1.1.15
        Fld Form/Rpt:   IP VOICE STATISTICS SUMMARY DATA REPORT
        Fld Format:     Single
        Fld(s) Name:    Peak Jit
        Fld Descr:      The peak amount of jitter recorded for the
                        call, measured in milliseconds.
        "
    ::= { avCmMeasIpVoStatSumDataYestEntry 15 }

avCmMeasIpVoStatSumDataYestPeakDly      OBJECT-TYPE
    SYNTAX      Integer32 (0..9999)
    MAX-ACCESS  read-only
    STATUS      current
    DESCRIPTION
        "
        Fld OID Name:   avCmMeasIpVoStatSumDataYestPeakDly
        Fld OID:        enterprises.6889.2.73.8.1.79.1.1.16
        Fld Form/Rpt:   IP VOICE STATISTICS SUMMARY DATA REPORT
        Fld Format:     Single
        Fld(s) Name:    Dly
        Fld Descr:      The peak round trip delay recorded for the
                        call, measured in milliseconds.
        "
    ::= { avCmMeasIpVoStatSumDataYestEntry 16 }

avCmMeasIpVoStatSumDataYestEC      OBJECT-TYPE
    SYNTAX      SnmpAdminString (SIZE (0..2))
    MAX-ACCESS  read-only
    STATUS      current
    DESCRIPTION
        "
        Fld OID Name:   avCmMeasIpVoStatSumDataYestEC
        Fld OID:        enterprises.6889.2.73.8.1.79.1.1.17
        Fld Form/Rpt:   IP VOICE STATISTICS SUMMARY DATA REPORT
        Fld Format:     Single
        Fld(s) Name:    EC
        Fld Descr:      Indicates whether the echo cancellation is on/off for 
			the call.
        "
    ::= { avCmMeasIpVoStatSumDataYestEntry 17 }

avCmMeasIpVoStatSumDataYestFEAddr      OBJECT-TYPE
    SYNTAX      SnmpAdminString (SIZE (0..41))
    MAX-ACCESS  read-only
    STATUS      current
    DESCRIPTION
        "
        Fld OID Name:   avCmMeasIpVoStatSumDataYestFEAddr
        Fld OID:        enterprises.6889.2.73.8.1.79.1.1.18
        Fld Form/Rpt:   IP VOICE STATISTICS SUMMARY DATA REPORT
        Fld Format:     Single
        Fld(s) Name:    FE-Addr
        Fld Descr:      An object containing the far-end ip-address.
        "
    ::= { avCmMeasIpVoStatSumDataYestEntry 18 }

-- ******************** avCmMeasAnnAllLstHr Group *************************

-- MIB GROUP DESCRIPTION

-- MIB Group Name:
--		avCmMeasAnnAllLstHr Group
-- OID:
--		enterprises.6889.2.73.8.1.80
-- Description:
--		The avCmMeasAnnAllLstHr MIB Group uses the 
--		"list measurements announcement all last-hour" command to 
--		retrieve measurements information for all announcement 
--		information for the last hour.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements announcement all last-hour
-- Form/Report Name:
--		1. VOICE ANNOUNCEMENT MEASUREMENTS
-- Reference Document:
--		1. A detailed description of the command and form can be
--		   found in document referenced by REF_DOC_4 in the
--		   DOCUMENT REFERENCE SECTION.
-- Command Permission/User-profile:
--		1. No special permissions needed.

avCmMeasAnnAllLstHr	OBJECT IDENTIFIER ::= { avCmObjects 80 }

avCmMeasAnnAllLstHrTable	OBJECT-TYPE
    SYNTAX	SEQUENCE OF AvCmMeasAnnAllLstHrEntry
    MAX-ACCESS	not-accessible
    STATUS	current
    DESCRIPTION
	"
	Fld OID Name:	avCmMeasAnnAllLstHrEntry
	Fld OID:	enterprises.6889.2.73.8.1.80.1
	Fld Form/Rpt:	NA
	Fld Format:	NA
	Fld(s) Name:	NA
	Fld Descr:	A list of the avCmMeasAnnAllLstHr entries
	"
    ::= { avCmMeasAnnAllLstHr 1 }

avCmMeasAnnAllLstHrEntry	OBJECT-TYPE
    SYNTAX	AvCmMeasAnnAllLstHrEntry
    MAX-ACCESS	not-accessible
    STATUS	current
    DESCRIPTION
	"
	Fld OID Name:	avCmMeasAnnAllLstHrEntry
	Fld OID:	enterprises.6889.2.73.8.1.80.1.1
	Fld Form/Rpt:	NA
	Fld Format:	NA
	Fld(s) Name:	NA
	Fld Descr:	A avCmMeasAnnAllLstHr entry containing objects of the
			avCmMeasAnnAllLstHr information sent by the switch.
	"
    INDEX    { avCmMeasAnnAllLstHrIdx }
    ::= { avCmMeasAnnAllLstHrTable 1 }

AvCmMeasAnnAllLstHrEntry ::= SEQUENCE {
		avCmMeasAnnAllLstHrIdx
		    SnmpAdminString,
		avCmMeasAnnAllLstHrExtension
		    SnmpAdminString,
		avCmMeasAnnAllLstHrRunDate
		    SnmpAdminString,
		avCmMeasAnnAllLstHrName
		    SnmpAdminString,
		avCmMeasAnnAllLstHrMeasHour
		    Integer32,
		avCmMeasAnnAllLstHrPlayRequests
		    Integer32,
		avCmMeasAnnAllLstHrCallsQueued
		    Integer32,
		avCmMeasAnnAllLstHrASP
		    Integer32,
		avCmMeasAnnAllLstHrPSP
		    Integer32,
		avCmMeasAnnAllLstHrQueueDrops
		    Integer32,
		avCmMeasAnnAllLstHrMportPlays
		    Integer32,
		avCmMeasAnnAllLstHrMxPorts
		    Integer32,
		avCmMeasAnnAllLstHrMaxCallers
		    Integer32
		}

avCmMeasAnnAllLstHrIdx	OBJECT-TYPE
    SYNTAX	SnmpAdminString (SIZE (0..17))
    MAX-ACCESS	not-accessible
    STATUS	current
    DESCRIPTION
	"
	Fld OID Name:	avCmMeasAnnAllLstHrIdx
	Fld OID:	enterprises.6889.2.73.8.1.80.1.1.1
	Fld Format:	NA
	Fld(s) Name:	NA
	Fld Descr:	An object that uniquely identifies each Increment of 
			data.
	"
    ::= { avCmMeasAnnAllLstHrEntry 1 }

avCmMeasAnnAllLstHrExtension	OBJECT-TYPE
    SYNTAX	SnmpAdminString (SIZE (0..17))
    MAX-ACCESS	read-only
    STATUS	current
    DESCRIPTION
	"
	Fld OID Name:	avCmMeasAnnAllLstHrExtension
	Fld OID:	enterprises.6889.2.73.8.1.80.1.1.2
	Fld Form/Rpt:	VOICE ANNOUNCEMENT MEASUREMENTS
	Fld Format:	Single Field
	Fld(s) Name:	Extension
	Fld Descr:	An object containing the announcement extension.
	"
    ::= { avCmMeasAnnAllLstHrEntry 2 }

avCmMeasAnnAllLstHrRunDate	OBJECT-TYPE
    SYNTAX	SnmpAdminString (SIZE (0..28))
    MAX-ACCESS	read-only
    STATUS	current
    DESCRIPTION
	"
	Fld OID Name:	avCmMeasAnnAllLstHrRunDate
	Fld OID:	enterprises.6889.2.73.8.1.80.1.1.3
	Fld Form/Rpt:	VOICE ANNOUNCEMENT MEASUREMENTS
	Fld Format:	Single Field
	Fld(s) Name:	Date
	Fld Descr:	An object containing the Date the command was executed.
	"
    ::= { avCmMeasAnnAllLstHrEntry 3 }

avCmMeasAnnAllLstHrName   OBJECT-TYPE
    SYNTAX	SnmpAdminString (SIZE (0..25))
    MAX-ACCESS  read-only
    STATUS      current
    DESCRIPTION
        "
        Fld OID Name:   avCmMeasAnnAllLstHrName
        Fld OID:        enterprises.6889.2.73.8.1.80.1.1.4
        Fld Form/Rpt:   VOICE ANNOUNCEMENT MEASUREMENTS
        Fld Format:     Single Field
        Fld(s) Name:    Name
        Fld Descr:      An object containing the 24 characters of the 
			announcement name.
        "
    ::= { avCmMeasAnnAllLstHrEntry 4 }


avCmMeasAnnAllLstHrMeasHour	OBJECT-TYPE
    SYNTAX	Integer32 (0..9999)
    MAX-ACCESS	read-only
    STATUS	current
    DESCRIPTION
	"
	Fld OID Name:	avCmMeasAnnAllLstHrMeasHour
	Fld OID:	enterprises.6889.2.73.8.1.80.1.1.5
	Fld Form/Rpt:	VOICE ANNOUNCEMENT MEASUREMENTS
	Fld Format:	Single Field
	Fld(s) Name:	Meas Hour
	Fld Descr:	An object containing the measurement hour.
	"
    ::= { avCmMeasAnnAllLstHrEntry 5 }

avCmMeasAnnAllLstHrPlayRequests	OBJECT-TYPE
    SYNTAX	Integer32 (0..99999)
    MAX-ACCESS	read-only
    STATUS	current
    DESCRIPTION
	"
	Fld OID Name:	avCmMeasAnnAllLstHrPlayRequests
	Fld OID:	enterprises.6889.2.73.8.1.80.1.1.6
	Fld Form/Rpt:	VOICE ANNOUNCEMENT MEASUREMENTS
	Fld Format:	Single Field
	Fld(s) Name:	Play Reqts
	Fld Descr:	An object containing the number of play requests
			for the announcement.
	"
    ::= { avCmMeasAnnAllLstHrEntry 6 }

avCmMeasAnnAllLstHrCallsQueued OBJECT-TYPE
    SYNTAX      Integer32 (0..99999)
    MAX-ACCESS  read-only
    STATUS      current
    DESCRIPTION
        "
        Fld OID Name:   avCmMeasAnnAllLstHrCallsQueued
        Fld OID:        enterprises.6889.2.73.8.1.80.1.1.7
        Fld Form/Rpt:   VOICE ANNOUNCEMENT MEASUREMENTS
        Fld Format:     Single Field
        Fld(s) Name:    Calls Que
        Fld Descr:      An object containing the number of calls for an 
			announcement that had to queue waiting for a port 
			during the period.
        "
    ::= { avCmMeasAnnAllLstHrEntry 7 }


avCmMeasAnnAllLstHrASP OBJECT-TYPE
    SYNTAX      Integer32 (0..9999)
    MAX-ACCESS  read-only
    STATUS      current
    DESCRIPTION
        "
        Fld OID Name:   avCmMeasAnnAllLstHrASP
        Fld OID:        enterprises.6889.2.73.8.1.80.1.1.8
        Fld Form/Rpt:   VOICE ANNOUNCEMENT MEASUREMENTS
        Fld Format:     Single Field
        Fld(s) Name:    ASP
        Fld Descr:      An object containing from time waiting for announcement
			to play to when it starts playing in seconds averaged 
			over the period.  Calls abandoned while in the waiting 
			for announcement port queue are not to be included.
        "
    ::= { avCmMeasAnnAllLstHrEntry 8 }

avCmMeasAnnAllLstHrPSP OBJECT-TYPE
    SYNTAX      Integer32 (0..9999)
    MAX-ACCESS  read-only
    STATUS      current
    DESCRIPTION
        "
        Fld OID Name:   avCmMeasAnnAllLstHrPSP
        Fld OID:        enterprises.6889.2.73.8.1.80.1.1.9
        Fld Form/Rpt:   VOICE ANNOUNCEMENT MEASUREMENTS
        Fld Format:     Single Field
        Fld(s) Name:    PSP
        Fld Descr:      An object containing the peak speed to play an 
			announcement.
        "
    ::= { avCmMeasAnnAllLstHrEntry 9 }


avCmMeasAnnAllLstHrQueueDrops OBJECT-TYPE
    SYNTAX      Integer32 (0..99999)
    MAX-ACCESS  read-only
    STATUS      current
    DESCRIPTION
        "
        Fld OID Name:   avCmMeasAnnAllLstHrQueueDrops
        Fld OID:        enterprises.6889.2.73.8.1.80.1.1.10
        Fld Form/Rpt:   VOICE ANNOUNCEMENT MEASUREMENTS
        Fld Format:     Single Field
        Fld(s) Name:    Queue Drops
        Fld Descr:      An object containing - count of the individual calls 
			that had to queue but dropped while waiting during the 
			period - this includes calls abandoned by the caller 
			and VOA (VDN of origin Announcements) aborts but should 
			exclude calls that were waiting but answered by an 
			agent.
        "
    ::= { avCmMeasAnnAllLstHrEntry 10 }


avCmMeasAnnAllLstHrMportPlays OBJECT-TYPE
    SYNTAX      Integer32 (0..99999)
    MAX-ACCESS  read-only
    STATUS      current
    DESCRIPTION
        "
        Fld OID Name:   avCmMeasAnnAllLstHrMportPlays
        Fld OID:        enterprises.6889.2.73.8.1.80.1.1.11
        Fld Form/Rpt:   VOICE ANNOUNCEMENT MEASUREMENTS
        Fld Format:     Single Field
        Fld(s) Name:    Mport Plays
        Fld Descr:      An object containing - count of how many times the 
			announcement is being played out of more than one port 
			at the same time during the period.
        "
    ::= { avCmMeasAnnAllLstHrEntry 11 }


avCmMeasAnnAllLstHrMxPorts OBJECT-TYPE
    SYNTAX      Integer32 (0..99)
    MAX-ACCESS  read-only
    STATUS      current
    DESCRIPTION
        "
        Fld OID Name:   avCmMeasAnnAllLstHrMxPorts
        Fld OID:        enterprises.6889.2.73.8.1.80.1.1.12
        Fld Form/Rpt:   VOICE ANNOUNCEMENT MEASUREMENTS
        Fld Format:     Single Field
        Fld(s) Name:    Mx Pt
        Fld Descr:      An object containing the peak number of ports used for 
			the announcement during the period.
        "
    ::= { avCmMeasAnnAllLstHrEntry 12 }


avCmMeasAnnAllLstHrMaxCallers OBJECT-TYPE
    SYNTAX      Integer32 (0..999)
    MAX-ACCESS  read-only
    STATUS      current
    DESCRIPTION
        "
        Fld OID Name:   avCmMeasAnnAllLstHrMaxCallers
        Fld OID:        enterprises.6889.2.73.8.1.80.1.1.13
        Fld Form/Rpt:   VOICE ANNOUNCEMENT MEASUREMENTS
        Fld Format:     Single Field
        Fld(s) Name:    Max Cls
        Fld Descr:      An object containing the peak number callers connected 
			to a port at the same time for this announcement during
			the period
        "
    ::= { avCmMeasAnnAllLstHrEntry 13 }


-- ******************** avCmMeasAnnAllToday Group *************************

-- MIB GROUP DESCRIPTION

-- MIB Group Name:
--		avCmMeasAnnAllToday Group
-- OID:
--		enterprises.6889.2.73.8.1.81
-- Description:
--		The avCmMeasAnnAllToday MIB Group uses the 
--		"list measurements announcement all today-peak" command to 
--		retrieve measurements information for all announcement 
--		information for the current day.
--		
-- Releases Supported:
--		CM6.3.100 and greater
-- Polling Type:
--		Performance/Utilization
-- Polling Interval:
--		No more than once an hour because the data is only updated
--		after the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements announcement all today-peak
-- Form/Report Name:
--		1. VOICE ANNOUNCEMENT MEASUREMENTS
-- Reference Document:
--		1. A detailed description of the command and form can be
--		   found in document referenced by REF_DOC_4 in the
--		   DOCUMENT REFERENCE SECTION.
-- Command Permission/User-profile:
--		1. No special permissions needed.

avCmMeasAnnAllToday	OBJECT IDENTIFIER ::= { avCmObjects 81 }

avCmMeasAnnAllTodayTable	OBJECT-TYPE
    SYNTAX	SEQUENCE OF AvCmMeasAnnAllTodayEntry
    MAX-ACCESS	not-accessible
    STATUS	current
    DESCRIPTION
	"
	Fld OID Name:	avCmMeasAnnAllTodayEntry
	Fld OID:	enterprises.6889.2.73.8.1.81.1
	Fld Form/Rpt:	NA
	Fld Format:	NA
	Fld(s) Name:	NA
	Fld Descr:	A list of the avCmMeasAnnAllToday entries
	"
    ::= { avCmMeasAnnAllToday 1 }

avCmMeasAnnAllTodayEntry	OBJECT-TYPE
    SYNTAX	AvCmMeasAnnAllTodayEntry
    MAX-ACCESS	not-accessible
    STATUS	current
    DESCRIPTION
	"
	Fld OID Name:	avCmMeasAnnAllTodayEntry
	Fld OID:	enterprises.6889.2.73.8.1.81.1.1
	Fld Form/Rpt:	NA
	Fld Format:	NA
	Fld(s) Name:	NA
	Fld Descr:	A avCmMeasAnnAllToday entry containing objects of the
			avCmMeasAnnAllToday information sent by the switch.
	"
    INDEX    { avCmMeasAnnAllTodayIdx }
    ::= { avCmMeasAnnAllTodayTable 1 }

AvCmMeasAnnAllTodayEntry ::= SEQUENCE {
		avCmMeasAnnAllTodayIdx
		    SnmpAdminString,
		avCmMeasAnnAllTodayExtension
		    SnmpAdminString,
		avCmMeasAnnAllTodayRunDate
		    SnmpAdminString,
		avCmMeasAnnAllTodayName
		    SnmpAdminString,
		avCmMeasAnnAllTodayMeasHour
		    Integer32,
		avCmMeasAnnAllTodayPlayRequests
		    Integer32,
		avCmMeasAnnAllTodayCallsQueued
		    Integer32,
		avCmMeasAnnAllTodayASP
		    Integer32,
		avCmMeasAnnAllTodayPSP
		    Integer32,
		avCmMeasAnnAllTodayQueueDrops
		    Integer32,
		avCmMeasAnnAllTodayMportPlays
		    Integer32,
		avCmMeasAnnAllTodayMxPorts
		    Integer32,
		avCmMeasAnnAllTodayMaxCallers
		    Integer32
		}

avCmMeasAnnAllTodayIdx	OBJECT-TYPE
    SYNTAX	SnmpAdminString (SIZE (0..17))
    MAX-ACCESS	not-accessible
    STATUS	current
    DESCRIPTION
	"
	Fld OID Name:	avCmMeasAnnAllTodayIdx
	Fld OID:	enterprises.6889.2.73.8.1.81.1.1.1
	Fld Format:	NA
	Fld(s) Name:	NA
	Fld Descr:	An object that uniquely identifies each Increment of 
			data.
	"
    ::= { avCmMeasAnnAllTodayEntry 1 }

avCmMeasAnnAllTodayExtension	OBJECT-TYPE
    SYNTAX	SnmpAdminString (SIZE (0..17))
    MAX-ACCESS	read-only
    STATUS	current
    DESCRIPTION
	"
	Fld OID Name:	avCmMeasAnnAllTodayExtension
	Fld OID:	enterprises.6889.2.73.8.1.81.1.1.2
	Fld Form/Rpt:	VOICE ANNOUNCEMENT MEASUREMENTS
	Fld Format:	Single Field
	Fld(s) Name:	Extension
	Fld Descr:	An object containing the announcement extension.
	"
    ::= { avCmMeasAnnAllTodayEntry 2 }

avCmMeasAnnAllTodayRunDate	OBJECT-TYPE
    SYNTAX	SnmpAdminString (SIZE (0..28))
    MAX-ACCESS	read-only
    STATUS	current
    DESCRIPTION
	"
	Fld OID Name:	avCmMeasAnnAllTodayRunDate
	Fld OID:	enterprises.6889.2.73.8.1.81.1.1.3
	Fld Form/Rpt:	VOICE ANNOUNCEMENT MEASUREMENTS
	Fld Format:	Single Field
	Fld(s) Name:	Date
	Fld Descr:	An object containing the Date the command was executed.
	"
    ::= { avCmMeasAnnAllTodayEntry 3 }

avCmMeasAnnAllTodayName   OBJECT-TYPE
    SYNTAX	SnmpAdminString (SIZE (0..25))
    MAX-ACCESS  read-only
    STATUS      current
    DESCRIPTION
        "
        Fld OID Name:   avCmMeasAnnAllTodayName
        Fld OID:        enterprises.6889.2.73.8.1.81.1.1.4
        Fld Form/Rpt:   VOICE ANNOUNCEMENT MEASUREMENTS
        Fld Format:     Single Field
        Fld(s) Name:    Name
        Fld Descr:      An object containing the 24 characters of the 
			announcement name.
        "
    ::= { avCmMeasAnnAllTodayEntry 4 }


avCmMeasAnnAllTodayMeasHour	OBJECT-TYPE
    SYNTAX	Integer32 (0..9999)
    MAX-ACCESS	read-only
    STATUS	current
    DESCRIPTION
	"
	Fld OID Name:	avCmMeasAnnAllTodayMeasHour
	Fld OID:	enterprises.6889.2.73.8.1.81.1.1.5
	Fld Form/Rpt:	VOICE ANNOUNCEMENT MEASUREMENTS
	Fld Format:	Single Field
	Fld(s) Name:	Meas Hour
	Fld Descr:	An object containing the measurement hour.
	"
    ::= { avCmMeasAnnAllTodayEntry 5 }

avCmMeasAnnAllTodayPlayRequests	OBJECT-TYPE
    SYNTAX	Integer32 (0..99999)
    MAX-ACCESS	read-only
    STATUS	current
    DESCRIPTION
	"
	Fld OID Name:	avCmMeasAnnAllTodayPlayRequests
	Fld OID:	enterprises.6889.2.73.8.1.81.1.1.6
	Fld Form/Rpt:	VOICE ANNOUNCEMENT MEASUREMENTS
	Fld Format:	Single Field
	Fld(s) Name:	Play Reqts
	Fld Descr:	An object containing the number of play requests
			for the announcement.
	"
    ::= { avCmMeasAnnAllTodayEntry 6 }

avCmMeasAnnAllTodayCallsQueued OBJECT-TYPE
    SYNTAX      Integer32 (0..99999)
    MAX-ACCESS  read-only
    STATUS      current
    DESCRIPTION
        "
        Fld OID Name:   avCmMeasAnnAllTodayCallsQueued
        Fld OID:        enterprises.6889.2.73.8.1.81.1.1.7
        Fld Form/Rpt:   VOICE ANNOUNCEMENT MEASUREMENTS
        Fld Format:     Single Field
        Fld(s) Name:    Calls Que
        Fld Descr:      An object containing the number of calls for an 
			announcement that had to queue waiting for a port 
			during the period.
        "
    ::= { avCmMeasAnnAllTodayEntry 7 }


avCmMeasAnnAllTodayASP OBJECT-TYPE
    SYNTAX      Integer32 (0..9999)
    MAX-ACCESS  read-only
    STATUS      current
    DESCRIPTION
        "
        Fld OID Name:   avCmMeasAnnAllTodayASP
        Fld OID:        enterprises.6889.2.73.8.1.81.1.1.8
        Fld Form/Rpt:   VOICE ANNOUNCEMENT MEASUREMENTS
        Fld Format:     Single Field
        Fld(s) Name:    ASP
        Fld Descr:      An object containing from time waiting for announcement
			to play to when it starts playing in seconds averaged 
			over the period.  Calls abandoned while in the waiting 
			for announcement port queue are not to be included.
        "
    ::= { avCmMeasAnnAllTodayEntry 8 }

avCmMeasAnnAllTodayPSP OBJECT-TYPE
    SYNTAX      Integer32 (0..9999)
    MAX-ACCESS  read-only
    STATUS      current
    DESCRIPTION
        "
        Fld OID Name:   avCmMeasAnnAllTodayPSP
        Fld OID:        enterprises.6889.2.73.8.1.81.1.1.9
        Fld Form/Rpt:   VOICE ANNOUNCEMENT MEASUREMENTS
        Fld Format:     Single Field
        Fld(s) Name:    PSP
        Fld Descr:      An object containing the peak speed to play an 
			announcement.
        "
    ::= { avCmMeasAnnAllTodayEntry 9 }


avCmMeasAnnAllTodayQueueDrops OBJECT-TYPE
    SYNTAX      Integer32 (0..99999)
    MAX-ACCESS  read-only
    STATUS      current
    DESCRIPTION
        "
        Fld OID Name:   avCmMeasAnnAllTodayQueueDrops
        Fld OID:        enterprises.6889.2.73.8.1.81.1.1.10
        Fld Form/Rpt:   VOICE ANNOUNCEMENT MEASUREMENTS
        Fld Format:     Single Field
        Fld(s) Name:    Queue Drops
        Fld Descr:      An object containing - count of the individual calls 
			that had to queue but dropped while waiting during the 
			period - this includes calls abandoned by the caller 
			and VOA (VDN of origin Announcements) aborts but should 
			exclude calls that were waiting but answered by an 
			agent.
        "
    ::= { avCmMeasAnnAllTodayEntry 10 }


avCmMeasAnnAllTodayMportPlays OBJECT-TYPE
    SYNTAX      Integer32 (0..99999)
    MAX-ACCESS  read-only
    STATUS      current
    DESCRIPTION
        "
        Fld OID Name:   avCmMeasAnnAllTodayMportPlays
        Fld OID:        enterprises.6889.2.73.8.1.81.1.1.11
        Fld Form/Rpt:   VOICE ANNOUNCEMENT MEASUREMENTS
        Fld Format:     Single Field
        Fld(s) Name:    Mport Plays
        Fld Descr:      An object containing - count of how many times the 
			announcement is being played out of more than one port 
			at the same time during the period.
        "
    ::= { avCmMeasAnnAllTodayEntry 11 }


avCmMeasAnnAllTodayMxPorts OBJECT-TYPE
    SYNTAX      Integer32 (0..99)
    MAX-ACCESS  read-only
    STATUS      current
    DESCRIPTION
        "
        Fld OID Name:   avCmMeasAnnAllTodayMxPorts
        Fld OID:        enterprises.6889.2.73.8.1.81.1.1.12
        Fld Form/Rpt:   VOICE ANNOUNCEMENT MEASUREMENTS
        Fld Format:     Single Field
        Fld(s) Name:    Mx Pt
        Fld Descr:      An object containing the peak number of ports used for 
			the announcement during the period.
        "
    ::= { avCmMeasAnnAllTodayEntry 12 }


avCmMeasAnnAllTodayMaxCallers OBJECT-TYPE
    SYNTAX      Integer32 (0..999)
    MAX-ACCESS  read-only
    STATUS      current
    DESCRIPTION
        "
        Fld OID Name:   avCmMeasAnnAllTodayMaxCallers
        Fld OID:        enterprises.6889.2.73.8.1.81.1.1.13
        Fld Form/Rpt:   VOICE ANNOUNCEMENT MEASUREMENTS
        Fld Format:     Single Field
        Fld(s) Name:    Max Cls
        Fld Descr:      An object containing the peak number callers connected 
			to a port at the same time for this announcement during
			the period
        "
    ::= { avCmMeasAnnAllTodayEntry 13 }


-- ******************** avCmMeasAnnAllYest Group *************************

-- MIB GROUP DESCRIPTION

-- MIB Group Name:
--		avCmMeasAnnAllYest Group
-- OID:
--		enterprises.6889.2.73.8.1.82
-- Description:
--		The avCmMeasAnnAllYest MIB Group uses the 
--		"list measurements announcement all yesterday-peak" command to 
--		retrieve measurements information for all announcement 
--		information for the previous day.
--		
-- Releases Supported:
--		CM6.3.100 and greater
-- Polling Type:
--		Performance/Utilization
-- Polling Interval:
--		No more than once a day because the data is only updated
--		after the beginning of the new day.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements announcement all yesterday-peak
-- Form/Report Name:
--		1. VOICE ANNOUNCEMENT MEASUREMENTS
-- Reference Document:
--		1. A detailed description of the command and form can be
--		   found in document referenced by REF_DOC_4 in the
--		   DOCUMENT REFERENCE SECTION.
-- Command Permission/User-profile:
--		1. No special permissions needed.

avCmMeasAnnAllYest	OBJECT IDENTIFIER ::= { avCmObjects 82 }

avCmMeasAnnAllYestTable	OBJECT-TYPE
    SYNTAX	SEQUENCE OF AvCmMeasAnnAllYestEntry
    MAX-ACCESS	not-accessible
    STATUS	current
    DESCRIPTION
	"
	Fld OID Name:	avCmMeasAnnAllYestEntry
	Fld OID:	enterprises.6889.2.73.8.1.82.1
	Fld Form/Rpt:	NA
	Fld Format:	NA
	Fld(s) Name:	NA
	Fld Descr:	A list of the avCmMeasAnnAllYest entries
	"
    ::= { avCmMeasAnnAllYest 1 }

avCmMeasAnnAllYestEntry	OBJECT-TYPE
    SYNTAX	AvCmMeasAnnAllYestEntry
    MAX-ACCESS	not-accessible
    STATUS	current
    DESCRIPTION
	"
	Fld OID Name:	avCmMeasAnnAllYestEntry
	Fld OID:	enterprises.6889.2.73.8.1.82.1.1
	Fld Form/Rpt:	NA
	Fld Format:	NA
	Fld(s) Name:	NA
	Fld Descr:	A avCmMeasAnnAllYest entry containing objects of the
			avCmMeasAnnAllYest information sent by the switch.
	"
    INDEX    { avCmMeasAnnAllYestIdx }
    ::= { avCmMeasAnnAllYestTable 1 }

AvCmMeasAnnAllYestEntry ::= SEQUENCE {
		avCmMeasAnnAllYestIdx
		    SnmpAdminString,
		avCmMeasAnnAllYestExtension
		    SnmpAdminString,
		avCmMeasAnnAllYestRunDate
		    SnmpAdminString,
		avCmMeasAnnAllYestName
		    SnmpAdminString,
		avCmMeasAnnAllYestMeasHour
		    Integer32,
		avCmMeasAnnAllYestPlayRequests
		    Integer32,
		avCmMeasAnnAllYestCallsQueued
		    Integer32,
		avCmMeasAnnAllYestASP
		    Integer32,
		avCmMeasAnnAllYestPSP
		    Integer32,
		avCmMeasAnnAllYestQueueDrops
		    Integer32,
		avCmMeasAnnAllYestMportPlays
		    Integer32,
		avCmMeasAnnAllYestMxPorts
		    Integer32,
		avCmMeasAnnAllYestMaxCallers
		    Integer32
		}

avCmMeasAnnAllYestIdx	OBJECT-TYPE
    SYNTAX	SnmpAdminString (SIZE (0..17))
    MAX-ACCESS	not-accessible
    STATUS	current
    DESCRIPTION
	"
	Fld OID Name:	avCmMeasAnnAllYestIdx
	Fld OID:	enterprises.6889.2.73.8.1.82.1.1.1
	Fld Format:	NA
	Fld(s) Name:	NA
	Fld Descr:	An object that uniquely identifies each Increment of 
			data.
	"
    ::= { avCmMeasAnnAllYestEntry 1 }

avCmMeasAnnAllYestExtension	OBJECT-TYPE
    SYNTAX	SnmpAdminString (SIZE (0..17))
    MAX-ACCESS	read-only
    STATUS	current
    DESCRIPTION
	"
	Fld OID Name:	avCmMeasAnnAllYestExtension
	Fld OID:	enterprises.6889.2.73.8.1.82.1.1.2
	Fld Form/Rpt:	VOICE ANNOUNCEMENT MEASUREMENTS
	Fld Format:	Single Field
	Fld(s) Name:	Extension
	Fld Descr:	An object containing the announcement extension.
	"
    ::= { avCmMeasAnnAllYestEntry 2 }

avCmMeasAnnAllYestRunDate	OBJECT-TYPE
    SYNTAX	SnmpAdminString (SIZE (0..28))
    MAX-ACCESS	read-only
    STATUS	current
    DESCRIPTION
	"
	Fld OID Name:	avCmMeasAnnAllYestRunDate
	Fld OID:	enterprises.6889.2.73.8.1.82.1.1.3
	Fld Form/Rpt:	VOICE ANNOUNCEMENT MEASUREMENTS
	Fld Format:	Single Field
	Fld(s) Name:	Date
	Fld Descr:	An object containing the Date the command was executed.
	"
    ::= { avCmMeasAnnAllYestEntry 3 }

avCmMeasAnnAllYestName   OBJECT-TYPE
    SYNTAX	SnmpAdminString (SIZE (0..25))
    MAX-ACCESS  read-only
    STATUS      current
    DESCRIPTION
        "
        Fld OID Name:   avCmMeasAnnAllYestName
        Fld OID:        enterprises.6889.2.73.8.1.82.1.1.4
        Fld Form/Rpt:   VOICE ANNOUNCEMENT MEASUREMENTS
        Fld Format:     Single Field
        Fld(s) Name:    Name
        Fld Descr:      An object containing the 24 characters of the 
			announcement name.
        "
    ::= { avCmMeasAnnAllYestEntry 4 }


avCmMeasAnnAllYestMeasHour	OBJECT-TYPE
    SYNTAX	Integer32 (0..9999)
    MAX-ACCESS	read-only
    STATUS	current
    DESCRIPTION
	"
	Fld OID Name:	avCmMeasAnnAllYestMeasHour
	Fld OID:	enterprises.6889.2.73.8.1.82.1.1.5
	Fld Form/Rpt:	VOICE ANNOUNCEMENT MEASUREMENTS
	Fld Format:	Single Field
	Fld(s) Name:	Meas Hour
	Fld Descr:	An object containing the measurement hour.
	"
    ::= { avCmMeasAnnAllYestEntry 5 }

avCmMeasAnnAllYestPlayRequests	OBJECT-TYPE
    SYNTAX	Integer32 (0..99999)
    MAX-ACCESS	read-only
    STATUS	current
    DESCRIPTION
	"
	Fld OID Name:	avCmMeasAnnAllYestPlayRequests
	Fld OID:	enterprises.6889.2.73.8.1.82.1.1.6
	Fld Form/Rpt:	VOICE ANNOUNCEMENT MEASUREMENTS
	Fld Format:	Single Field
	Fld(s) Name:	Play Reqts
	Fld Descr:	An object containing the number of play requests
			for the announcement.
	"
    ::= { avCmMeasAnnAllYestEntry 6 }

avCmMeasAnnAllYestCallsQueued OBJECT-TYPE
    SYNTAX      Integer32 (0..99999)
    MAX-ACCESS  read-only
    STATUS      current
    DESCRIPTION
        "
        Fld OID Name:   avCmMeasAnnAllYestCallsQueued
        Fld OID:        enterprises.6889.2.73.8.1.82.1.1.7
        Fld Form/Rpt:   VOICE ANNOUNCEMENT MEASUREMENTS
        Fld Format:     Single Field
        Fld(s) Name:    Calls Que
        Fld Descr:      An object containing the number of calls for an 
			announcement that had to queue waiting for a port 
			during the period.
        "
    ::= { avCmMeasAnnAllYestEntry 7 }


avCmMeasAnnAllYestASP OBJECT-TYPE
    SYNTAX      Integer32 (0..9999)
    MAX-ACCESS  read-only
    STATUS      current
    DESCRIPTION
        "
        Fld OID Name:   avCmMeasAnnAllYestASP
        Fld OID:        enterprises.6889.2.73.8.1.82.1.1.8
        Fld Form/Rpt:   VOICE ANNOUNCEMENT MEASUREMENTS
        Fld Format:     Single Field
        Fld(s) Name:    ASP
        Fld Descr:      An object containing from time waiting for announcement
			to play to when it starts playing in seconds averaged 
			over the period.  Calls abandoned while in the waiting 
			for announcement port queue are not to be included.
        "
    ::= { avCmMeasAnnAllYestEntry 8 }

avCmMeasAnnAllYestPSP OBJECT-TYPE
    SYNTAX      Integer32 (0..9999)
    MAX-ACCESS  read-only
    STATUS      current
    DESCRIPTION
        "
        Fld OID Name:   avCmMeasAnnAllYestPSP
        Fld OID:        enterprises.6889.2.73.8.1.82.1.1.9
        Fld Form/Rpt:   VOICE ANNOUNCEMENT MEASUREMENTS
        Fld Format:     Single Field
        Fld(s) Name:    PSP
        Fld Descr:      An object containing the peak speed to play an 
			announcement.
        "
    ::= { avCmMeasAnnAllYestEntry 9 }


avCmMeasAnnAllYestQueueDrops OBJECT-TYPE
    SYNTAX      Integer32 (0..99999)
    MAX-ACCESS  read-only
    STATUS      current
    DESCRIPTION
        "
        Fld OID Name:   avCmMeasAnnAllYestQueueDrops
        Fld OID:        enterprises.6889.2.73.8.1.82.1.1.10
        Fld Form/Rpt:   VOICE ANNOUNCEMENT MEASUREMENTS
        Fld Format:     Single Field
        Fld(s) Name:    Queue Drops
        Fld Descr:      An object containing - count of the individual calls 
			that had to queue but dropped while waiting during the 
			period - this includes calls abandoned by the caller 
			and VOA (VDN of origin Announcements) aborts but should 
			exclude calls that were waiting but answered by an 
			agent.
        "
    ::= { avCmMeasAnnAllYestEntry 10 }


avCmMeasAnnAllYestMportPlays OBJECT-TYPE
    SYNTAX      Integer32 (0..99999)
    MAX-ACCESS  read-only
    STATUS      current
    DESCRIPTION
        "
        Fld OID Name:   avCmMeasAnnAllYestMportPlays
        Fld OID:        enterprises.6889.2.73.8.1.82.1.1.11
        Fld Form/Rpt:   VOICE ANNOUNCEMENT MEASUREMENTS
        Fld Format:     Single Field
        Fld(s) Name:    Mport Plays
        Fld Descr:      An object containing - count of how many times the 
			announcement is being played out of more than one port 
			at the same time during the period.
        "
    ::= { avCmMeasAnnAllYestEntry 11 }


avCmMeasAnnAllYestMxPorts OBJECT-TYPE
    SYNTAX      Integer32 (0..99)
    MAX-ACCESS  read-only
    STATUS      current
    DESCRIPTION
        "
        Fld OID Name:   avCmMeasAnnAllYestMxPorts
        Fld OID:        enterprises.6889.2.73.8.1.82.1.1.12
        Fld Form/Rpt:   VOICE ANNOUNCEMENT MEASUREMENTS
        Fld Format:     Single Field
        Fld(s) Name:    Mx Pt
        Fld Descr:      An object containing the peak number of ports used for 
			the announcement during the period.
        "
    ::= { avCmMeasAnnAllYestEntry 12 }


avCmMeasAnnAllYestMaxCallers OBJECT-TYPE
    SYNTAX      Integer32 (0..999)
    MAX-ACCESS  read-only
    STATUS      current
    DESCRIPTION
        "
        Fld OID Name:   avCmMeasAnnAllYestMaxCallers
        Fld OID:        enterprises.6889.2.73.8.1.82.1.1.13
        Fld Form/Rpt:   VOICE ANNOUNCEMENT MEASUREMENTS
        Fld Format:     Single Field
        Fld(s) Name:    Max Cls
        Fld Descr:      An object containing the peak number callers connected 
			to a port at the same time for this announcement during
			the period
        "
    ::= { avCmMeasAnnAllYestEntry 13 }

-- ******************** avCmPlatCmds  Group *************************

-- MIB GROUP DESCRIPTION

-- MIB Group Name:
--		avCmPlatCmds  Group
-- OID:
--		enterprises.6889.2.73.8.1.83
-- Description:
--		The avCmPlatCmds  MIB Group uses the 
--		"logc cmds"  command to 
--		retrieve bash command information.
--		
-- Releases Supported:
--		CM6.3.100 and greater
-- Polling Type:
--		Performance/Utilization
-- Polling Interval:
--		No more than once an hour. 
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. BASH
-- Command:
--		1. logc cmds
-- Form/Report Name:
--		1. Command History
-- Reference Document:
--		1. A detailed description of the command and form can be
--		   found in document referenced by REF_DOC_1 in the
--		   DOCUMENT REFERENCE SECTION.
-- Command Permission/User-profile:
--		1. No special permissions needed.

avCmPlatCmds	OBJECT IDENTIFIER ::= { avCmObjects 83 }

avCmPlatCmdsTable	OBJECT-TYPE
    SYNTAX	SEQUENCE OF AvCmPlatCmdsEntry
    MAX-ACCESS	not-accessible
    STATUS	current
    DESCRIPTION
	"
	Fld OID Name:	avCmPlatCmdsEntry
	Fld OID:	enterprises.6889.2.73.8.1.83.1
	Fld Form/Rpt:	NA
	Fld Format:	NA
	Fld(s) Name:	NA
	Fld Descr:	A list of the avCmPlatCmds entries
	"
    ::= { avCmPlatCmds 1 }

avCmPlatCmdsEntry	OBJECT-TYPE
    SYNTAX	AvCmPlatCmdsEntry
    MAX-ACCESS	not-accessible
    STATUS	current
    DESCRIPTION
	"
	Fld OID Name:	avCmPlatCmdsEntry
	Fld OID:	enterprises.6889.2.73.8.1.83.1.1
	Fld Form/Rpt:	NA
	Fld Format:	NA
	Fld(s) Name:	NA
	Fld Descr:	A avCmPlatCmds entry containing objects of the
			avCmPlatCmds information sent by the switch.
	"
    INDEX    { avCmPlatCmdsSeqIdx }
    ::= { avCmPlatCmdsTable 1 }

AvCmPlatCmdsEntry ::= SEQUENCE {
		avCmPlatCmdsSeqIdx
		    Integer32,
		avCmPlatCmdsDate
		    SnmpAdminString,
		avCmPlatCmdsTime
		    SnmpAdminString,
		avCmPlatCmdsSeqNumber
		    Integer32,
		avCmPlatCmdsPriority
		    SnmpAdminString,
		avCmPlatCmdsServerName
		    SnmpAdminString,
		avCmPlatCmdsLoginId
		    SnmpAdminString,
		avCmPlatCmdsCommand
		    SnmpAdminString
		}

avCmPlatCmdsSeqIdx	OBJECT-TYPE
    SYNTAX	Integer32 (0..99999)
    MAX-ACCESS	not-accessible
    STATUS	current
    DESCRIPTION
	"
	Fld OID Name:	avCmPlatCmdsSeqIdx
	Fld OID:	enterprises.6889.2.73.8.1.83.1.1.1
	Fld Format:	NA
	Fld(s) Name:	NA
	Fld Descr:	An object that uniquely identifies each Increment of 
			data.
	"
    ::= { avCmPlatCmdsEntry 1 }

avCmPlatCmdsDate	OBJECT-TYPE
    SYNTAX	SnmpAdminString (SIZE (0..9))
    MAX-ACCESS	read-only
    STATUS	current
    DESCRIPTION
	"
	Fld OID Name:	avCmPlatCmdsDate
	Fld OID:	enterprises.6889.2.73.8.1.83.1.1.2
	Fld Form/Rpt:	Command History
	Fld Format:	Single Field
	Fld(s) Name:	Date
	Fld Descr:	An object containing the date the command was executed.
	"
    ::= { avCmPlatCmdsEntry 2 }

avCmPlatCmdsTime	OBJECT-TYPE
    SYNTAX	SnmpAdminString (SIZE (0..10))
    MAX-ACCESS	read-only
    STATUS	current
    DESCRIPTION
	"
	Fld OID Name:	avCmPlatCmdsTime
	Fld OID:	enterprises.6889.2.73.8.1.83.1.1.3
	Fld Form/Rpt:	Command History
	Fld Format:	Single Field
	Fld(s) Name:	Time
	Fld Descr:	An object containing the time the command was executed.
	"
    ::= { avCmPlatCmdsEntry 3 }

avCmPlatCmdsSeqNumber   OBJECT-TYPE
    SYNTAX	Integer32 (0..99999)
    MAX-ACCESS  read-only
    STATUS      current
    DESCRIPTION
        "
        Fld OID Name:   avCmPlatCmdsSeqNumber
        Fld OID:        enterprises.6889.2.73.8.1.83.1.1.4
        Fld Form/Rpt:   Command History
        Fld Format:     Single Field
        Fld(s) Name:    Sequence Number
        Fld Descr:      An object containing the sequence number
			of the command.
        "
    ::= { avCmPlatCmdsEntry 4 }


avCmPlatCmdsPriority	OBJECT-TYPE
    SYNTAX	SnmpAdminString (SIZE (0..26))
    MAX-ACCESS	read-only
    STATUS	current
    DESCRIPTION
	"
	Fld OID Name:	avCmPlatCmdsPriority
	Fld OID:	enterprises.6889.2.73.8.1.83.1.1.5
	Fld Form/Rpt:	Command History
	Fld Format:	Single Field
	Fld(s) Name:	Priority
	Fld Descr:	An object containing the priority of the command.
	"
    ::= { avCmPlatCmdsEntry 5 }

avCmPlatCmdsServerName	OBJECT-TYPE
    SYNTAX	SnmpAdminString (SIZE (0..26))
    MAX-ACCESS	read-only
    STATUS	current
    DESCRIPTION
	"
	Fld OID Name:	avCmPlatCmdsServerName
	Fld OID:	enterprises.6889.2.73.8.1.83.1.1.6
	Fld Form/Rpt:	Command History
	Fld Format:	Single Field
	Fld(s) Name:	Server Name
	Fld Descr:	An object containing the server name on which the 
			command was issued.
	"
    ::= { avCmPlatCmdsEntry 6 }

avCmPlatCmdsLoginId OBJECT-TYPE
    SYNTAX	SnmpAdminString (SIZE (0..26))
    MAX-ACCESS  read-only
    STATUS      current
    DESCRIPTION
        "
        Fld OID Name:   avCmPlatCmdsLoginId
        Fld OID:        enterprises.6889.2.73.8.1.83.1.1.7
        Fld Form/Rpt:   Command History
        Fld Format:     Single Field
        Fld(s) Name:    Login Id
        Fld Descr:      An object containing the login id that issued the
			command.
        "
    ::= { avCmPlatCmdsEntry 7 }


avCmPlatCmdsCommand OBJECT-TYPE
    SYNTAX	SnmpAdminString (SIZE (0..201))
    MAX-ACCESS  read-only
    STATUS      current
    DESCRIPTION
        "
        Fld OID Name:   avCmPlatCmdsCommand
        Fld OID:        enterprises.6889.2.73.8.1.83.1.1.8
        Fld Form/Rpt:   Command History
        Fld Format:     Single Field
        Fld(s) Name:    Command
        Fld Descr:      An object containing the command issued by the user.
			
        "
    ::= { avCmPlatCmdsEntry 8 }

-- ******************** avCmListSigGrp Group *************************


-- MIB GROUP DESCRIPTION

-- MIB Group Name:
--		avCmListSigGrp Group
-- OID:
--		enterprises.6889.2.73.8.1.84
-- Description:
--		The avCmListSigGrp MIB Group uses the "list signaling-group"
-- 		command to retrieve the systems administered signaling group 
--		information. 
--		
-- Releases Supported:
--		CM6.3.100 and greater
-- Polling Type:
--		Configuration and Inventory
-- Polling Interval:
--		No more than once a day or when signaling administration is 
--		changed.
-- Default Caching Interval
-- 		600 seconds
-- Timeout Interval:
--		Initial Timeout should be set to 20 seconds.
-- Retry Interval:
--		Initial Retry should be set to 3.
-- Limitations:
--		Red/High - The data collected by this MIB Group will
--		increase as the number of administered signaling-groups 
--		increase. Consequently the data collected by this MIB Group 
--		could be very large and therefore may take a very long time to 
--		collect	and could impact system performance.
-- Command Type:
--		1. SAT
-- Command:
--		1. list signaling-group
-- Form/Report Name:
--		1. SIGNALING GROUPS 
-- Reference Document:
--		1. A detailed description of the command and form can be
--		   found in document referenced by REF_DOC_3 in the
--		   DOCUMENT REFERENCE SECTION.
-- Command Permission/User-profile:
--		1. No special permissions needed.

avCmListSigGrp	OBJECT IDENTIFIER ::= { avCmObjects 84 }

avCmListSigGrpTable	OBJECT-TYPE
    SYNTAX	SEQUENCE OF AvCmListSigGrpEntry
    MAX-ACCESS	not-accessible
    STATUS	current
    DESCRIPTION
	"
	Fld OID Name:	avCmListSigGrpEntry
	Fld OID:	enterprises.6889.2.73.8.1.84.1
	Fld Form/Rpt:	NA
	Fld Format:	NA
	Fld(s) Name:	NA
	Fld Descr:	A list of the avCmListSigGrp entries
	"
    ::= { avCmListSigGrp 1 }

avCmListSigGrpEntry	OBJECT-TYPE
    SYNTAX	AvCmListSigGrpEntry
    MAX-ACCESS	not-accessible
    STATUS	current
    DESCRIPTION
	"
	Fld OID Name:	avCmListSigGrpEntry
	Fld OID:	enterprises.6889.2.73.8.1.84.1.1
	Fld Form/Rpt:	NA
	Fld Format:	NA
	Fld(s) Name:	NA
	Fld Descr:	A avCmListSigGrp entry containing objects of the
			avCmListSigGrp information sent by the switch.
	"
    INDEX    { avCmListSigGrpIdx }
    ::= { avCmListSigGrpTable 1 }

AvCmListSigGrpEntry ::= SEQUENCE {
		avCmListSigGrpIdx
		    Integer32,
		avCmListSigGrpGrpNumber
		    Integer32,
		avCmListSigGrpGrpType
		    SnmpAdminString,
		avCmListSigGrpFAS
		    SnmpAdminString,
		avCmListSigGrpTrkBrds
		    Integer32,
		avCmListSigGrpPriDChannel
		    SnmpAdminString,
		avCmListSigGrpSecDChannel
		    SnmpAdminString,
		avCmListSigGrpMaxNCATSC
		    Integer32,
		avCmListSigGrpMaxCATSC
		    Integer32,
		avCmListSigGrpNoAdmdNCATSCs
		    Integer32,
		avCmListSigGrpNearNode
		    SnmpAdminString,
		avCmListSigGrpFarNode
		    SnmpAdminString
		}

avCmListSigGrpIdx	OBJECT-TYPE
    SYNTAX	Integer32 (0..2000)
    MAX-ACCESS	not-accessible
    STATUS	current
    DESCRIPTION
	"
	Fld OID Name:	avCmListSigGrpIdx
	Fld OID:	enterprises.6889.2.73.8.1.84.1.1.1
	Fld Format:	NA
	Fld(s) Name:	NA
	Fld Descr:	An object that uniquely identifies each SigGrp Group.
	"
    ::= { avCmListSigGrpEntry 1 }

avCmListSigGrpGrpNumber	OBJECT-TYPE
    SYNTAX	Integer32 (0..9999)
    MAX-ACCESS	read-only
    STATUS	current
    DESCRIPTION
	"
	Fld OID Name:	avCmListSigGrpGrpNumber
	Fld OID:	enterprises.6889.2.73.8.1.84.1.1.2
	Fld Form/Rpt:	SIGNALING GROUPS
	Fld Format:	Single Field
	Fld(s) Name:	List Command: Grp No 
	Fld Descr:	An object that uniquely identifies each signaling group.
	"
    ::= { avCmListSigGrpEntry 2 }

avCmListSigGrpGrpType	OBJECT-TYPE
    SYNTAX	SnmpAdminString (SIZE (0..14))
    MAX-ACCESS	read-only
    STATUS	current
    DESCRIPTION
	"
	Fld OID Name:	avCmListSigGrpGrpType
	Fld OID:	enterprises.6889.2.73.8.1.84.1.1.3
	Fld Form/Rpt:	SIGNALING GROUPS
	Fld Format:	Single Field
	Fld(s) Name:	List Command: Group Type
	Fld Descr:	An object that contains the signaling group type.
	"
    ::= { avCmListSigGrpEntry 3 }

avCmListSigGrpFAS	OBJECT-TYPE
    SYNTAX	SnmpAdminString (SIZE (0..2))
    MAX-ACCESS	read-only
    STATUS	current
    DESCRIPTION
	"
	Fld OID Name:	avCmListSigGrpFAS
	Fld OID:	enterprises.6889.2.73.8.1.84.1.1.4
	Fld Form/Rpt:	SIGNALING GROUPS
	Fld Format:	Single Field
	Fld(s) Name:	List Command: FAS
	Fld Descr:	An object that contains whether FAS is enabled for the
			signaling group.
	"
    ::= { avCmListSigGrpEntry 4 }

avCmListSigGrpTrkBrds	OBJECT-TYPE
    SYNTAX	Integer32 (0..99)
    MAX-ACCESS	read-only
    STATUS	current
    DESCRIPTION
	"
	Fld OID Name:	avCmListSigGrpTrkBrds
	Fld OID:	enterprises.6889.2.73.8.1.84.1.1.5
	Fld Form/Rpt:	SIGNALING GROUPS
	Fld Format:	Single Field
	Fld(s) Name:	List Command: Trunk Brds
	Fld Descr:	An object that contains the Number of trunk boards
			used by the signaling Group.
	"
    ::= { avCmListSigGrpEntry 5 }

avCmListSigGrpPriDChannel	OBJECT-TYPE
    SYNTAX	SnmpAdminString (SIZE (0..11))
    MAX-ACCESS	read-only
    STATUS	current
    DESCRIPTION
	"
	Fld OID Name:	avCmListSigGrpPriDChannel
	Fld OID:	enterprises.6889.2.73.8.1.84.1.1.6
	Fld Form/Rpt:	SIGNALING GROUPS
	Fld Format:	Single Field
	Fld(s) Name:	List Command: Pri D-Ch
	Fld Descr:	An object that contains the signaling group primary
			D Channel.
	"
    ::= { avCmListSigGrpEntry 6 }

avCmListSigGrpSecDChannel	OBJECT-TYPE
    SYNTAX	SnmpAdminString (SIZE (0..11))
    MAX-ACCESS	read-only
    STATUS	current
    DESCRIPTION
	"
	Fld OID Name:	avCmListSigGrpSecDChannel
	Fld OID:	enterprises.6889.2.73.8.1.84.1.1.7
	Fld Form/Rpt:	SIGNALING GROUPS
	Fld Format:	Single Field
	Fld(s) Name:	List Command: Sec D-Ch
	Fld Descr:	An object that contains the signaling group secondary
			D Channel.
	"
    ::= { avCmListSigGrpEntry 7 }

avCmListSigGrpMaxNCATSC		OBJECT-TYPE
    SYNTAX	Integer32 (0..999)
    MAX-ACCESS	read-only
    STATUS	current
    DESCRIPTION
	"
	Fld OID Name:	avCmListSigGrpMaxNCATSC
	Fld OID:	enterprises.6889.2.73.8.1.84.1.1.8
	Fld Form/Rpt:	SIGNALING GROUPS
	Fld Format:	Single Field
	Fld(s) Name:	List Command: Max NCA TSC
	Fld Descr:	An object that contains the Max NCA TSC
			for the Signaling Group.
	"
    ::= { avCmListSigGrpEntry 8 }

avCmListSigGrpMaxCATSC	OBJECT-TYPE
    SYNTAX	Integer32 (0..999)
    MAX-ACCESS	read-only
    STATUS	current
    DESCRIPTION
	"
	Fld OID Name:	avCmListSigGrpMaxCATSC
	Fld OID:	enterprises.6889.2.73.8.1.84.1.1.9
	Fld Form/Rpt:	SIGNALING GROUPS
	Fld Format:	Single Field
	Fld(s) Name:	List Command: Max CA TSC
	Fld Descr:	An object that contains the Max CA TSC of the
			Signaling Group.
	"
    ::= { avCmListSigGrpEntry 9 }

avCmListSigGrpNoAdmdNCATSCs	OBJECT-TYPE
    SYNTAX	Integer32 (0..999)
    MAX-ACCESS	read-only
    STATUS	current
    DESCRIPTION
	"
	Fld OID Name:	avCmListSigGrpNoAdmdNCATSCs
	Fld OID:	enterprises.6889.2.73.8.1.84.1.1.10
	Fld Form/Rpt:	SIGNALING GROUPS
	Fld Format:	Single Field
	Fld(s) Name:	List Command: No. Adm'd NCA TSCs
	Fld Descr:	An object that contains the Number of administered NCA
			TSCs for Signaling Group.
	"
    ::= { avCmListSigGrpEntry 10 }

avCmListSigGrpNearNode       OBJECT-TYPE
    SYNTAX      SnmpAdminString (SIZE (0..16))
    MAX-ACCESS  read-only
    STATUS      current
    DESCRIPTION
        "
        Fld OID Name:   avCmListSigGrpNearNode
        Fld OID:        enterprises.6889.2.73.8.1.84.1.1.11
        Fld Form/Rpt:   SIGNALING GROUPS
        Fld Format:     Single Field
        Fld(s) Name:    List Command: Near-node 
        Fld Descr:      An object that contains the near end node-name
                        associated with the signaling group.
        "
    ::= { avCmListSigGrpEntry 11 }


avCmListSigGrpFarNode       OBJECT-TYPE
    SYNTAX      SnmpAdminString (SIZE (0..16))
    MAX-ACCESS  read-only
    STATUS      current
    DESCRIPTION
        "
        Fld OID Name:   avCmListSigGrpFarNode
        Fld OID:        enterprises.6889.2.73.8.1.84.1.1.12
        Fld Form/Rpt:   SIGNALING GROUPS
        Fld Format:     Single Field
        Fld(s) Name:    List Command: Far-node 
        Fld Descr:      An object that contains the far end node-name
                        associated with the signaling group.
        "
    ::= { avCmListSigGrpEntry 12 }

-- ******************** avCmStatusSigGrp Group *************************


-- MIB GROUP DESCRIPTION

-- MIB Group Name:
--		avCmStatusSigGrp Group
-- OID:
--		enterprises.6889.2.73.8.1.85
-- Description:
--		The avCmStatusSigGrp MIB Group uses the 
--		"status  signaling-group" command to retrieve signaling-group 
--		status information. 
--		
-- Releases Supported:
--		CM6.3.100 and greater
-- Polling Type:
--		Configuration and Performance
-- Polling Interval:
--		No more than once an hour or when signaling administration is 
--		changed.
-- Default Caching Interval
-- 		600 seconds
-- Timeout Interval:
--		Initial Timeout should be set to 20 seconds.
-- Retry Interval:
--		Initial Retry should be set to 3.
-- Limitations:
--		Red/High - The data collected by this MIB Group will increase 
--		as the number of administered signaling-groups increase.
--		Consequently the data collected by this MIB Group could be
--		very large and therefore may take a very long time to collect
--		and could impact system performance.
-- Command Type:
--		1. SAT
-- Command:
--		1. status signaling-group
-- Form/Report Name:
--		1. STATUS SIGNALING GROUP 
-- Reference Document:
--		1. A detailed description of the command and form can be
--		   found in document referenced by REF_DOC_1 in the
--		   DOCUMENT REFERENCE SECTION.
-- Command Permission/User-profile:
--		1. No special permissions needed.

avCmStatusSigGrp	OBJECT IDENTIFIER ::= { avCmObjects 85 }

avCmStatusSigGrpTable	OBJECT-TYPE
    SYNTAX	SEQUENCE OF AvCmStatusSigGrpEntry
    MAX-ACCESS	not-accessible
    STATUS	current
    DESCRIPTION
	"
	Fld OID Name:	avCmStatusSigGrpEntry
	Fld OID:	enterprises.6889.2.73.8.1.85.1
	Fld Form/Rpt:	NA
	Fld Format:	NA
	Fld(s) Name:	NA
	Fld Descr:	A list of the avCmStatusSigGrp entries
	"
    ::= { avCmStatusSigGrp 1 }

avCmStatusSigGrpEntry	OBJECT-TYPE
    SYNTAX	AvCmStatusSigGrpEntry
    MAX-ACCESS	not-accessible
    STATUS	current
    DESCRIPTION
	"
	Fld OID Name:	avCmStatusSigGrpEntry
	Fld OID:	enterprises.6889.2.73.8.1.85.1.1
	Fld Form/Rpt:	NA
	Fld Format:	NA
	Fld(s) Name:	NA
	Fld Descr:	A avCmStatusSigGrp entry containing objects of the
			avCmStatusSigGrp information sent by the switch.
	"
    INDEX    { avCmStatusSigGrpIdx }
    ::= { avCmStatusSigGrpTable 1 }

AvCmStatusSigGrpEntry ::= SEQUENCE {
		avCmStatusSigGrpIdx
		    Integer32,
		avCmStatusSigGrpGrpNumber
		    Integer32,
		avCmStatusSigGrpGrpType
		    SnmpAdminString,
		avCmStatusSigGrpGrpState
		    SnmpAdminString
		}

avCmStatusSigGrpIdx	OBJECT-TYPE
    SYNTAX	Integer32 (0..2000)
    MAX-ACCESS	not-accessible
    STATUS	current
    DESCRIPTION
	"
	Fld OID Name:	avCmStatusSigGrpIdx
	Fld OID:	enterprises.6889.2.73.8.1.85.1.1.1
	Fld Format:	NA
	Fld(s) Name:	NA
	Fld Descr:	An object that uniquely identifies each SigGrp Group.
	"
    ::= { avCmStatusSigGrpEntry 1 }

avCmStatusSigGrpGrpNumber	OBJECT-TYPE
    SYNTAX	Integer32 (0..9999)
    MAX-ACCESS	read-only
    STATUS	current
    DESCRIPTION
	"
	Fld OID Name:	avCmStatusSigGrpGrpNumber
	Fld OID:	enterprises.6889.2.73.8.1.85.1.1.2
	Fld Form/Rpt:	STATUS SIGNALING GROUP
	Fld Format:	Single Field
	Fld(s) Name:	Status Command: Grp No 
	Fld Descr:	An object that uniquely identifies each signaling group.
	"
    ::= { avCmStatusSigGrpEntry 2 }

avCmStatusSigGrpGrpType	OBJECT-TYPE
    SYNTAX	SnmpAdminString (SIZE (0..35))
    MAX-ACCESS	read-only
    STATUS	current
    DESCRIPTION
	"
	Fld OID Name:	avCmStatusSigGrpGrpType
	Fld OID:	enterprises.6889.2.73.8.1.85.1.1.3
	Fld Form/Rpt:	STATUS SIGNALING GROUP
	Fld Format:	Single Field
	Fld(s) Name:	Status Command: Group Type
	Fld Descr:	An object that contains the signaling group type.
	"
    ::= { avCmStatusSigGrpEntry 3 }

avCmStatusSigGrpGrpState	OBJECT-TYPE
    SYNTAX	SnmpAdminString (SIZE (0..22))
    MAX-ACCESS	read-only
    STATUS	current
    DESCRIPTION
	"
	Fld OID Name:	avCmStatusSigGrpGrpState
	Fld OID:	enterprises.6889.2.73.8.1.85.1.1.4
	Fld Form/Rpt:	STATUS SIGNALING GROUP
	Fld Format:	Single Field
	Fld(s) Name:	Status Command: Group State
	Fld Descr:	An object that contains the state of the signaling
			group.
	"
    ::= { avCmStatusSigGrpEntry 4 }


-- ******************** avCmListHuntGrp Group *************************


-- MIB GROUP DESCRIPTION

-- MIB Group Name:
--		avCmListHuntGrp Group
-- OID:
--		enterprises.6889.2.73.8.1.86
-- Description:
--		The avCmListHuntGrp MIB Group uses the "list hunt-group"
-- 		command to retrieve hunt-group information. 
--		
-- Releases Supported:
--		CM7.0 and greater
-- Polling Type:
--		Configuration and Inventory
-- Polling Interval:
--		No more than once an hour or when hunt-group administration is 
--		changed.
-- Default Caching Interval
-- 		600 seconds
-- Timeout Interval:
--		Initial Timeout should be set to 20 seconds.
-- Retry Interval:
--		Initial Retry should be set to 3.
-- Limitations:
--		Red/High - The data collected by this MIB Group will
--		increase as the number of administered hunt-groups increase.
--		Consequently the data collected by this MIB Group could be
--		very large and therefore may take a very long time to collect
--		and could impact system performance.
-- Command Type:
--		1. SAT
-- Command:
--		1. list hunt-group
-- Form/Report Name:
--		1. HUNT GROUPS 
-- Reference Document:
--		1. A detailed description of the command and form can be
--		   found in document referenced by REF_DOC_4 in the
--		   DOCUMENT REFERENCE SECTION.
-- Command Permission/User-profile:
--		1. No special permissions needed.

avCmListHuntGrp	OBJECT IDENTIFIER ::= { avCmObjects 86 }

avCmListHuntGrpTable	OBJECT-TYPE
    SYNTAX	SEQUENCE OF AvCmStatushuntEntry
    MAX-ACCESS	not-accessible
    STATUS	current
    DESCRIPTION
	"
	Fld OID Name:	avCmListHuntGrpEntry
	Fld OID:	enterprises.6889.2.73.8.1.86.1
	Fld Form/Rpt:	NA
	Fld Format:	NA
	Fld(s) Name:	NA
	Fld Descr:	A list of the avCmListHuntGrp entries
	"
    ::= { avCmListHuntGrp 1 }

avCmListHuntGrpEntry	OBJECT-TYPE
    SYNTAX	AvCmStatushuntEntry
    MAX-ACCESS	not-accessible
    STATUS	current
    DESCRIPTION
	"
	Fld OID Name:	avCmListHuntGrpEntry
	Fld OID:	enterprises.6889.2.73.8.1.86.1.1
	Fld Form/Rpt:	NA
	Fld Format:	NA
	Fld(s) Name:	NA
	Fld Descr:	A avCmListHuntGrp entry containing objects of the
			avCmListHuntGrp information sent by the switch.
	"
    INDEX    { avCmListHuntGrpIdx }
    ::= { avCmListHuntGrpTable 1 }

AvCmStatushuntEntry ::= SEQUENCE {
		avCmListHuntGrpIdx
		    Integer32,
		avCmListHuntGrpGrpNumber
		    Integer32,
		avCmListHuntGrpGrpName
		    SnmpAdminString,
		avCmListHuntGrpGrpExt
		    SnmpAdminString,
		avCmListHuntGrpGrpType
		    SnmpAdminString,
		avCmListHuntGrpGrpAcdMeas
		    SnmpAdminString,
		avCmListHuntGrpGrpVec
		    SnmpAdminString,
		avCmListHuntGrpGrpMch
		    SnmpAdminString,
		avCmListHuntGrpGrpQue
		    SnmpAdminString,
		avCmListHuntGrpGrpNoMem
		    Integer32,
		avCmListHuntGrpCovPath
		    SnmpAdminString,
		avCmListHuntGrpNotifCtgAdj
		    SnmpAdminString,
		avCmListHuntGrpDomCtrl
		    SnmpAdminString,
		avCmListHuntGrpMsgCtr
		    SnmpAdminString,
		avCmListHuntGrpMsgCtrName
		    SnmpAdminString
		}

avCmListHuntGrpIdx	OBJECT-TYPE
    SYNTAX	Integer32 (0..9999)
    MAX-ACCESS	not-accessible
    STATUS	current
    DESCRIPTION
	"
	Fld OID Name:	avCmListHuntGrpIdx
	Fld OID:	enterprises.6889.2.73.8.1.86.1.1.1
	Fld Format:	NA
	Fld(s) Name:	NA
	Fld Descr:	An object that uniquely identifies each hunt Group.
	"
    ::= { avCmListHuntGrpEntry 1 }

avCmListHuntGrpGrpNumber	OBJECT-TYPE
    SYNTAX	Integer32 (0..9999)
    MAX-ACCESS	read-only
    STATUS	current
    DESCRIPTION
	"
	Fld OID Name:	avCmListHuntGrpGrpNumber
	Fld OID:	enterprises.6889.2.73.8.1.86.1.1.2
	Fld Form/Rpt:	HUNT GROUPS
	Fld Format:	Single Field
	Fld(s) Name:	Grp No. 
	Fld Descr:	An object that uniquely identifies each hunt-group.
	"
    ::= { avCmListHuntGrpEntry 2 }

avCmListHuntGrpGrpName	OBJECT-TYPE
    SYNTAX	SnmpAdminString (SIZE (0..28))
    MAX-ACCESS	read-only
    STATUS	current
    DESCRIPTION
	"
	Fld OID Name:	avCmListHuntGrpGrpName
	Fld OID:	enterprises.6889.2.73.8.1.86.1.1.3
	Fld Form/Rpt:	HUNT GROUPS
	Fld Format:	Single Field
	Fld(s) Name:	Grp Name
	Fld Descr:	An object that contains the hunt-group Name.
	"
    ::= { avCmListHuntGrpEntry 3 }


avCmListHuntGrpGrpExt  OBJECT-TYPE
    SYNTAX      SnmpAdminString (SIZE (0..17))
    MAX-ACCESS  read-only
    STATUS      current
    DESCRIPTION
        "
        Fld OID Name:   avCmListHuntGrpGrpExt
        Fld OID:        enterprises.6889.2.73.8.1.86.1.1.4
        Fld Form/Rpt:   HUNT GROUPS
        Fld Format:     Single Field
        Fld(s) Name:    Ext
        Fld Descr:      An object that contains the hunt-group extension.
        "
    ::= { avCmListHuntGrpEntry 4 }

avCmListHuntGrpGrpType	OBJECT-TYPE
    SYNTAX	SnmpAdminString (SIZE (0..8))
    MAX-ACCESS	read-only
    STATUS	current
    DESCRIPTION
	"
	Fld OID Name:	avCmListHuntGrpGrpType
	Fld OID:	enterprises.6889.2.73.8.1.86.1.1.5
	Fld Form/Rpt:	HUNT GROUPS
	Fld Format:	Single Field
	Fld(s) Name:	Grp Type
	Fld Descr:	An object that contains the hunt-group type.
	"
    ::= { avCmListHuntGrpEntry 5 }

avCmListHuntGrpGrpAcdMeas	OBJECT-TYPE
    SYNTAX	SnmpAdminString (SIZE (0..4))
    MAX-ACCESS	read-only
    STATUS	current
    DESCRIPTION
	"
	Fld OID Name:	avCmListHuntGrpGrpAcdMeas
	Fld OID:	enterprises.6889.2.73.8.1.86.1.1.6
	Fld Form/Rpt:	HUNT GROUPS
	Fld Format:	Single Field
	Fld(s) Name:	ACD/MEAS
	Fld Descr:	An object that contains whether the hunt-group is ACD
			and measured.
	"
    ::= { avCmListHuntGrpEntry 6 }

avCmListHuntGrpGrpVec	OBJECT-TYPE
    SYNTAX	SnmpAdminString (SIZE (0..2))
    MAX-ACCESS	read-only
    STATUS	current
    DESCRIPTION
	"
	Fld OID Name:	avCmListHuntGrpGrpVec
	Fld OID:	enterprises.6889.2.73.8.1.86.1.1.7
	Fld Form/Rpt:	HUNT GROUPS
	Fld Format:	Single Field
	Fld(s) Name:	Vec
	Fld Descr:	An object that contains whether the hunt-group is 
			a vector.
	"
    ::= { avCmListHuntGrpEntry 7 }


avCmListHuntGrpGrpMch   OBJECT-TYPE
    SYNTAX      SnmpAdminString (SIZE (0..5))
    MAX-ACCESS  read-only
    STATUS      current
    DESCRIPTION
        "
        Fld OID Name:   avCmListHuntGrpGrpMch
        Fld OID:        enterprises.6889.2.73.8.1.86.1.1.8
        Fld Form/Rpt:   HUNT GROUPS
        Fld Format:     Single Field
        Fld(s) Name:    MCH
        Fld Descr:      An object that contains whether the hunt-group is 
                        Multiple Call Handling.
        "
    ::= { avCmListHuntGrpEntry 8 }

avCmListHuntGrpGrpQue   OBJECT-TYPE
    SYNTAX      SnmpAdminString (SIZE (0..2))
    MAX-ACCESS  read-only
    STATUS      current
    DESCRIPTION
        "
        Fld OID Name:   avCmListHuntGrpGrpQue
        Fld OID:        enterprises.6889.2.73.8.1.86.1.1.9
        Fld Form/Rpt:   HUNT GROUPS
        Fld Format:     Single Field
        Fld(s) Name:    Que
        Fld Descr:      An object that contains whether the hunt-group has 
                        a queue.
        "
    ::= { avCmListHuntGrpEntry 9 }


avCmListHuntGrpGrpNoMem        OBJECT-TYPE
    SYNTAX      Integer32 (0..9999)
    MAX-ACCESS  read-only
    STATUS      current
    DESCRIPTION
        "
        Fld OID Name:   avCmListHuntGrpGrpNoMem
        Fld OID:        enterprises.6889.2.73.8.1.86.1.1.10
        Fld Form/Rpt:   HUNT GROUPS
        Fld Format:     Single Field
        Fld(s) Name:    No Mem
        Fld Descr:      An object that identifies the number of group members. 
        "
    ::= { avCmListHuntGrpEntry 10 }

avCmListHuntGrpCovPath   OBJECT-TYPE
    SYNTAX      SnmpAdminString (SIZE (0..5))
    MAX-ACCESS  read-only
    STATUS      current
    DESCRIPTION
        "
        Fld OID Name:   avCmListHuntGrpCovPath
        Fld OID:        enterprises.6889.2.73.8.1.86.1.1.11
        Fld Form/Rpt:   HUNT GROUPS
        Fld Format:     Single Field
        Fld(s) Name:    Cov Path
        Fld Descr:      An object that contains whether the hunt-group has 
                        a coverage path associated with it.
        "
    ::= { avCmListHuntGrpEntry 11 }


avCmListHuntGrpNotifCtgAdj   OBJECT-TYPE
    SYNTAX      SnmpAdminString (SIZE (0..5))
    MAX-ACCESS  read-only
    STATUS      current
    DESCRIPTION
        "
        Fld OID Name:   avCmListHuntGrpNotifCtgAdj
        Fld OID:        enterprises.6889.2.73.8.1.86.1.1.12
        Fld Form/Rpt:   HUNT GROUPS
        Fld Format:     Single Field
        Fld(s) Name:    Cov Path
        Fld Descr:      An object that contains whether the hunt-group has
                        NotifCtgAdj.
        "
    ::= { avCmListHuntGrpEntry 12 }


avCmListHuntGrpDomCtrl   OBJECT-TYPE
    SYNTAX      SnmpAdminString (SIZE (0..3))
    MAX-ACCESS  read-only
    STATUS      current
    DESCRIPTION
        "
        Fld OID Name:   avCmListHuntGrpDomCtrl
        Fld OID:        enterprises.6889.2.73.8.1.86.1.1.13
        Fld Form/Rpt:   HUNT GROUPS
        Fld Format:     Single Field
        Fld(s) Name:    Dom Ctrl
        Fld Descr:      An object that contains whether the hunt-group has
                        Domain Control.
        "
    ::= { avCmListHuntGrpEntry 13 }


avCmListHuntGrpMsgCtr   OBJECT-TYPE
    SYNTAX      SnmpAdminString (SIZE (0..2))
    MAX-ACCESS  read-only
    STATUS      current
    DESCRIPTION
        "
        Fld OID Name:   avCmListHuntGrpMsgCtr
        Fld OID:        enterprises.6889.2.73.8.1.86.1.1.14
        Fld Form/Rpt:   HUNT GROUPS
        Fld Format:     Single Field
        Fld(s) Name:    Message Center
        Fld Descr:      An object that contains whether the hunt-group has
                        Message Center.
        "
    ::= { avCmListHuntGrpEntry 14 }

avCmListHuntGrpMsgCtrName   OBJECT-TYPE
    SYNTAX      SnmpAdminString (SIZE (0..8))
    MAX-ACCESS  read-only
    STATUS      current
    DESCRIPTION
        "
        Fld OID Name:   avCmListHuntGrpMsgCtrName
        Fld OID:        enterprises.6889.2.73.8.1.86.1.1.15
        Fld Form/Rpt:   HUNT GROUPS
        Fld Format:     Single Field
        Fld(s) Name:    Message Center Name
        Fld Descr:      An object that contains the name of the Message Center.
        "
    ::= { avCmListHuntGrpEntry 15 }


-- ******************** avCmMeasHuntGrpLstHr Group *************************

-- MIB GROUP DESCRIPTION

-- MIB Group Name:
--		avCmMeasHuntGrpLstHr Group
-- OID:
--		enterprises.6889.2.73.8.1.87
-- Description:
--		The avCmMeasHuntGrpLstHr MIB Group uses the "list measurements
--		hunt-group last-hour" command to retrieve hunt-group data 
--		from the last hour.
--		
-- Releases Supported:
--		CM6.3.100 and greater
-- Polling Type:
--		Performance/Utilization
-- Polling Interval:
--		No more than once an hour because the data is only updated
--		near the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements hunt-group last-hour
-- Form/Report Name:
--		1. HUNT GROUP MEASUREMENTS
-- Reference Document:
--		1. A detailed description of the command and form can be
--		   found in document referenced by REF_DOC_4 in the
--		   DOCUMENT REFERENCE SECTION.
-- Command Permission/User-profile:
--		1. No special permissions needed.

avCmMeasHuntGrpLstHr	OBJECT IDENTIFIER ::= { avCmObjects 87 }

avCmMeasHuntGrpLstHrTable	OBJECT-TYPE
    SYNTAX	SEQUENCE OF AvCmMeasHuntGrpLstHrEntry
    MAX-ACCESS	not-accessible
    STATUS	current
    DESCRIPTION
	"
	Fld OID Name:	avCmMeasHuntGrpLstHrEntry
	Fld OID:	enterprises.6889.2.73.8.1.87.1
	Fld Form/Rpt:	NA
	Fld Format:	NA
	Fld(s) Name:	NA
	Fld Descr:	A list of the avCmMeasHuntGrpLstHr entries
	"
    ::= { avCmMeasHuntGrpLstHr 1 }

avCmMeasHuntGrpLstHrEntry	OBJECT-TYPE
    SYNTAX	AvCmMeasHuntGrpLstHrEntry
    MAX-ACCESS	not-accessible
    STATUS	current
    DESCRIPTION
	"
	Fld OID Name:	avCmMeasHuntGrpLstHrEntry
	Fld OID:	enterprises.6889.2.73.8.1.87.1.1
	Fld Form/Rpt:	NA
	Fld Format:	NA
	Fld(s) Name:	NA
	Fld Descr:	A avCmMeasHuntGrpLstHr entry containing objects of the
			avCmMeasHuntGrpLstHr information sent by the switch.
	"
    INDEX    { avCmMeasHuntGrpLstHrHuntGrpIdx }
    ::= { avCmMeasHuntGrpLstHrTable 1 }

AvCmMeasHuntGrpLstHrEntry ::= SEQUENCE {
		avCmMeasHuntGrpLstHrHuntGrpIdx
		    Integer32,
		avCmMeasHuntGrpLstHrHuntGrpNo
		    Integer32,
		avCmMeasHuntGrpLstHrRunDate
		    SnmpAdminString,
		avCmMeasHuntGrpLstHrGrpName
		    SnmpAdminString,
		avCmMeasHuntGrpLstHrGroupSiz
		    Integer32,
		avCmMeasHuntGrpLstHrMeasHour
		    Integer32,
		avCmMeasHuntGrpLstHrTotalUsage 
		    Integer32,
		avCmMeasHuntGrpLstHrCallsAns
		    Integer32,
		avCmMeasHuntGrpLstHrGrpQue
		    SnmpAdminString,
		avCmMeasHuntGrpLstHrCallsQue
		    Integer32,
		avCmMeasHuntGrpLstHrQueOvfl
		    Integer32,
		avCmMeasHuntGrpLstHrTimeAvail
		    Integer32,
		avCmMeasHuntGrpLstHrSpeedAns
		    Integer32,
		avCmMeasHuntGrpLstHrTyp
		    SnmpAdminString,
		avCmMeasHuntGrpLstHrAban
		    Integer32
		}

avCmMeasHuntGrpLstHrHuntGrpIdx	OBJECT-TYPE
    SYNTAX	Integer32 (0..9999)
    MAX-ACCESS	not-accessible
    STATUS	current
    DESCRIPTION
	"
	Fld OID Name:	avCmMeasHuntGrpLstHrHuntGrpIdx
	Fld OID:	enterprises.6889.2.73.8.1.87.1.1.1
	Fld Format:	NA
	Fld(s) Name:	NA
	Fld Descr:	An object that uniquely identifies each Increment of 
			data.
	"
    ::= { avCmMeasHuntGrpLstHrEntry 1 }

avCmMeasHuntGrpLstHrHuntGrpNo	OBJECT-TYPE
    SYNTAX	Integer32 (0..9999)
    MAX-ACCESS	read-only
    STATUS	current
    DESCRIPTION
	"
	Fld OID Name:	avCmMeasHuntGrpLstHrHuntGrpNo
	Fld OID:	enterprises.6889.2.73.8.1.87.1.1.2
	Fld Form/Rpt:	HUNT GROUP MEASUREMENTS
	Fld Format:	Single Field
	Fld(s) Name:	Hunt Group
	Fld Descr:	An object containing the hunt group number.
	"
    ::= { avCmMeasHuntGrpLstHrEntry 2 }

avCmMeasHuntGrpLstHrRunDate	OBJECT-TYPE
    SYNTAX	SnmpAdminString (SIZE (0..28))
    MAX-ACCESS	read-only
    STATUS	current
    DESCRIPTION
	"
	Fld OID Name:	avCmMeasHuntGrpLstHrRunDate
	Fld OID:	enterprises.6889.2.73.8.1.87.1.1.3
	Fld Form/Rpt:	HUNT GROUP MEASUREMENTS
	Fld Format:	Single Field
	Fld(s) Name:	Date
	Fld Descr:	An object containing the Date the command was executed.
	"
    ::= { avCmMeasHuntGrpLstHrEntry 3 }

avCmMeasHuntGrpLstHrGrpName   OBJECT-TYPE
    SYNTAX	SnmpAdminString (SIZE (0..28))
    MAX-ACCESS  read-only
    STATUS      current
    DESCRIPTION
        "
        Fld OID Name:   avCmMeasHuntGrpLstHrGrpName
        Fld OID:        enterprises.6889.2.73.8.1.87.1.1.4
        Fld Form/Rpt:   HUNT GROUP MEASUREMENTS
        Fld Format:     Single Field
        Fld(s) Name:    Grp Name
        Fld Descr:      An object containing the name of the hunt group.
        "
    ::= { avCmMeasHuntGrpLstHrEntry 4 }


avCmMeasHuntGrpLstHrGroupSiz	OBJECT-TYPE
    SYNTAX	Integer32 (0..999)
    MAX-ACCESS	read-only
    STATUS	current
    DESCRIPTION
	"
	Fld OID Name:	avCmMeasHuntGrpLstHrGroupSiz
	Fld OID:	enterprises.6889.2.73.8.1.87.1.1.5
	Fld Form/Rpt:	HUNT GROUP MEASUREMENTS
	Fld Format:	Single Field
	Fld(s) Name:	Grp Siz
	Fld Descr:	An object containing the hunt group size.
	"
    ::= { avCmMeasHuntGrpLstHrEntry 5 }

avCmMeasHuntGrpLstHrMeasHour	OBJECT-TYPE
    SYNTAX	Integer32 (0..9999)
    MAX-ACCESS	read-only
    STATUS	current
    DESCRIPTION
	"
	Fld OID Name:	avCmMeasHuntGrpLstHrMeasHour
	Fld OID:	enterprises.6889.2.73.8.1.87.1.1.6
	Fld Form/Rpt:	HUNT GROUP MEASUREMENTS
	Fld Format:	Single Field
	Fld(s) Name:	Meas Hour
	Fld Descr:	An object containing the measurement hour.
	"
    ::= { avCmMeasHuntGrpLstHrEntry 6 }

avCmMeasHuntGrpLstHrTotalUsage	OBJECT-TYPE
    SYNTAX	Integer32 (0..99999)
    MAX-ACCESS	read-only
    STATUS	current
    DESCRIPTION
	"
	Fld OID Name:	avCmMeasHuntGrpLstHrTotalUsage
	Fld OID:	enterprises.6889.2.73.8.1.87.1.1.7
	Fld Form/Rpt:	HUNT GROUP MEASUREMENTS
	Fld Format:	Single Field
	Fld(s) Name:	Total Usage
	Fld Descr:	An object containing total time hunt groups are busy 
			with calls during the measurement period (in CCS).
	"
    ::= { avCmMeasHuntGrpLstHrEntry 7 }

avCmMeasHuntGrpLstHrCallsAns	OBJECT-TYPE
    SYNTAX	Integer32 (0..999999)
    MAX-ACCESS	read-only
    STATUS	current
    DESCRIPTION
	"
	Fld OID Name:	avCmMeasHuntGrpLstHrCallsAns
	Fld OID:	enterprises.6889.2.73.8.1.87.1.1.8
	Fld Form/Rpt:	HUNT GROUP MEASUREMENTS
	Fld Format:	Single Field
	Fld(s) Name:	Calls Ans
	Fld Descr:	An object containing the number of call answered.
	"
    ::= { avCmMeasHuntGrpLstHrEntry 8 }

avCmMeasHuntGrpLstHrGrpQue	OBJECT-TYPE
    SYNTAX	SnmpAdminString (SIZE (0..2))
    MAX-ACCESS	read-only
    STATUS	current
    DESCRIPTION
	"
	Fld OID Name:	avCmMeasHuntGrpLstHrGrpQue
	Fld OID:	enterprises.6889.2.73.8.1.87.1.1.9
	Fld Form/Rpt:	HUNT GROUP MEASUREMENTS
	Fld Format:	Single Field
	Fld(s) Name:	Que
	Fld Descr:	Field that indicates if there is a queue.
	"
    ::= { avCmMeasHuntGrpLstHrEntry 9 }

avCmMeasHuntGrpLstHrCallsQue	OBJECT-TYPE
    SYNTAX	Integer32 (0..99999)
    MAX-ACCESS	read-only
    STATUS	current
    DESCRIPTION
	"
	Fld OID Name:	avCmMeasHuntGrpLstHrCallsQue
	Fld OID:	enterprises.6889.2.73.8.1.87.1.1.10
	Fld Form/Rpt:	HUNT GROUP MEASUREMENTS
	Fld Format:	Single Field
	Fld(s) Name:	Calls Que
	Fld Descr:	Total number of calls that arrive to find all members 
			of the hunt group busy and are placed in the hunt group
			queue. Calls Queued includes all calls that go to 
			coverage
			
	"
    ::= { avCmMeasHuntGrpLstHrEntry 10 }

avCmMeasHuntGrpLstHrQueOvfl	OBJECT-TYPE
    SYNTAX	Integer32 (0..99999)
    MAX-ACCESS	read-only
    STATUS	current
    DESCRIPTION
	"
	Fld OID Name:	avCmMeasHuntGrpLstHrQueOvfl
	Fld OID:	enterprises.6889.2.73.8.1.87.1.1.11
	Fld Form/Rpt:	HUNT GROUP MEASUREMENTS
	Fld Format:	Single Field
	Fld(s) Name:	Que Ovfl
	Fld Descr:	The number of calls that arrive when all slots in the 
			hunt group queue are occupied.
	"
    ::= { avCmMeasHuntGrpLstHrEntry 11 }

avCmMeasHuntGrpLstHrTimeAvail	OBJECT-TYPE
    SYNTAX	Integer32 (0..9999)
    MAX-ACCESS	read-only
    STATUS	current
    DESCRIPTION
	"
	Fld OID Name:	avCmMeasHuntGrpLstHrTimeAvail
	Fld OID:	enterprises.6889.2.73.8.1.87.1.1.12
	Fld Form/Rpt:	HUNT GROUP MEASUREMENTS
	Fld Format:	Single Field
	Fld(s) Name:	Time Avail
	Fld Descr:	The total time (in CCS) the hunt group extensions are 
			not in use but are available to receive hunt group 
			calls during the measurement hour. Time Available
			is calculated only when an agent (extension) is ready 
			to receive calls from the specified hunt group.
	"
    ::= { avCmMeasHuntGrpLstHrEntry 12 }

avCmMeasHuntGrpLstHrSpeedAns	OBJECT-TYPE
    SYNTAX	Integer32 (0..9999)
    MAX-ACCESS	read-only
    STATUS	current
    DESCRIPTION
	"
	Fld OID Name:	avCmMeasHuntGrpLstHrSpeedAns
	Fld OID:	enterprises.6889.2.73.8.1.87.1.1.13
	Fld Form/Rpt:	HUNT GROUP MEASUREMENTS
	Fld Format:	Single Field
	Fld(s) Name:	Speed Ans
	Fld Descr:	Speed of Answer (seconds). The average time interval 
			(in seconds) from when the call first enters the hunt 
			group or hunt group queue until the call is answered by
			a hunt group member. This does not include the time 
			taken by a forced first announcement.
			
	"
    ::= { avCmMeasHuntGrpLstHrEntry 13 }

avCmMeasHuntGrpLstHrTyp	OBJECT-TYPE
    SYNTAX	SnmpAdminString (SIZE (0..4))
    MAX-ACCESS	read-only
    STATUS	current
    DESCRIPTION
	"
	Fld OID Name:	avCmMeasHuntGrpLstHrTyp
	Fld OID:	enterprises.6889.2.73.8.1.87.1.1.14
	Fld Form/Rpt:	HUNT GROUP MEASUREMENTS
	Fld Format:	Single Field
	Fld(s) Name:	Typ
	Fld Descr:	Identifies one of the following type of hunt group:
			- ddc: direct department calling
			- ucd: uniform call distribution
			- ead: expert agent distribution
	"
    ::= { avCmMeasHuntGrpLstHrEntry 14 }

avCmMeasHuntGrpLstHrAban	OBJECT-TYPE
    SYNTAX	Integer32 (0..999)
    MAX-ACCESS	read-only
    STATUS	current
    DESCRIPTION
	"
	Fld OID Name:	avCmMeasHuntGrpLstHrAban
	Fld OID:	enterprises.6889.2.73.8.1.87.1.1.15
	Fld Form/Rpt:	HUNT GROUP MEASUREMENTS
	Fld Format:	Single Field
	Fld(s) Name:	Aban
	Fld Descr:	The total number of calls which attempt to reach the 
			hunt group but abandon the attempt before being 
			answered. Calls might abandon either while in the hunt 
			group queue or while ringing a hunt group extension. 
			This total does not include calls answered by Call 
			Pick Up, other hunt groups, or calls abandoned while 
			listening to a forced first announcement.
	"
    ::= { avCmMeasHuntGrpLstHrEntry 15 }

-- ******************** avCmMeasHuntGrpToday Group *************************

-- MIB GROUP DESCRIPTION

-- MIB Group Name:
--		avCmMeasHuntGrpToday Group
-- OID:
--		enterprises.6889.2.73.8.1.88
-- Description:
--		The avCmMeasHuntGrpToday MIB Group uses the "list measurements
--		hunt-group today" command to retrieve hunt-group data 
--		from the last hour.
--		
-- Releases Supported:
--		CM6.3.100 and greater
-- Polling Type:
--		Performance/Utilization
-- Polling Interval:
--		No more than once an hour because the data is only updated
--		near the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements hunt-group today
-- Form/Report Name:
--		1. HUNT GROUP MEASUREMENTS
-- Reference Document:
--		1. A detailed description of the command and form can be
--		   found in document referenced by REF_DOC_4 in the
--		   DOCUMENT REFERENCE SECTION.
-- Command Permission/User-profile:
--		1. No special permissions needed.

avCmMeasHuntGrpToday	OBJECT IDENTIFIER ::= { avCmObjects 88 }

avCmMeasHuntGrpTodayTable	OBJECT-TYPE
    SYNTAX	SEQUENCE OF AvCmMeasHuntGrpTodayEntry
    MAX-ACCESS	not-accessible
    STATUS	current
    DESCRIPTION
	"
	Fld OID Name:	avCmMeasHuntGrpTodayEntry
	Fld OID:	enterprises.6889.2.73.8.1.88.1
	Fld Form/Rpt:	NA
	Fld Format:	NA
	Fld(s) Name:	NA
	Fld Descr:	A list of the avCmMeasHuntGrpToday entries
	"
    ::= { avCmMeasHuntGrpToday 1 }

avCmMeasHuntGrpTodayEntry	OBJECT-TYPE
    SYNTAX	AvCmMeasHuntGrpTodayEntry
    MAX-ACCESS	not-accessible
    STATUS	current
    DESCRIPTION
	"
	Fld OID Name:	avCmMeasHuntGrpTodayEntry
	Fld OID:	enterprises.6889.2.73.8.1.88.1.1
	Fld Form/Rpt:	NA
	Fld Format:	NA
	Fld(s) Name:	NA
	Fld Descr:	A avCmMeasHuntGrpToday entry containing objects of the
			avCmMeasHuntGrpToday information sent by the switch.
	"
    INDEX    { avCmMeasHuntGrpTodayHuntGrpIdx }
    ::= { avCmMeasHuntGrpTodayTable 1 }

AvCmMeasHuntGrpTodayEntry ::= SEQUENCE {
		avCmMeasHuntGrpTodayHuntGrpIdx
		    Integer32,
		avCmMeasHuntGrpTodayHuntGrpNo
		    Integer32,
		avCmMeasHuntGrpTodayRunDate
		    SnmpAdminString,
		avCmMeasHuntGrpTodayGrpName
		    SnmpAdminString,
		avCmMeasHuntGrpTodayGroupSiz
		    Integer32,
		avCmMeasHuntGrpTodayMeasHour
		    Integer32,
		avCmMeasHuntGrpTodayTotalUsage 
		    Integer32,
		avCmMeasHuntGrpTodayCallsAns
		    Integer32,
		avCmMeasHuntGrpTodayGrpQue
		    SnmpAdminString,
		avCmMeasHuntGrpTodayCallsQue
		    Integer32,
		avCmMeasHuntGrpTodayQueOvfl
		    Integer32,
		avCmMeasHuntGrpTodayTimeAvail
		    Integer32,
		avCmMeasHuntGrpTodaySpeedAns
		    Integer32,
		avCmMeasHuntGrpTodayTyp
		    SnmpAdminString,
		avCmMeasHuntGrpTodayAban
		    Integer32
		}

avCmMeasHuntGrpTodayHuntGrpIdx	OBJECT-TYPE
    SYNTAX	Integer32 (0..9999)
    MAX-ACCESS	not-accessible
    STATUS	current
    DESCRIPTION
	"
	Fld OID Name:	avCmMeasHuntGrpTodayHuntGrpIdx
	Fld OID:	enterprises.6889.2.73.8.1.88.1.1.1
	Fld Format:	NA
	Fld(s) Name:	NA
	Fld Descr:	An object that uniquely identifies each Increment of 
			data.
	"
    ::= { avCmMeasHuntGrpTodayEntry 1 }

avCmMeasHuntGrpTodayHuntGrpNo	OBJECT-TYPE
    SYNTAX	Integer32 (0..9999)
    MAX-ACCESS	read-only
    STATUS	current
    DESCRIPTION
	"
	Fld OID Name:	avCmMeasHuntGrpTodayHuntGrpNo
	Fld OID:	enterprises.6889.2.73.8.1.88.1.1.2
	Fld Form/Rpt:	HUNT GROUP MEASUREMENTS
	Fld Format:	Single Field
	Fld(s) Name:	Hunt Group
	Fld Descr:	An object containing the hunt group number.
	"
    ::= { avCmMeasHuntGrpTodayEntry 2 }

avCmMeasHuntGrpTodayRunDate	OBJECT-TYPE
    SYNTAX	SnmpAdminString (SIZE (0..28))
    MAX-ACCESS	read-only
    STATUS	current
    DESCRIPTION
	"
	Fld OID Name:	avCmMeasHuntGrpTodayRunDate
	Fld OID:	enterprises.6889.2.73.8.1.88.1.1.3
	Fld Form/Rpt:	HUNT GROUP MEASUREMENTS
	Fld Format:	Single Field
	Fld(s) Name:	Date
	Fld Descr:	An object containing the Date the command was executed.
	"
    ::= { avCmMeasHuntGrpTodayEntry 3 }

avCmMeasHuntGrpTodayGrpName   OBJECT-TYPE
    SYNTAX	SnmpAdminString (SIZE (0..28))
    MAX-ACCESS  read-only
    STATUS      current
    DESCRIPTION
        "
        Fld OID Name:   avCmMeasHuntGrpTodayGrpName
        Fld OID:        enterprises.6889.2.73.8.1.88.1.1.4
        Fld Form/Rpt:   HUNT GROUP MEASUREMENTS
        Fld Format:     Single Field
        Fld(s) Name:    Grp Name
        Fld Descr:      An object containing the name of the hunt group.
        "
    ::= { avCmMeasHuntGrpTodayEntry 4 }


avCmMeasHuntGrpTodayGroupSiz	OBJECT-TYPE
    SYNTAX	Integer32 (0..999)
    MAX-ACCESS	read-only
    STATUS	current
    DESCRIPTION
	"
	Fld OID Name:	avCmMeasHuntGrpTodayGroupSiz
	Fld OID:	enterprises.6889.2.73.8.1.88.1.1.5
	Fld Form/Rpt:	HUNT GROUP MEASUREMENTS
	Fld Format:	Single Field
	Fld(s) Name:	Grp Siz
	Fld Descr:	An object containing the hunt group size.
	"
    ::= { avCmMeasHuntGrpTodayEntry 5 }

avCmMeasHuntGrpTodayMeasHour	OBJECT-TYPE
    SYNTAX	Integer32 (0..9999)
    MAX-ACCESS	read-only
    STATUS	current
    DESCRIPTION
	"
	Fld OID Name:	avCmMeasHuntGrpTodayMeasHour
	Fld OID:	enterprises.6889.2.73.8.1.88.1.1.6
	Fld Form/Rpt:	HUNT GROUP MEASUREMENTS
	Fld Format:	Single Field
	Fld(s) Name:	Meas Hour
	Fld Descr:	An object containing the measurement hour.
	"
    ::= { avCmMeasHuntGrpTodayEntry 6 }

avCmMeasHuntGrpTodayTotalUsage	OBJECT-TYPE
    SYNTAX	Integer32 (0..99999)
    MAX-ACCESS	read-only
    STATUS	current
    DESCRIPTION
	"
	Fld OID Name:	avCmMeasHuntGrpTodayTotalUsage
	Fld OID:	enterprises.6889.2.73.8.1.88.1.1.7
	Fld Form/Rpt:	HUNT GROUP MEASUREMENTS
	Fld Format:	Single Field
	Fld(s) Name:	Total Usage
	Fld Descr:	An object containing total time hunt groups are busy 
			with calls during the measurement period (in CCS).
	"
    ::= { avCmMeasHuntGrpTodayEntry 7 }

avCmMeasHuntGrpTodayCallsAns	OBJECT-TYPE
    SYNTAX	Integer32 (0..999999)
    MAX-ACCESS	read-only
    STATUS	current
    DESCRIPTION
	"
	Fld OID Name:	avCmMeasHuntGrpTodayCallsAns
	Fld OID:	enterprises.6889.2.73.8.1.88.1.1.8
	Fld Form/Rpt:	HUNT GROUP MEASUREMENTS
	Fld Format:	Single Field
	Fld(s) Name:	Calls Ans
	Fld Descr:	An object containing the number of call answered.
	"
    ::= { avCmMeasHuntGrpTodayEntry 8 }

avCmMeasHuntGrpTodayGrpQue	OBJECT-TYPE
    SYNTAX	SnmpAdminString (SIZE (0..2))
    MAX-ACCESS	read-only
    STATUS	current
    DESCRIPTION
	"
	Fld OID Name:	avCmMeasHuntGrpTodayGrpQue
	Fld OID:	enterprises.6889.2.73.8.1.88.1.1.9
	Fld Form/Rpt:	HUNT GROUP MEASUREMENTS
	Fld Format:	Single Field
	Fld(s) Name:	Que
	Fld Descr:	Field that indicates if there is a queue.
	"
    ::= { avCmMeasHuntGrpTodayEntry 9 }

avCmMeasHuntGrpTodayCallsQue	OBJECT-TYPE
    SYNTAX	Integer32 (0..99999)
    MAX-ACCESS	read-only
    STATUS	current
    DESCRIPTION
	"
	Fld OID Name:	avCmMeasHuntGrpTodayCallsQue
	Fld OID:	enterprises.6889.2.73.8.1.88.1.1.10
	Fld Form/Rpt:	HUNT GROUP MEASUREMENTS
	Fld Format:	Single Field
	Fld(s) Name:	Calls Que
	Fld Descr:	Total number of calls that arrive to find all members 
			of the hunt group busy and are placed in the hunt group
			queue. Calls Queued includes all calls that go to 
			coverage
			
	"
    ::= { avCmMeasHuntGrpTodayEntry 10 }

avCmMeasHuntGrpTodayQueOvfl	OBJECT-TYPE
    SYNTAX	Integer32 (0..99999)
    MAX-ACCESS	read-only
    STATUS	current
    DESCRIPTION
	"
	Fld OID Name:	avCmMeasHuntGrpTodayQueOvfl
	Fld OID:	enterprises.6889.2.73.8.1.88.1.1.11
	Fld Form/Rpt:	HUNT GROUP MEASUREMENTS
	Fld Format:	Single Field
	Fld(s) Name:	Que Ovfl
	Fld Descr:	The number of calls that arrive when all slots in the 
			hunt group queue are occupied.
	"
    ::= { avCmMeasHuntGrpTodayEntry 11 }

avCmMeasHuntGrpTodayTimeAvail	OBJECT-TYPE
    SYNTAX	Integer32 (0..9999)
    MAX-ACCESS	read-only
    STATUS	current
    DESCRIPTION
	"
	Fld OID Name:	avCmMeasHuntGrpTodayTimeAvail
	Fld OID:	enterprises.6889.2.73.8.1.88.1.1.12
	Fld Form/Rpt:	HUNT GROUP MEASUREMENTS
	Fld Format:	Single Field
	Fld(s) Name:	Time Avail
	Fld Descr:	The total time (in CCS) the hunt group extensions are 
			not in use but are available to receive hunt group 
			calls during the measurement hour. Time Available
			is calculated only when an agent (extension) is ready 
			to receive calls from the specified hunt group.
	"
    ::= { avCmMeasHuntGrpTodayEntry 12 }

avCmMeasHuntGrpTodaySpeedAns	OBJECT-TYPE
    SYNTAX	Integer32 (0..9999)
    MAX-ACCESS	read-only
    STATUS	current
    DESCRIPTION
	"
	Fld OID Name:	avCmMeasHuntGrpTodaySpeedAns
	Fld OID:	enterprises.6889.2.73.8.1.88.1.1.13
	Fld Form/Rpt:	HUNT GROUP MEASUREMENTS
	Fld Format:	Single Field
	Fld(s) Name:	Speed Ans
	Fld Descr:	Speed of Answer (seconds). The average time interval 
			(in seconds) from when the call first enters the hunt 
			group or hunt group queue until the call is answered by
			a hunt group member. This does not include the time 
			taken by a forced first announcement.
			
	"
    ::= { avCmMeasHuntGrpTodayEntry 13 }

avCmMeasHuntGrpTodayTyp	OBJECT-TYPE
    SYNTAX	SnmpAdminString (SIZE (0..4))
    MAX-ACCESS	read-only
    STATUS	current
    DESCRIPTION
	"
	Fld OID Name:	avCmMeasHuntGrpTodayQueAbd
	Fld OID:	enterprises.6889.2.73.8.1.88.1.1.14
	Fld Form/Rpt:	HUNT GROUP MEASUREMENTS
	Fld Format:	Single Field
	Fld(s) Name:	Typ
	Fld Descr:	Identifies one of the following type of hunt group:
			- ddc: direct department calling
			- ucd: uniform call distribution
			- ead: expert agent distribution
	"
    ::= { avCmMeasHuntGrpTodayEntry 14 }

avCmMeasHuntGrpTodayAban	OBJECT-TYPE
    SYNTAX	Integer32 (0..999)
    MAX-ACCESS	read-only
    STATUS	current
    DESCRIPTION
	"
	Fld OID Name:	avCmMeasHuntGrpTodayAban
	Fld OID:	enterprises.6889.2.73.8.1.88.1.1.15
	Fld Form/Rpt:	HUNT GROUP MEASUREMENTS
	Fld Format:	Single Field
	Fld(s) Name:	Aban
	Fld Descr:	The total number of calls which attempt to reach the 
			hunt group but abandon the attempt before being 
			answered. Calls might abandon either while in the hunt 
			group queue or while ringing a hunt group extension. 
			This total does not include calls answered by Call 
			Pick Up, other hunt groups, or calls abandoned while 
			listening to a forced first announcement.
	"
    ::= { avCmMeasHuntGrpTodayEntry 15 }

-- ******************** avCmMeasHuntGrpYest Group *************************

-- MIB GROUP DESCRIPTION

-- MIB Group Name:
--		avCmMeasHuntGrpYest Group
-- OID:
--		enterprises.6889.2.73.8.1.89
-- Description:
--		The avCmMeasHuntGrpYest MIB Group uses the "list measurements
--		hunt-group yesterday" command to retrieve hunt-group data 
--		from the last hour.
--		
-- Releases Supported:
--		CM6.3.100 and greater
-- Polling Type:
--		Performance/Utilization
-- Polling Interval:
--		No more than once an hour because the data is only updated
--		near the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements hunt-group yesterday
-- Form/Report Name:
--		1. HUNT GROUP MEASUREMENTS
-- Reference Document:
--		1. A detailed description of the command and form can be
--		   found in document referenced by REF_DOC_4 in the
--		   DOCUMENT REFERENCE SECTION.
-- Command Permission/User-profile:
--		1. No special permissions needed.

avCmMeasHuntGrpYest	OBJECT IDENTIFIER ::= { avCmObjects 89 }

avCmMeasHuntGrpYestTable	OBJECT-TYPE
    SYNTAX	SEQUENCE OF AvCmMeasHuntGrpYestEntry
    MAX-ACCESS	not-accessible
    STATUS	current
    DESCRIPTION
	"
	Fld OID Name:	avCmMeasHuntGrpYestEntry
	Fld OID:	enterprises.6889.2.73.8.1.89.1
	Fld Form/Rpt:	NA
	Fld Format:	NA
	Fld(s) Name:	NA
	Fld Descr:	A list of the avCmMeasHuntGrpYest entries
	"
    ::= { avCmMeasHuntGrpYest 1 }

avCmMeasHuntGrpYestEntry	OBJECT-TYPE
    SYNTAX	AvCmMeasHuntGrpYestEntry
    MAX-ACCESS	not-accessible
    STATUS	current
    DESCRIPTION
	"
	Fld OID Name:	avCmMeasHuntGrpYestEntry
	Fld OID:	enterprises.6889.2.73.8.1.89.1.1
	Fld Form/Rpt:	NA
	Fld Format:	NA
	Fld(s) Name:	NA
	Fld Descr:	A avCmMeasHuntGrpYest entry containing objects of the
			avCmMeasHuntGrpYest information sent by the switch.
	"
    INDEX    { avCmMeasHuntGrpYestHuntGrpIdx }
    ::= { avCmMeasHuntGrpYestTable 1 }

AvCmMeasHuntGrpYestEntry ::= SEQUENCE {
		avCmMeasHuntGrpYestHuntGrpIdx
		    Integer32,
		avCmMeasHuntGrpYestHuntGrpNo
		    Integer32,
		avCmMeasHuntGrpYestRunDate
		    SnmpAdminString,
		avCmMeasHuntGrpYestGrpName
		    SnmpAdminString,
		avCmMeasHuntGrpYestGroupSiz
		    Integer32,
		avCmMeasHuntGrpYestMeasHour
		    Integer32,
		avCmMeasHuntGrpYestTotalUsage 
		    Integer32,
		avCmMeasHuntGrpYestCallsAns
		    Integer32,
		avCmMeasHuntGrpYestGrpQue
		    SnmpAdminString,
		avCmMeasHuntGrpYestCallsQue
		    Integer32,
		avCmMeasHuntGrpYestQueOvfl
		    Integer32,
		avCmMeasHuntGrpYestTimeAvail
		    Integer32,
		avCmMeasHuntGrpYestSpeedAns
		    Integer32,
		avCmMeasHuntGrpYestTyp
		    SnmpAdminString,
		avCmMeasHuntGrpYestAban
		    Integer32
		}

avCmMeasHuntGrpYestHuntGrpIdx	OBJECT-TYPE
    SYNTAX	Integer32 (0..9999)
    MAX-ACCESS	not-accessible
    STATUS	current
    DESCRIPTION
	"
	Fld OID Name:	avCmMeasHuntGrpYestHuntGrpIdx
	Fld OID:	enterprises.6889.2.73.8.1.89.1.1.1
	Fld Format:	NA
	Fld(s) Name:	NA
	Fld Descr:	An object that uniquely identifies each Increment of 
			data.
	"
    ::= { avCmMeasHuntGrpYestEntry 1 }

avCmMeasHuntGrpYestHuntGrpNo	OBJECT-TYPE
    SYNTAX	Integer32 (0..9999)
    MAX-ACCESS	read-only
    STATUS	current
    DESCRIPTION
	"
	Fld OID Name:	avCmMeasHuntGrpYestHuntGrpNo
	Fld OID:	enterprises.6889.2.73.8.1.89.1.1.2
	Fld Form/Rpt:	HUNT GROUP MEASUREMENTS
	Fld Format:	Single Field
	Fld(s) Name:	Hunt Group
	Fld Descr:	An object containing the hunt group number.
	"
    ::= { avCmMeasHuntGrpYestEntry 2 }

avCmMeasHuntGrpYestRunDate	OBJECT-TYPE
    SYNTAX	SnmpAdminString (SIZE (0..28))
    MAX-ACCESS	read-only
    STATUS	current
    DESCRIPTION
	"
	Fld OID Name:	avCmMeasHuntGrpYestRunDate
	Fld OID:	enterprises.6889.2.73.8.1.89.1.1.3
	Fld Form/Rpt:	HUNT GROUP MEASUREMENTS
	Fld Format:	Single Field
	Fld(s) Name:	Date
	Fld Descr:	An object containing the Date the command was executed.
	"
    ::= { avCmMeasHuntGrpYestEntry 3 }

avCmMeasHuntGrpYestGrpName   OBJECT-TYPE
    SYNTAX	SnmpAdminString (SIZE (0..28))
    MAX-ACCESS  read-only
    STATUS      current
    DESCRIPTION
        "
        Fld OID Name:   avCmMeasHuntGrpYestGrpName
        Fld OID:        enterprises.6889.2.73.8.1.89.1.1.4
        Fld Form/Rpt:   HUNT GROUP MEASUREMENTS
        Fld Format:     Single Field
        Fld(s) Name:    Grp Name
        Fld Descr:      An object containing the name of the hunt group.
        "
    ::= { avCmMeasHuntGrpYestEntry 4 }


avCmMeasHuntGrpYestGroupSiz	OBJECT-TYPE
    SYNTAX	Integer32 (0..999)
    MAX-ACCESS	read-only
    STATUS	current
    DESCRIPTION
	"
	Fld OID Name:	avCmMeasHuntGrpYestGroupSiz
	Fld OID:	enterprises.6889.2.73.8.1.89.1.1.5
	Fld Form/Rpt:	HUNT GROUP MEASUREMENTS
	Fld Format:	Single Field
	Fld(s) Name:	Grp Siz
	Fld Descr:	An object containing the hunt group size.
	"
    ::= { avCmMeasHuntGrpYestEntry 5 }

avCmMeasHuntGrpYestMeasHour	OBJECT-TYPE
    SYNTAX	Integer32 (0..9999)
    MAX-ACCESS	read-only
    STATUS	current
    DESCRIPTION
	"
	Fld OID Name:	avCmMeasHuntGrpYestMeasHour
	Fld OID:	enterprises.6889.2.73.8.1.89.1.1.6
	Fld Form/Rpt:	HUNT GROUP MEASUREMENTS
	Fld Format:	Single Field
	Fld(s) Name:	Meas Hour
	Fld Descr:	An object containing the measurement hour.
	"
    ::= { avCmMeasHuntGrpYestEntry 6 }

avCmMeasHuntGrpYestTotalUsage	OBJECT-TYPE
    SYNTAX	Integer32 (0..99999)
    MAX-ACCESS	read-only
    STATUS	current
    DESCRIPTION
	"
	Fld OID Name:	avCmMeasHuntGrpYestTotalUsage
	Fld OID:	enterprises.6889.2.73.8.1.89.1.1.7
	Fld Form/Rpt:	HUNT GROUP MEASUREMENTS
	Fld Format:	Single Field
	Fld(s) Name:	Total Usage
	Fld Descr:	An object containing total time hunt groups are busy 
			with calls during the measurement period (in CCS).
	"
    ::= { avCmMeasHuntGrpYestEntry 7 }

avCmMeasHuntGrpYestCallsAns	OBJECT-TYPE
    SYNTAX	Integer32 (0..999999)
    MAX-ACCESS	read-only
    STATUS	current
    DESCRIPTION
	"
	Fld OID Name:	avCmMeasHuntGrpYestCallsAns
	Fld OID:	enterprises.6889.2.73.8.1.89.1.1.8
	Fld Form/Rpt:	HUNT GROUP MEASUREMENTS
	Fld Format:	Single Field
	Fld(s) Name:	Calls Ans
	Fld Descr:	An object containing the number of call answered.
	"
    ::= { avCmMeasHuntGrpYestEntry 8 }

avCmMeasHuntGrpYestGrpQue	OBJECT-TYPE
    SYNTAX	SnmpAdminString (SIZE (0..2))
    MAX-ACCESS	read-only
    STATUS	current
    DESCRIPTION
	"
	Fld OID Name:	avCmMeasHuntGrpYestGrpQue
	Fld OID:	enterprises.6889.2.73.8.1.89.1.1.9
	Fld Form/Rpt:	HUNT GROUP MEASUREMENTS
	Fld Format:	Single Field
	Fld(s) Name:	Que
	Fld Descr:	Field that indicates if there is a queue.
	"
    ::= { avCmMeasHuntGrpYestEntry 9 }

avCmMeasHuntGrpYestCallsQue	OBJECT-TYPE
    SYNTAX	Integer32 (0..99999)
    MAX-ACCESS	read-only
    STATUS	current
    DESCRIPTION
	"
	Fld OID Name:	avCmMeasHuntGrpYestCallsQue
	Fld OID:	enterprises.6889.2.73.8.1.89.1.1.10
	Fld Form/Rpt:	HUNT GROUP MEASUREMENTS
	Fld Format:	Single Field
	Fld(s) Name:	Calls Que
	Fld Descr:	Total number of calls that arrive to find all members 
			of the hunt group busy and are placed in the hunt group
			queue. Calls Queued includes all calls that go to 
			coverage
			
	"
    ::= { avCmMeasHuntGrpYestEntry 10 }

avCmMeasHuntGrpYestQueOvfl	OBJECT-TYPE
    SYNTAX	Integer32 (0..99999)
    MAX-ACCESS	read-only
    STATUS	current
    DESCRIPTION
	"
	Fld OID Name:	avCmMeasHuntGrpYestQueOvfl
	Fld OID:	enterprises.6889.2.73.8.1.89.1.1.11
	Fld Form/Rpt:	HUNT GROUP MEASUREMENTS
	Fld Format:	Single Field
	Fld(s) Name:	Que Ovfl
	Fld Descr:	The number of calls that arrive when all slots in the 
			hunt group queue are occupied.
	"
    ::= { avCmMeasHuntGrpYestEntry 11 }

avCmMeasHuntGrpYestTimeAvail	OBJECT-TYPE
    SYNTAX	Integer32 (0..9999)
    MAX-ACCESS	read-only
    STATUS	current
    DESCRIPTION
	"
	Fld OID Name:	avCmMeasHuntGrpYestTimeAvail
	Fld OID:	enterprises.6889.2.73.8.1.89.1.1.12
	Fld Form/Rpt:	HUNT GROUP MEASUREMENTS
	Fld Format:	Single Field
	Fld(s) Name:	Time Avail
	Fld Descr:	The total time (in CCS) the hunt group extensions are 
			not in use but are available to receive hunt group 
			calls during the measurement hour. Time Available
			is calculated only when an agent (extension) is ready 
			to receive calls from the specified hunt group.
	"
    ::= { avCmMeasHuntGrpYestEntry 12 }

avCmMeasHuntGrpYestSpeedAns	OBJECT-TYPE
    SYNTAX	Integer32 (0..9999)
    MAX-ACCESS	read-only
    STATUS	current
    DESCRIPTION
	"
	Fld OID Name:	avCmMeasHuntGrpYestSpeedAns
	Fld OID:	enterprises.6889.2.73.8.1.89.1.1.13
	Fld Form/Rpt:	HUNT GROUP MEASUREMENTS
	Fld Format:	Single Field
	Fld(s) Name:	Speed Ans
	Fld Descr:	Speed of Answer (seconds). The average time interval 
			(in seconds) from when the call first enters the hunt 
			group or hunt group queue until the call is answered by
			a hunt group member. This does not include the time 
			taken by a forced first announcement.
			
	"
    ::= { avCmMeasHuntGrpYestEntry 13 }

avCmMeasHuntGrpYestTyp	OBJECT-TYPE
    SYNTAX	SnmpAdminString (SIZE (0..4))
    MAX-ACCESS	read-only
    STATUS	current
    DESCRIPTION
	"
	Fld OID Name:	avCmMeasHuntGrpYestTyp
	Fld OID:	enterprises.6889.2.73.8.1.89.1.1.14
	Fld Form/Rpt:	HUNT GROUP MEASUREMENTS
	Fld Format:	Single Field
	Fld(s) Name:	Typ
	Fld Descr:	Identifies one of the following type of hunt group:
			- ddc: direct department calling
			- ucd: uniform call distribution
			- ead: expert agent distribution
	"
    ::= { avCmMeasHuntGrpYestEntry 14 }

avCmMeasHuntGrpYestAban	OBJECT-TYPE
    SYNTAX	Integer32 (0..999)
    MAX-ACCESS	read-only
    STATUS	current
    DESCRIPTION
	"
	Fld OID Name:	avCmMeasHuntGrpYestAban
	Fld OID:	enterprises.6889.2.73.8.1.89.1.1.15
	Fld Form/Rpt:	HUNT GROUP MEASUREMENTS
	Fld Format:	Single Field
	Fld(s) Name:	Aban
	Fld Descr:	The total number of calls which attempt to reach the 
			hunt group but abandon the attempt before being 
			answered. Calls might abandon either while in the hunt 
			group queue or while ringing a hunt group extension. 
			This total does not include calls answered by Call 
			Pick Up, other hunt groups, or calls abandoned while 
			listening to a forced first announcement.
	"
    ::= { avCmMeasHuntGrpYestEntry 15 }


-- ******************** avCmListIpInterfaceAll Group *************************

-- MIB GROUP DESCRIPTION

-- MIB Group Name:
--		avCmListIpInterfaceAll Group
-- OID:
--		enterprises.6889.2.73.8.1.90
-- Description:
--		The avCmListIpInterfaceAll MIB Group uses the "list ip-interface
--		all" command to retrieve all ip-interface data. 
--		
-- Releases Supported:
--		CM6.3.100 and greater
-- Polling Type:
--		Performance/Utilization
-- Polling Interval:
--		No more than once daily.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list ip-interface all
-- Form/Report Name:
--		1. IP INTERFACES
-- Reference Document:
--		1. A detailed description of the command and form can be
--		   found in document referenced by REF_DOC_3 in the
--		   DOCUMENT REFERENCE SECTION.
-- Command Permission/User-profile:
--		1. No special permissions needed.

avCmListIpInterfaceAll	OBJECT IDENTIFIER ::= { avCmObjects 90 }

avCmListIpInterfaceAllTable	OBJECT-TYPE
    SYNTAX	SEQUENCE OF AvCmListIpInterfaceAllEntry
    MAX-ACCESS	not-accessible
    STATUS	current
    DESCRIPTION
	"
	Fld OID Name:	avCmListIpInterfaceAllEntry
	Fld OID:	enterprises.6889.2.73.8.1.90.1
	Fld Form/Rpt:	NA
	Fld Format:	NA
	Fld(s) Name:	NA
	Fld Descr:	A list of the avCmListIpInterfaceAll entries
	"
    ::= { avCmListIpInterfaceAll 1 }

avCmListIpInterfaceAllEntry	OBJECT-TYPE
    SYNTAX	AvCmListIpInterfaceAllEntry
    MAX-ACCESS	not-accessible
    STATUS	current
    DESCRIPTION
	"
	Fld OID Name:	avCmListIpInterfaceAllEntry
	Fld OID:	enterprises.6889.2.73.8.1.90.1.1
	Fld Form/Rpt:	NA
	Fld Format:	NA
	Fld(s) Name:	NA
	Fld Descr:	A avCmListIpInterfaceAll entry containing objects of the
			avCmListIpInterfaceAll information sent by the switch.
	"
    INDEX    { avCmListIpInterfaceAllSlotIdx, avCmListIpInterfaceAllIdx }
    ::= { avCmListIpInterfaceAllTable 1 }

AvCmListIpInterfaceAllEntry ::= SEQUENCE {
		avCmListIpInterfaceAllSlotIdx
		    SnmpAdminString,
		avCmListIpInterfaceAllIdx
		    Integer32,
		avCmListIpInterfaceAllOn
		    SnmpAdminString,
		avCmListIpInterfaceAllType
		    SnmpAdminString,
		avCmListIpInterfaceAllSlot
		    SnmpAdminString,
		avCmListIpInterfaceAllCode
		    SnmpAdminString,
		avCmListIpInterfaceAllSfx
		    SnmpAdminString,
		avCmListIpInterfaceAllNodeName
		    SnmpAdminString,
		avCmListIpInterfaceAllMask 
		    SnmpAdminString,
		avCmListIpInterfaceAllNetRgn
		    Integer32,
		avCmListIpInterfaceAllVlan
		    SnmpAdminString,
		avCmListIpInterfaceAllIpAddress
		    SnmpAdminString,
		avCmListIpInterfaceAllGatewayNode
		    SnmpAdminString,
		avCmListIpInterfaceAllOn2
		    SnmpAdminString,
		avCmListIpInterfaceAllType2
		    SnmpAdminString,
		avCmListIpInterfaceAllSlot2
		    SnmpAdminString,
		avCmListIpInterfaceAllCode2
		    SnmpAdminString,
		avCmListIpInterfaceAllSfx2
		    SnmpAdminString,
		avCmListIpInterfaceAllNodeName2
		    SnmpAdminString,
		avCmListIpInterfaceAllMask2 
		    SnmpAdminString,
		avCmListIpInterfaceAllNetRgn2
		    Integer32,
		avCmListIpInterfaceAllVlan2
		    SnmpAdminString,
		avCmListIpInterfaceAllIpAddress2
		    SnmpAdminString,
		avCmListIpInterfaceAllGatewayNode2
		    SnmpAdminString
		}

avCmListIpInterfaceAllSlotIdx	OBJECT-TYPE
    SYNTAX	SnmpAdminString (SIZE (0..6))
    MAX-ACCESS	not-accessible
    STATUS	current
    DESCRIPTION
	"
	Fld OID Name:	avCmListIpInterfaceAllSlotIdx
	Fld OID:	enterprises.6889.2.73.8.1.90.1.1.1
	Fld Format:	NA
	Fld(s) Name:	NA
	Fld Descr:	An object that uniquely identifies each Increment of 
			data.
	"
    ::= { avCmListIpInterfaceAllEntry 1 }

avCmListIpInterfaceAllIdx   OBJECT-TYPE
    SYNTAX	Integer32 (0..9999)
    MAX-ACCESS  not-accessible
    STATUS      current
    DESCRIPTION
        "
        Fld OID Name:   avCmListIpInterfaceAllIdx
        Fld OID:        enterprises.6889.2.73.8.1.90.1.1.2
        Fld Format:     NA
        Fld(s) Name:    NA
        Fld Descr:      An object that uniquely identifies each Increment of
                        data.
        "
    ::= { avCmListIpInterfaceAllEntry 2 }


avCmListIpInterfaceAllOn	OBJECT-TYPE
    SYNTAX	SnmpAdminString (SIZE (0..2))
    MAX-ACCESS	read-only
    STATUS	current
    DESCRIPTION
	"
	Fld OID Name:	avCmListIpInterfaceAllOn
	Fld OID:	enterprises.6889.2.73.8.1.90.1.1.3
	Fld Form/Rpt:	IP INTERFACES
	Fld Format:	Single Field
	Fld(s) Name:	ON
	Fld Descr:	An object containing whether the ip-interface is 
			enabled.
	"
    ::= { avCmListIpInterfaceAllEntry 3 }

avCmListIpInterfaceAllType	OBJECT-TYPE
    SYNTAX	SnmpAdminString (SIZE (0..7))
    MAX-ACCESS	read-only
    STATUS	current
    DESCRIPTION
	"
	Fld OID Name:	avCmListIpInterfaceAllType
	Fld OID:	enterprises.6889.2.73.8.1.90.1.1.4
	Fld Form/Rpt:	IP INTERFACES
	Fld Format:	Single Field
	Fld(s) Name:	Type
	Fld Descr:	An object containing the type of ip-interface.
	"
    ::= { avCmListIpInterfaceAllEntry 4 }

avCmListIpInterfaceAllSlot   OBJECT-TYPE
    SYNTAX	SnmpAdminString (SIZE (0..6))
    MAX-ACCESS  read-only
    STATUS      current
    DESCRIPTION
        "
        Fld OID Name:   avCmListIpInterfaceAllSlot
        Fld OID:        enterprises.6889.2.73.8.1.90.1.1.5
        Fld Form/Rpt:   IP INTERFACES
        Fld Format:     Single Field
        Fld(s) Name:    Slot
        Fld Descr:      An object containing the slot where the ip-interface 
			resides.
        "
    ::= { avCmListIpInterfaceAllEntry 5 }


avCmListIpInterfaceAllCode	OBJECT-TYPE
    SYNTAX	SnmpAdminString (SIZE (0..7))
    MAX-ACCESS	read-only
    STATUS	current
    DESCRIPTION
	"
	Fld OID Name:	avCmListIpInterfaceAllCode
	Fld OID:	enterprises.6889.2.73.8.1.90.1.1.6
	Fld Form/Rpt:	IP INTERFACES
	Fld Format:	Single Field
	Fld(s) Name:	Code/
	Fld Descr:	An object containing the TN code of the board.
	"
    ::= { avCmListIpInterfaceAllEntry 6 }

avCmListIpInterfaceAllSfx	OBJECT-TYPE
    SYNTAX	SnmpAdminString (SIZE (0..2))
    MAX-ACCESS	read-only
    STATUS	current
    DESCRIPTION
	"
	Fld OID Name:	avCmListIpInterfaceAllSfx
	Fld OID:	enterprises.6889.2.73.8.1.90.1.1.7
	Fld Form/Rpt:	IP INTERFACES
	Fld Format:	Single Field
	Fld(s) Name:	Sfx
	Fld Descr:	An object containing the suffix of the board.
	"
    ::= { avCmListIpInterfaceAllEntry 7 }

avCmListIpInterfaceAllNodeName	OBJECT-TYPE
    SYNTAX	SnmpAdminString (SIZE (0..16))
    MAX-ACCESS	read-only
    STATUS	current
    DESCRIPTION
	"
	Fld OID Name:	avCmListIpInterfaceAllNodeName
	Fld OID:	enterprises.6889.2.73.8.1.90.1.1.8
	Fld Form/Rpt:	IP INTERFACES
	Fld Format:	Single Field
	Fld(s) Name:	Node Name
	Fld Descr:	An object containing the Node Name used by the 
			ip-intereface.
	"
    ::= { avCmListIpInterfaceAllEntry 8 }

avCmListIpInterfaceAllMask	OBJECT-TYPE
    SYNTAX	SnmpAdminString (SIZE (0..4))
    MAX-ACCESS	read-only
    STATUS	current
    DESCRIPTION
	"
	Fld OID Name:	avCmListIpInterfaceAllMask
	Fld OID:	enterprises.6889.2.73.8.1.90.1.1.9
	Fld Form/Rpt:	IP INTERFACES
	Fld Format:	Single Field
	Fld(s) Name:	Mask
	Fld Descr:	An object containing the mask of the ip-interface.
	"
    ::= { avCmListIpInterfaceAllEntry 9 }

avCmListIpInterfaceAllNetRgn	OBJECT-TYPE
    SYNTAX	Integer32 (0..9999)
    MAX-ACCESS	read-only
    STATUS	current
    DESCRIPTION
	"
	Fld OID Name:	avCmListIpInterfaceAllNetRgn
	Fld OID:	enterprises.6889.2.73.8.1.90.1.1.10
	Fld Form/Rpt:	IP INTERFACES
	Fld Format:	Single Field
	Fld(s) Name:	Net Rgn
	Fld Descr:	Field that displays network region used by the 
			ip-interface.
	"
    ::= { avCmListIpInterfaceAllEntry 10 }

avCmListIpInterfaceAllVlan	OBJECT-TYPE
    SYNTAX	SnmpAdminString (SIZE (0..5))
    MAX-ACCESS	read-only
    STATUS	current
    DESCRIPTION
	"
	Fld OID Name:	avCmListIpInterfaceAllVlan
	Fld OID:	enterprises.6889.2.73.8.1.90.1.1.11
	Fld Form/Rpt:	IP INTERFACES
	Fld Format:	Single Field
	Fld(s) Name:	VLAN
	Fld Descr:	Field that displays the virtual lan used by the 
			ip-interface.
	"
    ::= { avCmListIpInterfaceAllEntry 11 }

avCmListIpInterfaceAllIpAddress	OBJECT-TYPE
    SYNTAX	SnmpAdminString (SIZE (0..41))
    MAX-ACCESS	read-only
    STATUS	current
    DESCRIPTION
	"
	Fld OID Name:	avCmListIpInterfaceAllIpAddress
	Fld OID:	enterprises.6889.2.73.8.1.90.1.1.12
	Fld Form/Rpt:	IP INTERFACES
	Fld Format:	Single Field
	Fld(s) Name:	IP Address
	Fld Descr:	The IP Address associated with the ip-interface.
	"
    ::= { avCmListIpInterfaceAllEntry 12 }

avCmListIpInterfaceAllGatewayNode	OBJECT-TYPE
    SYNTAX	SnmpAdminString (SIZE (0..41))
    MAX-ACCESS	read-only
    STATUS	current
    DESCRIPTION
	"
	Fld OID Name:	avCmListIpInterfaceAllGatewayNode
	Fld OID:	enterprises.6889.2.73.8.1.90.1.1.13
	Fld Form/Rpt:	IP INTERFACES
	Fld Format:	Single Field
	Fld(s) Name:	Gateway Node
	Fld Descr:	The IP Address associated with the ip-interface.
	"
    ::= { avCmListIpInterfaceAllEntry 13 }


avCmListIpInterfaceAllOn2	OBJECT-TYPE
    SYNTAX	SnmpAdminString (SIZE (0..2))
    MAX-ACCESS	read-only
    STATUS	current
    DESCRIPTION
	"
	Fld OID Name:	avCmListIpInterfaceAllOn2
	Fld OID:	enterprises.6889.2.73.8.1.90.1.1.14
	Fld Form/Rpt:	IP INTERFACES
	Fld Format:	Single Field
	Fld(s) Name:	ON
	Fld Descr:	An object containing whether the duplicated 
			ip-interface is enabled.
	"
    ::= { avCmListIpInterfaceAllEntry 14 }

avCmListIpInterfaceAllType2	OBJECT-TYPE
    SYNTAX	SnmpAdminString (SIZE (0..7))
    MAX-ACCESS	read-only
    STATUS	current
    DESCRIPTION
	"
	Fld OID Name:	avCmListIpInterfaceAllType
	Fld OID:	enterprises.6889.2.73.8.1.90.1.1.15
	Fld Form/Rpt:	IP INTERFACES
	Fld Format:	Single Field
	Fld(s) Name:	Type
	Fld Descr:	An object containing the duplicated type of 
			ip-interface.
	"
    ::= { avCmListIpInterfaceAllEntry 15 }

avCmListIpInterfaceAllSlot2   OBJECT-TYPE
    SYNTAX	SnmpAdminString (SIZE (0..6))
    MAX-ACCESS  read-only
    STATUS      current
    DESCRIPTION
        "
        Fld OID Name:   avCmListIpInterfaceAllSlot2
        Fld OID:        enterprises.6889.2.73.8.1.90.1.1.16
        Fld Form/Rpt:   IP INTERFACES
        Fld Format:     Single Field
        Fld(s) Name:    Slot
        Fld Descr:      An object containing the slot where the duplicated 
			ip-interface resides.
        "
    ::= { avCmListIpInterfaceAllEntry 16 }


avCmListIpInterfaceAllCode2	OBJECT-TYPE
    SYNTAX	SnmpAdminString (SIZE (0..7))
    MAX-ACCESS	read-only
    STATUS	current
    DESCRIPTION
	"
	Fld OID Name:	avCmListIpInterfaceAllCode2
	Fld OID:	enterprises.6889.2.73.8.1.90.1.1.17
	Fld Form/Rpt:	IP INTERFACES
	Fld Format:	Single Field
	Fld(s) Name:	Code/
	Fld Descr:	An object containing the TN code of the duplicate board.
	"
    ::= { avCmListIpInterfaceAllEntry 17 }

avCmListIpInterfaceAllSfx2	OBJECT-TYPE
    SYNTAX	SnmpAdminString (SIZE (0..2))
    MAX-ACCESS	read-only
    STATUS	current
    DESCRIPTION
	"
	Fld OID Name:	avCmListIpInterfaceAllSfx2
	Fld OID:	enterprises.6889.2.73.8.1.90.1.1.18
	Fld Form/Rpt:	IP INTERFACES
	Fld Format:	Single Field
	Fld(s) Name:	Sfx
	Fld Descr:	An object containing the suffix of the duplicated board.
	"
    ::= { avCmListIpInterfaceAllEntry 18 }

avCmListIpInterfaceAllNodeName2	OBJECT-TYPE
    SYNTAX	SnmpAdminString (SIZE (0..16))
    MAX-ACCESS	read-only
    STATUS	current
    DESCRIPTION
	"
	Fld OID Name:	avCmListIpInterfaceAllNodeName2
	Fld OID:	enterprises.6889.2.73.8.1.90.1.1.19
	Fld Form/Rpt:	IP INTERFACES
	Fld Format:	Single Field
	Fld(s) Name:	Node Name
	Fld Descr:	An object containing the Node Name used by the 
			duplicated ip-intereface.
	"
    ::= { avCmListIpInterfaceAllEntry 19 }

avCmListIpInterfaceAllMask2	OBJECT-TYPE
    SYNTAX	SnmpAdminString (SIZE (0..4))
    MAX-ACCESS	read-only
    STATUS	current
    DESCRIPTION
	"
	Fld OID Name:	avCmListIpInterfaceAllMask2
	Fld OID:	enterprises.6889.2.73.8.1.90.1.1.20
	Fld Form/Rpt:	IP INTERFACES
	Fld Format:	Single Field
	Fld(s) Name:	Mask
	Fld Descr:	An object containing the mask of the duplicated 
			ip-interface.
	"
    ::= { avCmListIpInterfaceAllEntry 20 }

avCmListIpInterfaceAllNetRgn2	OBJECT-TYPE
    SYNTAX	Integer32 (0..9999)
    MAX-ACCESS	read-only
    STATUS	current
    DESCRIPTION
	"
	Fld OID Name:	avCmListIpInterfaceAllNetRgn2
	Fld OID:	enterprises.6889.2.73.8.1.90.1.1.21
	Fld Form/Rpt:	IP INTERFACES
	Fld Format:	Single Field
	Fld(s) Name:	Net Rgn
	Fld Descr:	Field that displays network region used by the 
			ip-interface.
	"
    ::= { avCmListIpInterfaceAllEntry 21 }

avCmListIpInterfaceAllVlan2	OBJECT-TYPE
    SYNTAX	SnmpAdminString (SIZE (0..5))
    MAX-ACCESS	read-only
    STATUS	current
    DESCRIPTION
	"
	Fld OID Name:	avCmListIpInterfaceAllVlan2
	Fld OID:	enterprises.6889.2.73.8.1.90.1.1.22
	Fld Form/Rpt:	IP INTERFACES
	Fld Format:	Single Field
	Fld(s) Name:	VLAN
	Fld Descr:	Field that displays the virtual lan used by the 
			ip-interface.
	"
    ::= { avCmListIpInterfaceAllEntry 22 }

avCmListIpInterfaceAllIpAddress2	OBJECT-TYPE
    SYNTAX	SnmpAdminString (SIZE (0..41))
    MAX-ACCESS	read-only
    STATUS	current
    DESCRIPTION
	"
	Fld OID Name:	avCmListIpInterfaceAllIpAddress2
	Fld OID:	enterprises.6889.2.73.8.1.90.1.1.23
	Fld Form/Rpt:	IP INTERFACES
	Fld Format:	Single Field
	Fld(s) Name:	IP Address
	Fld Descr:	The IP Address associated with the duplicate 
			ip-interface.
	"
    ::= { avCmListIpInterfaceAllEntry 23 }

avCmListIpInterfaceAllGatewayNode2	OBJECT-TYPE
    SYNTAX	SnmpAdminString (SIZE (0..41))
    MAX-ACCESS	read-only
    STATUS	current
    DESCRIPTION
	"
	Fld OID Name:	avCmListIpInterfaceAllGatewayNode2
	Fld OID:	enterprises.6889.2.73.8.1.90.1.1.24
	Fld Form/Rpt:	IP INTERFACES
	Fld Format:	Single Field
	Fld(s) Name:	Gateway Node
	Fld Descr:	The IP Address associated with the ip-interface.
	"
    ::= { avCmListIpInterfaceAllEntry 24 }

-- ****************** avCmListIpInterfaceMedpro Group *************************

-- MIB GROUP DESCRIPTION

-- MIB Group Name:
--		avCmListIpInterfaceMedpro Group
-- OID:
--		enterprises.6889.2.73.8.1.91
-- Description:
--		The avCmListIpInterfaceMedpro MIB Group uses the 
--		"list ip-interface medpro" command to retrieve media-processor
--		 ip-interface data. 
--		
-- Releases Supported:
--		CM6.3.100 and greater
-- Polling Type:
--		Performance/Utilization
-- Polling Interval:
--		No more than once daily.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list ip-interface medpro
-- Form/Report Name:
--		1. IP INTERFACES
-- Reference Document:
--		1. A detailed description of the command and form can be
--		   found in document referenced by REF_DOC_3 in the
--		   DOCUMENT REFERENCE SECTION.
-- Command Permission/User-profile:
--		1. No special permissions needed.

avCmListIpInterfaceMedpro	OBJECT IDENTIFIER ::= { avCmObjects 91 }

avCmListIpInterfaceMedproTable	OBJECT-TYPE
    SYNTAX	SEQUENCE OF AvCmListIpInterfaceMedproEntry
    MAX-ACCESS	not-accessible
    STATUS	current
    DESCRIPTION
	"
	Fld OID Name:	avCmListIpInterfaceMedproEntry
	Fld OID:	enterprises.6889.2.73.8.1.91.1
	Fld Form/Rpt:	NA
	Fld Format:	NA
	Fld(s) Name:	NA
	Fld Descr:	A list of the avCmListIpInterfaceMedpro entries
	"
    ::= { avCmListIpInterfaceMedpro 1 }

avCmListIpInterfaceMedproEntry	OBJECT-TYPE
    SYNTAX	AvCmListIpInterfaceMedproEntry
    MAX-ACCESS	not-accessible
    STATUS	current
    DESCRIPTION
	"
	Fld OID Name:	avCmListIpInterfaceMedproEntry
	Fld OID:	enterprises.6889.2.73.8.1.91.1.1
	Fld Form/Rpt:	NA
	Fld Format:	NA
	Fld(s) Name:	NA
	Fld Descr:	A avCmListIpInterfaceMedpro entry containing objects of the
			avCmListIpInterfaceMedpro information sent by the switch.
	"
    INDEX    { avCmListIpInterfaceMedproSlotIdx, avCmListIpInterfaceMedproIdx }
    ::= { avCmListIpInterfaceMedproTable 1 }

AvCmListIpInterfaceMedproEntry ::= SEQUENCE {
		avCmListIpInterfaceMedproSlotIdx
		    SnmpAdminString,
		avCmListIpInterfaceMedproIdx
		    Integer32,
		avCmListIpInterfaceMedproOn
		    SnmpAdminString,
		avCmListIpInterfaceMedproType
		    SnmpAdminString,
		avCmListIpInterfaceMedproSlot
		    SnmpAdminString,
		avCmListIpInterfaceMedproCode
		    SnmpAdminString,
		avCmListIpInterfaceMedproSfx
		    SnmpAdminString,
		avCmListIpInterfaceMedproNodeName
		    SnmpAdminString,
		avCmListIpInterfaceMedproMask 
		    SnmpAdminString,
		avCmListIpInterfaceMedproNetRgn
		    Integer32,
		avCmListIpInterfaceMedproVlan
		    SnmpAdminString,
		avCmListIpInterfaceMedproVirtualNode
		    SnmpAdminString,
		avCmListIpInterfaceMedproIpAddress
		    SnmpAdminString,
		avCmListIpInterfaceMedproGatewayNode
		    SnmpAdminString,
		avCmListIpInterfaceMedproOn2
		    SnmpAdminString,
		avCmListIpInterfaceMedproType2
		    SnmpAdminString,
		avCmListIpInterfaceMedproSlot2
		    SnmpAdminString,
		avCmListIpInterfaceMedproCode2
		    SnmpAdminString,
		avCmListIpInterfaceMedproSfx2
		    SnmpAdminString,
		avCmListIpInterfaceMedproNodeName2
		    SnmpAdminString,
		avCmListIpInterfaceMedproMask2 
		    SnmpAdminString,
		avCmListIpInterfaceMedproNetRgn2
		    Integer32,
		avCmListIpInterfaceMedproVlan2
		    SnmpAdminString,
		avCmListIpInterfaceMedproVirtualNode2
		    SnmpAdminString,
		avCmListIpInterfaceMedproIpAddress2
		    SnmpAdminString,
		avCmListIpInterfaceMedproGatewayNode2
		    SnmpAdminString
		}

avCmListIpInterfaceMedproSlotIdx	OBJECT-TYPE
    SYNTAX	SnmpAdminString (SIZE (0..6))
    MAX-ACCESS	not-accessible
    STATUS	current
    DESCRIPTION
	"
	Fld OID Name:	avCmListIpInterfaceMedproSlotIdx
	Fld OID:	enterprises.6889.2.73.8.1.91.1.1.1
	Fld Format:	NA
	Fld(s) Name:	NA
	Fld Descr:	An object that uniquely identifies each Increment of 
			data.
	"
    ::= { avCmListIpInterfaceMedproEntry 1 }

avCmListIpInterfaceMedproIdx   OBJECT-TYPE
    SYNTAX	Integer32 (0..9999)
    MAX-ACCESS  not-accessible
    STATUS      current
    DESCRIPTION
        "
        Fld OID Name:   avCmListIpInterfaceMedproIdx
        Fld OID:        enterprises.6889.2.73.8.1.91.1.1.2
        Fld Format:     NA
        Fld(s) Name:    NA
        Fld Descr:      An object that uniquely identifies each Increment of
                        data.
        "
    ::= { avCmListIpInterfaceMedproEntry 2 }


avCmListIpInterfaceMedproOn	OBJECT-TYPE
    SYNTAX	SnmpAdminString (SIZE (0..2))
    MAX-ACCESS	read-only
    STATUS	current
    DESCRIPTION
	"
	Fld OID Name:	avCmListIpInterfaceMedproOn
	Fld OID:	enterprises.6889.2.73.8.1.91.1.1.3
	Fld Form/Rpt:	IP INTERFACES
	Fld Format:	Single Field
	Fld(s) Name:	ON
	Fld Descr:	An object containing whether the ip-interface is 
			enabled.
	"
    ::= { avCmListIpInterfaceMedproEntry 3 }

avCmListIpInterfaceMedproType	OBJECT-TYPE
    SYNTAX	SnmpAdminString (SIZE (0..7))
    MAX-ACCESS	read-only
    STATUS	current
    DESCRIPTION
	"
	Fld OID Name:	avCmListIpInterfaceMedproType
	Fld OID:	enterprises.6889.2.73.8.1.91.1.1.4
	Fld Form/Rpt:	IP INTERFACES
	Fld Format:	Single Field
	Fld(s) Name:	Type
	Fld Descr:	An object containing the type of ip-interface.
	"
    ::= { avCmListIpInterfaceMedproEntry 4 }

avCmListIpInterfaceMedproSlot   OBJECT-TYPE
    SYNTAX	SnmpAdminString (SIZE (0..6))
    MAX-ACCESS  read-only
    STATUS      current
    DESCRIPTION
        "
        Fld OID Name:   avCmListIpInterfaceMedproSlot
        Fld OID:        enterprises.6889.2.73.8.1.91.1.1.5
        Fld Form/Rpt:   IP INTERFACES
        Fld Format:     Single Field
        Fld(s) Name:    Slot
        Fld Descr:      An object containing the slot where the ip-interface 
			resides.
        "
    ::= { avCmListIpInterfaceMedproEntry 5 }


avCmListIpInterfaceMedproCode	OBJECT-TYPE
    SYNTAX	SnmpAdminString (SIZE (0..7))
    MAX-ACCESS	read-only
    STATUS	current
    DESCRIPTION
	"
	Fld OID Name:	avCmListIpInterfaceMedproCode
	Fld OID:	enterprises.6889.2.73.8.1.91.1.1.6
	Fld Form/Rpt:	IP INTERFACES
	Fld Format:	Single Field
	Fld(s) Name:	Code/
	Fld Descr:	An object containing the TN code of the board.
	"
    ::= { avCmListIpInterfaceMedproEntry 6 }

avCmListIpInterfaceMedproSfx	OBJECT-TYPE
    SYNTAX	SnmpAdminString (SIZE (0..2))
    MAX-ACCESS	read-only
    STATUS	current
    DESCRIPTION
	"
	Fld OID Name:	avCmListIpInterfaceMedproSfx
	Fld OID:	enterprises.6889.2.73.8.1.91.1.1.7
	Fld Form/Rpt:	IP INTERFACES
	Fld Format:	Single Field
	Fld(s) Name:	Sfx
	Fld Descr:	An object containing the suffix of the board.
	"
    ::= { avCmListIpInterfaceMedproEntry 7 }

avCmListIpInterfaceMedproNodeName	OBJECT-TYPE
    SYNTAX	SnmpAdminString (SIZE (0..16))
    MAX-ACCESS	read-only
    STATUS	current
    DESCRIPTION
	"
	Fld OID Name:	avCmListIpInterfaceMedproNodeName
	Fld OID:	enterprises.6889.2.73.8.1.91.1.1.8
	Fld Form/Rpt:	IP INTERFACES
	Fld Format:	Single Field
	Fld(s) Name:	Node Name
	Fld Descr:	An object containing the Node Name used by the 
			ip-intereface.
	"
    ::= { avCmListIpInterfaceMedproEntry 8 }

avCmListIpInterfaceMedproMask	OBJECT-TYPE
    SYNTAX	SnmpAdminString (SIZE (0..4))
    MAX-ACCESS	read-only
    STATUS	current
    DESCRIPTION
	"
	Fld OID Name:	avCmListIpInterfaceMedproMask
	Fld OID:	enterprises.6889.2.73.8.1.91.1.1.9
	Fld Form/Rpt:	IP INTERFACES
	Fld Format:	Single Field
	Fld(s) Name:	Mask
	Fld Descr:	An object containing the mask of the ip-interface.
	"
    ::= { avCmListIpInterfaceMedproEntry 9 }

avCmListIpInterfaceMedproNetRgn	OBJECT-TYPE
    SYNTAX	Integer32 (0..9999)
    MAX-ACCESS	read-only
    STATUS	current
    DESCRIPTION
	"
	Fld OID Name:	avCmListIpInterfaceMedproNetRgn
	Fld OID:	enterprises.6889.2.73.8.1.91.1.1.10
	Fld Form/Rpt:	IP INTERFACES
	Fld Format:	Single Field
	Fld(s) Name:	Net Rgn
	Fld Descr:	Field that displays network region used by the 
			ip-interface.
	"
    ::= { avCmListIpInterfaceMedproEntry 10 }

avCmListIpInterfaceMedproVlan      OBJECT-TYPE
    SYNTAX      SnmpAdminString (SIZE (0..5))
    MAX-ACCESS  read-only
    STATUS      current
    DESCRIPTION
        "
        Fld OID Name:   avCmListIpInterfaceMedproVlan
        Fld OID:        enterprises.6889.2.73.8.1.91.1.1.11
        Fld Form/Rpt:   IP INTERFACES
        Fld Format:     Single Field
        Fld(s) Name:    VLAN
        Fld Descr:      Field that displays the virtual lan used by the
                        ip-interface.
        "
    ::= { avCmListIpInterfaceMedproEntry 11 }

avCmListIpInterfaceMedproVirtualNode       OBJECT-TYPE
    SYNTAX      SnmpAdminString (SIZE (0..41))
    MAX-ACCESS  read-only
    STATUS      current
    DESCRIPTION
        "
        Fld OID Name:   avCmListIpInterfaceMedproVirtualNode
        Fld OID:        enterprises.6889.2.73.8.1.91.1.1.12

        Fld Form/Rpt:   IP INTERFACES
        Fld Format:     Single Field
        Fld(s) Name:    Virtual Node
        Fld Descr:      The virtual node associated with the ip-interface.
        "
    ::= { avCmListIpInterfaceMedproEntry 12 }

avCmListIpInterfaceMedproIpAddress OBJECT-TYPE
    SYNTAX      SnmpAdminString (SIZE (0..41))
    MAX-ACCESS  read-only
    STATUS      current
    DESCRIPTION
        "
        Fld OID Name:   avCmListIpInterfaceMedproIpAddress
        Fld OID:        enterprises.6889.2.73.8.1.91.1.1.13
        Fld Form/Rpt:   IP INTERFACES
        Fld Format:     Single Field
        Fld(s) Name:    IP Address
        Fld Descr:      The IP Address associated with the ip-interface.
        "
    ::= { avCmListIpInterfaceMedproEntry 13 }

avCmListIpInterfaceMedproGatewayNode OBJECT-TYPE
    SYNTAX      SnmpAdminString (SIZE (0..41))
    MAX-ACCESS  read-only
    STATUS      current
    DESCRIPTION
        "
        Fld OID Name:   avCmListIpInterfaceMedproGatewayNode
        Fld OID:        enterprises.6889.2.73.8.1.91.1.1.14
        Fld Form/Rpt:   IP INTERFACES
        Fld Format:     Single Field
        Fld(s) Name:    IP Address
        Fld Descr:      The IP Address associated with the ip-interface.
        "
    ::= { avCmListIpInterfaceMedproEntry 14 }


avCmListIpInterfaceMedproOn2	OBJECT-TYPE
    SYNTAX	SnmpAdminString (SIZE (0..2))
    MAX-ACCESS	read-only
    STATUS	current
    DESCRIPTION
	"
	Fld OID Name:	avCmListIpInterfaceMedproOn2
	Fld OID:	enterprises.6889.2.73.8.1.91.1.1.15
	Fld Form/Rpt:	IP INTERFACES
	Fld Format:	Single Field
	Fld(s) Name:	ON
	Fld Descr:	An object containing whether the duplicate
			ip-interface is enabled.
	"
    ::= { avCmListIpInterfaceMedproEntry 15 }

avCmListIpInterfaceMedproType2	OBJECT-TYPE
    SYNTAX	SnmpAdminString (SIZE (0..7))
    MAX-ACCESS	read-only
    STATUS	current
    DESCRIPTION
	"
	Fld OID Name:	avCmListIpInterfaceMedproType2
	Fld OID:	enterprises.6889.2.73.8.1.91.1.1.16
	Fld Form/Rpt:	IP INTERFACES
	Fld Format:	Single Field
	Fld(s) Name:	Type
	Fld Descr:	An object containing the type of the duplicate 
			ip-interface.
	"
    ::= { avCmListIpInterfaceMedproEntry 16 }

avCmListIpInterfaceMedproSlot2   OBJECT-TYPE
    SYNTAX	SnmpAdminString (SIZE (0..6))
    MAX-ACCESS  read-only
    STATUS      current
    DESCRIPTION
        "
        Fld OID Name:   avCmListIpInterfaceMedproSlot2
        Fld OID:        enterprises.6889.2.73.8.1.91.1.1.17
        Fld Form/Rpt:   IP INTERFACES
        Fld Format:     Single Field
        Fld(s) Name:    Slot
        Fld Descr:      An object containing the slot where the duplicate 
		        ip-interface resides.
        "
    ::= { avCmListIpInterfaceMedproEntry 17 }


avCmListIpInterfaceMedproCode2	OBJECT-TYPE
    SYNTAX	SnmpAdminString (SIZE (0..7))
    MAX-ACCESS	read-only
    STATUS	current
    DESCRIPTION
	"
	Fld OID Name:	avCmListIpInterfaceMedproCode2
	Fld OID:	enterprises.6889.2.73.8.1.91.1.1.18
	Fld Form/Rpt:	IP INTERFACES
	Fld Format:	Single Field
	Fld(s) Name:	Code/
	Fld Descr:	An object containing the TN code of the duplicate board.
	"
    ::= { avCmListIpInterfaceMedproEntry 18 }

avCmListIpInterfaceMedproSfx2	OBJECT-TYPE
    SYNTAX	SnmpAdminString (SIZE (0..2))
    MAX-ACCESS	read-only
    STATUS	current
    DESCRIPTION
	"
	Fld OID Name:	avCmListIpInterfaceMedproSfx2
	Fld OID:	enterprises.6889.2.73.8.1.91.1.1.19
	Fld Form/Rpt:	IP INTERFACES
	Fld Format:	Single Field
	Fld(s) Name:	Sfx
	Fld Descr:	An object containing the suffix of the duplicate board.
	"
    ::= { avCmListIpInterfaceMedproEntry 19 }

avCmListIpInterfaceMedproNodeName2	OBJECT-TYPE
    SYNTAX	SnmpAdminString (SIZE (0..16))
    MAX-ACCESS	read-only
    STATUS	current
    DESCRIPTION
	"
	Fld OID Name:	avCmListIpInterfaceMedproNodeName2
	Fld OID:	enterprises.6889.2.73.8.1.91.1.1.20
	Fld Form/Rpt:	IP INTERFACES
	Fld Format:	Single Field
	Fld(s) Name:	Node Name
	Fld Descr:	An object containing the Node Name used by the 
			duplicate ip-intereface.
	"
    ::= { avCmListIpInterfaceMedproEntry 20 }

avCmListIpInterfaceMedproMask2	OBJECT-TYPE
    SYNTAX	SnmpAdminString (SIZE (0..4))
    MAX-ACCESS	read-only
    STATUS	current
    DESCRIPTION
	"
	Fld OID Name:	avCmListIpInterfaceMedproMask
	Fld OID:	enterprises.6889.2.73.8.1.91.1.1.21
	Fld Form/Rpt:	IP INTERFACES
	Fld Format:	Single Field
	Fld(s) Name:	Mask
	Fld Descr:	An object containing the mask of the ip-interface.
	"
    ::= { avCmListIpInterfaceMedproEntry 21 }

avCmListIpInterfaceMedproNetRgn2	OBJECT-TYPE
    SYNTAX	Integer32 (0..9999)
    MAX-ACCESS	read-only
    STATUS	current
    DESCRIPTION
	"
	Fld OID Name:	avCmListIpInterfaceMedproNetRgn2
	Fld OID:	enterprises.6889.2.73.8.1.91.1.1.22
	Fld Form/Rpt:	IP INTERFACES
	Fld Format:	Single Field
	Fld(s) Name:	Net Rgn
	Fld Descr:	Field that displays network region used by the 
			ip-interface.
	"
    ::= { avCmListIpInterfaceMedproEntry 22 }

avCmListIpInterfaceMedproVlan2      OBJECT-TYPE
    SYNTAX      SnmpAdminString (SIZE (0..5))
    MAX-ACCESS  read-only
    STATUS      current
    DESCRIPTION
        "
        Fld OID Name:   avCmListIpInterfaceMedproVlan2
        Fld OID:        enterprises.6889.2.73.8.1.91.1.1.23
        Fld Form/Rpt:   IP INTERFACES
        Fld Format:     Single Field
        Fld(s) Name:    VLAN
        Fld Descr:      Field that displays the virtual lan used by the
                        ip-interface.
        "
    ::= { avCmListIpInterfaceMedproEntry 23 }

avCmListIpInterfaceMedproVirtualNode2       OBJECT-TYPE
    SYNTAX      SnmpAdminString (SIZE (0..41))
    MAX-ACCESS  read-only
    STATUS      current
    DESCRIPTION
        "
        Fld OID Name:   avCmListIpInterfaceMedproVirtualNode2
        Fld OID:        enterprises.6889.2.73.8.1.91.1.1.24

        Fld Form/Rpt:   IP INTERFACES
        Fld Format:     Single Field
        Fld(s) Name:    Virtual Node
        Fld Descr:      The virtual node associated with the ip-interface.
        "
    ::= { avCmListIpInterfaceMedproEntry 24 }

avCmListIpInterfaceMedproIpAddress2 OBJECT-TYPE
    SYNTAX      SnmpAdminString (SIZE (0..41))
    MAX-ACCESS  read-only
    STATUS      current
    DESCRIPTION
        "
        Fld OID Name:   avCmListIpInterfaceMedproIpAddress2
        Fld OID:        enterprises.6889.2.73.8.1.91.1.1.25
        Fld Form/Rpt:   IP INTERFACES
        Fld Format:     Single Field
        Fld(s) Name:    IP Address
        Fld Descr:      The IP Address associated with the ip-interface.
        "
    ::= { avCmListIpInterfaceMedproEntry 25 }

avCmListIpInterfaceMedproGatewayNode2 OBJECT-TYPE
    SYNTAX      SnmpAdminString (SIZE (0..41))
    MAX-ACCESS  read-only
    STATUS      current
    DESCRIPTION
        "
        Fld OID Name:   avCmListIpInterfaceMedproGatewayNode2
        Fld OID:        enterprises.6889.2.73.8.1.91.1.1.26
        Fld Form/Rpt:   IP INTERFACES
        Fld Format:     Single Field
        Fld(s) Name:    IP Address
        Fld Descr:      The IP Address associated with the ip-interface.
        "
    ::= { avCmListIpInterfaceMedproEntry 26 }

-- ****************** avCmStatusMedproBrd Group *************************

-- MIB GROUP DESCRIPTION

-- MIB Group Name:
--		avCmStatusMedproBrd Group
-- OID:
--		enterprises.6889.2.73.8.1.92
-- Description:
--		The avCmStatusMedproBrd MIB Group uses the 
--		"list ip-interface medpro" command to retrieve media-processor
--		 ip-interface status data. 
--		
-- Releases Supported:
--		CM6.3.100 and greater
-- Polling Type:
--		Performance/Utilization
-- Polling Interval:
--		No more than once daily.
-- Default Caching Interval
-- 		300 seconds
-- Timeout Interval:
--		Initial Timeout should be set to 20 seconds.
-- Retry Interval:
--		Initial Retry should be set to 3.
-- Limitations:
--		Red/High - The data collected by this MIB Group will
--		increase as the number of administered ip-interface 
--		media-processors  increase.
--		Consequently the data collected by this MIB Group could be
--		very large and therefore may take a very long time to collect
--		and could impact system performance.
-- Command Type:
--		1. SAT
-- Command:
--		1. status media-processor board
-- Form/Report Name:
--		1. MEDIA-PROCESSOR STATUS 
-- Reference Document:
--		1. A detailed description of the command and form can be
--		   found in document referenced by REF_DOC_1 in the
--		   DOCUMENT REFERENCE SECTION.
-- Command Permission/User-profile:
--		1. No special permissions needed.

avCmStatusMedproBrd	OBJECT IDENTIFIER ::= { avCmObjects 92 }

avCmStatusMedproBrdTable	OBJECT-TYPE
    SYNTAX	SEQUENCE OF AvCmStatusMedproBrdEntry
    MAX-ACCESS	not-accessible
    STATUS	current
    DESCRIPTION
	"
	Fld OID Name:	avCmStatusMedproBrdEntry
	Fld OID:	enterprises.6889.2.73.8.1.92.1
	Fld Form/Rpt:	NA
	Fld Format:	NA
	Fld(s) Name:	NA
	Fld Descr:	A list of the avCmStatusMedproBrd entries
	"
    ::= { avCmStatusMedproBrd 1 }

avCmStatusMedproBrdEntry	OBJECT-TYPE
    SYNTAX	AvCmStatusMedproBrdEntry
    MAX-ACCESS	not-accessible
    STATUS	current
    DESCRIPTION
	"
	Fld OID Name:	avCmStatusMedproBrdEntry
	Fld OID:	enterprises.6889.2.73.8.1.92.1.1
	Fld Form/Rpt:	NA
	Fld Format:	NA
	Fld(s) Name:	NA
	Fld Descr:	A avCmStatusMedproBrd entry containing objects of the
			avCmStatusMedproBrd information sent by the switch.
	"
    INDEX    { avCmStatusMedproBrdBoardLocIdx }
    ::= { avCmStatusMedproBrdTable 1 }

AvCmStatusMedproBrdEntry ::= SEQUENCE {
		avCmStatusMedproBrdBoardLocIdx
		    SnmpAdminString,
		avCmStatusMedproBrdBoardLoc
		    SnmpAdminString,
		avCmStatusMedproBrdState
		    SnmpAdminString,
		avCmStatusMedproBrdNodeName
		    SnmpAdminString,
		avCmStatusMedproBrdIpAddess
		    SnmpAdminString,
		avCmStatusMedproBrdSubnetMask
		    SnmpAdminString,
		avCmStatusMedproBrdGatewayAddr
		    SnmpAdminString,
		avCmStatusMedproBrdMACAddress
		    SnmpAdminString,
		avCmStatusMedproBrdEtherEnabled 
		    SnmpAdminString,
		avCmStatusMedproBrdDSPChanStatus1
		    SnmpAdminString,
		avCmStatusMedproBrdDSPChanStatus2
		    SnmpAdminString,
		avCmStatusMedproBrdDSPChanStatus3
		    SnmpAdminString,
		avCmStatusMedproBrdDSPChanStatus4
		    SnmpAdminString,
		avCmStatusMedproBrdDupDSPChanStatus5
		    SnmpAdminString,
		avCmStatusMedproBrdDupDSPChanStatus6
		    SnmpAdminString,
		avCmStatusMedproBrdDupDSPChanStatus7
		    SnmpAdminString,
		avCmStatusMedproBrdDupDSPChanStatus8
		    SnmpAdminString,
		avCmStatusMedproBrdNetworkRegion
		    SnmpAdminString,
		avCmStatusMedproBrdDupNetworkRegion
		    SnmpAdminString,
		avCmStatusMedproBrdStandbyRefreshed
		    SnmpAdminString,
		avCmStatusMedproBrdSharedIP 
		    SnmpAdminString,
		avCmStatusMedproBrdSharedVirtMAC
		    SnmpAdminString,
		avCmStatusMedproBrdDupBoardLoc
		    SnmpAdminString,
		avCmStatusMedproBrdDupState
		    SnmpAdminString,
		avCmStatusMedproBrdDupNodeName
		    SnmpAdminString,
		avCmStatusMedproBrdDupIpAddess
		    SnmpAdminString,
		avCmStatusMedproBrdDupSubnetMask
		    SnmpAdminString,
		avCmStatusMedproBrdDupGatewayAddr
		    SnmpAdminString,
		avCmStatusMedproBrdDupMACAddress
		    SnmpAdminString,
		avCmStatusMedproBrdDupEtherEnabled
		    SnmpAdminString,
		avCmStatusMedproBrdLinkMPCL
		    SnmpAdminString,
		avCmStatusMedproBrdLinkEth
		    SnmpAdminString,
		avCmStatusMedproBrdLinkPeer
		    SnmpAdminString,
		avCmStatusMedproBrdAlarmMaj
		    SnmpAdminString,
		avCmStatusMedproBrdAlarmMin
		    SnmpAdminString,
		avCmStatusMedproBrdAlarmWrn
		    SnmpAdminString,
		avCmStatusMedproBrdDupLinkMPCL
		    SnmpAdminString,
		avCmStatusMedproBrdDupLinkEth
		    SnmpAdminString,
		avCmStatusMedproBrdDupLinkPeer
		    SnmpAdminString,
		avCmStatusMedproBrdDupAlarmMaj
		    SnmpAdminString,
		avCmStatusMedproBrdDupAlarmMin
		    SnmpAdminString,
		avCmStatusMedproBrdDupAlarmWrn
		    SnmpAdminString,
		avCmStatusMedproBrdLocked
		    SnmpAdminString,
		avCmStatusMedproBrdIPV6Address
		    SnmpAdminString,
		avCmStatusMedproBrdIPV6SubnetMask
		    SnmpAdminString,
		avCmStatusMedproBrdIPV6GatewayAddr
		    SnmpAdminString,
		avCmStatusMedproBrdIPV6NodeName
		    SnmpAdminString,
		avCmStatusMedproBrdIPV6EtherEnable
		    SnmpAdminString
		}

avCmStatusMedproBrdBoardLocIdx	OBJECT-TYPE
    SYNTAX	SnmpAdminString (SIZE (0..6))
    MAX-ACCESS	not-accessible
    STATUS	current
    DESCRIPTION
	"
	Fld OID Name:	avCmStatusMedproBrdBoardLocIdx
	Fld OID:	enterprises.6889.2.73.8.1.92.1.1.1
	Fld Format:	NA
	Fld(s) Name:	NA
	Fld Descr:	An object that uniquely identifies each Increment of 
			data.
	"
    ::= { avCmStatusMedproBrdEntry 1 }

avCmStatusMedproBrdBoardLoc   OBJECT-TYPE
    SYNTAX	SnmpAdminString (SIZE (0..6))
    MAX-ACCESS	read-only
    STATUS	current
    DESCRIPTION
	"
	Fld OID Name:	avCmStatusMedproBrdBoardLoc
	Fld OID:	enterprises.6889.2.73.8.1.92.1.1.2
	Fld Form/Rpt:	MEDIA-PROCESSOR STATUS
	Fld Format:	Single Field
	Fld(s) Name:	Board Loc
	Fld Descr:	An object containing whether the ip-interface is 
			located.
	"
    ::= { avCmStatusMedproBrdEntry 2 }

avCmStatusMedproBrdState	OBJECT-TYPE
    SYNTAX	SnmpAdminString (SIZE (0..8))
    MAX-ACCESS	read-only
    STATUS	current
    DESCRIPTION
	"
	Fld OID Name:	avCmStatusMedproBrdState
	Fld OID:	enterprises.6889.2.73.8.1.92.1.1.3
	Fld Form/Rpt:	MEDIA-PROCESSOR STATUS
	Fld Format:	Single Field
	Fld(s) Name:	State
	Fld Descr:	A DisplayString Object that contains state of the media 
			processor board (values can be 'active', 
			'standby' or 'init').
	"
    ::= { avCmStatusMedproBrdEntry 3 }

avCmStatusMedproBrdNodeName	OBJECT-TYPE
    SYNTAX	SnmpAdminString (SIZE (0..16))
    MAX-ACCESS	read-only
    STATUS	current
    DESCRIPTION
	"
	Fld OID Name:	avCmStatusMedproBrdNodeName
	Fld OID:	enterprises.6889.2.73.8.1.92.1.1.4
	Fld Form/Rpt:	MEDIA-PROCESSOR STATUS
	Fld Format:	Single Field
	Fld(s) Name:	Node Name:
	Fld Descr:	A DisplayString Object that contains the node name for 
			the media processor board.
	"
    ::= { avCmStatusMedproBrdEntry 4 }

avCmStatusMedproBrdIpAddess	OBJECT-TYPE
    SYNTAX	SnmpAdminString (SIZE (0..20))
    MAX-ACCESS	read-only
    STATUS	current
    DESCRIPTION
	"
	Fld OID Name:	avCmStatusMedproBrdIpAddess
	Fld OID:	enterprises.6889.2.73.8.1.92.1.1.5
	Fld Form/Rpt:	MEDIA-PROCESSOR STATUS
	Fld Format:	Single Field
	Fld(s) Name:	IP Address
	Fld Descr:	A DisplayString Object that contains the IPV4 address 
			for the media processor board.
	"
    ::= { avCmStatusMedproBrdEntry 5 }

avCmStatusMedproBrdSubnetMask	OBJECT-TYPE
    SYNTAX	SnmpAdminString (SIZE (0..16))
    MAX-ACCESS	read-only
    STATUS	current
    DESCRIPTION
	"
	Fld OID Name:	avCmStatusMedproBrdSubnetMask
	Fld OID:	enterprises.6889.2.73.8.1.92.1.1.6
	Fld Form/Rpt:	MEDIA-PROCESSOR STATUS
	Fld Format:	Single Field
	Fld(s) Name:	Subnet Mask
	Fld Descr:	Object that contains the IPV4 subnet mask for the
			media processor board.
	"
    ::= { avCmStatusMedproBrdEntry 6 }

avCmStatusMedproBrdGatewayAddr	OBJECT-TYPE
    SYNTAX	SnmpAdminString (SIZE (0..17))
    MAX-ACCESS	read-only
    STATUS	current
    DESCRIPTION
	"
	Fld OID Name:	avCmStatusMedproBrdGatewayAddr
	Fld OID:	enterprises.6889.2.73.8.1.92.1.1.7
	Fld Form/Rpt:	MEDIA-PROCESSOR STATUS
	Fld Format:	Single Field
	Fld(s) Name:	Gateway Address
	Fld Descr:	An object containing the Gateway Address of the 
			media processor board.
	"
    ::= { avCmStatusMedproBrdEntry 7 }

avCmStatusMedproBrdMACAddress	OBJECT-TYPE
    SYNTAX	SnmpAdminString (SIZE (0..19))
    MAX-ACCESS	read-only
    STATUS	current
    DESCRIPTION
	"
	Fld OID Name:	avCmStatusMedproBrdMACAddress
	Fld OID:	enterprises.6889.2.73.8.1.92.1.1.8
	Fld Form/Rpt:	MEDIA-PROCESSOR STATUS
	Fld Format:	Single Field
	Fld(s) Name:	MAC Address
	Fld Descr:	Field that displays the MAC Address used by the 
			media processor board.
	"
    ::= { avCmStatusMedproBrdEntry 8 }

avCmStatusMedproBrdEtherEnabled      OBJECT-TYPE
    SYNTAX      SnmpAdminString (SIZE (0..4))
    MAX-ACCESS  read-only
    STATUS      current
    DESCRIPTION
        "
        Fld OID Name:   avCmStatusMedproBrdEtherEnabled
        Fld OID:        enterprises.6889.2.73.8.1.92.1.1.9
        Fld Form/Rpt:   MEDIA-PROCESSOR STATUS
        Fld Format:     Single Field
        Fld(s) Name:    Ethernet Enabled
        Fld Descr:      A DisplayString Object that designates whether or not 
			the IP interface is enabled (yes or no) for the 
			media processor board.
        "
    ::= { avCmStatusMedproBrdEntry 9 }

avCmStatusMedproBrdDSPChanStatus1       OBJECT-TYPE
    SYNTAX      SnmpAdminString (SIZE (0..36))
    MAX-ACCESS  read-only
    STATUS      current
    DESCRIPTION
        "
        Fld OID Name:   avCmStatusMedproBrdDSPChanStatus1
        Fld OID:        enterprises.6889.2.73.8.1.92.1.1.10

        Fld Form/Rpt:   MEDIA-PROCESSOR STATUS
        Fld Format:     Single Field
        Fld(s) Name:    DSP 1 Channel Status
        Fld Descr:      A DisplayString Object that contains the service state 
			of the respective DSP resource (for the media processor
			board).
        "
    ::= { avCmStatusMedproBrdEntry 10 }


avCmStatusMedproBrdDSPChanStatus2       OBJECT-TYPE
    SYNTAX      SnmpAdminString (SIZE (0..36))
    MAX-ACCESS  read-only
    STATUS      current
    DESCRIPTION
        "
        Fld OID Name:   avCmStatusMedproBrdDSPChanStatus2
        Fld OID:        enterprises.6889.2.73.8.1.92.1.1.11

        Fld Form/Rpt:   MEDIA-PROCESSOR STATUS
        Fld Format:     Single Field
        Fld(s) Name:    DSP 2 Channel Status
        Fld Descr:      A DisplayString Object that contains the service state 
			of the respective DSP resource (for the media processor
			board).
        "
    ::= { avCmStatusMedproBrdEntry 11 }

avCmStatusMedproBrdDSPChanStatus3       OBJECT-TYPE
    SYNTAX      SnmpAdminString (SIZE (0..36))
    MAX-ACCESS  read-only
    STATUS      current
    DESCRIPTION
        "
        Fld OID Name:   avCmStatusMedproBrdDSPChanStatus3
        Fld OID:        enterprises.6889.2.73.8.1.92.1.1.12

        Fld Form/Rpt:   MEDIA-PROCESSOR STATUS
        Fld Format:     Single Field
        Fld(s) Name:    DSP 3 Channel Status
        Fld Descr:      A DisplayString Object that contains the service state 
			of the respective DSP resource (for the media processor
			board).
        "
    ::= { avCmStatusMedproBrdEntry 12 }


avCmStatusMedproBrdDSPChanStatus4       OBJECT-TYPE
    SYNTAX      SnmpAdminString (SIZE (0..36))
    MAX-ACCESS  read-only
    STATUS      current
    DESCRIPTION
        "
        Fld OID Name:   avCmStatusMedproBrdDSPChanStatus4
        Fld OID:        enterprises.6889.2.73.8.1.92.1.1.13

        Fld Form/Rpt:   MEDIA-PROCESSOR STATUS
        Fld Format:     Single Field
        Fld(s) Name:    DSP 4 Channel Status
        Fld Descr:      A DisplayString Object that contains the service state
                        of the respective DSP resource (for the media processor
                        board).
        "
    ::= { avCmStatusMedproBrdEntry 13 }


avCmStatusMedproBrdDupDSPChanStatus5       OBJECT-TYPE
    SYNTAX      SnmpAdminString (SIZE (0..36))
    MAX-ACCESS  read-only
    STATUS      current
    DESCRIPTION
        "
        Fld OID Name:   avCmStatusMedproBrdDupDSPChanStatus5
        Fld OID:        enterprises.6889.2.73.8.1.92.1.1.14

        Fld Form/Rpt:   MEDIA-PROCESSOR STATUS
        Fld Format:     Single Field
        Fld(s) Name:    DSP 5 Channel Status
        Fld Descr:      A DisplayString Object that contains the service state
                        of the respective DSP resource (for the media processor
                        board).
        "
    ::= { avCmStatusMedproBrdEntry 14 }


avCmStatusMedproBrdDupDSPChanStatus6       OBJECT-TYPE
    SYNTAX      SnmpAdminString (SIZE (0..36))
    MAX-ACCESS  read-only
    STATUS      current
    DESCRIPTION
        "
        Fld OID Name:   avCmStatusMedproBrdDupDSPChanStatus6
        Fld OID:        enterprises.6889.2.73.8.1.92.1.1.15

        Fld Form/Rpt:   MEDIA-PROCESSOR STATUS
        Fld Format:     Single Field
        Fld(s) Name:    DSP 6 Channel Status
        Fld Descr:      A DisplayString Object that contains the service state
                        of the respective DSP resource (for the media processor
                        board).
        "
    ::= { avCmStatusMedproBrdEntry 15 }

avCmStatusMedproBrdDupDSPChanStatus7       OBJECT-TYPE
    SYNTAX      SnmpAdminString (SIZE (0..36))
    MAX-ACCESS  read-only
    STATUS      current
    DESCRIPTION
        "
        Fld OID Name:   avCmStatusMedproBrdDupDSPChanStatus7
        Fld OID:        enterprises.6889.2.73.8.1.92.1.1.16

        Fld Form/Rpt:   MEDIA-PROCESSOR STATUS
        Fld Format:     Single Field
        Fld(s) Name:    DSP 7 Channel Status
        Fld Descr:      A DisplayString Object that contains the service state
                        of the respective DSP resource (for the media processor
                        board).
        "
    ::= { avCmStatusMedproBrdEntry 16 }


avCmStatusMedproBrdDupDSPChanStatus8       OBJECT-TYPE
    SYNTAX      SnmpAdminString (SIZE (0..36))
    MAX-ACCESS  read-only
    STATUS      current
    DESCRIPTION
        "
        Fld OID Name:   avCmStatusMedproBrdDupDSPChanStatus8
        Fld OID:        enterprises.6889.2.73.8.1.92.1.1.17

        Fld Form/Rpt:   MEDIA-PROCESSOR STATUS
        Fld Format:     Single Field
        Fld(s) Name:    DSP 8 Channel Status
        Fld Descr:      A DisplayString Object that contains the service state
                        of the respective DSP resource (for the media processor
                        board).
        "
    ::= { avCmStatusMedproBrdEntry 17 }


avCmStatusMedproBrdNetworkRegion       OBJECT-TYPE
    SYNTAX      SnmpAdminString (SIZE (0..5))
    MAX-ACCESS  read-only
    STATUS      current
    DESCRIPTION
        "
        Fld OID Name:   avCmStatusMedproBrdNetworkRegion
        Fld OID:        enterprises.6889.2.73.8.1.92.1.1.18

        Fld Form/Rpt:   MEDIA-PROCESSOR STATUS
        Fld Format:     Single Field
        Fld(s) Name:    Network Region
        Fld Descr:      A DisplayString Object that contains the network region
                        for the media processor board.
        "
    ::= { avCmStatusMedproBrdEntry 18 }

avCmStatusMedproBrdDupNetworkRegion OBJECT-TYPE
    SYNTAX      SnmpAdminString (SIZE (0..5))
    MAX-ACCESS  read-only
    STATUS      current
    DESCRIPTION
        "
        Fld OID Name:   avCmStatusMedproBrdDupNetworkRegion
        Fld OID:        enterprises.6889.2.73.8.1.92.1.1.19
        Fld Form/Rpt:   MEDIA-PROCESSOR STATUS
        Fld Format:     Single Field
        Fld(s) Name:    Duplicate Network Region
        Fld Descr:      A DisplayString Object that contains the alternate 
			network region number for the media processor board.
        "
    ::= { avCmStatusMedproBrdEntry 19 }

avCmStatusMedproBrdStandbyRefreshed OBJECT-TYPE
    SYNTAX      SnmpAdminString (SIZE (0..4))
    MAX-ACCESS  read-only
    STATUS      current
    DESCRIPTION
        "
        Fld OID Name:   avCmStatusMedproBrdStandbyRefreshed
        Fld OID:        enterprises.6889.2.73.8.1.92.1.1.20
        Fld Form/Rpt:   MEDIA-PROCESSOR STATUS
        Fld Format:     Single Field
        Fld(s) Name:    Standby Refreshed
        Fld Descr:      Object that indicates whether the standby board
            		in a duplicated pair of media processor boards is in 
			sync with the active board (yes or no).
        "
    ::= { avCmStatusMedproBrdEntry 20 }


avCmStatusMedproBrdSharedIP	OBJECT-TYPE
    SYNTAX	SnmpAdminString (SIZE (0..17))
    MAX-ACCESS	read-only
    STATUS	current
    DESCRIPTION
	"
	Fld OID Name:	avCmStatusMedproBrdSharedIP
	Fld OID:	enterprises.6889.2.73.8.1.92.1.1.21
	Fld Form/Rpt:	MEDIA-PROCESSOR STATUS
	Fld Format:	Single Field
	Fld(s) Name:	Shared IP Address
	Fld Descr:	Object that contains the shared virtual IP address
            		between two duplicated media processor boards.
	"
    ::= { avCmStatusMedproBrdEntry 21 }

avCmStatusMedproBrdSharedVirtMAC	OBJECT-TYPE
    SYNTAX	SnmpAdminString (SIZE (0..19))
    MAX-ACCESS	read-only
    STATUS	current
    DESCRIPTION
	"
	Fld OID Name:	avCmStatusMedproBrdSharedVirtMAC
	Fld OID:	enterprises.6889.2.73.8.1.92.1.1.22
	Fld Form/Rpt:	MEDIA-PROCESSOR STATUS
	Fld Format:	Single Field
	Fld(s) Name:	Shared Virtual MAC Address
	Fld Descr:	Object that contains the shared virtual MAC address 
            		between two duplicated media processor boards.
	"
    ::= { avCmStatusMedproBrdEntry 22 }

avCmStatusMedproBrdDupBoardLoc   OBJECT-TYPE
    SYNTAX	SnmpAdminString (SIZE (0..6))
    MAX-ACCESS  read-only
    STATUS      current
    DESCRIPTION
        "
        Fld OID Name:   avCmStatusMedproBrdDupBoardLoc
        Fld OID:        enterprises.6889.2.73.8.1.92.1.1.23
        Fld Form/Rpt:   MEDIA-PROCESSOR STATUS
        Fld Format:     Single Field
        Fld(s) Name:    Board Loc
        Fld Descr:      An object containing the location where the duplicate 
		        media processor resides.
        "
    ::= { avCmStatusMedproBrdEntry 23 }


avCmStatusMedproBrdDupState	OBJECT-TYPE
    SYNTAX	SnmpAdminString (SIZE (0..8))
    MAX-ACCESS	read-only
    STATUS	current
    DESCRIPTION
	"
	Fld OID Name:	avCmStatusMedproBrdDupState
	Fld OID:	enterprises.6889.2.73.8.1.92.1.1.24
	Fld Form/Rpt:	MEDIA-PROCESSOR STATUS
	Fld Format:	Single Field
	Fld(s) Name:	State
	Fld Descr:	DisplayString Object that contains state of the 
			duplicate media processor board (values can be 
			'active', 'standby' or 'init').
	"
    ::= { avCmStatusMedproBrdEntry 24 }

avCmStatusMedproBrdDupNodeName	OBJECT-TYPE
    SYNTAX	SnmpAdminString (SIZE (0..16))
    MAX-ACCESS	read-only
    STATUS	current
    DESCRIPTION
	"
	Fld OID Name:	avCmStatusMedproBrdDupNodeName
	Fld OID:	enterprises.6889.2.73.8.1.92.1.1.25
	Fld Form/Rpt:	MEDIA-PROCESSOR STATUS
	Fld Format:	Single Field
	Fld(s) Name:	Node Name
	Fld Descr:	Object that contains the node name for the
            		duplicate media processor board.
	"
    ::= { avCmStatusMedproBrdEntry 25 }


avCmStatusMedproBrdDupIpAddess	OBJECT-TYPE
    SYNTAX	SnmpAdminString (SIZE (0..20))
    MAX-ACCESS	read-only
    STATUS	current
    DESCRIPTION
	"
	Fld OID Name:	avCmStatusMedproBrdDupIpAddess
	Fld OID:	enterprises.6889.2.73.8.1.92.1.1.26
	Fld Form/Rpt:	MEDIA-PROCESSOR STATUS
	Fld Format:	Single Field
	Fld(s) Name:	IP Address
	Fld Descr:	A DisplayString Object that contains the IPV4 address 
			for the duplicated media processor board.
	"
    ::= { avCmStatusMedproBrdEntry 26 }

avCmStatusMedproBrdDupSubnetMask	OBJECT-TYPE
    SYNTAX	SnmpAdminString (SIZE (0..16))
    MAX-ACCESS	read-only
    STATUS	current
    DESCRIPTION
	"
	Fld OID Name:	avCmStatusMedproBrdDupSubnetMask
	Fld OID:	enterprises.6889.2.73.8.1.92.1.1.27
	Fld Form/Rpt:	MEDIA-PROCESSOR STATUS
	Fld Format:	Single Field
	Fld(s) Name:	Subnet Mask
	Fld Descr:	Object that contains the IPV4 subnet mask for the
			duplicated media processor board.
	"
    ::= { avCmStatusMedproBrdEntry 27 }

avCmStatusMedproBrdDupGatewayAddr	OBJECT-TYPE
    SYNTAX	SnmpAdminString (SIZE (0..17))
    MAX-ACCESS	read-only
    STATUS	current
    DESCRIPTION
	"
	Fld OID Name:	avCmStatusMedproBrdDupGatewayAddr
	Fld OID:	enterprises.6889.2.73.8.1.92.1.1.28
	Fld Form/Rpt:	MEDIA-PROCESSOR STATUS
	Fld Format:	Single Field
	Fld(s) Name:	Gateway Address
	Fld Descr:	An object containing the Gateway Address of the 
			duplicated media processor board.
	"
    ::= { avCmStatusMedproBrdEntry 28 }

avCmStatusMedproBrdDupMACAddress	OBJECT-TYPE
    SYNTAX	SnmpAdminString (SIZE (0..19))
    MAX-ACCESS	read-only
    STATUS	current
    DESCRIPTION
	"
	Fld OID Name:	avCmStatusMedproBrdDupMACAddress
	Fld OID:	enterprises.6889.2.73.8.1.92.1.1.29
	Fld Form/Rpt:	MEDIA-PROCESSOR STATUS
	Fld Format:	Single Field
	Fld(s) Name:	MAC Address
	Fld Descr:	Field that displays the MAC Address used by the 
			duplicated media processor board.
	"
    ::= { avCmStatusMedproBrdEntry 29 }

avCmStatusMedproBrdDupEtherEnabled      OBJECT-TYPE
    SYNTAX      SnmpAdminString (SIZE (0..4))
    MAX-ACCESS  read-only
    STATUS      current
    DESCRIPTION
        "
        Fld OID Name:   avCmStatusMedproBrdDupEtherEnabled
        Fld OID:        enterprises.6889.2.73.8.1.92.1.1.30
        Fld Form/Rpt:   MEDIA-PROCESSOR STATUS
        Fld Format:     Single Field
        Fld(s) Name:    Ethernet Enabled
        Fld Descr:      A DisplayString Object that designates whether or not 
			the IP interface is enabled (yes or no) for the 
			duplicated media processor board.
        "
    ::= { avCmStatusMedproBrdEntry 30 }

avCmStatusMedproBrdLinkMPCL       OBJECT-TYPE
    SYNTAX      SnmpAdminString (SIZE (0..3))
    MAX-ACCESS  read-only
    STATUS      current
    DESCRIPTION
        "
        Fld OID Name:   avCmStatusMedproBrdLinkMPCL
        Fld OID:        enterprises.6889.2.73.8.1.92.1.1.31

        Fld Form/Rpt:   MEDIA-PROCESSOR STATUS
        Fld Format:     Single Field
        Fld(s) Name:    Link  MPCL
        Fld Descr:      Object that indicates the status of the Media
            		Processor Control Link ('up' or 'dn') for the media 
			processor board.
        "
    ::= { avCmStatusMedproBrdEntry 31 }


avCmStatusMedproBrdLinkEth       OBJECT-TYPE
    SYNTAX      SnmpAdminString (SIZE (0..3))
    MAX-ACCESS  read-only
    STATUS      current
    DESCRIPTION
        "
        Fld OID Name:   avCmStatusMedproBrdLinkEth
        Fld OID:        enterprises.6889.2.73.8.1.92.1.1.32

        Fld Form/Rpt:   MEDIA-PROCESSOR STATUS
        Fld Format:     Single Field
        Fld(s) Name:    Link ETH
        Fld Descr:      Object that indicates the status of the Ethernet
            		Link ('up' or 'dn') for the media processor board.
        "
    ::= { avCmStatusMedproBrdEntry 32 }

avCmStatusMedproBrdLinkPeer       OBJECT-TYPE
    SYNTAX      SnmpAdminString (SIZE (0..3))
    MAX-ACCESS  read-only
    STATUS      current
    DESCRIPTION
        "
        Fld OID Name:   avCmStatusMedproBrdLinkPeer
        Fld OID:        enterprises.6889.2.73.8.1.92.1.1.33

        Fld Form/Rpt:   MEDIA-PROCESSOR STATUS
        Fld Format:     Single Field
        Fld(s) Name:    Link Peer
        Fld Descr:      A DisplayString Object that indicates the status of 
			the Peer Link ('up' or 'dn') for the media processor 
			board.
        "
    ::= { avCmStatusMedproBrdEntry 33 }


avCmStatusMedproBrdAlarmMaj       OBJECT-TYPE
    SYNTAX      SnmpAdminString (SIZE (0..3))
    MAX-ACCESS  read-only
    STATUS      current
    DESCRIPTION
        "
        Fld OID Name:   avCmStatusMedproBrdAlarmMaj
        Fld OID:        enterprises.6889.2.73.8.1.92.1.1.34

        Fld Form/Rpt:   MEDIA-PROCESSOR STATUS
        Fld Format:     Single Field
        Fld(s) Name:    Alarms MAJ
        Fld Descr:      Object that indicates the number of major alarms
            		active on the media processor board.
        "
    ::= { avCmStatusMedproBrdEntry 34 }


avCmStatusMedproBrdAlarmMin       OBJECT-TYPE
    SYNTAX      SnmpAdminString (SIZE (0..3))
    MAX-ACCESS  read-only
    STATUS      current
    DESCRIPTION
        "
        Fld OID Name:   avCmStatusMedproBrdAlarmMin
        Fld OID:        enterprises.6889.2.73.8.1.92.1.1.35

        Fld Form/Rpt:   MEDIA-PROCESSOR STATUS
        Fld Format:     Single Field
        Fld(s) Name:    Alarms MIN
        Fld Descr:      Object that indicates the number of minor alarms
            		active on the media processor board.
        "
    ::= { avCmStatusMedproBrdEntry 35 }


avCmStatusMedproBrdAlarmWrn       OBJECT-TYPE
    SYNTAX      SnmpAdminString (SIZE (0..3))
    MAX-ACCESS  read-only
    STATUS      current
    DESCRIPTION
        "
        Fld OID Name:   avCmStatusMedproBrdAlarmWrn
        Fld OID:        enterprises.6889.2.73.8.1.92.1.1.36

        Fld Form/Rpt:   MEDIA-PROCESSOR STATUS
        Fld Format:     Single Field
        Fld(s) Name:    Alarms WRN
        Fld Descr:      Object that indicates the number of warning
                        active on the media processor board.
        "
    ::= { avCmStatusMedproBrdEntry 36 }

avCmStatusMedproBrdDupLinkMPCL       OBJECT-TYPE
    SYNTAX      SnmpAdminString (SIZE (0..3))
    MAX-ACCESS  read-only
    STATUS      current
    DESCRIPTION
        "
        Fld OID Name:   avCmStatusMedproBrdDupLinkMPCL
        Fld OID:        enterprises.6889.2.73.8.1.92.1.1.37

        Fld Form/Rpt:   MEDIA-PROCESSOR STATUS
        Fld Format:     Single Field
        Fld(s) Name:    Dup Link MPCL
        Fld Descr:      Object that indicates the status of the Media
                        Processor Control Link ('up' or 'dn') for the duplicate 
                        media processor board.
        "
    ::= { avCmStatusMedproBrdEntry 37 }


avCmStatusMedproBrdDupLinkEth       OBJECT-TYPE
    SYNTAX      SnmpAdminString (SIZE (0..3))
    MAX-ACCESS  read-only
    STATUS      current
    DESCRIPTION
        "
        Fld OID Name:   avCmStatusMedproBrdDupLinkEth
        Fld OID:        enterprises.6889.2.73.8.1.92.1.1.38

        Fld Form/Rpt:   MEDIA-PROCESSOR STATUS
        Fld Format:     Single Field
        Fld(s) Name:    Dup Link ETH
        Fld Descr:      Object that indicates the status of the Ethernet
            		Link ('up' or 'dn') for the duplicate media processor 
			board.
        "
    ::= { avCmStatusMedproBrdEntry 38 }

avCmStatusMedproBrdDupLinkPeer	OBJECT-TYPE
    SYNTAX	SnmpAdminString (SIZE (0..3))
    MAX-ACCESS	read-only
    STATUS	current
    DESCRIPTION
	"
	Fld OID Name:	avCmStatusMedproBrdDupLinkPeer
	Fld OID:	enterprises.6889.2.73.8.1.92.1.1.39
	Fld Form/Rpt:	MEDIA-PROCESSOR STATUS
	Fld Format:	Single Field
	Fld(s) Name:	Dup Link Peer
	Fld Descr:	Object that indicates the status of the Peer
            		Link ('up' or 'dn') for the duplicate media processor 
			board.
	"
    ::= { avCmStatusMedproBrdEntry 39 }

avCmStatusMedproBrdDupAlarmMaj	OBJECT-TYPE
    SYNTAX	SnmpAdminString (SIZE (0..3))
    MAX-ACCESS	read-only
    STATUS	current
    DESCRIPTION
	"
	Fld OID Name:	avCmStatusMedproBrdDupAlarmMaj
	Fld OID:	enterprises.6889.2.73.8.1.92.1.1.40
	Fld Form/Rpt:	MEDIA-PROCESSOR STATUS
	Fld Format:	Single Field
	Fld(s) Name:	Dup Alarm MAJ
	Fld Descr:	Object that indicates the number of major alarms
            		active on the duplicate media processor board.
	"
    ::= { avCmStatusMedproBrdEntry 40 }

avCmStatusMedproBrdDupAlarmMin	OBJECT-TYPE
    SYNTAX	SnmpAdminString (SIZE (0..3))
    MAX-ACCESS	read-only
    STATUS	current
    DESCRIPTION
	"
	Fld OID Name:	avCmStatusMedproBrdDupAlarmMin
	Fld OID:	enterprises.6889.2.73.8.1.92.1.1.41
	Fld Form/Rpt:	MEDIA-PROCESSOR STATUS
	Fld Format:	Single Field
	Fld(s) Name:	Dup Alarm MIN
	Fld Descr:	Object that indicates the number of minor alarms
			active on the duplicate media processor board.
	"
    ::= { avCmStatusMedproBrdEntry 41 }

avCmStatusMedproBrdDupAlarmWrn	OBJECT-TYPE
    SYNTAX	SnmpAdminString (SIZE (0..3))
    MAX-ACCESS	read-only
    STATUS	current
    DESCRIPTION
	"
	Fld OID Name:	avCmStatusMedproBrdDupAlarmWrn
	Fld OID:	enterprises.6889.2.73.8.1.92.1.1.42
	Fld Form/Rpt:	MEDIA-PROCESSOR STATUS
	Fld Format:	Single Field
	Fld(s) Name:	Alarm WRN
	Fld Descr:	Object that indicates the number of warning alarms
			active on the duplicate media processor board.
	"
    ::= { avCmStatusMedproBrdEntry 42 }

avCmStatusMedproBrdLocked      OBJECT-TYPE
    SYNTAX      SnmpAdminString (SIZE (0..4))
    MAX-ACCESS  read-only
    STATUS      current
    DESCRIPTION
        "
        Fld OID Name:   avCmStatusMedproBrdLocked
        Fld OID:        enterprises.6889.2.73.8.1.92.1.1.43
        Fld Form/Rpt:   MEDIA-PROCESSOR STATUS
        Fld Format:     Single Field
        Fld(s) Name:    Locked
        Fld Descr:      Object that indicates whether the set medpro
            		override and lock command argument is in use 
			(yes or no).
        "
    ::= { avCmStatusMedproBrdEntry 43 }

avCmStatusMedproBrdIPV6Address       OBJECT-TYPE
    SYNTAX      SnmpAdminString (SIZE (0..45))
    MAX-ACCESS  read-only
    STATUS      current
    DESCRIPTION
        "
        Fld OID Name:   avCmStatusMedproBrdIPV6Address
        Fld OID:        enterprises.6889.2.73.8.1.92.1.1.44

        Fld Form/Rpt:   MEDIA-PROCESSOR STATUS
        Fld Format:     Single Field
        Fld(s) Name:    IPV6 Address
        Fld Descr:      Object that contains the source IPV6 address for
            		the media processor board.
        "
    ::= { avCmStatusMedproBrdEntry 44 }

avCmStatusMedproBrdIPV6SubnetMask OBJECT-TYPE
    SYNTAX      SnmpAdminString (SIZE (0..4))
    MAX-ACCESS  read-only
    STATUS      current
    DESCRIPTION
        "
        Fld OID Name:   avCmStatusMedproBrdIPV6SubnetMask
        Fld OID:        enterprises.6889.2.73.8.1.92.1.1.45
        Fld Form/Rpt:   MEDIA-PROCESSOR STATUS
        Fld Format:     Single Field
        Fld(s) Name:    IPV6 Subnet Mask
        Fld Descr:      Object that contains the IPV6 subnet mask for the
            		media processor board.
        "
    ::= { avCmStatusMedproBrdEntry 45 }

avCmStatusMedproBrdIPV6GatewayAddr OBJECT-TYPE
    SYNTAX      SnmpAdminString (SIZE (0..41))
    MAX-ACCESS  read-only
    STATUS      current
    DESCRIPTION
        "
        Fld OID Name:   avCmStatusMedproBrdIPV6GatewayAddr
        Fld OID:        enterprises.6889.2.73.8.1.92.1.1.46
        Fld Form/Rpt:   MEDIA-PROCESSOR STATUS
        Fld Format:     Single Field
        Fld(s) Name:    IPV6 Gateway Address
        Fld Descr:      Object that contains the IPV6 gateway address for the
            		media processor board.
        "
    ::= { avCmStatusMedproBrdEntry 46 }

avCmStatusMedproBrdIPV6NodeName OBJECT-TYPE
    SYNTAX      SnmpAdminString (SIZE (0..16))
    MAX-ACCESS  read-only
    STATUS      current
    DESCRIPTION
        "
        Fld OID Name:   avCmStatusMedproBrdIPV6NodeName
        Fld OID:        enterprises.6889.2.73.8.1.92.1.1.47
        Fld Form/Rpt:   MEDIA-PROCESSOR STATUS
        Fld Format:     Single Field
        Fld(s) Name:    IPV6 Node Name
        Fld Descr:      The IPV6 Node Name associated with the ip-interface.
        "
    ::= { avCmStatusMedproBrdEntry 47 }

avCmStatusMedproBrdIPV6EtherEnable OBJECT-TYPE
    SYNTAX      SnmpAdminString (SIZE (0..4))
    MAX-ACCESS  read-only
    STATUS      current
    DESCRIPTION
        "
        Fld OID Name:   avCmStatusMedproBrdIPV6EtherEnable
        Fld OID:        enterprises.6889.2.73.8.1.92.1.1.48
        Fld Form/Rpt:   MEDIA-PROCESSOR STATUS
        Fld Format:     Single Field
        Fld(s) Name:    IPV6 Ethernet Enabled
        Fld Descr:      The IPV6 Ethernet Enabled associated with the media 
			processor.
        "
    ::= { avCmStatusMedproBrdEntry 48 }

-- ******************** avCmListIpServerIntf Group *************************

-- MIB GROUP DESCRIPTION

-- MIB Group Name:
--		avCmListIpServerIntf Group
-- OID:
--		enterprises.6889.2.73.8.1.93
-- Description:
--		The avCmListIpServerIntf MIB Group uses the "list 
--		ipserver-interface" command to retrieve all ip-interface data. 
--		
-- Releases Supported:
--		CM6.3.100 and greater
-- Polling Type:
--		Inventory and Configuration.
-- Polling Interval:
--		No more than once daily.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list  ipserver-interface
-- Form/Report Name:
--		1. IP SERVER INTERFACE INFORMATION
-- Reference Document:
--		1. A detailed description of the command and form can be
--		   found in document referenced by REF_DOC_3 in the
--		   DOCUMENT REFERENCE SECTION.
-- Command Permission/User-profile:
--		1. No special permissions needed.

avCmListIpServerIntf	OBJECT IDENTIFIER ::= { avCmObjects 93 }

avCmListIpServerIntfTable	OBJECT-TYPE
    SYNTAX	SEQUENCE OF AvCmListIpServerIntfEntry
    MAX-ACCESS	not-accessible
    STATUS	current
    DESCRIPTION
	"
	Fld OID Name:	avCmListIpServerIntfEntry
	Fld OID:	enterprises.6889.2.73.8.1.93.1
	Fld Form/Rpt:	NA
	Fld Format:	NA
	Fld(s) Name:	NA
	Fld Descr:	A list of the avCmListIpServerIntf entries
	"
    ::= { avCmListIpServerIntf 1 }

avCmListIpServerIntfEntry	OBJECT-TYPE
    SYNTAX	AvCmListIpServerIntfEntry
    MAX-ACCESS	not-accessible
    STATUS	current
    DESCRIPTION
	"
	Fld OID Name:	avCmListIpServerIntfEntry
	Fld OID:	enterprises.6889.2.73.8.1.93.1.1
	Fld Form/Rpt:	NA
	Fld Format:	NA
	Fld(s) Name:	NA
	Fld Descr:	A avCmListIpServerIntf entry containing objects of the
			avCmListIpServerIntf information sent by the switch.
	"
    INDEX    { avCmListIpServerIntfIdx }
    ::= { avCmListIpServerIntfTable 1 }

AvCmListIpServerIntfEntry ::= SEQUENCE {
		avCmListIpServerIntfIdx
		    Integer32,
		avCmListIpServerIntfPortNtwkNum
		    Integer32,
		avCmListIpServerIntfPriBdLoc
		    SnmpAdminString,
		avCmListIpServerIntfPrimaryIPAddress
		    SnmpAdminString,
		avCmListIpServerIntfPrimaryHostName
		    SnmpAdminString,
		avCmListIpServerIntfPrimaryDHCPID
		    SnmpAdminString,
		avCmListIpServerIntfServState
		    SnmpAdminString,
		avCmListIpServerIntfControlState 
		    SnmpAdminString,
		avCmListIpServerIntfStateOfHealthCPEG
		    SnmpAdminString,
		avCmListIpServerIntfSecondaryBdLoc
		    SnmpAdminString,
		avCmListIpServerIntfSecondaryIPAddress
		    SnmpAdminString,
		avCmListIpServerIntfSecondaryHostName
		    SnmpAdminString,
		avCmListIpServerIntfSecondaryDHCPID
		    SnmpAdminString,
		avCmListIpServerIntfSecondaryServState
		    SnmpAdminString,
		avCmListIpServerIntfSecondaryControlState
		    SnmpAdminString,
		avCmListIpServerIntfSecondaryStateOfHealth
		    SnmpAdminString
		}

avCmListIpServerIntfIdx	OBJECT-TYPE
    SYNTAX      Integer32 (0..999)
    MAX-ACCESS	not-accessible
    STATUS	current
    DESCRIPTION
	"
	Fld OID Name:	avCmListIpServerIntfIdx
	Fld OID:	enterprises.6889.2.73.8.1.93.1.1.1
	Fld Format:	NA
	Fld(s) Name:	NA
	Fld Descr:	An object that uniquely identifies each Increment of 
			data.
	"
    ::= { avCmListIpServerIntfEntry 1 }

avCmListIpServerIntfPortNtwkNum   OBJECT-TYPE
    SYNTAX	Integer32 (0..999)
    MAX-ACCESS	read-only
    STATUS      current
    DESCRIPTION
        "
        Fld OID Name:   avCmListIpServerIntfPortNtwkNum
        Fld OID:        enterprises.6889.2.73.8.1.93.1.1.2
	Fld Form/Rpt:	IP SERVER INTERFACE INFORMATION
	Fld Format:	Single Field
	Fld(s) Name:	PortNtwkNum
	Fld Descr:	An object containing the port network associated
			with the ipserver-interface.
        "
    ::= { avCmListIpServerIntfEntry 2 }


avCmListIpServerIntfPriBdLoc	OBJECT-TYPE
    SYNTAX	SnmpAdminString (SIZE (0..6))
    MAX-ACCESS	read-only
    STATUS	current
    DESCRIPTION
	"
	Fld OID Name:	avCmListIpServerIntfPriBdLoc
	Fld OID:	enterprises.6889.2.73.8.1.93.1.1.3
	Fld Form/Rpt:	IP SERVER INTERFACE INFORMATION
	Fld Format:	Single Field
	Fld(s) Name:	Pri Bd Loc
	Fld Descr:	An object containing the location of the primary
			IP SERVER INTFC board.
	"
    ::= { avCmListIpServerIntfEntry 3 }

avCmListIpServerIntfPrimaryIPAddress	OBJECT-TYPE
    SYNTAX	SnmpAdminString (SIZE (0..16))
    MAX-ACCESS	read-only
    STATUS	current
    DESCRIPTION
	"
	Fld OID Name:	avCmListIpServerIntfPrimaryIPAddress
	Fld OID:	enterprises.6889.2.73.8.1.93.1.1.4
	Fld Form/Rpt:	IP SERVER INTERFACE INFORMATION
	Fld Format:	Single Field
	Fld(s) Name:	Primary IP Address
	Fld Descr:	An object containing the Primary
			IP Address.
	"
    ::= { avCmListIpServerIntfEntry 4 }

avCmListIpServerIntfPrimaryHostName   OBJECT-TYPE
    SYNTAX	SnmpAdminString (SIZE (0..17))
    MAX-ACCESS  read-only
    STATUS      current
    DESCRIPTION
        "
        Fld OID Name:   avCmListIpServerIntfPrimaryHostName
        Fld OID:        enterprises.6889.2.73.8.1.93.1.1.5
        Fld Form/Rpt:   IP SERVER INTERFACE INFORMATION
        Fld Format:     Single Field
        Fld(s) Name:    Primary Host Name
        Fld Descr:      An object containing the primary host name.
        "
    ::= { avCmListIpServerIntfEntry 5 }


avCmListIpServerIntfPrimaryDHCPID	OBJECT-TYPE
    SYNTAX	SnmpAdminString (SIZE (0..10))
    MAX-ACCESS	read-only
    STATUS	current
    DESCRIPTION
	"
	Fld OID Name:	avCmListIpServerIntfPrimaryDHCPID
	Fld OID:	enterprises.6889.2.73.8.1.93.1.1.6
	Fld Form/Rpt:	IP SERVER INTERFACE INFORMATION
	Fld Format:	Single Field
	Fld(s) Name:	Primary DHCP ID
	Fld Descr:	An object containing the DHCP ID.
	"
    ::= { avCmListIpServerIntfEntry 6 }

avCmListIpServerIntfServState	OBJECT-TYPE
    SYNTAX	SnmpAdminString (SIZE (0..4))
    MAX-ACCESS	read-only
    STATUS	current
    DESCRIPTION
	"
	Fld OID Name:	avCmListIpServerIntfServState
	Fld OID:	enterprises.6889.2.73.8.1.93.1.1.7
	Fld Form/Rpt:	IP SERVER INTERFACE INFORMATION
	Fld Format:	Single Field
	Fld(s) Name:	Serv State
	Fld Descr:	An object containing the Service State of the IP SERVER
			INTERFACE
	"
    ::= { avCmListIpServerIntfEntry 7 }

avCmListIpServerIntfControlState	OBJECT-TYPE
    SYNTAX	SnmpAdminString (SIZE (0..8))
    MAX-ACCESS	read-only
    STATUS	current
    DESCRIPTION
	"
	Fld OID Name:	avCmListIpServerIntfControlState
	Fld OID:	enterprises.6889.2.73.8.1.93.1.1.8
	Fld Form/Rpt:	IP SERVER INTERFACE INFORMATION
	Fld Format:	Single Field
	Fld(s) Name:	Control State
	Fld Descr:	An object containing the Control State of the IP SERVER 
                        INTERFACE.
	"
    ::= { avCmListIpServerIntfEntry 8 }

avCmListIpServerIntfStateOfHealthCPEG	OBJECT-TYPE
    SYNTAX	SnmpAdminString (SIZE (0..8))
    MAX-ACCESS	read-only
    STATUS	current
    DESCRIPTION
	"
	Fld OID Name:	avCmListIpServerIntfStateOfHealthCPEG
	Fld OID:	enterprises.6889.2.73.8.1.93.1.1.9
	Fld Form/Rpt:	IP SERVER INTERFACE INFORMATION
	Fld Format:	Single Field
	Fld(s) Name:	State Of Health C P E G
	Fld Descr:	An object containing the state of health of the IP 
			SERVER INTERFACE.
	"
    ::= { avCmListIpServerIntfEntry 9 }

avCmListIpServerIntfSecondaryBdLoc	OBJECT-TYPE
    SYNTAX	SnmpAdminString (SIZE (0..6))
    MAX-ACCESS	read-only
    STATUS	current
    DESCRIPTION
	"
	Fld OID Name:	avCmListIpServerIntfSecondaryBdLoc
	Fld OID:	enterprises.6889.2.73.8.1.93.1.1.10
	Fld Form/Rpt:	IP SERVER INTERFACE INFORMATION
	Fld Format:	Single Field
	Fld(s) Name:	Sec Bd Loc
	Fld Descr:	Field that displays the secondary board location.
	"
    ::= { avCmListIpServerIntfEntry 10 }

avCmListIpServerIntfSecondaryIPAddress	OBJECT-TYPE
    SYNTAX	SnmpAdminString (SIZE (0..16))
    MAX-ACCESS	read-only
    STATUS	current
    DESCRIPTION
	"
	Fld OID Name:	avCmListIpServerIntfSecondaryIPAddress
	Fld OID:	enterprises.6889.2.73.8.1.93.1.1.11
	Fld Form/Rpt:	IP SERVER INTERFACE INFORMATION
	Fld Format:	Single Field
	Fld(s) Name:	Secondary IP Address
	Fld Descr:	Field that contains the secondary IP Address.
	"
    ::= { avCmListIpServerIntfEntry 11 }

avCmListIpServerIntfSecondaryHostName	OBJECT-TYPE
    SYNTAX	SnmpAdminString (SIZE (0..17))
    MAX-ACCESS	read-only
    STATUS	current
    DESCRIPTION
	"
	Fld OID Name:	avCmListIpServerIntfSecondaryHostName
	Fld OID:	enterprises.6889.2.73.8.1.93.1.1.12
	Fld Form/Rpt:	IP SERVER INTERFACE INFORMATION
	Fld Format:	Single Field
	Fld(s) Name:	Secondary Host Name
	Fld Descr:	The Secondary Host Name of the IP SERVER INTERFACE.
	"
    ::= { avCmListIpServerIntfEntry 12 }

avCmListIpServerIntfSecondaryDHCPID	OBJECT-TYPE
    SYNTAX	SnmpAdminString (SIZE (0..10))
    MAX-ACCESS	read-only
    STATUS	current
    DESCRIPTION
	"
	Fld OID Name:	avCmListIpServerIntfSecondaryDHCPID
	Fld OID:	enterprises.6889.2.73.8.1.93.1.1.13
	Fld Form/Rpt:	IP SERVER INTERFACE INFORMATION
	Fld Format:	Single Field
	Fld(s) Name:	Secondary DHCP ID
	Fld Descr:	The Secondary DHCP ID of the IP server interface.
	"
    ::= { avCmListIpServerIntfEntry 13 }


avCmListIpServerIntfSecondaryServState	OBJECT-TYPE
    SYNTAX	SnmpAdminString (SIZE (0..4))
    MAX-ACCESS	read-only
    STATUS	current
    DESCRIPTION
	"
	Fld OID Name:	avCmListIpServerIntfSecondaryServState
	Fld OID:	enterprises.6889.2.73.8.1.93.1.1.14
	Fld Form/Rpt:	IP SERVER INTERFACE INFORMATION
	Fld Format:	Single Field
	Fld(s) Name:	Secondary Serv State
	Fld Descr:	An object containing the service state of the secondary
			ipserver interface. 
	"
    ::= { avCmListIpServerIntfEntry 14 }

avCmListIpServerIntfSecondaryControlState	OBJECT-TYPE
    SYNTAX	SnmpAdminString (SIZE (0..8))
    MAX-ACCESS	read-only
    STATUS	current
    DESCRIPTION
	"
	Fld OID Name:	avCmListIpServerIntfSecondaryControlState
	Fld OID:	enterprises.6889.2.73.8.1.93.1.1.15
	Fld Form/Rpt:	IP SERVER INTERFACE INFORMATION
	Fld Format:	Single Field
	Fld(s) Name:	Secondary Control State
	Fld Descr:	An object containing the  control state of
			the secondary ipserver interface.
	"
    ::= { avCmListIpServerIntfEntry 15 }

avCmListIpServerIntfSecondaryStateOfHealth   OBJECT-TYPE
    SYNTAX	SnmpAdminString (SIZE (0..8))
    MAX-ACCESS  read-only
    STATUS      current
    DESCRIPTION
        "
        Fld OID Name:   avCmListIpServerIntfSecondaryStateOfHealth
        Fld OID:        enterprises.6889.2.73.8.1.93.1.1.16
        Fld Form/Rpt:   IP SERVER INTERFACE INFORMATION
        Fld Format:     Single Field
        Fld(s) Name:    Secondary State Of Health C P E G
        Fld Descr:      An object containing the Secondary State of health.
        "
    ::= { avCmListIpServerIntfEntry 16 }

-- ******************** avCmStatusLink Group *************************

-- MIB GROUP DESCRIPTION

-- MIB Group Name:
--		avCmStatusLink Group
-- OID:
--		enterprises.6889.2.73.8.1.94
-- Description:
--		The avCmStatusLink MIB Group uses the "status 
--		link" command to retrieve link status data
--		
-- Releases Supported:
--		CM6.3.100 and greater
-- Polling Type:
--		Inventory and Performance/Utilization
-- Polling Interval:
--		No more than once  an hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. status link 1-254 or 'procr'
-- Form/Report Name:
--		1.  LINK/PORT STATUS
-- Reference Document:
--		1. A detailed description of the command and form can be
--		   found in document referenced by REF_DOC_1 in the
--		   DOCUMENT REFERENCE SECTION.
-- Command Permission/User-profile:
--		1. No special permissions needed.

avCmStatusLink	OBJECT IDENTIFIER ::= { avCmObjects 94 }

avCmStatusLinkTable	OBJECT-TYPE
    SYNTAX	SEQUENCE OF AvCmStatusLinkEntry
    MAX-ACCESS	not-accessible
    STATUS	current
    DESCRIPTION
	"
	Fld OID Name:	avCmStatusLinkEntry
	Fld OID:	enterprises.6889.2.73.8.1.94.1
	Fld Form/Rpt:	NA
	Fld Format:	NA
	Fld(s) Name:	NA
	Fld Descr:	A list of the avCmStatusLink entries
	"
    ::= { avCmStatusLink 1 }

avCmStatusLinkEntry	OBJECT-TYPE
    SYNTAX	AvCmStatusLinkEntry
    MAX-ACCESS	not-accessible
    STATUS	current
    DESCRIPTION
	"
	Fld OID Name:	avCmStatusLinkEntry
	Fld OID:	enterprises.6889.2.73.8.1.94.1.1
	Fld Form/Rpt:	NA
	Fld Format:	NA
	Fld(s) Name:	NA
	Fld Descr:	A avCmStatusLink entry containing objects of the
			avCmStatusLink information sent by the switch.
	"
    INDEX    { avCmStatusLinkIdx }
    ::= { avCmStatusLinkTable 1 }

AvCmStatusLinkEntry ::= SEQUENCE {
		avCmStatusLinkIdx
		    SnmpAdminString,
		avCmStatusLinkNum
		    SnmpAdminString,
		avCmStatusLinkStatus
		    SnmpAdminString,
		avCmStatusLinkType
		    SnmpAdminString,
		avCmStatusLinkName
		    SnmpAdminString,
		avCmStatusLinkServicePortLoc
		    SnmpAdminString,
		avCmStatusLinkDataExt
		    SnmpAdminString,
		avCmStatusLinkServiceState
		    SnmpAdminString,
		avCmStatusLinkNodeName 
		    SnmpAdminString,
		avCmStatusLinkSourceIpAddress
		    SnmpAdminString,
		avCmStatusLinkBroadcastAddress
		    SnmpAdminString,
		avCmStatusLinkPhysicalAddress
		    SnmpAdminString,
		avCmStatusLinkEthEnabled
		    SnmpAdminString,
		avCmStatusLinkEthMaintBusy
		    SnmpAdminString,
		avCmStatusLinkEthActiveChannels
		    SnmpAdminString,
		avCmStatusLinkPPPEnabled
		    SnmpAdminString,
		avCmStatusLinkPPPMaintBusy
		    SnmpAdminString,
		avCmStatusLinkPPPActiveChannels
		    SnmpAdminString,
		avCmStatusLinkAssocClanModem
		    SnmpAdminString,
		avCmStatusLinkConnSpeed
		    SnmpAdminString,
                avCmStatusLinkV6Status
                    SnmpAdminString,
                avCmStatusLinkV6Type
                    SnmpAdminString,
		avCmStatusLinkV6ServicePortLoc
		    SnmpAdminString,
		avCmStatusLinkV6NodeName 
		    SnmpAdminString,
		avCmStatusLinkV6SourceIpAddress
		    SnmpAdminString,
		avCmStatusLinkV6BroadcastAddress
		    SnmpAdminString,
		avCmStatusLinkV6EthEnabled
		    SnmpAdminString,
		avCmStatusLinkV6EthMaintBusy
		    SnmpAdminString,
		avCmStatusLinkV6EthActiveChannels
		    SnmpAdminString
		}

avCmStatusLinkIdx	OBJECT-TYPE
    SYNTAX	SnmpAdminString (SIZE (0..6))
    MAX-ACCESS	not-accessible
    STATUS	current
    DESCRIPTION
	"
	Fld OID Name:	avCmStatusLinkIdx
	Fld OID:	enterprises.6889.2.73.8.1.94.1.1.1
	Fld Format:	NA
	Fld(s) Name:	NA
	Fld Descr:	An object that uniquely identifies each Increment of 
			data.
	"
    ::= { avCmStatusLinkEntry 1 }

avCmStatusLinkNum   OBJECT-TYPE
    SYNTAX	SnmpAdminString (SIZE (0..6))
    MAX-ACCESS	read-only
    STATUS      current
    DESCRIPTION
        "
        Fld OID Name:   avCmStatusLinkNum
        Fld OID:        enterprises.6889.2.73.8.1.94.1.1.2
	Fld Form/Rpt:	LINK/PORT STATUS
	Fld Format:	Single Field
	Fld(s) Name:	Link Number
	Fld Descr:	An object containing the link number.
        "
    ::= { avCmStatusLinkEntry 2 }

avCmStatusLinkStatus   OBJECT-TYPE
    SYNTAX	SnmpAdminString (SIZE (0..26))
    MAX-ACCESS	read-only
    STATUS      current
    DESCRIPTION
        "
        Fld OID Name:   avCmStatusLinkStatus
        Fld OID:        enterprises.6889.2.73.8.1.94.1.1.3
	Fld Form/Rpt:	LINK/PORT STATUS
	Fld Format:	Single Field
	Fld(s) Name:	Link Status
	Fld Descr:	An object containing the link state.
        "
    ::= { avCmStatusLinkEntry 3 }



avCmStatusLinkType	OBJECT-TYPE
    SYNTAX	SnmpAdminString (SIZE (0..11))
    MAX-ACCESS	read-only
    STATUS	current
    DESCRIPTION
	"
	Fld OID Name:	avCmStatusLinkType
	Fld OID:	enterprises.6889.2.73.8.1.94.1.1.4
	Fld Form/Rpt:	LINK/PORT STATUS
	Fld Format:	Single Field
	Fld(s) Name:	Type
	Fld Descr:	An object containing the type of link.
	"
    ::= { avCmStatusLinkEntry 4 }

avCmStatusLinkName	OBJECT-TYPE
    SYNTAX	SnmpAdminString (SIZE (0..29))
    MAX-ACCESS	read-only
    STATUS	current
    DESCRIPTION
	"
	Fld OID Name:	avCmStatusLinkName
	Fld OID:	enterprises.6889.2.73.8.1.94.1.1.5
	Fld Form/Rpt:	LINK/PORT STATUS
	Fld Format:	Single Field
	Fld(s) Name:	Link Name
	Fld Descr:	An object containing the Link Name.
	"
    ::= { avCmStatusLinkEntry 5 }

avCmStatusLinkServicePortLoc   OBJECT-TYPE
    SYNTAX	SnmpAdminString (SIZE (0..17))
    MAX-ACCESS  read-only
    STATUS      current
    DESCRIPTION
        "
        Fld OID Name:   avCmStatusLinkServicePortLoc
        Fld OID:        enterprises.6889.2.73.8.1.94.1.1.6
        Fld Form/Rpt:   LINK/PORT STATUS
        Fld Format:     Single Field
        Fld(s) Name:    Service Port Location
        Fld Descr:      An object containing the Service Port Location.
        "
    ::= { avCmStatusLinkEntry 6 }


avCmStatusLinkDataExt	OBJECT-TYPE
    SYNTAX	SnmpAdminString (SIZE (0..17))
    MAX-ACCESS	read-only
    STATUS	current
    DESCRIPTION
	"
	Fld OID Name:	avCmStatusLinkDataExt
	Fld OID:	enterprises.6889.2.73.8.1.94.1.1.7
	Fld Form/Rpt:	LINK/PORT STATUS
	Fld Format:	Single Field
	Fld(s) Name:	Service Port Data Extension
	Fld Descr:	An object containing the Service Port Data Extension.
	"
    ::= { avCmStatusLinkEntry 7 }

avCmStatusLinkServiceState	OBJECT-TYPE
    SYNTAX	SnmpAdminString (SIZE (0..17))
    MAX-ACCESS	read-only
    STATUS	current
    DESCRIPTION
	"
	Fld OID Name:	avCmStatusLinkServiceState
	Fld OID:	enterprises.6889.2.73.8.1.94.1.1.8
	Fld Form/Rpt:	LINK/PORT STATUS
	Fld Format:	Single Field
	Fld(s) Name:	Service State
	Fld Descr:	An object containing the Service State of the link.
	"
    ::= { avCmStatusLinkEntry 8 }

avCmStatusLinkNodeName	OBJECT-TYPE
    SYNTAX	SnmpAdminString (SIZE (0..16))
    MAX-ACCESS	read-only
    STATUS	current
    DESCRIPTION
	"
	Fld OID Name:	avCmStatusLinkNodeName
	Fld OID:	enterprises.6889.2.73.8.1.94.1.1.9
	Fld Form/Rpt:	LINK/PORT STATUS
	Fld Format:	Single Field
	Fld(s) Name:	Node Name
	Fld Descr:	An object containing the Node Name associated with the
                        link.
	"
    ::= { avCmStatusLinkEntry 9 }

avCmStatusLinkSourceIpAddress	OBJECT-TYPE
    SYNTAX	SnmpAdminString (SIZE (0..45))
    MAX-ACCESS	read-only
    STATUS	current
    DESCRIPTION
	"
	Fld OID Name:	avCmStatusLinkSourceIpAddress
	Fld OID:	enterprises.6889.2.73.8.1.94.1.1.10
	Fld Form/Rpt:	LINK/PORT STATUS
	Fld Format:	Single Field
	Fld(s) Name:	Source IP Address
	Fld Descr:	An object containing the Source IP Address.
	"
    ::= { avCmStatusLinkEntry 10 }

avCmStatusLinkBroadcastAddress	OBJECT-TYPE
    SYNTAX	SnmpAdminString (SIZE (0..41))
    MAX-ACCESS	read-only
    STATUS	current
    DESCRIPTION
	"
	Fld OID Name:	avCmStatusLinkBroadcastAddress
	Fld OID:	enterprises.6889.2.73.8.1.94.1.1.11
	Fld Form/Rpt:	LINK/PORT STATUS
	Fld Format:	Single Field
	Fld(s) Name:	Broadcast Address
	Fld Descr:	Field that displays the Broadcast Address.
	"
    ::= { avCmStatusLinkEntry 11 }

avCmStatusLinkPhysicalAddress	OBJECT-TYPE
    SYNTAX	SnmpAdminString (SIZE (0..18))
    MAX-ACCESS	read-only
    STATUS	current
    DESCRIPTION
	"
	Fld OID Name:	avCmStatusLinkPhysicalAddress
	Fld OID:	enterprises.6889.2.73.8.1.94.1.1.12
	Fld Form/Rpt:	LINK/PORT STATUS
	Fld Format:	Single Field
	Fld(s) Name:	Physical Address
	Fld Descr:	Field that contains the Physical Address.
	"
    ::= { avCmStatusLinkEntry 12 }

avCmStatusLinkEthEnabled	OBJECT-TYPE
    SYNTAX	SnmpAdminString (SIZE (0..4))
    MAX-ACCESS	read-only
    STATUS	current
    DESCRIPTION
	"
	Fld OID Name:	avCmStatusLinkEthEnabled
	Fld OID:	enterprises.6889.2.73.8.1.94.1.1.13
	Fld Form/Rpt:	LINK/PORT STATUS
	Fld Format:	Single Field
	Fld(s) Name:	Enabled
	Fld Descr:	An object containing whether the link is ethernet enabled. 
	"
    ::= { avCmStatusLinkEntry 13 }

avCmStatusLinkEthMaintBusy	OBJECT-TYPE
    SYNTAX	SnmpAdminString (SIZE (0..4))
    MAX-ACCESS	read-only
    STATUS	current
    DESCRIPTION
	"
	Fld OID Name:	avCmStatusLinkEthMaintBusy
	Fld OID:	enterprises.6889.2.73.8.1.94.1.1.14
	Fld Form/Rpt:	LINK/PORT STATUS
	Fld Format:	Single Field
	Fld(s) Name:	Maintenance Busy
	Fld Descr:	An object containing whether the link is Maintenance 
			Busy.
	"
    ::= { avCmStatusLinkEntry 14 }


avCmStatusLinkEthActiveChannels	OBJECT-TYPE
    SYNTAX	SnmpAdminString (SIZE (0..5))
    MAX-ACCESS	read-only
    STATUS	current
    DESCRIPTION
	"
	Fld OID Name:	avCmStatusLinkEthActiveChannels
	Fld OID:	enterprises.6889.2.73.8.1.94.1.1.15
	Fld Form/Rpt:	LINK/PORT STATUS
	Fld Format:	Single Field
	Fld(s) Name:	Active Channels 
	Fld Descr:	An object containing the number of Active Channels
			associated with the link. 
	"
    ::= { avCmStatusLinkEntry 15 }

avCmStatusLinkPPPEnabled	OBJECT-TYPE
    SYNTAX	SnmpAdminString (SIZE (0..4))
    MAX-ACCESS	read-only
    STATUS	current
    DESCRIPTION
	"
	Fld OID Name:	avCmStatusLinkPPPEnabled
	Fld OID:	enterprises.6889.2.73.8.1.94.1.1.16
	Fld Form/Rpt:	LINK/PORT STATUS
	Fld Format:	Single Field
	Fld(s) Name:	PPP Enabled
	Fld Descr:	An object containing whether the link is PPP enabled.
	"
    ::= { avCmStatusLinkEntry 16 }

avCmStatusLinkPPPMaintBusy   OBJECT-TYPE
    SYNTAX	SnmpAdminString (SIZE (0..4))
    MAX-ACCESS  read-only
    STATUS      current
    DESCRIPTION
        "
        Fld OID Name:   avCmStatusLinkPPPMaintBusy
        Fld OID:        enterprises.6889.2.73.8.1.94.1.1.17
        Fld Form/Rpt:   LINK/PORT STATUS
        Fld Format:     Single Field
        Fld(s) Name:    PPP Maintenance Busy
        Fld Descr:      An object containing the link is PPP maintenance busy.
        "
    ::= { avCmStatusLinkEntry 17 }

avCmStatusLinkPPPActiveChannels   OBJECT-TYPE
    SYNTAX	SnmpAdminString (SIZE (0..5))
    MAX-ACCESS  read-only
    STATUS      current
    DESCRIPTION
        "
        Fld OID Name:   avCmStatusLinkPPPActiveChannels
        Fld OID:        enterprises.6889.2.73.8.1.94.1.1.18
        Fld Form/Rpt:   LINK/PORT STATUS
        Fld Format:     Single Field
        Fld(s) Name:    PPP Active Channels
        Fld Descr:      An object containing the number of active channels
			associated with a PPP link.
        "
    ::= { avCmStatusLinkEntry 18 }


avCmStatusLinkAssocClanModem   OBJECT-TYPE
    SYNTAX	SnmpAdminString (SIZE (0..3))
    MAX-ACCESS  read-only
    STATUS      current
    DESCRIPTION
        "
        Fld OID Name:   avCmStatusLinkAssocClanModem
        Fld OID:        enterprises.6889.2.73.8.1.94.1.1.19
        Fld Form/Rpt:   LINK/PORT STATUS
        Fld Format:     Single Field
        Fld(s) Name:    Associated C-LAN Modem
        Fld Descr:      An object containing the number of 
			Associated C-LAN Modems for the link.
        "
    ::= { avCmStatusLinkEntry 19 }


avCmStatusLinkConnSpeed   OBJECT-TYPE
    SYNTAX      SnmpAdminString (SIZE (0..8))
    MAX-ACCESS  read-only
    STATUS      current
    DESCRIPTION
        "
        Fld OID Name:   avCmStatusLinkConnSpeed
        Fld OID:        enterprises.6889.2.73.8.1.94.1.1.20
        Fld Form/Rpt:   LINK/PORT STATUS
        Fld Format:     Single Field
        Fld(s) Name:    Connect speed
        Fld Descr:      An object containing the Connect speed for the link.
        "
    ::= { avCmStatusLinkEntry 20 }

avCmStatusLinkV6Status   OBJECT-TYPE
    SYNTAX	SnmpAdminString (SIZE (0..26))
    MAX-ACCESS	read-only
    STATUS      current
    DESCRIPTION
        "
        Fld OID Name:   avCmStatusLinkV6Status
        Fld OID:        enterprises.6889.2.73.8.1.94.1.1.21
	Fld Form/Rpt:	LINK/PORT STATUS
	Fld Format:	Single Field
	Fld(s) Name:	Link Status
	Fld Descr:	An object containing the IPV6 link state.
        "
    ::= { avCmStatusLinkEntry 21 }


avCmStatusLinkV6Type   OBJECT-TYPE
    SYNTAX      SnmpAdminString (SIZE (0..16))
    MAX-ACCESS  read-only
    STATUS      current
    DESCRIPTION
        "
        Fld OID Name:   avCmStatusLinkV6NodeType
        Fld OID:        enterprises.6889.2.73.8.1.94.1.1.22
        Fld Form/Rpt:   LINK/PORT STATUS
        Fld Format:     Single Field
        Fld(s) Name:    IPV6 Link Type
        Fld Descr:      An object containing the IPV6 link type.
        "
    ::= { avCmStatusLinkEntry 22 }

avCmStatusLinkV6ServicePortLoc   OBJECT-TYPE
    SYNTAX      SnmpAdminString (SIZE (0..16))
    MAX-ACCESS  read-only
    STATUS      current
    DESCRIPTION
        "
        Fld OID Name:   avCmStatusLinkV6ServicePortLoc
        Fld OID:        enterprises.6889.2.73.8.1.94.1.1.23
        Fld Form/Rpt:   LINK/PORT STATUS
        Fld Format:     Single Field
        Fld(s) Name:    IPV6 Service Port Location
        Fld Descr:      An object containing the IPV6 Service Port Location.
        "
    ::= { avCmStatusLinkEntry 23 }

avCmStatusLinkV6NodeName   OBJECT-TYPE
    SYNTAX      SnmpAdminString (SIZE (0..16))
    MAX-ACCESS  read-only
    STATUS      current
    DESCRIPTION
        "
        Fld OID Name:   avCmStatusLinkV6NodeName
        Fld OID:        enterprises.6889.2.73.8.1.94.1.1.24
        Fld Form/Rpt:   LINK/PORT STATUS
        Fld Format:     Single Field
        Fld(s) Name:    IPV6 Node Name
        Fld Descr:      An object containing the IPV6 node name.
        "
    ::= { avCmStatusLinkEntry 24 }

avCmStatusLinkV6SourceIpAddress   OBJECT-TYPE
    SYNTAX      SnmpAdminString (SIZE (0..45))
    MAX-ACCESS  read-only
    STATUS      current
    DESCRIPTION
        "
        Fld OID Name:   avCmStatusLinkV6SourceIpAddress
        Fld OID:        enterprises.6889.2.73.8.1.94.1.1.25
        Fld Form/Rpt:   LINK/PORT STATUS
        Fld Format:     Single Field
        Fld(s) Name:    IPV6 Source IP Address
        Fld Descr:      An object containing the Connect speed for the link.
        "
    ::= { avCmStatusLinkEntry 25 }


avCmStatusLinkV6BroadcastAddress   OBJECT-TYPE
    SYNTAX      SnmpAdminString (SIZE (0..41))
    MAX-ACCESS  read-only
    STATUS      current
    DESCRIPTION
        "
        Fld OID Name:   avCmStatusLinkV6BroadcastAddress
        Fld OID:        enterprises.6889.2.73.8.1.94.1.1.26
        Fld Form/Rpt:   LINK/PORT STATUS
        Fld Format:     Single Field
        Fld(s) Name:    IPV6 Broadcast Address
        Fld Descr:      An object containing the second broadcast address.
        "
    ::= { avCmStatusLinkEntry 26 }

avCmStatusLinkV6EthEnabled   OBJECT-TYPE
    SYNTAX      SnmpAdminString (SIZE (0..4))
    MAX-ACCESS  read-only
    STATUS      current
    DESCRIPTION
        "
        Fld OID Name:   avCmStatusLinkV6EthEnabled
        Fld OID:        enterprises.6889.2.73.8.1.94.1.1.27
        Fld Form/Rpt:   LINK/PORT STATUS
        Fld Format:     Single Field
        Fld(s) Name:    IPV6 Enabled
        Fld Descr:      An object containing the link is enabled.
        "
    ::= { avCmStatusLinkEntry 27 }


avCmStatusLinkV6EthMaintBusy   OBJECT-TYPE
    SYNTAX      SnmpAdminString (SIZE (0..4))
    MAX-ACCESS  read-only
    STATUS      current
    DESCRIPTION
        "
        Fld OID Name:   avCmStatusLinkV6EthMaintBusy
        Fld OID:        enterprises.6889.2.73.8.1.94.1.1.28
        Fld Form/Rpt:   LINK/PORT STATUS
        Fld Format:     Single Field
        Fld(s) Name:    IPV6 Maintenance Busy
        Fld Descr:      An object containing whether the link is Maintenance 
			Busy.
        "
    ::= { avCmStatusLinkEntry 28 }


avCmStatusLinkV6EthActiveChannels   OBJECT-TYPE
    SYNTAX      SnmpAdminString (SIZE (0..5))
    MAX-ACCESS  read-only
    STATUS      current
    DESCRIPTION
        "
        Fld OID Name:   avCmStatusLinkV6EthActiveChannels
        Fld OID:        enterprises.6889.2.73.8.1.94.1.1.29
        Fld Form/Rpt:   LINK/PORT STATUS
        Fld Format:     Single Field
        Fld(s) Name:    IPV6 Active Channels
        Fld Descr:      An object containing the number of active ethernet
			channels.
        "
    ::= { avCmStatusLinkEntry 29 }

-- ******************** avCmListIPNetRegMonitor Group *************************

-- MIB GROUP DESCRIPTION

-- MIB Group Name:
--		avCmListIPNetRegMonitor Group
-- OID:
--		enterprises.6889.2.73.8.1.95
-- Description:
--		The avCmListIPNetRegMonitor MIB Group uses the "list 
--		ip-network-region monitor" command to retrieve all network-
--		region monitor related data. 
--		
-- Releases Supported:
--		CM6.3.100 and greater
-- Polling Type:
--		Inventory and Configuration.
-- Polling Interval:
--		No more than once daily or when administration is changed.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list ip-network-region monitor
-- Form/Report Name:
--		1.  IP NETWORK REGIONS MONITOR
-- Reference Document:
--		1. A detailed description of the command and form can be
--		   found in document referenced by REF_DOC_3 and REF_DOC_5
--		   in the DOCUMENT REFERENCE SECTION.
-- Command Permission/User-profile:
--		1. No special permissions needed.

avCmListIPNetRegMonitor	OBJECT IDENTIFIER ::= { avCmObjects 95 }

avCmListIPNetRegMonitorTable	OBJECT-TYPE
    SYNTAX	SEQUENCE OF AvCmListIPNetRegMonitorEntry
    MAX-ACCESS	not-accessible
    STATUS	current
    DESCRIPTION
	"
	Fld OID Name:	avCmListIPNetRegMonitorEntry
	Fld OID:	enterprises.6889.2.73.8.1.95.1
	Fld Form/Rpt:	NA
	Fld Format:	NA
	Fld(s) Name:	NA
	Fld Descr:	A list of the avCmListIPNetRegMonitor entries
	"
    ::= { avCmListIPNetRegMonitor 1 }

avCmListIPNetRegMonitorEntry	OBJECT-TYPE
    SYNTAX	AvCmListIPNetRegMonitorEntry
    MAX-ACCESS	not-accessible
    STATUS	current
    DESCRIPTION
	"
	Fld OID Name:	avCmListIPNetRegMonitorEntry
	Fld OID:	enterprises.6889.2.73.8.1.95.1.1
	Fld Form/Rpt:	NA
	Fld Format:	NA
	Fld(s) Name:	NA
	Fld Descr:	A avCmListIPNetRegMonitor entry containing objects of the
			avCmListIPNetRegMonitor information sent by the switch.
	"
    INDEX    { avCmListIPNetRegMonitorIdx }
    ::= { avCmListIPNetRegMonitorTable 1 }

AvCmListIPNetRegMonitorEntry ::= SEQUENCE {
		avCmListIPNetRegMonitorIdx
		    Integer32,
		avCmListIPNetRegMonitorRegion
		    Integer32,
		avCmListIPNetRegMonitorName
		    SnmpAdminString,
		avCmListIPNetRegMonitorPortNoIPv4
		    Integer32,
		avCmListIPNetRegMonitorRTCPMonIPv4Addr
		    SnmpAdminString,
		avCmListIPNetRegMonitorServiceReportPer
		    Integer32,
		avCmListIPNetRegMonitorCodecSet
		    SnmpAdminString,
		avCmListIPNetRegMonitorUDPPortRangeMin
		    Integer32,
		avCmListIPNetRegMonitorUDPPortRangeMax 
		    Integer32,
		avCmListIPNetRegMonitorPortNoIPv6
		    Integer32,
		avCmListIPNetRegMonitorRTCPMonIPv6Addr
		    SnmpAdminString
		}

avCmListIPNetRegMonitorIdx	OBJECT-TYPE
    SYNTAX      Integer32 (0..9999)
    MAX-ACCESS	not-accessible
    STATUS	current
    DESCRIPTION
	"
	Fld OID Name:	avCmListIPNetRegMonitorIdx
	Fld OID:	enterprises.6889.2.73.8.1.95.1.1.1
	Fld Format:	NA
	Fld(s) Name:	NA
	Fld Descr:	An object that uniquely identifies each Increment of 
			data.
	"
    ::= { avCmListIPNetRegMonitorEntry 1 }

avCmListIPNetRegMonitorRegion   OBJECT-TYPE
    SYNTAX      Integer32 (0..9999)
    MAX-ACCESS	read-only
    STATUS      current
    DESCRIPTION
        "
        Fld OID Name:   avCmListIPNetRegMonitorRegion
        Fld OID:        enterprises.6889.2.73.8.1.95.1.1.2
	Fld Form/Rpt:	IP NETWORK REGIONS MONITOR
	Fld Format:	Single Field
	Fld(s) Name:	Region
	Fld Descr:	An object containing the IP network region number.
        "
    ::= { avCmListIPNetRegMonitorEntry 2 }

avCmListIPNetRegMonitorName   OBJECT-TYPE
    SYNTAX	SnmpAdminString (SIZE (0..21))
    MAX-ACCESS	read-only
    STATUS      current
    DESCRIPTION
        "
        Fld OID Name:   avCmListIPNetRegMonitorName
        Fld OID:        enterprises.6889.2.73.8.1.95.1.1.3
	Fld Form/Rpt:	IP NETWORK REGIONS MONITOR
	Fld Format:	Single Field
	Fld(s) Name:	Name
	Fld Descr:	An object containing the region name.
        "
    ::= { avCmListIPNetRegMonitorEntry 3 }


avCmListIPNetRegMonitorPortNoIPv4	OBJECT-TYPE
    SYNTAX      Integer32 (0..99999)
    MAX-ACCESS	read-only
    STATUS	current
    DESCRIPTION
	"
	Fld OID Name:	avCmListIPNetRegMonitorPortNoIPv4
	Fld OID:	enterprises.6889.2.73.8.1.95.1.1.4
	Fld Form/Rpt:	IP NETWORK REGIONS MONITOR
	Fld Format:	Single Field
	Fld(s) Name:	Port No IPv4
	Fld Descr:	An object containing the IPV4 port number.
	"
    ::= { avCmListIPNetRegMonitorEntry 4 }

avCmListIPNetRegMonitorRTCPMonIPv4Addr	OBJECT-TYPE
    SYNTAX	SnmpAdminString (SIZE (0..17))
    MAX-ACCESS	read-only
    STATUS	current
    DESCRIPTION
	"
	Fld OID Name:	avCmListIPNetRegMonitorRTCPMonIPv4Addr
	Fld OID:	enterprises.6889.2.73.8.1.95.1.1.5
	Fld Form/Rpt:	IP NETWORK REGIONS MONITOR
	Fld Format:	Single Field
	Fld(s) Name:	IPv4 Address
	Fld Descr:	An object containing the RTCP Monitor IPv4 IP Address.
	"
    ::= { avCmListIPNetRegMonitorEntry 5 }

avCmListIPNetRegMonitorServiceReportPer   OBJECT-TYPE
    SYNTAX      Integer32 (0..99)
    MAX-ACCESS  read-only
    STATUS      current
    DESCRIPTION
        "
        Fld OID Name:   avCmListIPNetRegMonitorServiceReportPer
        Fld OID:        enterprises.6889.2.73.8.1.95.1.1.6
        Fld Form/Rpt:   IP NETWORK REGIONS MONITOR
        Fld Format:     Single Field
        Fld(s) Name:    Report Period
        Fld Descr:      An object containing the Report Period.
        "
    ::= { avCmListIPNetRegMonitorEntry 6 }


avCmListIPNetRegMonitorCodecSet	OBJECT-TYPE
    SYNTAX	SnmpAdminString (SIZE (0..5))
    MAX-ACCESS	read-only
    STATUS	current
    DESCRIPTION
	"
	Fld OID Name:	avCmListIPNetRegMonitorCodecSet
	Fld OID:	enterprises.6889.2.73.8.1.95.1.1.7
	Fld Form/Rpt:	IP NETWORK REGIONS MONITOR
	Fld Format:	Single Field
	Fld(s) Name:	Codec Set
	Fld Descr:	An object containing the codec set used by the region.
	"
    ::= { avCmListIPNetRegMonitorEntry 7 }

avCmListIPNetRegMonitorUDPPortRangeMin	OBJECT-TYPE
    SYNTAX      Integer32 (0..99999)
    MAX-ACCESS	read-only
    STATUS	current
    DESCRIPTION
	"
	Fld OID Name:	avCmListIPNetRegMonitorUDPPortRangeMin
	Fld OID:	enterprises.6889.2.73.8.1.95.1.1.8
	Fld Form/Rpt:	IP NETWORK REGIONS MONITOR
	Fld Format:	Single Field
	Fld(s) Name:	UDP Port Range Min
	Fld Descr:	An object containing the UDP port range minimum.
	"
    ::= { avCmListIPNetRegMonitorEntry 8 }

avCmListIPNetRegMonitorUDPPortRangeMax	OBJECT-TYPE
    SYNTAX      Integer32 (0..99999)
    MAX-ACCESS	read-only
    STATUS	current
    DESCRIPTION
	"
	Fld OID Name:	avCmListIPNetRegMonitorUDPPortRangeMax
	Fld OID:	enterprises.6889.2.73.8.1.95.1.1.9
	Fld Form/Rpt:	IP NETWORK REGIONS MONITOR
	Fld Format:	Single Field
	Fld(s) Name:	UDP Port Range Max
	Fld Descr:	An object containing the UDP Port Range Maximum.
	"
    ::= { avCmListIPNetRegMonitorEntry 9 }

avCmListIPNetRegMonitorPortNoIPv6	OBJECT-TYPE
    SYNTAX      Integer32 (0..99999)
    MAX-ACCESS	read-only
    STATUS	current
    DESCRIPTION
	"
	Fld OID Name:	avCmListIPNetRegMonitorPortNoIPv6
	Fld OID:	enterprises.6889.2.73.8.1.95.1.1.10
	Fld Form/Rpt:	IP NETWORK REGIONS MONITOR
	Fld Format:	Single Field
	Fld(s) Name:	Port No IPv6
	Fld Descr:	An object containing the IPV6 port number.
	"
    ::= { avCmListIPNetRegMonitorEntry 10 }

avCmListIPNetRegMonitorRTCPMonIPv6Addr	OBJECT-TYPE
    SYNTAX	SnmpAdminString (SIZE (0..41))
    MAX-ACCESS	read-only
    STATUS	current
    DESCRIPTION
	"
	Fld OID Name:	avCmListIPNetRegMonitorRTCPMonIPv6Addr
	Fld OID:	enterprises.6889.2.73.8.1.95.1.1.11
	Fld Form/Rpt:	IP NETWORK REGIONS MONITOR
	Fld Format:	Single Field
	Fld(s) Name:	IPv6 Address
	Fld Descr:	Field that displays the IPV6 address.
	"
    ::= { avCmListIPNetRegMonitorEntry 11 }

-- ******************** avCmStatIpNetRegion Group *************************

-- MIB GROUP DESCRIPTION

-- MIB Group Name:
--		avCmStatIpNetRegion Group
-- OID:
--		enterprises.6889.2.73.8.1.96
-- Description:
--		The avCmStatIpNetRegion MIB Group uses the "status 
--		ip-network-region" command to retrieve all network-
--		region related data. 
--		
-- Releases Supported:
--		CM6.3.100 and greater
-- Polling Type:
--		Inventory and Performance/Utilization
-- Polling Interval:
--		No more than once an hour.
-- Default Caching Interval
-- 		600 seconds
-- Timeout Interval:
--		Initial Timeout should be set to 45 seconds.
-- Retry Interval:
--		Initial Retry should be set to 3.
-- Limitations:
--		Red/High - The data collected by this MIB Group will
--		increase as the number of administered ip-interface 
--		media-processors  increase.
--		Consequently the data collected by this MIB Group could be
--		very large and therefore may take a very long time to collect
-- Command Type:
--		1. SAT
-- Command:
--		1. status ip-network-region 1-2000
-- Form/Report Name:
--		1.  Inter Network Region Bandwidth Status
-- Reference Document:
--		1. A detailed description of the command and form can be
--		   found in document referenced by REF_DOC_1 in the
--		   DOCUMENT REFERENCE SECTION.
-- Command Permission/User-profile:
--		1. No special permissions needed.

avCmStatIpNetRegion	OBJECT IDENTIFIER ::= { avCmObjects 96 }

avCmStatIpNetRegionTable	OBJECT-TYPE
    SYNTAX	SEQUENCE OF AvCmStatIpNetRegionEntry
    MAX-ACCESS	not-accessible
    STATUS	current
    DESCRIPTION
	"
	Fld OID Name:	avCmStatIpNetRegionEntry
	Fld OID:	enterprises.6889.2.73.8.1.96.1
	Fld Form/Rpt:	NA
	Fld Format:	NA
	Fld(s) Name:	NA
	Fld Descr:	A list of the avCmStatIpNetRegion entries
	"
    ::= { avCmStatIpNetRegion 1 }

avCmStatIpNetRegionEntry	OBJECT-TYPE
    SYNTAX	AvCmStatIpNetRegionEntry
    MAX-ACCESS	not-accessible
    STATUS	current
    DESCRIPTION
	"
	Fld OID Name:	avCmStatIpNetRegionEntry
	Fld OID:	enterprises.6889.2.73.8.1.96.1.1
	Fld Form/Rpt:	NA
	Fld Format:	NA
	Fld(s) Name:	NA
	Fld Descr:	A avCmStatIpNetRegion entry containing objects of the
			avCmStatIpNetRegion information sent by the switch.
	"
    INDEX    { avCmStatIpNetRegionSrcRegIdx, avCmStatIpNetRegionDstRegIdx }
    ::= { avCmStatIpNetRegionTable 1 }

AvCmStatIpNetRegionEntry ::= SEQUENCE {
		avCmStatIpNetRegionSrcRegIdx
		    Integer32,
		avCmStatIpNetRegionDstRegIdx
		    Integer32,
		avCmStatIpNetRegionSrcRgn
		    Integer32,
		avCmStatIpNetRegionDstRgn
		    Integer32,
		avCmStatIpNetRegionConnType
		    SnmpAdminString,
		avCmStatIpNetRegionConnStat
		    SnmpAdminString,
		avCmStatIpNetRegionBWlimit
		    SnmpAdminString,
		avCmStatIpNetRegionBWUnits
		    SnmpAdminString,
		avCmStatIpNetRegionBWUsedbitsTx
		    SnmpAdminString,
		avCmStatIpNetRegionBWUsedbitsRx 
		    SnmpAdminString,
		avCmStatIpNetRegionNumofConsTx
		    Integer32,
		avCmStatIpNetRegionNumofConsRx
		    Integer32,
		avCmStatIpNetRegionDenialCount
		    SnmpAdminString
		}

avCmStatIpNetRegionSrcRegIdx	OBJECT-TYPE
    SYNTAX      Integer32 (0..9999)
    MAX-ACCESS	not-accessible
    STATUS	current
    DESCRIPTION
	"
	Fld OID Name:	avCmStatIpNetRegionSrcRegIdx
	Fld OID:	enterprises.6889.2.73.8.1.96.1.1.1
	Fld Format:	NA
	Fld(s) Name:	NA
	Fld Descr:	An object that uniquely identifies each Increment of 
			data.
	"
    ::= { avCmStatIpNetRegionEntry 1 }

avCmStatIpNetRegionDstRegIdx	OBJECT-TYPE
    SYNTAX      Integer32 (0..9999)
    MAX-ACCESS	not-accessible
    STATUS	current
    DESCRIPTION
	"
	Fld OID Name:	avCmStatIpNetRegionDstRegIdx
	Fld OID:	enterprises.6889.2.73.8.1.96.1.1.2
	Fld Format:	NA
	Fld(s) Name:	NA
	Fld Descr:	An object that uniquely identifies each Increment of 
			data.
	"
    ::= { avCmStatIpNetRegionEntry 2 }

avCmStatIpNetRegionSrcRgn   OBJECT-TYPE
    SYNTAX      Integer32 (0..9999)
    MAX-ACCESS	read-only
    STATUS      current
    DESCRIPTION
        "
        Fld OID Name:   avCmStatIpNetRegionSrcRgn
        Fld OID:        enterprises.6889.2.73.8.1.96.1.1.3
	Fld Form/Rpt:	Inter Network Region Bandwidth Status
	Fld Format:	Single Field
	Fld(s) Name:	Src Rgn
	Fld Descr:	An  object containing the IP network region that is the
            		source of the VoIP traffic.
        "
    ::= { avCmStatIpNetRegionEntry 3 }


avCmStatIpNetRegionDstRgn	OBJECT-TYPE
    SYNTAX      Integer32 (0..9999)
    MAX-ACCESS	read-only
    STATUS	current
    DESCRIPTION
	"
	Fld OID Name:	avCmStatIpNetRegionDstRgn
	Fld OID:	enterprises.6889.2.73.8.1.96.1.1.4
	Fld Form/Rpt:	Inter Network Region Bandwidth Status
	Fld Format:	Single Field
	Fld(s) Name:	Dst Rgn
	Fld Descr:	An object containing the IP network region that is the
            		destination of the VoIP traffic.
	"
    ::= { avCmStatIpNetRegionEntry 4 }

avCmStatIpNetRegionConnType	OBJECT-TYPE
    SYNTAX	SnmpAdminString (SIZE (0..8))
    MAX-ACCESS	read-only
    STATUS	current
    DESCRIPTION
	"
	Fld OID Name:	avCmStatIpNetRegionConnType
	Fld OID:	enterprises.6889.2.73.8.1.96.1.1.5
	Fld Form/Rpt:	Inter Network Region Bandwidth Status
	Fld Format:	Single Field
	Fld(s) Name:	Conn Type
	Fld Descr:	An object containing the type of connection (either
            		direct or indirect).
	"
    ::= { avCmStatIpNetRegionEntry 5 }

avCmStatIpNetRegionConnStat   OBJECT-TYPE
    SYNTAX	SnmpAdminString (SIZE (0..5))
    MAX-ACCESS  read-only
    STATUS      current
    DESCRIPTION
        "
        Fld OID Name:   avCmStatIpNetRegionConnStat
        Fld OID:        enterprises.6889.2.73.8.1.96.1.1.6
        Fld Form/Rpt:   Inter Network Region Bandwidth Status
        Fld Format:     Single Field
        Fld(s) Name:    Conn Stat
        Fld Descr:      An object containing the status of connection (either
            		pass or fail).
        "
    ::= { avCmStatIpNetRegionEntry 6 }


avCmStatIpNetRegionBWlimit	OBJECT-TYPE
    SYNTAX	SnmpAdminString (SIZE (0..6))
    MAX-ACCESS	read-only
    STATUS	current
    DESCRIPTION
	"
	Fld OID Name:	avCmStatIpNetRegionBWlimit
	Fld OID:	enterprises.6889.2.73.8.1.96.1.1.7
	Fld Form/Rpt:	Inter Network Region Bandwidth Status
	Fld Format:	Single Field
	Fld(s) Name:	BW-limit
	Fld Descr:	An object containing the administered band width limit.
	"
    ::= { avCmStatIpNetRegionEntry 7 }

avCmStatIpNetRegionBWUnits	OBJECT-TYPE
    SYNTAX	SnmpAdminString (SIZE (0..8))
    MAX-ACCESS	read-only
    STATUS	current
    DESCRIPTION
	"
	Fld OID Name:	avCmStatIpNetRegionBWUnits
	Fld OID:	enterprises.6889.2.73.8.1.96.1.1.8
	Fld Form/Rpt:	Inter Network Region Bandwidth Status
	Fld Format:	Single Field
	Fld(s) Name:	BW Units
	Fld Descr:	An object containing the administered bandwidth
            		units (Calls, Kbits, Mbits, or NoLimit).
	"
    ::= { avCmStatIpNetRegionEntry 8 }

avCmStatIpNetRegionBWUsedbitsTx	OBJECT-TYPE
    SYNTAX	SnmpAdminString (SIZE (0..6))
    MAX-ACCESS	read-only
    STATUS	current
    DESCRIPTION
	"
	Fld OID Name:	avCmStatIpNetRegionBWUsedbitsTx
	Fld OID:	enterprises.6889.2.73.8.1.96.1.1.9
	Fld Form/Rpt:	Inter Network Region Bandwidth Status
	Fld Format:	Single Field
	Fld(s) Name:	BW-Used(bits) Tx
	Fld Descr:	An object containing the transmit bandwidth used
            		for direct connections only.
	"
    ::= { avCmStatIpNetRegionEntry 9 }

avCmStatIpNetRegionBWUsedbitsRx	OBJECT-TYPE
    SYNTAX	SnmpAdminString (SIZE (0..6))
    MAX-ACCESS	read-only
    STATUS	current
    DESCRIPTION
	"
	Fld OID Name:	avCmStatIpNetRegionBWUsedbitsRx
	Fld OID:	enterprises.6889.2.73.8.1.96.1.1.10
	Fld Form/Rpt:	Inter Network Region Bandwidth Status
	Fld Format:	Single Field
	Fld(s) Name:	BW-Used(bits) Rx
	Fld Descr:	An object containing the receive bandwidth used
            		for direct connections only.
	"
    ::= { avCmStatIpNetRegionEntry 10 }

avCmStatIpNetRegionNumofConsTx	OBJECT-TYPE
    SYNTAX      Integer32 (0..99999)
    MAX-ACCESS	read-only
    STATUS	current
    DESCRIPTION
	"
	Fld OID Name:	avCmStatIpNetRegionNumofConsTx
	Fld OID:	enterprises.6889.2.73.8.1.96.1.1.11
	Fld Form/Rpt:	Inter Network Region Bandwidth Status
	Fld Format:	Single Field
	Fld(s) Name:	Number of Connections Tx
	Fld Descr:	An object that contains the transmit connection count
            		for direct connections only.
	"
    ::= { avCmStatIpNetRegionEntry 11 }

avCmStatIpNetRegionNumofConsRx	OBJECT-TYPE
    SYNTAX      Integer32 (0..99999)
    MAX-ACCESS	read-only
    STATUS	current
    DESCRIPTION
	"
	Fld OID Name:	avCmStatIpNetRegionNumofConsRx
	Fld OID:	enterprises.6889.2.73.8.1.96.1.1.12
	Fld Form/Rpt:	Inter Network Region Bandwidth Status
	Fld Format:	Single Field
	Fld(s) Name:	Number of Connections Rx
	Fld Descr:	An Object containing the receive connection count
            		for direct connections only.
	"
    ::= { avCmStatIpNetRegionEntry 12 }

avCmStatIpNetRegionDenialCount	OBJECT-TYPE
    SYNTAX	SnmpAdminString (SIZE (0..4))
    MAX-ACCESS	read-only
    STATUS	current
    DESCRIPTION
	"
	Fld OID Name:	avCmStatIpNetRegionDenialCount
	Fld OID:	enterprises.6889.2.73.8.1.96.1.1.13
	Fld Form/Rpt:	Inter Network Region Bandwidth Status
	Fld Format:	Single Field
	Fld(s) Name:	Denial Count
	Fld Descr:	An 0bject containing the denial count.
	"
    ::= { avCmStatIpNetRegionEntry 13 }

-- ******************** avCmMeasToneRecLstHr Group *************************

-- MIB GROUP DESCRIPTION

-- MIB Group Name:
--		avCmMeasToneRecLstHr Group
-- OID:
--		enterprises.6889.2.73.8.1.97
-- Description:
--		The avCmMeasToneRecLstHr MIB Group uses the "list measurements
--		tone-receiver detail last-hour" command to retrieve tone 
--		receiver data from the last hour.
--		
-- Releases Supported:
--		CM6.3.100 and greater
-- Polling Type:
--		Performance/Utilization
-- Polling Interval:
--		No more than once an hour because the data is only updated
--		near the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements tone-receiver detail last-hour
-- Form/Report Name:
--		1. TONE RECEIVER DETAIL MEASUREMENTS
-- Reference Document:
--		1. A detailed description of the command and form can be
--		   found in document referenced by REF_DOC_4 in the
--		   DOCUMENT REFERENCE SECTION.
-- Command Permission/User-profile:
--		1. No special permissions needed.

avCmMeasToneRecLstHr	OBJECT IDENTIFIER ::= { avCmObjects 97 }

avCmMeasToneRecLstHrTable	OBJECT-TYPE
    SYNTAX	SEQUENCE OF AvCmMeasToneRecLstHrEntry
    MAX-ACCESS	not-accessible
    STATUS	current
    DESCRIPTION
	"
	Fld OID Name:	avCmMeasToneRecLstHrEntry
	Fld OID:	enterprises.6889.2.73.8.1.97.1
	Fld Form/Rpt:   TONE RECEIVER DETAIL MEASUREMENTS
	Fld Format:	NA
	Fld(s) Name:	NA
	Fld Descr:	A list of the avCmMeasToneRecLstHr entries
	"
    ::= { avCmMeasToneRecLstHr 1 }

avCmMeasToneRecLstHrEntry	OBJECT-TYPE
    SYNTAX	AvCmMeasToneRecLstHrEntry
    MAX-ACCESS	not-accessible
    STATUS	current
    DESCRIPTION
	"
	Fld OID Name:	avCmMeasToneRecLstHrEntry
	Fld OID:	enterprises.6889.2.73.8.1.97.1.1
	Fld Form/Rpt:   TONE RECEIVER DETAIL MEASUREMENTS
	Fld Format:	NA
	Fld(s) Name:	NA
	Fld Descr:	A avCmMeasToneRecLstHr entry containing objects of the
			avCmMeasToneRecLstHr information sent by the switch.
	"
    INDEX    { avCmMeasToneRecLstHrPnIdx }
    ::= { avCmMeasToneRecLstHrTable 1 }

AvCmMeasToneRecLstHrEntry ::= SEQUENCE {
		avCmMeasToneRecLstHrPnIdx
		    Integer32,
		avCmMeasToneRecLstHrPNNumber
		    Integer32,
		avCmMeasToneRecLstHrRunDate
		    SnmpAdminString,
		avCmMeasToneRecLstHrMeasHour
		    Integer32,
		avCmMeasToneRecLstHrDTMFPnReq
		    Integer32,
		avCmMeasToneRecLstHrDTMFPnAlloc
		    Integer32,
		avCmMeasToneRecLstHrDTMFPkAlloc 
		    Integer32,
		avCmMeasToneRecLstHrDTMFTotOffPN
		    Integer32,
		avCmMeasToneRecLstHrDTMFPkOffPN
		    Integer32,
		avCmMeasToneRecLstHrGPTDPnReq
		    Integer32,
		avCmMeasToneRecLstHrGPTDPnAlloc
		    Integer32,
		avCmMeasToneRecLstHrGPTDPkAlloc
		    Integer32,
		avCmMeasToneRecLstHrGPTDTotOffPN
		    Integer32,
		avCmMeasToneRecLstHrGPTDPkOffPN
		    Integer32,
		avCmMeasToneRecLstHrCCTTRPnReq
		    Integer32,
		avCmMeasToneRecLstHrCCTTRPnAlloc
		    Integer32,
		avCmMeasToneRecLstHrCCTRPkAlloc
		    Integer32,
		avCmMeasToneRecLstHrCCTTRTotOffPN
		    Integer32,
		avCmMeasToneRecLstHrCCTTRPkOffPN
		    Integer32,
		avCmMeasToneRecLstHrCCCPTRPnReq
		    Integer32,
		avCmMeasToneRecLstHrCCCPTRPnAlloc
		    Integer32,
		avCmMeasToneRecLstHrCCCPTRPkAlloc
		    Integer32,
		avCmMeasToneRecLstHrCCCPTRTotOffPN
		    Integer32,
		avCmMeasToneRecLstHrCCCPTRPkOffPN
		    Integer32,
		avCmMeasToneRecLstHrCCMFCRPnReq
		    Integer32,
		avCmMeasToneRecLstHrCCMFCRPnAlloc
		    Integer32,
		avCmMeasToneRecLstHrCCMFCRPkAlloc
		    Integer32,
		avCmMeasToneRecLstHrCCMFCRTotOffPN
		    Integer32,
		avCmMeasToneRecLstHrCCMFCRPkOffPN
		    Integer32
		}

avCmMeasToneRecLstHrPnIdx	OBJECT-TYPE
    SYNTAX	Integer32 (0..99)
    MAX-ACCESS	not-accessible
    STATUS	current
    DESCRIPTION
	"
	Fld OID Name:	avCmMeasToneRecLstHrPnIdx
	Fld OID:	enterprises.6889.2.73.8.1.97.1.1.1
	Fld Format:	NA
	Fld(s) Name:	NA
	Fld Descr:	An object that uniquely identifies each Increment of 
			data.
	"
    ::= { avCmMeasToneRecLstHrEntry 1 }

avCmMeasToneRecLstHrPNNumber	OBJECT-TYPE
    SYNTAX	Integer32 (0..99)
    MAX-ACCESS	read-only
    STATUS	current
    DESCRIPTION
	"
	Fld OID Name:	avCmMeasToneRecLstHrPNNumber
	Fld OID:	enterprises.6889.2.73.8.1.97.1.1.2
	Fld Form/Rpt:   TONE RECEIVER DETAIL MEASUREMENTS
	Fld Format:	Single Field
	Fld(s) Name:	PN
	Fld Descr:	An object containing the Port Network number in which 
			the tone receiver is located.
	"
    ::= { avCmMeasToneRecLstHrEntry 2 }

avCmMeasToneRecLstHrRunDate	OBJECT-TYPE
    SYNTAX	SnmpAdminString (SIZE (0..28))
    MAX-ACCESS	read-only
    STATUS	current
    DESCRIPTION
	"
	Fld OID Name:	avCmMeasToneRecLstHrRunDate
	Fld OID:	enterprises.6889.2.73.8.1.97.1.1.3
	Fld Form/Rpt:   TONE RECEIVER DETAIL MEASUREMENTS
	Fld Format:	Single Field
	Fld(s) Name:	Date
	Fld Descr:	An object containing the Date the command was executed.
	"
    ::= { avCmMeasToneRecLstHrEntry 3 }

avCmMeasToneRecLstHrMeasHour   OBJECT-TYPE
    SYNTAX	Integer32 (0..9999)
    MAX-ACCESS  read-only
    STATUS      current
    DESCRIPTION
        "
        Fld OID Name:   avCmMeasToneRecLstHrMeasHour
        Fld OID:        enterprises.6889.2.73.8.1.97.1.1.4
        Fld Form/Rpt:   TONE RECEIVER DETAIL MEASUREMENTS
        Fld Format:     Single Field
        Fld(s) Name:    Hour
        Fld Descr:      An object containing the Hour the measurement was taken.
        "
    ::= { avCmMeasToneRecLstHrEntry 4 }


avCmMeasToneRecLstHrDTMFPnReq	OBJECT-TYPE
    SYNTAX	Integer32 (0..99999)
    MAX-ACCESS	read-only
    STATUS	current
    DESCRIPTION
	"
	Fld OID Name:	avCmMeasToneRecLstHrDTMFPnReq
	Fld OID:	enterprises.6889.2.73.8.1.97.1.1.5
	Fld Form/Rpt:   TONE RECEIVER DETAIL MEASUREMENTS
	Fld Format:	Single Field
	Fld(s) Name:	DTMF PN Req
	Fld Descr:	An object containing the number of DTMF requests 
			within the PN.
	"
    ::= { avCmMeasToneRecLstHrEntry 5 }

avCmMeasToneRecLstHrDTMFPnAlloc	OBJECT-TYPE
    SYNTAX	Integer32 (0..99999)
    MAX-ACCESS	read-only
    STATUS	current
    DESCRIPTION
	"
	Fld OID Name:	avCmMeasToneRecLstHrDTMFPnAlloc
	Fld OID:	enterprises.6889.2.73.8.1.97.1.1.6
	Fld Form/Rpt:   TONE RECEIVER DETAIL MEASUREMENTS
	Fld Format:	Single Field
	Fld(s) Name:	DTMF PN Alloc
	Fld Descr:	An object containing the total number of DTMF receivers
			located in the listed PN that were allocated during 
			the last hour.
	"
    ::= { avCmMeasToneRecLstHrEntry 6 }

avCmMeasToneRecLstHrDTMFPkAlloc	OBJECT-TYPE
    SYNTAX	Integer32 (0..9999)
    MAX-ACCESS	read-only
    STATUS	current
    DESCRIPTION
	"
	Fld OID Name:	avCmMeasToneRecLstHrDTMFPkAlloc
	Fld OID:	enterprises.6889.2.73.8.1.97.1.1.7
	Fld Form/Rpt:   TONE RECEIVER DETAIL MEASUREMENTS
	Fld Format:	Single Field
	Fld(s) Name:	DTMF Peak Alloc
	Fld Descr:	An object containing the peak number of DTMF receivers 
			located in the listed PN that were in use 
			simulatneously.
	"
    ::= { avCmMeasToneRecLstHrEntry 7 }

avCmMeasToneRecLstHrDTMFTotOffPN	OBJECT-TYPE
    SYNTAX	Integer32 (0..9999)
    MAX-ACCESS	read-only
    STATUS	current
    DESCRIPTION
	"
	Fld OID Name:	avCmMeasToneRecLstHrDTMFTotOffPN
	Fld OID:	enterprises.6889.2.73.8.1.97.1.1.8
	Fld Form/Rpt:   TONE RECEIVER DETAIL MEASUREMENTS
	Fld Format:	Single Field
	Fld(s) Name:	DTMF Total Off-PN
	Fld Descr:	An object containing the total number of DTMF 
			receivers allocated of a different PN for requests 
			originated on this PN.
	"
    ::= { avCmMeasToneRecLstHrEntry 8 }

avCmMeasToneRecLstHrDTMFPkOffPN	OBJECT-TYPE
    SYNTAX	Integer32 (0..9999)
    MAX-ACCESS	read-only
    STATUS	current
    DESCRIPTION
	"
	Fld OID Name:	avCmMeasToneRecLstHrDTMFPkOffPN
	Fld OID:	enterprises.6889.2.73.8.1.97.1.1.9
	Fld Form/Rpt:   TONE RECEIVER DETAIL MEASUREMENTS
	Fld Format:	Single Field
	Fld(s) Name:	Peak Off-PN
	Fld Descr:	An object containing the peak number of DTMF receivers 
			simultaneously allocated on a different PN for requests
			originated on this PN.
	"
    ::= { avCmMeasToneRecLstHrEntry 9 }

avCmMeasToneRecLstHrGPTDPnReq	OBJECT-TYPE
    SYNTAX	Integer32 (0..99999)
    MAX-ACCESS	read-only
    STATUS	current
    DESCRIPTION
	"
	Fld OID Name:	avCmMeasToneRecLstHrGPTDPnReq
	Fld OID:	enterprises.6889.2.73.8.1.97.1.1.10
	Fld Form/Rpt:   TONE RECEIVER DETAIL MEASUREMENTS
	Fld Format:	Single Field
	Fld(s) Name:	GPTD PN Req
	Fld Descr:	An object containing the number of GPTD requests within 
			the PN.
	"
    ::= { avCmMeasToneRecLstHrEntry 10 }

avCmMeasToneRecLstHrGPTDPnAlloc	OBJECT-TYPE
    SYNTAX	Integer32 (0..99999)
    MAX-ACCESS	read-only
    STATUS	current
    DESCRIPTION
	"
	Fld OID Name:	avCmMeasToneRecLstHrGPTDPnAlloc
	Fld OID:	enterprises.6889.2.73.8.1.97.1.1.11
	Fld Form/Rpt:   TONE RECEIVER DETAIL MEASUREMENTS
	Fld Format:	Single Field
	Fld(s) Name:	GPTD PN Alloc
	Fld Descr:	An object containing the total number of GPTD 
			receivers located in the listed PN that were allocated 
			during the last hour.
	"
    ::= { avCmMeasToneRecLstHrEntry 11 }

avCmMeasToneRecLstHrGPTDPkAlloc	OBJECT-TYPE
    SYNTAX	Integer32 (0..9999)
    MAX-ACCESS	read-only
    STATUS	current
    DESCRIPTION
	"
	Fld OID Name:	avCmMeasToneRecLstHrGPTDPkAlloc
	Fld OID:	enterprises.6889.2.73.8.1.97.1.1.12
	Fld Form/Rpt:   TONE RECEIVER DETAIL MEASUREMENTS
	Fld Format:	Single Field
	Fld(s) Name:	GPTD PeaK Alloc
	Fld Descr:	An object containing the peak number of GPTD receivers 
			located in the listed PN that were in use 
			simulatneously.
	"
    ::= { avCmMeasToneRecLstHrEntry 12 }

avCmMeasToneRecLstHrGPTDTotOffPN	OBJECT-TYPE
    SYNTAX	Integer32 (0..9999)
    MAX-ACCESS	read-only
    STATUS	current
    DESCRIPTION
	"
	Fld OID Name:	avCmMeasToneRecLstHrGPTDTotOffPN
	Fld OID:	enterprises.6889.2.73.8.1.97.1.1.13
	Fld Form/Rpt:   TONE RECEIVER DETAIL MEASUREMENTS
	Fld Format:	Single Field
	Fld(s) Name:	GPTD Total  Off-PN
	Fld Descr:	An object containing the total number of GPTD 
			receivers allocated of a different PN for requests 
			originated on this PN.
	"
    ::= { avCmMeasToneRecLstHrEntry 13 }

avCmMeasToneRecLstHrGPTDPkOffPN	OBJECT-TYPE
    SYNTAX	Integer32 (0..9999)
    MAX-ACCESS	read-only
    STATUS	current
    DESCRIPTION
	"
	Fld OID Name:	avCmMeasToneRecLstHrGPTDPkOffPN
	Fld OID:	enterprises.6889.2.73.8.1.97.1.1.14
	Fld Form/Rpt:   TONE RECEIVER DETAIL MEASUREMENTS
	Fld Format:	Single Field
	Fld(s) Name:	GPTD Peak Off-PN
	Fld Descr:	An object containing the peak number of GPTD receivers 
			simultaneously allocated on a different PN for requests
			originated on this PN.
	"
    ::= { avCmMeasToneRecLstHrEntry 14 }

avCmMeasToneRecLstHrCCTTRPnReq	OBJECT-TYPE
    SYNTAX	Integer32 (0..99999)
    MAX-ACCESS	read-only
    STATUS	current
    DESCRIPTION
	"
	Fld OID Name:	avCmMeasToneRecLstHrCCTTRPnReq
	Fld OID:	enterprises.6889.2.73.8.1.97.1.1.15
	Fld Form/Rpt:   TONE RECEIVER DETAIL MEASUREMENTS
	Fld Format:	Single Field
	Fld(s) Name:	CC-TTR PN Req
	Fld Descr:	An object containing the number of CC-TTR requests 
			within the PN.
	"
    ::= { avCmMeasToneRecLstHrEntry 15 }

avCmMeasToneRecLstHrCCTTRPnAlloc	OBJECT-TYPE
    SYNTAX	Integer32 (0..99999)
    MAX-ACCESS	read-only
    STATUS	current
    DESCRIPTION
	"
	Fld OID Name:	avCmMeasToneRecLstHrCCTTRPnAlloc
	Fld OID:	enterprises.6889.2.73.8.1.97.1.1.16
	Fld Form/Rpt:   TONE RECEIVER DETAIL MEASUREMENTS
	Fld Format:	Single Field
	Fld(s) Name:	CC-TTR PN Alloc
	Fld Descr:	An object containing the total number of CC-TTR 
			receivers located in the listed PN that were allocated 
			during the last hour.
	"
    ::= { avCmMeasToneRecLstHrEntry 16 }

avCmMeasToneRecLstHrCCTRPkAlloc        OBJECT-TYPE
    SYNTAX      Integer32 (0..9999)
    MAX-ACCESS  read-only
    STATUS      current
    DESCRIPTION
        "
        Fld OID Name:   avCmMeasToneRecLstHrCCTRPkAlloc
        Fld OID:        enterprises.6889.2.73.8.1.97.1.1.17
        Fld Form/Rpt:   TONE RECEIVER DETAIL MEASUREMENTS
        Fld Format:     Single Field
        Fld(s) Name:    CC-TTR  Peak Alloc
        Fld Descr:      An object containing the peak number of CC-TTR 
			receivers located in the listed PN that were in use 
			simulatneously.
        "
    ::= { avCmMeasToneRecLstHrEntry 17 }

avCmMeasToneRecLstHrCCTTRTotOffPN        OBJECT-TYPE
    SYNTAX      Integer32 (0..9999)
    MAX-ACCESS  read-only
    STATUS      current
    DESCRIPTION
        "
        Fld OID Name:   avCmMeasToneRecLstHrCCTTRTotOffPN
        Fld OID:        enterprises.6889.2.73.8.1.97.1.1.18
        Fld Form/Rpt:   TONE RECEIVER DETAIL MEASUREMENTS
        Fld Format:     Single Field
        Fld(s) Name:    CC-TTR  Total Off-PN
        Fld Descr:      An object containing the total number of CC-TTR 
			receivers allocated of a different PN for requests 
			originated on this PN
        "
    ::= { avCmMeasToneRecLstHrEntry 18 }


avCmMeasToneRecLstHrCCTTRPkOffPN        OBJECT-TYPE
    SYNTAX      Integer32 (0..9999)
    MAX-ACCESS  read-only
    STATUS      current
    DESCRIPTION
        "
        Fld OID Name:   avCmMeasToneRecLstHrCCTTRPkOffPN
        Fld OID:        enterprises.6889.2.73.8.1.97.1.1.19
        Fld Form/Rpt:   TONE RECEIVER DETAIL MEASUREMENTS
        Fld Format:     Single Field
        Fld(s) Name:    CC-TTR  Peak Off-PN
        Fld Descr:      An object containing the Peak number of CC-TTR 
			receivers simultaneously allocated of a different PN 
			for requests originated on this PN
        "
    ::= { avCmMeasToneRecLstHrEntry 19 }

avCmMeasToneRecLstHrCCCPTRPnReq	OBJECT-TYPE
    SYNTAX	Integer32 (0..99999)
    MAX-ACCESS	read-only
    STATUS	current
    DESCRIPTION
	"
	Fld OID Name:	avCmMeasToneRecLstHrCCCPTRPnReq
	Fld OID:	enterprises.6889.2.73.8.1.97.1.1.20
	Fld Form/Rpt:   TONE RECEIVER DETAIL MEASUREMENTS
	Fld Format:	Single Field
	Fld(s) Name:	CC-CPTR PN Req
	Fld Descr:	An object containing the number of CC-CPTR  requests 
			within the PN.
	"
    ::= { avCmMeasToneRecLstHrEntry 20 }

avCmMeasToneRecLstHrCCCPTRPnAlloc	OBJECT-TYPE
    SYNTAX	Integer32 (0..99999)
    MAX-ACCESS	read-only
    STATUS	current
    DESCRIPTION
	"
	Fld OID Name:	avCmMeasToneRecLstHrCCCPTRPnAlloc
	Fld OID:	enterprises.6889.2.73.8.1.97.1.1.21
	Fld Form/Rpt:   TONE RECEIVER DETAIL MEASUREMENTS
	Fld Format:	Single Field
	Fld(s) Name:	CC-CPTR PN Alloc
	Fld Descr:	An object containing the total number of CC-CPTR 
			receivers located in the listed PN that were allocated 
			during the last hour.
	"
    ::= { avCmMeasToneRecLstHrEntry 21 }

avCmMeasToneRecLstHrCCCPTRPkAlloc        OBJECT-TYPE
    SYNTAX      Integer32 (0..9999)
    MAX-ACCESS  read-only
    STATUS      current
    DESCRIPTION
        "
        Fld OID Name:   avCmMeasToneRecLstHrCCCPTRPkAlloc
        Fld OID:        enterprises.6889.2.73.8.1.97.1.1.22
        Fld Form/Rpt:   TONE RECEIVER DETAIL MEASUREMENTS
        Fld Format:     Single Field
        Fld(s) Name:    CC-CPTR Peak Alloc
        Fld Descr:      An object containing the peak number of CC-CPTR
			receivers located in the listed PN that were in use 
			simulatneously.
        "
    ::= { avCmMeasToneRecLstHrEntry 22 }

avCmMeasToneRecLstHrCCCPTRTotOffPN        OBJECT-TYPE
    SYNTAX      Integer32 (0..9999)
    MAX-ACCESS  read-only
    STATUS      current
    DESCRIPTION
        "
        Fld OID Name:   avCmMeasToneRecLstHrCCCPTRTotOffPN
        Fld OID:        enterprises.6889.2.73.8.1.97.1.1.23
        Fld Form/Rpt:   TONE RECEIVER DETAIL MEASUREMENTS
        Fld Format:     Single Field
        Fld(s) Name:    CC-CPTR Total Off-PN
        Fld Descr:      An object containing the total number of CC-CPTR 
			receivers allocated of a different PN for requests 
			originated on this PN
        "
    ::= { avCmMeasToneRecLstHrEntry 23 }


avCmMeasToneRecLstHrCCCPTRPkOffPN        OBJECT-TYPE
    SYNTAX      Integer32 (0..9999)
    MAX-ACCESS  read-only
    STATUS      current
    DESCRIPTION
        "
        Fld OID Name:   avCmMeasToneRecLstHrCCCPTRPkOffPN
        Fld OID:        enterprises.6889.2.73.8.1.97.1.1.24
        Fld Form/Rpt:   TONE RECEIVER DETAIL MEASUREMENTS
        Fld Format:     Single Field
        Fld(s) Name:    CC-CPTR  Peak Off-PN
        Fld Descr:      An object containing the Peak number of CC-CPTR 
			receivers simultaneously allocated of a different PN 
			for requests originated on this PN
        "
    ::= { avCmMeasToneRecLstHrEntry 24 }

avCmMeasToneRecLstHrCCMFCRPnReq	OBJECT-TYPE
    SYNTAX	Integer32 (0..99999)
    MAX-ACCESS	read-only
    STATUS	current
    DESCRIPTION
	"
	Fld OID Name:	avCmMeasToneRecLstHrCCMFCRPnReq
	Fld OID:	enterprises.6889.2.73.8.1.97.1.1.25
	Fld Form/Rpt:   TONE RECEIVER DETAIL MEASUREMENTS
	Fld Format:	Single Field
	Fld(s) Name:	CC-MFCR PN Req
	Fld Descr:	An object containing the number of CC-MFCR  requests 
			within the PN.
	"
    ::= { avCmMeasToneRecLstHrEntry 25 }

avCmMeasToneRecLstHrCCMFCRPnAlloc	OBJECT-TYPE
    SYNTAX	Integer32 (0..99999)
    MAX-ACCESS	read-only
    STATUS	current
    DESCRIPTION
	"
	Fld OID Name:	avCmMeasToneRecLstHrCCMFCRPnAlloc
	Fld OID:	enterprises.6889.2.73.8.1.97.1.1.26
	Fld Form/Rpt:   TONE RECEIVER DETAIL MEASUREMENTS
	Fld Format:	Single Field
	Fld(s) Name:	CC-MFCR PN Alloc
	Fld Descr:	An object containing the total number of CC-MFCR 
			receivers located in the listed PN that were allocated 
			during the last hour.
	"
    ::= { avCmMeasToneRecLstHrEntry 26 }

avCmMeasToneRecLstHrCCMFCRPkAlloc        OBJECT-TYPE
    SYNTAX      Integer32 (0..9999)
    MAX-ACCESS  read-only
    STATUS      current
    DESCRIPTION
        "
        Fld OID Name:   avCmMeasToneRecLstHrCCMFCRPkAlloc
        Fld OID:        enterprises.6889.2.73.8.1.97.1.1.27
        Fld Form/Rpt:   TONE RECEIVER DETAIL MEASUREMENTS
        Fld Format:     Single Field
        Fld(s) Name:    CC-MFCR Peak Alloc
        Fld Descr:      An object containing the peak number of CC-MFCR
			receivers located in the listed PN that were in use 
			simulatneously.
        "
    ::= { avCmMeasToneRecLstHrEntry 27 }

avCmMeasToneRecLstHrCCMFCRTotOffPN        OBJECT-TYPE
    SYNTAX      Integer32 (0..9999)
    MAX-ACCESS  read-only
    STATUS      current
    DESCRIPTION
        "
        Fld OID Name:   avCmMeasToneRecLstHrCCMFCRTotOffPN
        Fld OID:        enterprises.6889.2.73.8.1.97.1.1.28
        Fld Form/Rpt:   TONE RECEIVER DETAIL MEASUREMENTS
        Fld Format:     Single Field
        Fld(s) Name:    CC-MFCR Total Off-PN
        Fld Descr:      An object containing the total number of CC-MFCR 
			receivers allocated of a different PN for requests 
			originated on this PN
        "
    ::= { avCmMeasToneRecLstHrEntry 28 }


avCmMeasToneRecLstHrCCMFCRPkOffPN        OBJECT-TYPE
    SYNTAX      Integer32 (0..9999)
    MAX-ACCESS  read-only
    STATUS      current
    DESCRIPTION
        "
        Fld OID Name:   avCmMeasToneRecLstHrCCMFCRPkOffPN
        Fld OID:        enterprises.6889.2.73.8.1.97.1.1.29
        Fld Form/Rpt:   TONE RECEIVER DETAIL MEASUREMENTS
        Fld Format:     Single Field
        Fld(s) Name:    CC-MFCR Peak Off-PN
        Fld Descr:      An object containing the Peak number of CC-MFCR 
			receivers simultaneously allocated of a different PN 
			for requests originated on this PN
        "
    ::= { avCmMeasToneRecLstHrEntry 29 }


-- ******************** avCmMeasToneRecToday Group *************************

-- MIB GROUP DESCRIPTION

-- MIB Group Name:
--		avCmMeasToneRecToday Group
-- OID:
--		enterprises.6889.2.73.8.1.98
-- Description:
--		The avCmMeasToneRecToday MIB Group uses the "list measurements
--		tone-receiver detail today" command to retrieve tone-receiver
--		data for the peak hour of the current day.
--		
-- Releases Supported:
--		CM6.3.100 and greater
-- Polling Type:
--		Performance/Utilization
-- Polling Interval:
--		No more than once an hour because the data is only updated
--		near the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements tone-receiver detail today
-- Form/Report Name:
--		1. TONE RECEIVER DETAIL MEASUREMENTS
-- Reference Document:
--		1. A detailed description of the command and form can be
--		   found in document referenced by REF_DOC_4 in the
--		   DOCUMENT REFERENCE SECTION.
-- Command Permission/User-profile:
--		1. No special permissions needed.

avCmMeasToneRecToday	OBJECT IDENTIFIER ::= { avCmObjects 98 }

avCmMeasToneRecTodayTable	OBJECT-TYPE
    SYNTAX	SEQUENCE OF AvCmMeasToneRecTodayEntry
    MAX-ACCESS	not-accessible
    STATUS	current
    DESCRIPTION
	"
	Fld OID Name:	avCmMeasToneRecTodayEntry
	Fld OID:	enterprises.6889.2.73.8.1.98.1
	Fld Form/Rpt:   TONE RECEIVER DETAIL MEASUREMENTS
	Fld Format:	NA
	Fld(s) Name:	NA
	Fld Descr:	A list of the avCmMeasToneRecToday entries
	"
    ::= { avCmMeasToneRecToday 1 }

avCmMeasToneRecTodayEntry	OBJECT-TYPE
    SYNTAX	AvCmMeasToneRecTodayEntry
    MAX-ACCESS	not-accessible
    STATUS	current
    DESCRIPTION
	"
	Fld OID Name:	avCmMeasToneRecTodayEntry
	Fld OID:	enterprises.6889.2.73.8.1.98.1.1
	Fld Form/Rpt:   TONE RECEIVER DETAIL MEASUREMENTS
	Fld Format:	NA
	Fld(s) Name:	NA
	Fld Descr:	A avCmMeasToneRecToday entry containing objects of the
			avCmMeasToneRecToday information sent by the switch.
	"
    INDEX    { avCmMeasToneRecTodayPnIdx }
    ::= { avCmMeasToneRecTodayTable 1 }

AvCmMeasToneRecTodayEntry ::= SEQUENCE {
		avCmMeasToneRecTodayPnIdx
		    Integer32,
		avCmMeasToneRecTodayPNNumber
		    Integer32,
		avCmMeasToneRecTodayRunDate
		    SnmpAdminString,
		avCmMeasToneRecTodayMeasHour
		    Integer32,
		avCmMeasToneRecTodayDTMFPnReq
		    Integer32,
		avCmMeasToneRecTodayDTMFPnAlloc
		    Integer32,
		avCmMeasToneRecTodayDTMFPkAlloc 
		    Integer32,
		avCmMeasToneRecTodayDTMFTotOffPN
		    Integer32,
		avCmMeasToneRecTodayDTMFPkOffPN
		    Integer32,
		avCmMeasToneRecTodayGPTDPnReq
		    Integer32,
		avCmMeasToneRecTodayGPTDPnAlloc
		    Integer32,
		avCmMeasToneRecTodayGPTDPkAlloc
		    Integer32,
		avCmMeasToneRecTodayGPTDTotOffPN
		    Integer32,
		avCmMeasToneRecTodayGPTDPkOffPN
		    Integer32,
		avCmMeasToneRecTodayCCTTRPnReq
		    Integer32,
		avCmMeasToneRecTodayCCTTRPnAlloc
		    Integer32,
		avCmMeasToneRecTodayCCTRPkAlloc
		    Integer32,
		avCmMeasToneRecTodayCCTTRTotOffPN
		    Integer32,
		avCmMeasToneRecTodayCCTTRPkOffPN
		    Integer32,
		avCmMeasToneRecTodayCCCPTRPnReq
		    Integer32,
		avCmMeasToneRecTodayCCCPTRPnAlloc
		    Integer32,
		avCmMeasToneRecTodayCCCPTRPkAlloc
		    Integer32,
		avCmMeasToneRecTodayCCCPTRTotOffPN
		    Integer32,
		avCmMeasToneRecTodayCCCPTRPkOffPN
		    Integer32,
		avCmMeasToneRecTodayCCMFCRPnReq
		    Integer32,
		avCmMeasToneRecTodayCCMFCRPnAlloc
		    Integer32,
		avCmMeasToneRecTodayCCMFCRPkAlloc
		    Integer32,
		avCmMeasToneRecTodayCCMFCRTotOffPN
		    Integer32,
		avCmMeasToneRecTodayCCMFCRPkOffPN
		    Integer32
		}

avCmMeasToneRecTodayPnIdx	OBJECT-TYPE
    SYNTAX	Integer32 (0..99)
    MAX-ACCESS	not-accessible
    STATUS	current
    DESCRIPTION
	"
	Fld OID Name:	avCmMeasToneRecTodayPnIdx
	Fld OID:	enterprises.6889.2.73.8.1.98.1.1.1
	Fld Format:	NA
	Fld(s) Name:	NA
	Fld Descr:	An object that uniquely identifies each Increment of 
			data.
	"
    ::= { avCmMeasToneRecTodayEntry 1 }

avCmMeasToneRecTodayPNNumber	OBJECT-TYPE
    SYNTAX	Integer32 (0..99)
    MAX-ACCESS	read-only
    STATUS	current
    DESCRIPTION
	"
	Fld OID Name:	avCmMeasToneRecTodayPNNumber
	Fld OID:	enterprises.6889.2.73.8.1.98.1.1.2
	Fld Form/Rpt:   TONE RECEIVER DETAIL MEASUREMENTS
	Fld Format:	Single Field
	Fld(s) Name:	PN
	Fld Descr:	An object containing the Port Network number in which 
			the tone receiver is located.
	"
    ::= { avCmMeasToneRecTodayEntry 2 }

avCmMeasToneRecTodayRunDate	OBJECT-TYPE
    SYNTAX	SnmpAdminString (SIZE (0..28))
    MAX-ACCESS	read-only
    STATUS	current
    DESCRIPTION
	"
	Fld OID Name:	avCmMeasToneRecTodayRunDate
	Fld OID:	enterprises.6889.2.73.8.1.98.1.1.3
	Fld Form/Rpt:   TONE RECEIVER DETAIL MEASUREMENTS
	Fld Format:	Single Field
	Fld(s) Name:	Date
	Fld Descr:	An object containing the Date the command was executed.
	"
    ::= { avCmMeasToneRecTodayEntry 3 }

avCmMeasToneRecTodayMeasHour   OBJECT-TYPE
    SYNTAX	Integer32 (0..9999)
    MAX-ACCESS  read-only
    STATUS      current
    DESCRIPTION
        "
        Fld OID Name:   avCmMeasToneRecTodayMeasHour
        Fld OID:        enterprises.6889.2.73.8.1.98.1.1.4
        Fld Form/Rpt:   TONE RECEIVER DETAIL MEASUREMENTS
        Fld Format:     Single Field
        Fld(s) Name:    Hour
        Fld Descr:      An object containing the Hour the measurement was taken.
        "
    ::= { avCmMeasToneRecTodayEntry 4 }


avCmMeasToneRecTodayDTMFPnReq	OBJECT-TYPE
    SYNTAX	Integer32 (0..99999)
    MAX-ACCESS	read-only
    STATUS	current
    DESCRIPTION
	"
	Fld OID Name:	avCmMeasToneRecTodayDTMFPnReq
	Fld OID:	enterprises.6889.2.73.8.1.98.1.1.5
	Fld Form/Rpt:   TONE RECEIVER DETAIL MEASUREMENTS
	Fld Format:	Single Field
	Fld(s) Name:	DTMF PN Req
	Fld Descr:	An object containing the number of DTMF requests 
			within the PN.
	"
    ::= { avCmMeasToneRecTodayEntry 5 }

avCmMeasToneRecTodayDTMFPnAlloc	OBJECT-TYPE
    SYNTAX	Integer32 (0..99999)
    MAX-ACCESS	read-only
    STATUS	current
    DESCRIPTION
	"
	Fld OID Name:	avCmMeasToneRecTodayDTMFPnAlloc
	Fld OID:	enterprises.6889.2.73.8.1.98.1.1.6
	Fld Form/Rpt:   TONE RECEIVER DETAIL MEASUREMENTS
	Fld Format:	Single Field
	Fld(s) Name:	DTMF PN Alloc
	Fld Descr:	An object containing the total number of DTMF receivers
			located in the listed PN that were allocated during 
			the listed hour.
	"
    ::= { avCmMeasToneRecTodayEntry 6 }

avCmMeasToneRecTodayDTMFPkAlloc	OBJECT-TYPE
    SYNTAX	Integer32 (0..9999)
    MAX-ACCESS	read-only
    STATUS	current
    DESCRIPTION
	"
	Fld OID Name:	avCmMeasToneRecTodayDTMFPkAlloc
	Fld OID:	enterprises.6889.2.73.8.1.98.1.1.7
	Fld Form/Rpt:   TONE RECEIVER DETAIL MEASUREMENTS
	Fld Format:	Single Field
	Fld(s) Name:	DTMF Peak Alloc
	Fld Descr:	An object containing the peak number of DTMF receivers 
			located in the listed PN that were in use 
			simulatneously.
	"
    ::= { avCmMeasToneRecTodayEntry 7 }

avCmMeasToneRecTodayDTMFTotOffPN	OBJECT-TYPE
    SYNTAX	Integer32 (0..9999)
    MAX-ACCESS	read-only
    STATUS	current
    DESCRIPTION
	"
	Fld OID Name:	avCmMeasToneRecTodayDTMFTotOffPN
	Fld OID:	enterprises.6889.2.73.8.1.98.1.1.8
	Fld Form/Rpt:   TONE RECEIVER DETAIL MEASUREMENTS
	Fld Format:	Single Field
	Fld(s) Name:	DTMF Total Off-PN
	Fld Descr:	An object containing the total number of DTMF 
			receivers allocated of a different PN for requests 
			originated on this PN.
	"
    ::= { avCmMeasToneRecTodayEntry 8 }

avCmMeasToneRecTodayDTMFPkOffPN	OBJECT-TYPE
    SYNTAX	Integer32 (0..9999)
    MAX-ACCESS	read-only
    STATUS	current
    DESCRIPTION
	"
	Fld OID Name:	avCmMeasToneRecTodayDTMFPkOffPN
	Fld OID:	enterprises.6889.2.73.8.1.98.1.1.9
	Fld Form/Rpt:   TONE RECEIVER DETAIL MEASUREMENTS
	Fld Format:	Single Field
	Fld(s) Name:	DTMF Peak Off-PN
	Fld Descr:	An object containing the peak number of DTMF receivers 
			simultaneously allocated on a different PN for requests
			originated on this PN.
	"
    ::= { avCmMeasToneRecTodayEntry 9 }

avCmMeasToneRecTodayGPTDPnReq	OBJECT-TYPE
    SYNTAX	Integer32 (0..99999)
    MAX-ACCESS	read-only
    STATUS	current
    DESCRIPTION
	"
	Fld OID Name:	avCmMeasToneRecTodayGPTDPnReq
	Fld OID:	enterprises.6889.2.73.8.1.98.1.1.10
	Fld Form/Rpt:   TONE RECEIVER DETAIL MEASUREMENTS
	Fld Format:	Single Field
	Fld(s) Name:	GPTD PN Req
	Fld Descr:	An object containing the number of GPTD requests within 
			the PN.
	"
    ::= { avCmMeasToneRecTodayEntry 10 }

avCmMeasToneRecTodayGPTDPnAlloc	OBJECT-TYPE
    SYNTAX	Integer32 (0..99999)
    MAX-ACCESS	read-only
    STATUS	current
    DESCRIPTION
	"
	Fld OID Name:	avCmMeasToneRecTodayGPTDPnAlloc
	Fld OID:	enterprises.6889.2.73.8.1.98.1.1.11
	Fld Form/Rpt:   TONE RECEIVER DETAIL MEASUREMENTS
	Fld Format:	Single Field
	Fld(s) Name:	GPTD PN Alloc
	Fld Descr:	An object containing the total number of GPTD 
			receivers located in the listed PN that were allocated 
			during the listed hour.
	"
    ::= { avCmMeasToneRecTodayEntry 11 }

avCmMeasToneRecTodayGPTDPkAlloc	OBJECT-TYPE
    SYNTAX	Integer32 (0..9999)
    MAX-ACCESS	read-only
    STATUS	current
    DESCRIPTION
	"
	Fld OID Name:	avCmMeasToneRecTodayGPTDPkAlloc
	Fld OID:	enterprises.6889.2.73.8.1.98.1.1.12
	Fld Form/Rpt:   TONE RECEIVER DETAIL MEASUREMENTS
	Fld Format:	Single Field
	Fld(s) Name:	GPTD PeaK Alloc
	Fld Descr:	An object containing the peak number of GPTD receivers 
			located in the listed PN that were in use 
			simulatneously.
	"
    ::= { avCmMeasToneRecTodayEntry 12 }

avCmMeasToneRecTodayGPTDTotOffPN	OBJECT-TYPE
    SYNTAX	Integer32 (0..9999)
    MAX-ACCESS	read-only
    STATUS	current
    DESCRIPTION
	"
	Fld OID Name:	avCmMeasToneRecTodayGPTDTotOffPN
	Fld OID:	enterprises.6889.2.73.8.1.98.1.1.13
	Fld Form/Rpt:   TONE RECEIVER DETAIL MEASUREMENTS
	Fld Format:	Single Field
	Fld(s) Name:	GPTD Total  Off-PN
	Fld Descr:	An object containing the total number of GPTD 
			receivers allocated of a different PN for requests 
			originated on this PN.
	"
    ::= { avCmMeasToneRecTodayEntry 13 }

avCmMeasToneRecTodayGPTDPkOffPN	OBJECT-TYPE
    SYNTAX	Integer32 (0..9999)
    MAX-ACCESS	read-only
    STATUS	current
    DESCRIPTION
	"
	Fld OID Name:	avCmMeasToneRecTodayGPTDPkOffPN
	Fld OID:	enterprises.6889.2.73.8.1.98.1.1.14
	Fld Form/Rpt:   TONE RECEIVER DETAIL MEASUREMENTS
	Fld Format:	Single Field
	Fld(s) Name:	GPTD Peak Off-PN
	Fld Descr:	An object containing the peak number of GPTD receivers 
			simultaneously allocated on a different PN for requests
			originated on this PN.
	"
    ::= { avCmMeasToneRecTodayEntry 14 }

avCmMeasToneRecTodayCCTTRPnReq	OBJECT-TYPE
    SYNTAX	Integer32 (0..99999)
    MAX-ACCESS	read-only
    STATUS	current
    DESCRIPTION
	"
	Fld OID Name:	avCmMeasToneRecTodayCCTTRPnReq
	Fld OID:	enterprises.6889.2.73.8.1.98.1.1.15
	Fld Form/Rpt:   TONE RECEIVER DETAIL MEASUREMENTS
	Fld Format:	Single Field
	Fld(s) Name:	CC-TTR PN Req
	Fld Descr:	An object containing the number of CC-TTR requests 
			within the PN.
	"
    ::= { avCmMeasToneRecTodayEntry 15 }

avCmMeasToneRecTodayCCTTRPnAlloc	OBJECT-TYPE
    SYNTAX	Integer32 (0..99999)
    MAX-ACCESS	read-only
    STATUS	current
    DESCRIPTION
	"
	Fld OID Name:	avCmMeasToneRecTodayCCTTRPnAlloc
	Fld OID:	enterprises.6889.2.73.8.1.98.1.1.16
	Fld Form/Rpt:   TONE RECEIVER DETAIL MEASUREMENTS
	Fld Format:	Single Field
	Fld(s) Name:	CC-TTR PN Alloc
	Fld Descr:	An object containing the total number of CC-TTR 
			receivers located in the listed PN that were allocated 
			during the listed hour.
	"
    ::= { avCmMeasToneRecTodayEntry 16 }

avCmMeasToneRecTodayCCTRPkAlloc        OBJECT-TYPE
    SYNTAX      Integer32 (0..9999)
    MAX-ACCESS  read-only
    STATUS      current
    DESCRIPTION
        "
        Fld OID Name:   avCmMeasToneRecTodayCCTRPkAlloc
        Fld OID:        enterprises.6889.2.73.8.1.98.1.1.17
        Fld Form/Rpt:   TONE RECEIVER DETAIL MEASUREMENTS
        Fld Format:     Single Field
        Fld(s) Name:    CC-TTR  Peak Alloc
        Fld Descr:      An object containing the peak number of CC-TTR 
			receivers located in the listed PN that were in use 
			simulatneously.
        "
    ::= { avCmMeasToneRecTodayEntry 17 }

avCmMeasToneRecTodayCCTTRTotOffPN        OBJECT-TYPE
    SYNTAX      Integer32 (0..9999)
    MAX-ACCESS  read-only
    STATUS      current
    DESCRIPTION
        "
        Fld OID Name:   avCmMeasToneRecTodayCCTTRTotOffPN
        Fld OID:        enterprises.6889.2.73.8.1.98.1.1.18
        Fld Form/Rpt:   TONE RECEIVER DETAIL MEASUREMENTS
        Fld Format:     Single Field
        Fld(s) Name:    CC-TTR  Total Off-PN
        Fld Descr:      An object containing the total number of CC-TTR 
			receivers allocated of a different PN for requests 
			originated on this PN
        "
    ::= { avCmMeasToneRecTodayEntry 18 }


avCmMeasToneRecTodayCCTTRPkOffPN        OBJECT-TYPE
    SYNTAX      Integer32 (0..9999)
    MAX-ACCESS  read-only
    STATUS      current
    DESCRIPTION
        "
        Fld OID Name:   avCmMeasToneRecTodayCCTTRPkOffPN
        Fld OID:        enterprises.6889.2.73.8.1.98.1.1.19
        Fld Form/Rpt:   TONE RECEIVER DETAIL MEASUREMENTS
        Fld Format:     Single Field
        Fld(s) Name:    CC-TTR  Peak Off-PN
        Fld Descr:      An object containing the Peak number of CC-TTR 
			receivers simultaneously allocated of a different PN 
			for requests originated on this PN
        "
    ::= { avCmMeasToneRecTodayEntry 19 }

avCmMeasToneRecTodayCCCPTRPnReq	OBJECT-TYPE
    SYNTAX	Integer32 (0..99999)
    MAX-ACCESS	read-only
    STATUS	current
    DESCRIPTION
	"
	Fld OID Name:	avCmMeasToneRecTodayCCCPTRPnReq
	Fld OID:	enterprises.6889.2.73.8.1.98.1.1.20
	Fld Form/Rpt:   TONE RECEIVER DETAIL MEASUREMENTS
	Fld Format:	Single Field
	Fld(s) Name:	CC-CPTR PN Req
	Fld Descr:	An object containing the number of CC-CPTR  requests 
			within the PN.
	"
    ::= { avCmMeasToneRecTodayEntry 20 }

avCmMeasToneRecTodayCCCPTRPnAlloc	OBJECT-TYPE
    SYNTAX	Integer32 (0..99999)
    MAX-ACCESS	read-only
    STATUS	current
    DESCRIPTION
	"
	Fld OID Name:	avCmMeasToneRecTodayCCCPTRPnAlloc
	Fld OID:	enterprises.6889.2.73.8.1.98.1.1.21
	Fld Form/Rpt:   TONE RECEIVER DETAIL MEASUREMENTS
	Fld Format:	Single Field
	Fld(s) Name:	CC-CPTR PN Alloc
	Fld Descr:	An object containing the total number of CC-CPTR 
			receivers located in the listed PN that were allocated 
			during the listed hour.
	"
    ::= { avCmMeasToneRecTodayEntry 21 }

avCmMeasToneRecTodayCCCPTRPkAlloc        OBJECT-TYPE
    SYNTAX      Integer32 (0..9999)
    MAX-ACCESS  read-only
    STATUS      current
    DESCRIPTION
        "
        Fld OID Name:   avCmMeasToneRecTodayCCCPTRPkAlloc
        Fld OID:        enterprises.6889.2.73.8.1.98.1.1.22
        Fld Form/Rpt:   TONE RECEIVER DETAIL MEASUREMENTS
        Fld Format:     Single Field
        Fld(s) Name:    CC-CPTR Peak Alloc
        Fld Descr:      An object containing the peak number of CC-CPTR
			receivers located in the listed PN that were in use 
			simulatneously.
        "
    ::= { avCmMeasToneRecTodayEntry 22 }

avCmMeasToneRecTodayCCCPTRTotOffPN        OBJECT-TYPE
    SYNTAX      Integer32 (0..9999)
    MAX-ACCESS  read-only
    STATUS      current
    DESCRIPTION
        "
        Fld OID Name:   avCmMeasToneRecTodayCCCPTRTotOffPN
        Fld OID:        enterprises.6889.2.73.8.1.98.1.1.23
        Fld Form/Rpt:   TONE RECEIVER DETAIL MEASUREMENTS
        Fld Format:     Single Field
        Fld(s) Name:    CC-CPTR Total Off-PN
        Fld Descr:      An object containing the total number of CC-CPTR 
			receivers allocated of a different PN for requests 
			originated on this PN
        "
    ::= { avCmMeasToneRecTodayEntry 23 }


avCmMeasToneRecTodayCCCPTRPkOffPN        OBJECT-TYPE
    SYNTAX      Integer32 (0..9999)
    MAX-ACCESS  read-only
    STATUS      current
    DESCRIPTION
        "
        Fld OID Name:   avCmMeasToneRecTodayCCCPTRPkOffPN
        Fld OID:        enterprises.6889.2.73.8.1.98.1.1.24
        Fld Form/Rpt:   TONE RECEIVER DETAIL MEASUREMENTS
        Fld Format:     Single Field
        Fld(s) Name:    CC-CPTR  Peak Off-PN
        Fld Descr:      An object containing the Peak number of CC-CPTR 
			receivers simultaneously allocated of a different PN 
			for requests originated on this PN
        "
    ::= { avCmMeasToneRecTodayEntry 24 }

avCmMeasToneRecTodayCCMFCRPnReq	OBJECT-TYPE
    SYNTAX	Integer32 (0..99999)
    MAX-ACCESS	read-only
    STATUS	current
    DESCRIPTION
	"
	Fld OID Name:	avCmMeasToneRecTodayCCMFCRPnReq
	Fld OID:	enterprises.6889.2.73.8.1.98.1.1.25
	Fld Form/Rpt:   TONE RECEIVER DETAIL MEASUREMENTS
	Fld Format:	Single Field
	Fld(s) Name:	CC-MFCR PN Req
	Fld Descr:	An object containing the number of CC-MFCR  requests 
			within the PN.
	"
    ::= { avCmMeasToneRecTodayEntry 25 }

avCmMeasToneRecTodayCCMFCRPnAlloc	OBJECT-TYPE
    SYNTAX	Integer32 (0..99999)
    MAX-ACCESS	read-only
    STATUS	current
    DESCRIPTION
	"
	Fld OID Name:	avCmMeasToneRecTodayCCMFCRPnAlloc
	Fld OID:	enterprises.6889.2.73.8.1.98.1.1.26
	Fld Form/Rpt:   TONE RECEIVER DETAIL MEASUREMENTS
	Fld Format:	Single Field
	Fld(s) Name:	CC-MFCR PN Alloc
	Fld Descr:	An object containing the total number of CC-MFCR 
			receivers located in the listed PN that were allocated 
			during the listed hour.
	"
    ::= { avCmMeasToneRecTodayEntry 26 }

avCmMeasToneRecTodayCCMFCRPkAlloc        OBJECT-TYPE
    SYNTAX      Integer32 (0..9999)
    MAX-ACCESS  read-only
    STATUS      current
    DESCRIPTION
        "
        Fld OID Name:   avCmMeasToneRecTodayCCMFCRPkAlloc
        Fld OID:        enterprises.6889.2.73.8.1.98.1.1.27
        Fld Form/Rpt:   TONE RECEIVER DETAIL MEASUREMENTS
        Fld Format:     Single Field
        Fld(s) Name:    CC-MFCR Peak Alloc
        Fld Descr:      An object containing the peak number of CC-MFCR
			receivers located in the listed PN that were in use 
			simulatneously.
        "
    ::= { avCmMeasToneRecTodayEntry 27 }

avCmMeasToneRecTodayCCMFCRTotOffPN        OBJECT-TYPE
    SYNTAX      Integer32 (0..9999)
    MAX-ACCESS  read-only
    STATUS      current
    DESCRIPTION
        "
        Fld OID Name:   avCmMeasToneRecTodayCCMFCRTotOffPN
        Fld OID:        enterprises.6889.2.73.8.1.98.1.1.28
        Fld Form/Rpt:   TONE RECEIVER DETAIL MEASUREMENTS
        Fld Format:     Single Field
        Fld(s) Name:    CC-MFCR Total Off-PN
        Fld Descr:      An object containing the total number of CC-MFCR 
			receivers allocated of a different PN for requests 
			originated on this PN
        "
    ::= { avCmMeasToneRecTodayEntry 28 }


avCmMeasToneRecTodayCCMFCRPkOffPN        OBJECT-TYPE
    SYNTAX      Integer32 (0..9999)
    MAX-ACCESS  read-only
    STATUS      current
    DESCRIPTION
        "
        Fld OID Name:   avCmMeasToneRecTodayCCMFCRPkOffPN
        Fld OID:        enterprises.6889.2.73.8.1.98.1.1.29
        Fld Form/Rpt:   TONE RECEIVER DETAIL MEASUREMENTS
        Fld Format:     Single Field
        Fld(s) Name:    CC-MFCR Peak Off-PN
        Fld Descr:      An object containing the Peak number of CC-MFCR 
			receivers simultaneously allocated of a different PN 
			for requests originated on this PN
        "
    ::= { avCmMeasToneRecTodayEntry 29 }

-- ******************** avCmMeasToneRecYest Group *************************

-- MIB GROUP DESCRIPTION

-- MIB Group Name:
--		avCmMeasToneRecYest Group
-- OID:
--		enterprises.6889.2.73.8.1.99
-- Description:
--		The avCmMeasToneRecYest MIB Group uses the "list measurements
--		tone-receiver detail yesterday" command to retrieve peak
--		hour tone-receiver data for yesterday.
--		
-- Releases Supported:
--		CM6.3.100 and greater
-- Polling Type:
--		Performance/Utilization
-- Polling Interval:
--		No more than once a daily because the data is only updated
--		at the beginning of the day after midnight.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements tone-receiver detail yesterday
-- Form/Report Name:
--		1. TONE RECEIVER DETAIL MEASUREMENTS
-- Reference Document:
--		1. A detailed description of the command and form can be
--		   found in document referenced by REF_DOC_4 in the
--		   DOCUMENT REFERENCE SECTION.
-- Command Permission/User-profile:
--		1. No special permissions needed.

avCmMeasToneRecYest	OBJECT IDENTIFIER ::= { avCmObjects 99 }

avCmMeasToneRecYestTable	OBJECT-TYPE
    SYNTAX	SEQUENCE OF AvCmMeasToneRecYestEntry
    MAX-ACCESS	not-accessible
    STATUS	current
    DESCRIPTION
	"
	Fld OID Name:	avCmMeasToneRecYestEntry
	Fld OID:	enterprises.6889.2.73.8.1.99.1
	Fld Form/Rpt:   TONE RECEIVER DETAIL MEASUREMENTS
	Fld Format:	NA
	Fld(s) Name:	NA
	Fld Descr:	A list of the avCmMeasToneRecYest entries
	"
    ::= { avCmMeasToneRecYest 1 }

avCmMeasToneRecYestEntry	OBJECT-TYPE
    SYNTAX	AvCmMeasToneRecYestEntry
    MAX-ACCESS	not-accessible
    STATUS	current
    DESCRIPTION
	"
	Fld OID Name:	avCmMeasToneRecYestEntry
	Fld OID:	enterprises.6889.2.73.8.1.99.1.1
	Fld Form/Rpt:   TONE RECEIVER DETAIL MEASUREMENTS
	Fld Format:	NA
	Fld(s) Name:	NA
	Fld Descr:	A avCmMeasToneRecYest entry containing objects of the
			avCmMeasToneRecYest information sent by the switch.
	"
    INDEX    { avCmMeasToneRecYestPnIdx }
    ::= { avCmMeasToneRecYestTable 1 }

AvCmMeasToneRecYestEntry ::= SEQUENCE {
		avCmMeasToneRecYestPnIdx
		    Integer32,
		avCmMeasToneRecYestPNNumber
		    Integer32,
		avCmMeasToneRecYestRunDate
		    SnmpAdminString,
		avCmMeasToneRecYestMeasHour
		    Integer32,
		avCmMeasToneRecYestDTMFPnReq
		    Integer32,
		avCmMeasToneRecYestDTMFPnAlloc
		    Integer32,
		avCmMeasToneRecYestDTMFPkAlloc 
		    Integer32,
		avCmMeasToneRecYestDTMFTotOffPN
		    Integer32,
		avCmMeasToneRecYestDTMFPkOffPN
		    Integer32,
		avCmMeasToneRecYestGPTDPnReq
		    Integer32,
		avCmMeasToneRecYestGPTDPnAlloc
		    Integer32,
		avCmMeasToneRecYestGPTDPkAlloc
		    Integer32,
		avCmMeasToneRecYestGPTDTotOffPN
		    Integer32,
		avCmMeasToneRecYestGPTDPkOffPN
		    Integer32,
		avCmMeasToneRecYestCCTTRPnReq
		    Integer32,
		avCmMeasToneRecYestCCTTRPnAlloc
		    Integer32,
		avCmMeasToneRecYestCCTRPkAlloc
		    Integer32,
		avCmMeasToneRecYestCCTTRTotOffPN
		    Integer32,
		avCmMeasToneRecYestCCTTRPkOffPN
		    Integer32,
		avCmMeasToneRecYestCCCPTRPnReq
		    Integer32,
		avCmMeasToneRecYestCCCPTRPnAlloc
		    Integer32,
		avCmMeasToneRecYestCCCPTRPkAlloc
		    Integer32,
		avCmMeasToneRecYestCCCPTRTotOffPN
		    Integer32,
		avCmMeasToneRecYestCCCPTRPkOffPN
		    Integer32,
		avCmMeasToneRecYestCCMFCRPnReq
		    Integer32,
		avCmMeasToneRecYestCCMFCRPnAlloc
		    Integer32,
		avCmMeasToneRecYestCCMFCRPkAlloc
		    Integer32,
		avCmMeasToneRecYestCCMFCRTotOffPN
		    Integer32,
		avCmMeasToneRecYestCCMFCRPkOffPN
		    Integer32
		}

avCmMeasToneRecYestPnIdx	OBJECT-TYPE
    SYNTAX	Integer32 (0..99)
    MAX-ACCESS	not-accessible
    STATUS	current
    DESCRIPTION
	"
	Fld OID Name:	avCmMeasToneRecYestPnIdx
	Fld OID:	enterprises.6889.2.73.8.1.99.1.1.1
	Fld Format:	NA
	Fld(s) Name:	NA
	Fld Descr:	An object that uniquely identifies each Increment of 
			data.
	"
    ::= { avCmMeasToneRecYestEntry 1 }

avCmMeasToneRecYestPNNumber	OBJECT-TYPE
    SYNTAX	Integer32 (0..99)
    MAX-ACCESS	read-only
    STATUS	current
    DESCRIPTION
	"
	Fld OID Name:	avCmMeasToneRecYestPNNumber
	Fld OID:	enterprises.6889.2.73.8.1.99.1.1.2
	Fld Form/Rpt:   TONE RECEIVER DETAIL MEASUREMENTS
	Fld Format:	Single Field
	Fld(s) Name:	PN
	Fld Descr:	An object containing the Port Network number in which 
			the tone receiver is located.
	"
    ::= { avCmMeasToneRecYestEntry 2 }

avCmMeasToneRecYestRunDate	OBJECT-TYPE
    SYNTAX	SnmpAdminString (SIZE (0..28))
    MAX-ACCESS	read-only
    STATUS	current
    DESCRIPTION
	"
	Fld OID Name:	avCmMeasToneRecYestRunDate
	Fld OID:	enterprises.6889.2.73.8.1.99.1.1.3
	Fld Form/Rpt:   TONE RECEIVER DETAIL MEASUREMENTS
	Fld Format:	Single Field
	Fld(s) Name:	Date
	Fld Descr:	An object containing the Date the command was executed.
	"
    ::= { avCmMeasToneRecYestEntry 3 }

avCmMeasToneRecYestMeasHour   OBJECT-TYPE
    SYNTAX	Integer32 (0..9999)
    MAX-ACCESS  read-only
    STATUS      current
    DESCRIPTION
        "
        Fld OID Name:   avCmMeasToneRecYestMeasHour
        Fld OID:        enterprises.6889.2.73.8.1.99.1.1.4
        Fld Form/Rpt:   TONE RECEIVER DETAIL MEASUREMENTS
        Fld Format:     Single Field
        Fld(s) Name:    Hour
        Fld Descr:      An object containing the Hour the measurement was taken.
        "
    ::= { avCmMeasToneRecYestEntry 4 }


avCmMeasToneRecYestDTMFPnReq	OBJECT-TYPE
    SYNTAX	Integer32 (0..99999)
    MAX-ACCESS	read-only
    STATUS	current
    DESCRIPTION
	"
	Fld OID Name:	avCmMeasToneRecYestDTMFPnReq
	Fld OID:	enterprises.6889.2.73.8.1.99.1.1.5
	Fld Form/Rpt:   TONE RECEIVER DETAIL MEASUREMENTS
	Fld Format:	Single Field
	Fld(s) Name:	DTMF PN Req
	Fld Descr:	An object containing the number of DTMF requests 
			within the PN.
	"
    ::= { avCmMeasToneRecYestEntry 5 }

avCmMeasToneRecYestDTMFPnAlloc	OBJECT-TYPE
    SYNTAX	Integer32 (0..99999)
    MAX-ACCESS	read-only
    STATUS	current
    DESCRIPTION
	"
	Fld OID Name:	avCmMeasToneRecYestDTMFPnAlloc
	Fld OID:	enterprises.6889.2.73.8.1.99.1.1.6
	Fld Form/Rpt:   TONE RECEIVER DETAIL MEASUREMENTS
	Fld Format:	Single Field
	Fld(s) Name:	DTMF PN Alloc
	Fld Descr:	An object containing the total number of DTMF receivers
			located in the listed PN that were allocated during 
			the listed hour.
	"
    ::= { avCmMeasToneRecYestEntry 6 }

avCmMeasToneRecYestDTMFPkAlloc	OBJECT-TYPE
    SYNTAX	Integer32 (0..9999)
    MAX-ACCESS	read-only
    STATUS	current
    DESCRIPTION
	"
	Fld OID Name:	avCmMeasToneRecYestDTMFPkAlloc
	Fld OID:	enterprises.6889.2.73.8.1.99.1.1.7
	Fld Form/Rpt:   TONE RECEIVER DETAIL MEASUREMENTS
	Fld Format:	Single Field
	Fld(s) Name:	DTMF Peak Alloc
	Fld Descr:	An object containing the peak number of DTMF receivers 
			located in the listed PN that were in use 
			simulatneously.
	"
    ::= { avCmMeasToneRecYestEntry 7 }

avCmMeasToneRecYestDTMFTotOffPN	OBJECT-TYPE
    SYNTAX	Integer32 (0..9999)
    MAX-ACCESS	read-only
    STATUS	current
    DESCRIPTION
	"
	Fld OID Name:	avCmMeasToneRecYestDTMFTotOffPN
	Fld OID:	enterprises.6889.2.73.8.1.99.1.1.8
	Fld Form/Rpt:   TONE RECEIVER DETAIL MEASUREMENTS
	Fld Format:	Single Field
	Fld(s) Name:	DTMF Total Off-PN
	Fld Descr:	An object containing the total number of DTMF 
			receivers allocated of a different PN for requests 
			originated on this PN.
	"
    ::= { avCmMeasToneRecYestEntry 8 }

avCmMeasToneRecYestDTMFPkOffPN	OBJECT-TYPE
    SYNTAX	Integer32 (0..9999)
    MAX-ACCESS	read-only
    STATUS	current
    DESCRIPTION
	"
	Fld OID Name:	avCmMeasToneRecYestDTMFPkOffPN
	Fld OID:	enterprises.6889.2.73.8.1.99.1.1.9
	Fld Form/Rpt:   TONE RECEIVER DETAIL MEASUREMENTS
	Fld Format:	Single Field
	Fld(s) Name:	Peak Off-PN
	Fld Descr:	An object containing the peak number of DTMF receivers 
			simultaneously allocated on a different PN for requests
			originated on this PN.
	"
    ::= { avCmMeasToneRecYestEntry 9 }

avCmMeasToneRecYestGPTDPnReq	OBJECT-TYPE
    SYNTAX	Integer32 (0..99999)
    MAX-ACCESS	read-only
    STATUS	current
    DESCRIPTION
	"
	Fld OID Name:	avCmMeasToneRecYestGPTDPnReq
	Fld OID:	enterprises.6889.2.73.8.1.99.1.1.10
	Fld Form/Rpt:   TONE RECEIVER DETAIL MEASUREMENTS
	Fld Format:	Single Field
	Fld(s) Name:	GPTD PN Req
	Fld Descr:	An object containing the number of GPTD requests within 
			the PN.
	"
    ::= { avCmMeasToneRecYestEntry 10 }

avCmMeasToneRecYestGPTDPnAlloc	OBJECT-TYPE
    SYNTAX	Integer32 (0..99999)
    MAX-ACCESS	read-only
    STATUS	current
    DESCRIPTION
	"
	Fld OID Name:	avCmMeasToneRecYestGPTDPnAlloc
	Fld OID:	enterprises.6889.2.73.8.1.99.1.1.11
	Fld Form/Rpt:   TONE RECEIVER DETAIL MEASUREMENTS
	Fld Format:	Single Field
	Fld(s) Name:	GPTD PN Alloc
	Fld Descr:	An object containing the total number of GPTD 
			receivers located in the listed PN that were allocated 
			during the listed hour.
	"
    ::= { avCmMeasToneRecYestEntry 11 }

avCmMeasToneRecYestGPTDPkAlloc	OBJECT-TYPE
    SYNTAX	Integer32 (0..9999)
    MAX-ACCESS	read-only
    STATUS	current
    DESCRIPTION
	"
	Fld OID Name:	avCmMeasToneRecYestGPTDPkAlloc
	Fld OID:	enterprises.6889.2.73.8.1.99.1.1.12
	Fld Form/Rpt:   TONE RECEIVER DETAIL MEASUREMENTS
	Fld Format:	Single Field
	Fld(s) Name:	GPTD PeaK Alloc
	Fld Descr:	An object containing the peak number of GPTD receivers 
			located in the listed PN that were in use 
			simulatneously.
	"
    ::= { avCmMeasToneRecYestEntry 12 }

avCmMeasToneRecYestGPTDTotOffPN	OBJECT-TYPE
    SYNTAX	Integer32 (0..9999)
    MAX-ACCESS	read-only
    STATUS	current
    DESCRIPTION
	"
	Fld OID Name:	avCmMeasToneRecYestGPTDTotOffPN
	Fld OID:	enterprises.6889.2.73.8.1.99.1.1.13
	Fld Form/Rpt:   TONE RECEIVER DETAIL MEASUREMENTS
	Fld Format:	Single Field
	Fld(s) Name:	GPTD Total  Off-PN
	Fld Descr:	An object containing the total number of GPTD 
			receivers allocated of a different PN for requests 
			originated on this PN.
	"
    ::= { avCmMeasToneRecYestEntry 13 }

avCmMeasToneRecYestGPTDPkOffPN	OBJECT-TYPE
    SYNTAX	Integer32 (0..9999)
    MAX-ACCESS	read-only
    STATUS	current
    DESCRIPTION
	"
	Fld OID Name:	avCmMeasToneRecYestGPTDPkOffPN
	Fld OID:	enterprises.6889.2.73.8.1.99.1.1.14
	Fld Form/Rpt:   TONE RECEIVER DETAIL MEASUREMENTS
	Fld Format:	Single Field
	Fld(s) Name:	GPTD Peak Off-PN
	Fld Descr:	An object containing the peak number of GPTD receivers 
			simultaneously allocated on a different PN for requests
			originated on this PN.
	"
    ::= { avCmMeasToneRecYestEntry 14 }

avCmMeasToneRecYestCCTTRPnReq	OBJECT-TYPE
    SYNTAX	Integer32 (0..99999)
    MAX-ACCESS	read-only
    STATUS	current
    DESCRIPTION
	"
	Fld OID Name:	avCmMeasToneRecYestCCTTRPnReq
	Fld OID:	enterprises.6889.2.73.8.1.99.1.1.15
	Fld Form/Rpt:   TONE RECEIVER DETAIL MEASUREMENTS
	Fld Format:	Single Field
	Fld(s) Name:	CC-TTR PN Req
	Fld Descr:	An object containing the number of CC-TTR requests 
			within the PN.
	"
    ::= { avCmMeasToneRecYestEntry 15 }

avCmMeasToneRecYestCCTTRPnAlloc	OBJECT-TYPE
    SYNTAX	Integer32 (0..99999)
    MAX-ACCESS	read-only
    STATUS	current
    DESCRIPTION
	"
	Fld OID Name:	avCmMeasToneRecYestCCTTRPnAlloc
	Fld OID:	enterprises.6889.2.73.8.1.99.1.1.16
	Fld Form/Rpt:   TONE RECEIVER DETAIL MEASUREMENTS
	Fld Format:	Single Field
	Fld(s) Name:	CC-TTR PN Alloc
	Fld Descr:	An object containing the total number of CC-TTR 
			receivers located in the listed PN that were allocated 
			during the listed hour.
	"
    ::= { avCmMeasToneRecYestEntry 16 }

avCmMeasToneRecYestCCTRPkAlloc        OBJECT-TYPE
    SYNTAX      Integer32 (0..9999)
    MAX-ACCESS  read-only
    STATUS      current
    DESCRIPTION
        "
        Fld OID Name:   avCmMeasToneRecYestCCTRPkAlloc
        Fld OID:        enterprises.6889.2.73.8.1.99.1.1.17
        Fld Form/Rpt:   TONE RECEIVER DETAIL MEASUREMENTS
        Fld Format:     Single Field
        Fld(s) Name:    CC-TTR  Peak Alloc
        Fld Descr:      An object containing the peak number of CC-TTR 
			receivers located in the listed PN that were in use 
			simulatneously.
        "
    ::= { avCmMeasToneRecYestEntry 17 }

avCmMeasToneRecYestCCTTRTotOffPN        OBJECT-TYPE
    SYNTAX      Integer32 (0..9999)
    MAX-ACCESS  read-only
    STATUS      current
    DESCRIPTION
        "
        Fld OID Name:   avCmMeasToneRecYestCCTTRTotOffPN
        Fld OID:        enterprises.6889.2.73.8.1.99.1.1.18
        Fld Form/Rpt:   TONE RECEIVER DETAIL MEASUREMENTS
        Fld Format:     Single Field
        Fld(s) Name:    CC-TTR  Total Off-PN
        Fld Descr:      An object containing the total number of CC-TTR 
			receivers allocated of a different PN for requests 
			originated on this PN
        "
    ::= { avCmMeasToneRecYestEntry 18 }


avCmMeasToneRecYestCCTTRPkOffPN        OBJECT-TYPE
    SYNTAX      Integer32 (0..9999)
    MAX-ACCESS  read-only
    STATUS      current
    DESCRIPTION
        "
        Fld OID Name:   avCmMeasToneRecYestCCTTRPkOffPN
        Fld OID:        enterprises.6889.2.73.8.1.99.1.1.19
        Fld Form/Rpt:   TONE RECEIVER DETAIL MEASUREMENTS
        Fld Format:     Single Field
        Fld(s) Name:    CC-TTR  Peak Off-PN
        Fld Descr:      An object containing the Peak number of CC-TTR 
			receivers simultaneously allocated of a different PN 
			for requests originated on this PN
        "
    ::= { avCmMeasToneRecYestEntry 19 }

avCmMeasToneRecYestCCCPTRPnReq	OBJECT-TYPE
    SYNTAX	Integer32 (0..99999)
    MAX-ACCESS	read-only
    STATUS	current
    DESCRIPTION
	"
	Fld OID Name:	avCmMeasToneRecYestCCCPTRPnReq
	Fld OID:	enterprises.6889.2.73.8.1.99.1.1.20
	Fld Form/Rpt:   TONE RECEIVER DETAIL MEASUREMENTS
	Fld Format:	Single Field
	Fld(s) Name:	CC-CPTR PN Req
	Fld Descr:	An object containing the number of CC-CPTR  requests 
			within the PN.
	"
    ::= { avCmMeasToneRecYestEntry 20 }

avCmMeasToneRecYestCCCPTRPnAlloc	OBJECT-TYPE
    SYNTAX	Integer32 (0..99999)
    MAX-ACCESS	read-only
    STATUS	current
    DESCRIPTION
	"
	Fld OID Name:	avCmMeasToneRecYestCCCPTRPnAlloc
	Fld OID:	enterprises.6889.2.73.8.1.99.1.1.21
	Fld Form/Rpt:   TONE RECEIVER DETAIL MEASUREMENTS
	Fld Format:	Single Field
	Fld(s) Name:	CC-CPTR PN Alloc
	Fld Descr:	An object containing the total number of CC-CPTR 
			receivers located in the listed PN that were allocated 
			during the listed hour.
	"
    ::= { avCmMeasToneRecYestEntry 21 }

avCmMeasToneRecYestCCCPTRPkAlloc        OBJECT-TYPE
    SYNTAX      Integer32 (0..9999)
    MAX-ACCESS  read-only
    STATUS      current
    DESCRIPTION
        "
        Fld OID Name:   avCmMeasToneRecYestCCCPTRPkAlloc
        Fld OID:        enterprises.6889.2.73.8.1.99.1.1.22
        Fld Form/Rpt:   TONE RECEIVER DETAIL MEASUREMENTS
        Fld Format:     Single Field
        Fld(s) Name:    CC-CPTR Peak Alloc
        Fld Descr:      An object containing the peak number of CC-CPTR
			receivers located in the listed PN that were in use 
			simulatneously.
        "
    ::= { avCmMeasToneRecYestEntry 22 }

avCmMeasToneRecYestCCCPTRTotOffPN        OBJECT-TYPE
    SYNTAX      Integer32 (0..9999)
    MAX-ACCESS  read-only
    STATUS      current
    DESCRIPTION
        "
        Fld OID Name:   avCmMeasToneRecYestCCCPTRTotOffPN
        Fld OID:        enterprises.6889.2.73.8.1.99.1.1.23
        Fld Form/Rpt:   TONE RECEIVER DETAIL MEASUREMENTS
        Fld Format:     Single Field
        Fld(s) Name:    CC-CPTR Total Off-PN
        Fld Descr:      An object containing the total number of CC-CPTR 
			receivers allocated of a different PN for requests 
			originated on this PN
        "
    ::= { avCmMeasToneRecYestEntry 23 }


avCmMeasToneRecYestCCCPTRPkOffPN        OBJECT-TYPE
    SYNTAX      Integer32 (0..9999)
    MAX-ACCESS  read-only
    STATUS      current
    DESCRIPTION
        "
        Fld OID Name:   avCmMeasToneRecYestCCCPTRPkOffPN
        Fld OID:        enterprises.6889.2.73.8.1.99.1.1.24
        Fld Form/Rpt:   TONE RECEIVER DETAIL MEASUREMENTS
        Fld Format:     Single Field
        Fld(s) Name:    CC-CPTR  Peak Off-PN
        Fld Descr:      An object containing the Peak number of CC-CPTR 
			receivers simultaneously allocated of a different PN 
			for requests originated on this PN
        "
    ::= { avCmMeasToneRecYestEntry 24 }

avCmMeasToneRecYestCCMFCRPnReq	OBJECT-TYPE
    SYNTAX	Integer32 (0..99999)
    MAX-ACCESS	read-only
    STATUS	current
    DESCRIPTION
	"
	Fld OID Name:	avCmMeasToneRecYestCCMFCRPnReq
	Fld OID:	enterprises.6889.2.73.8.1.99.1.1.25
	Fld Form/Rpt:   TONE RECEIVER DETAIL MEASUREMENTS
	Fld Format:	Single Field
	Fld(s) Name:	CC-MFCR PN Req
	Fld Descr:	An object containing the number of CC-MFCR  requests 
			within the PN.
	"
    ::= { avCmMeasToneRecYestEntry 25 }

avCmMeasToneRecYestCCMFCRPnAlloc	OBJECT-TYPE
    SYNTAX	Integer32 (0..99999)
    MAX-ACCESS	read-only
    STATUS	current
    DESCRIPTION
	"
	Fld OID Name:	avCmMeasToneRecYestCCMFCRPnAlloc
	Fld OID:	enterprises.6889.2.73.8.1.99.1.1.26
	Fld Form/Rpt:   TONE RECEIVER DETAIL MEASUREMENTS
	Fld Format:	Single Field
	Fld(s) Name:	CC-MFCR PN Alloc
	Fld Descr:	An object containing the total number of CC-MFCR 
			receivers located in the listed PN that were allocated 
			during the listed hour.
	"
    ::= { avCmMeasToneRecYestEntry 26 }

avCmMeasToneRecYestCCMFCRPkAlloc        OBJECT-TYPE
    SYNTAX      Integer32 (0..9999)
    MAX-ACCESS  read-only
    STATUS      current
    DESCRIPTION
        "
        Fld OID Name:   avCmMeasToneRecYestCCMFCRPkAlloc
        Fld OID:        enterprises.6889.2.73.8.1.99.1.1.27
        Fld Form/Rpt:   TONE RECEIVER DETAIL MEASUREMENTS
        Fld Format:     Single Field
        Fld(s) Name:    CC-MFCR Peak Alloc
        Fld Descr:      An object containing the peak number of CC-MFCR
			receivers located in the listed PN that were in use 
			simulatneously.
        "
    ::= { avCmMeasToneRecYestEntry 27 }

avCmMeasToneRecYestCCMFCRTotOffPN        OBJECT-TYPE
    SYNTAX      Integer32 (0..9999)
    MAX-ACCESS  read-only
    STATUS      current
    DESCRIPTION
        "
        Fld OID Name:   avCmMeasToneRecYestCCMFCRTotOffPN
        Fld OID:        enterprises.6889.2.73.8.1.99.1.1.28
        Fld Form/Rpt:   TONE RECEIVER DETAIL MEASUREMENTS
        Fld Format:     Single Field
        Fld(s) Name:    CC-MFCR Total Off-PN
        Fld Descr:      An object containing the total number of CC-MFCR 
			receivers allocated of a different PN for requests 
			originated on this PN
        "
    ::= { avCmMeasToneRecYestEntry 28 }


avCmMeasToneRecYestCCMFCRPkOffPN        OBJECT-TYPE
    SYNTAX      Integer32 (0..9999)
    MAX-ACCESS  read-only
    STATUS      current
    DESCRIPTION
        "
        Fld OID Name:   avCmMeasToneRecYestCCMFCRPkOffPN
        Fld OID:        enterprises.6889.2.73.8.1.99.1.1.29
        Fld Form/Rpt:   TONE RECEIVER DETAIL MEASUREMENTS
        Fld Format:     Single Field
        Fld(s) Name:    CC-MFCR Peak Off-PN
        Fld Descr:      An object containing the Peak number of CC-MFCR 
			receivers simultaneously allocated of a different PN 
			for requests originated on this PN
        "
    ::= { avCmMeasToneRecYestEntry 29 }

-- ******************** avCmMeasToneRecSumLstHr Group *************************

-- MIB GROUP DESCRIPTION

-- MIB Group Name:
--		avCmMeasToneRecSumLstHr Group
-- OID:
--		enterprises.6889.2.73.8.1.100
-- Description:
--		The avCmMeasToneRecSumLstHr MIB Group uses the 
--		"list measurements tone-receiver summary last-hour" command to 
--		retrieve tone-receiver data from the listed hour.
--		
-- Releases Supported:
--		CM6.3.100 and greater
-- Polling Type:
--		Performance/Utilization
-- Polling Interval:
--		No more than once an hour because the data is only updated
--		near the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements tone-receiver summary last-hour
-- Form/Report Name:
--		1. TONE RECEIVER SUMMARY MEASUREMENTS
-- Reference Document:
--		1. A detailed description of the command and form can be
--		   found in document referenced by REF_DOC_4 in the
--		   DOCUMENT REFERENCE SECTION.
-- Command Permission/User-profile:
--		1. No special permissions needed.

avCmMeasToneRecSumLstHr	OBJECT IDENTIFIER ::= { avCmObjects 100 }

avCmMeasToneRecSumLstHrRunDate	OBJECT-TYPE
    SYNTAX	SnmpAdminString (SIZE (0..28))
    MAX-ACCESS	read-only
    STATUS	current
    DESCRIPTION
	"
	Fld OID Name:	avCmMeasToneRecSumLstHrRunDate
	Fld OID:	enterprises.6889.2.73.8.1.100.1
	Fld Form/Rpt:   TONE RECEIVER SUMMARY MEASUREMENTS
	Fld Format:	Single Field
	Fld(s) Name:	Date
	Fld Descr:	An object containing the Date the command was executed.
	"
    ::= { avCmMeasToneRecSumLstHr 1 }


avCmMeasToneRecSumLstHrMeasHour   OBJECT-TYPE
    SYNTAX	Integer32 (0..9999)
    MAX-ACCESS  read-only
    STATUS      current
    DESCRIPTION
        "
        Fld OID Name:   avCmMeasToneRecSumLstHrMeasHour
        Fld OID:        enterprises.6889.2.73.8.1.100.2
        Fld Form/Rpt:   TONE RECEIVER SUMMARY MEASUREMENTS
        Fld Format:     Single Field
        Fld(s) Name:    Hour
        Fld Descr:      An object containing the Hour the measurement was taken.
        "
    ::= { avCmMeasToneRecSumLstHr 2 }


avCmMeasToneRecSumLstHrDTMFHour 	OBJECT-TYPE
    SYNTAX	Integer32 (0..9999)
    MAX-ACCESS	read-only
    STATUS	current
    DESCRIPTION
	"
	Fld OID Name:	avCmMeasToneRecSumLstHrDTMFHour
	Fld OID:	enterprises.6889.2.73.8.1.100.3
	Fld Form/Rpt:   TONE RECEIVER SUMMARY MEASUREMENTS
	Fld Format:	Single Field
	Fld(s) Name:	DTMF Hour
	Fld Descr:	An object containing the hour the measurement was
			taken.
	"
    ::= { avCmMeasToneRecSumLstHr 3 }

avCmMeasToneRecSumLstHrDTMFTReq	OBJECT-TYPE
    SYNTAX	Integer32 (0..999999)
    MAX-ACCESS	read-only
    STATUS	current
    DESCRIPTION
	"
	Fld OID Name:	avCmMeasToneRecSumLstHrDTMFTReq
	Fld OID:	enterprises.6889.2.73.8.1.100.4
	Fld Form/Rpt:   TONE RECEIVER SUMMARY MEASUREMENTS
	Fld Format:	Single Field
	Fld(s) Name:	DTMF Total Request
	Fld Descr:	An object containing the system-wide total number of 
			requests for tone receivers of this type for the 
			measurement interval.
	"
    ::= { avCmMeasToneRecSumLstHr 4 }

avCmMeasToneRecSumLstHrDTMFPReq   OBJECT-TYPE
    SYNTAX	Integer32 (0..99999)
    MAX-ACCESS	read-only
    STATUS	current
    DESCRIPTION
	"
	Fld OID Name:	avCmMeasToneRecSumLstHrDTMFPReq
	Fld OID:	enterprises.6889.2.73.8.1.100.5
	Fld Form/Rpt:   TONE RECEIVER SUMMARY MEASUREMENTS
	Fld Format:	Single Field
	Fld(s) Name:	DTMF Peak Request
	Fld Descr:	An object containing the system-wide peak number of 
			simultaneous requests for tone receivers of this type 
			that occurred at any one time over the measurement 
			interval.
	"
    ::= { avCmMeasToneRecSumLstHr 5 }

avCmMeasToneRecSumLstHrDTMFTQueued	OBJECT-TYPE
    SYNTAX	Integer32 (0..99999)
    MAX-ACCESS	read-only
    STATUS	current
    DESCRIPTION
	"
	Fld OID Name:	avCmMeasToneRecSumLstHrDTMFTQueued
	Fld OID:	enterprises.6889.2.73.8.1.100.6
	Fld Form/Rpt:   TONE RECEIVER SUMMARY MEASUREMENTS
	Fld Format:	Single Field
	Fld(s) Name:	DTMF Total Queued
	Fld Descr:	An object containing the system-wide total number of 
			requests queued for tone receivers of this type during 
			the measurement interval.
	"
    ::= { avCmMeasToneRecSumLstHr 6 }

avCmMeasToneRecSumLstHrDTMFPQueued	OBJECT-TYPE
    SYNTAX	Integer32 (0..99)
    MAX-ACCESS	read-only
    STATUS	current
    DESCRIPTION
	"
	Fld OID Name:	avCmMeasToneRecSumLstHrDTMFPQueued
	Fld OID:	enterprises.6889.2.73.8.1.100.7
	Fld Form/Rpt:   TONE RECEIVER SUMMARY MEASUREMENTS
	Fld Format:	Single Field
	Fld(s) Name:	DTMF Peak Queued
	Fld Descr:	An object containing the system-wide peak number of 
			requests queued at any one time during the measurement 
			hour for tone receivers of this type.
	"
    ::= { avCmMeasToneRecSumLstHr 7 }

avCmMeasToneRecSumLstHrDTMFTDenied	OBJECT-TYPE
    SYNTAX	Integer32 (0..9999)
    MAX-ACCESS	read-only
    STATUS	current
    DESCRIPTION
	"
	Fld OID Name:	avCmMeasToneRecSumLstHrDTMFTDenied
	Fld OID:	enterprises.6889.2.73.8.1.100.8
	Fld Form/Rpt:   TONE RECEIVER SUMMARY MEASUREMENTS
	Fld Format:	Single Field
	Fld(s) Name:	DTMF Total Denied
	Fld Descr:	An object containing the system-wide total number of 
			requests that were denied because no receivers of this 
			type were available during the measurement hour.
	"
    ::= { avCmMeasToneRecSumLstHr 8 }

avCmMeasToneRecSumLstHrDTMFPDenied	OBJECT-TYPE
    SYNTAX	Integer32 (0..9999)
    MAX-ACCESS	read-only
    STATUS	current
    DESCRIPTION
	"
	Fld OID Name:	avCmMeasToneRecSumLstHrDTMFPDenied
	Fld OID:	enterprises.6889.2.73.8.1.100.9
	Fld Form/Rpt:   TONE RECEIVER SUMMARY MEASUREMENTS
	Fld Format:	Single Field
	Fld(s) Name:	DTMF Peak Denied
	Fld Descr:	An object containing the system-wide peak number of 
			requests that were denied at any one time because no 
			receivers of this type were available during the 
			measurement hour.
	"
    ::= { avCmMeasToneRecSumLstHr 9 }

avCmMeasToneRecSumLstHrGPTDHour	OBJECT-TYPE
    SYNTAX	Integer32 (0..9999)
    MAX-ACCESS	read-only
    STATUS	current
    DESCRIPTION
	"
	Fld OID Name:	avCmMeasToneRecSumLstHrGPTDHour
	Fld OID:	enterprises.6889.2.73.8.1.100.10
	Fld Form/Rpt:   TONE RECEIVER SUMMARY MEASUREMENTS
	Fld Format:	Single Field
	Fld(s) Name:	GPTD Hour
	Fld Descr:	An object containing the Hour the measurement was 
			taken.
	"
    ::= { avCmMeasToneRecSumLstHr 10 }

avCmMeasToneRecSumLstHrGPTDTReq		OBJECT-TYPE
    SYNTAX	Integer32 (0..999999)
    MAX-ACCESS	read-only
    STATUS	current
    DESCRIPTION
	"
	Fld OID Name:	avCmMeasToneRecSumLstHrGPTDTReq
	Fld OID:	enterprises.6889.2.73.8.1.100.11
	Fld Form/Rpt:   TONE RECEIVER SUMMARY MEASUREMENTS
	Fld Format:	Single Field
	Fld(s) Name:	GPTD Total Req
	Fld Descr:	An object containing the system-wide total number of 
			requests for tone receivers of this type for the 
			measurement interval.
	"
    ::= { avCmMeasToneRecSumLstHr 11 }

avCmMeasToneRecSumLstHrGPTDPReq 	OBJECT-TYPE
    SYNTAX	Integer32 (0..999999)
    MAX-ACCESS	read-only
    STATUS	current
    DESCRIPTION
	"
	Fld OID Name:	avCmMeasToneRecSumLstHrGPTDPReq
	Fld OID:	enterprises.6889.2.73.8.1.100.12
	Fld Form/Rpt:   TONE RECEIVER SUMMARY MEASUREMENTS
	Fld Format:	Single Field
	Fld(s) Name:	GPTD Peak Req
	Fld Descr:	An object containing the system-wide peak number of 
			simultaneous requests for tone receivers of this type 
			that occurred at any one time over the measurement 
			interval.
	"
    ::= { avCmMeasToneRecSumLstHr 12 }

avCmMeasToneRecSumLstHrGPTDTDenied	OBJECT-TYPE
    SYNTAX	Integer32 (0..9999)
    MAX-ACCESS	read-only
    STATUS	current
    DESCRIPTION
	"
	Fld OID Name:	avCmMeasToneRecSumLstHrGPTDTDenied
	Fld OID:	enterprises.6889.2.73.8.1.100.13
	Fld Form/Rpt:   TONE RECEIVER SUMMARY MEASUREMENTS
	Fld Format:	Single Field
	Fld(s) Name:	GPTD Total Denied
	Fld Descr:	An object containing the system-wide total number of 
			requests that were denied because no receivers of this 
			type were available during the measurement hour.
	"
    ::= { avCmMeasToneRecSumLstHr 13 }

avCmMeasToneRecSumLstHrGPTDPDenied	OBJECT-TYPE
    SYNTAX	Integer32 (0..9999)
    MAX-ACCESS	read-only
    STATUS	current
    DESCRIPTION
	"
	Fld OID Name:	avCmMeasToneRecSumLstHrGPTDPDenied
	Fld OID:	enterprises.6889.2.73.8.1.100.14
	Fld Form/Rpt:   TONE RECEIVER SUMMARY MEASUREMENTS
	Fld Format:	Single Field
	Fld(s) Name:	GPTD Peak Denied
	Fld Descr:      An object containing the system-wide peak number of 
			requests that were denied at any one time because no 
			receivers of this type were available during the 
			measurement hour.	
	"
    ::= { avCmMeasToneRecSumLstHr 14 }

avCmMeasToneRecSumLstHrCCTTRHour        OBJECT-TYPE
    SYNTAX      Integer32 (0..9999)
    MAX-ACCESS  read-only
    STATUS      current
    DESCRIPTION
        "
        Fld OID Name:   avCmMeasToneRecSumLstHrCCTTRHour
        Fld OID:        enterprises.6889.2.73.8.1.100.15
        Fld Form/Rpt:   TONE RECEIVER SUMMARY MEASUREMENTS
        Fld Format:     Single Field
        Fld(s) Name:    CC-TTR Hour 
        Fld Descr: 	An object containing the Hour the measurement was 
			taken.     
        "
    ::= { avCmMeasToneRecSumLstHr 15 }

avCmMeasToneRecSumLstHrCCTTRTReq         OBJECT-TYPE
    SYNTAX      Integer32 (0..999999)
    MAX-ACCESS  read-only
    STATUS      current
    DESCRIPTION
        "
        Fld OID Name:   avCmMeasToneRecSumLstHrCCTTRTReq 
        Fld OID:        enterprises.6889.2.73.8.1.100.16
        Fld Form/Rpt:   TONE RECEIVER SUMMARY MEASUREMENTS
        Fld Format:     Single Field
        Fld(s) Name:    CC-TTR  Total Req
        Fld Descr:      An object containing the system-wide total number of 
			requests for tone receivers of this type for the 
			measurement interval.
        "
    ::= { avCmMeasToneRecSumLstHr 16 }


avCmMeasToneRecSumLstHrCCTTRPReq        OBJECT-TYPE
    SYNTAX      Integer32 (0..99999)
    MAX-ACCESS  read-only
    STATUS      current
    DESCRIPTION
        "
        Fld OID Name:   avCmMeasToneRecSumLstHrCCTTRPReq 
        Fld OID:        enterprises.6889.2.73.8.1.100.17
        Fld Form/Rpt:   TONE RECEIVER SUMMARY MEASUREMENTS
        Fld Format:     Single Field
        Fld(s) Name:    CC-TTR  Peak Req
        Fld Descr:      An object containing the system-wide peak number of 
			simultaneous requests for tone receivers of this type 
			that occurred at any one time over the measurement 
			interval.
        "
    ::= { avCmMeasToneRecSumLstHr 17 }

avCmMeasToneRecSumLstHrCCTTRTQueued	OBJECT-TYPE
    SYNTAX	Integer32 (0..99999)
    MAX-ACCESS	read-only
    STATUS	current
    DESCRIPTION
	"
	Fld OID Name:	avCmMeasToneRecSumLstHrCCTTRTQueued
	Fld OID:	enterprises.6889.2.73.8.1.100.18
	Fld Form/Rpt:   TONE RECEIVER SUMMARY MEASUREMENTS
	Fld Format:	Single Field
	Fld(s) Name:	CC-TTR Total Queued
	Fld Descr:	An object containing the system-wide total number of 
			requests queued for tone receivers of this type during 
			the measurement interval.
	"
    ::= { avCmMeasToneRecSumLstHr 18 }

avCmMeasToneRecSumLstHrCCTTRPQueued	OBJECT-TYPE
    SYNTAX	Integer32 (0..99)
    MAX-ACCESS	read-only
    STATUS	current
    DESCRIPTION
	"
	Fld OID Name:	avCmMeasToneRecSumLstHrCCTTRPQueued
	Fld OID:	enterprises.6889.2.73.8.1.100.19
	Fld Form/Rpt:   TONE RECEIVER SUMMARY MEASUREMENTS
	Fld Format:	Single Field
	Fld(s) Name:	CC-TTR Peak Queued
	Fld Descr:	An object containing the system-wide peak number of 
			requests queued at any one time during the measurement 
			hour for tone receivers of this type.
	"
    ::= { avCmMeasToneRecSumLstHr 19 }

avCmMeasToneRecSumLstHrCCTTRTDenied	OBJECT-TYPE
    SYNTAX      Integer32 (0..9999)
    MAX-ACCESS  read-only
    STATUS      current
    DESCRIPTION
        "
        Fld OID Name:   avCmMeasToneRecSumLstHrCCTTRTDenied
        Fld OID:        enterprises.6889.2.73.8.1.100.20
        Fld Form/Rpt:   TONE RECEIVER SUMMARY MEASUREMENTS
        Fld Format:     Single Field
        Fld(s) Name:    CC-TTR Total Denied
        Fld Descr:      An object containing the system-wide total number of 
			requests that were denied because no receivers of this 
			type were available during the measurement hour. 
        "
    ::= { avCmMeasToneRecSumLstHr 20 }

avCmMeasToneRecSumLstHrCCTTRPDenied        OBJECT-TYPE
    SYNTAX      Integer32 (0..9999)
    MAX-ACCESS  read-only
    STATUS      current
    DESCRIPTION
        "
        Fld OID Name:   avCmMeasToneRecSumLstHrCCTTRPDenied
        Fld OID:        enterprises.6889.2.73.8.1.100.21
        Fld Form/Rpt:   TONE RECEIVER SUMMARY MEASUREMENTS
        Fld Format:     Single Field
        Fld(s) Name:    CC-TTR Peak Denied
        Fld Descr:      An object containing the system-wide peak number of 
			requests that were denied at any one time because no 
			receivers of this type were available during the 
			measurement hour.
        "
    ::= { avCmMeasToneRecSumLstHr 21 }


avCmMeasToneRecSumLstHrCCCPTRHour        OBJECT-TYPE
    SYNTAX      Integer32 (0..9999)
    MAX-ACCESS  read-only
    STATUS      current
    DESCRIPTION
        "
        Fld OID Name:   avCmMeasToneRecSumLstHrCCCPTRHour
        Fld OID:        enterprises.6889.2.73.8.1.100.22
        Fld Form/Rpt:   TONE RECEIVER SUMMARY MEASUREMENTS
        Fld Format:     Single Field
        Fld(s) Name:    CC-CPTR Hour 
        Fld Descr: 	An object containing the Hour the measurement was 
			taken.     
        "
    ::= { avCmMeasToneRecSumLstHr 22 }

avCmMeasToneRecSumLstHrCCCPTRTReq         OBJECT-TYPE
    SYNTAX      Integer32 (0..999999)
    MAX-ACCESS  read-only
    STATUS      current
    DESCRIPTION
        "
        Fld OID Name:   avCmMeasToneRecSumLstHrCCCPTRTReq 
        Fld OID:        enterprises.6889.2.73.8.1.100.23
        Fld Form/Rpt:   TONE RECEIVER SUMMARY MEASUREMENTS
        Fld Format:     Single Field
        Fld(s) Name:    CC-CPTR  Total Req
        Fld Descr:      An object containing the system-wide total number of 
			requests for tone receivers of this type for the 
			measurement interval.
        "
    ::= { avCmMeasToneRecSumLstHr 23 }


avCmMeasToneRecSumLstHrCCCPTRPReq        OBJECT-TYPE
    SYNTAX      Integer32 (0..99999)
    MAX-ACCESS  read-only
    STATUS      current
    DESCRIPTION
        "
        Fld OID Name:   avCmMeasToneRecSumLstHrCCCPTRPReq 
        Fld OID:        enterprises.6889.2.73.8.1.100.24
        Fld Form/Rpt:   TONE RECEIVER SUMMARY MEASUREMENTS
        Fld Format:     Single Field
        Fld(s) Name:    CC-CPTR  Peak Req
        Fld Descr:      An object containing the system-wide peak number of 
			simultaneous requests for tone receivers of this type 
			that occurred at any one time over the measurement 
			interval.
        "
    ::= { avCmMeasToneRecSumLstHr 24 }

avCmMeasToneRecSumLstHrCCCPTRTDenied	OBJECT-TYPE
    SYNTAX      Integer32 (0..9999)
    MAX-ACCESS  read-only
    STATUS      current
    DESCRIPTION
        "
        Fld OID Name:   avCmMeasToneRecSumLstHrCCCPTRTDenied
        Fld OID:        enterprises.6889.2.73.8.1.100.25
        Fld Form/Rpt:   TONE RECEIVER SUMMARY MEASUREMENTS
        Fld Format:     Single Field
        Fld(s) Name:    CC-CPTR Total Denied
        Fld Descr:      An object containing the system-wide total number of 
			requests that were denied because no receivers of this 
			type were available during the measurement hour. 
        "
    ::= { avCmMeasToneRecSumLstHr 25 }

avCmMeasToneRecSumLstHrCCCPTRPDenied        OBJECT-TYPE
    SYNTAX      Integer32 (0..9999)
    MAX-ACCESS  read-only
    STATUS      current
    DESCRIPTION
        "
        Fld OID Name:   avCmMeasToneRecSumLstHrCCCPTRPDenied
        Fld OID:        enterprises.6889.2.73.8.1.100.26
        Fld Form/Rpt:   TONE RECEIVER SUMMARY MEASUREMENTS
        Fld Format:     Single Field
        Fld(s) Name:    CC-CPTR Peak Denied
        Fld Descr:      An object containing the system-wide peak number of 
			requests that were denied at any one time because no 
			receivers of this type were available during the 
			measurement hour.
        "
    ::= { avCmMeasToneRecSumLstHr 26 }


avCmMeasToneRecSumLstHrCCMFCRHour        OBJECT-TYPE
    SYNTAX      Integer32 (0..9999)
    MAX-ACCESS  read-only
    STATUS      current
    DESCRIPTION
        "
        Fld OID Name:   avCmMeasToneRecSumLstHrCCMFCRHour
        Fld OID:        enterprises.6889.2.73.8.1.100.27
        Fld Form/Rpt:   TONE RECEIVER SUMMARY MEASUREMENTS
        Fld Format:     Single Field
        Fld(s) Name:    CC-MFCR Hour 
        Fld Descr: 	An object containing the Hour the measurement was 
			taken.     
        "
    ::= { avCmMeasToneRecSumLstHr 27 }

avCmMeasToneRecSumLstHrCCMFCRTReq         OBJECT-TYPE
    SYNTAX      Integer32 (0..999999)
    MAX-ACCESS  read-only
    STATUS      current
    DESCRIPTION
        "
        Fld OID Name:   avCmMeasToneRecSumLstHrCCMFCRTReq 
        Fld OID:        enterprises.6889.2.73.8.1.100.28
        Fld Form/Rpt:   TONE RECEIVER SUMMARY MEASUREMENTS
        Fld Format:     Single Field
        Fld(s) Name:    CC-MFCR  Total Req
        Fld Descr:      An object containing the system-wide total number of 
			requests for tone receivers of this type for the 
			measurement interval.
        "
    ::= { avCmMeasToneRecSumLstHr 28 }


avCmMeasToneRecSumLstHrCCMFCRPReq        OBJECT-TYPE
    SYNTAX      Integer32 (0..99999)
    MAX-ACCESS  read-only
    STATUS      current
    DESCRIPTION
        "
        Fld OID Name:   avCmMeasToneRecSumLstHrCCMFCRPReq 
        Fld OID:        enterprises.6889.2.73.8.1.100.29
        Fld Form/Rpt:   TONE RECEIVER SUMMARY MEASUREMENTS
        Fld Format:     Single Field
        Fld(s) Name:    CC-MFCR  Peak Req
        Fld Descr:      An object containing the system-wide peak number of 
			simultaneous requests for tone receivers of this type 
			that occurred at any one time over the measurement 
			interval.
        "
    ::= { avCmMeasToneRecSumLstHr 29 }

avCmMeasToneRecSumLstHrCCMFCRTDenied	OBJECT-TYPE
    SYNTAX      Integer32 (0..9999)
    MAX-ACCESS  read-only
    STATUS      current
    DESCRIPTION
        "
        Fld OID Name:   avCmMeasToneRecSumLstHrCCMFCRTDenied
        Fld OID:        enterprises.6889.2.73.8.1.100.30
        Fld Form/Rpt:   TONE RECEIVER SUMMARY MEASUREMENTS
        Fld Format:     Single Field
        Fld(s) Name:    CC-MFCR Total Denied
        Fld Descr:      An object containing the system-wide total number of 
			requests that were denied because no receivers of this 
			type were available during the measurement hour. 
        "
    ::= { avCmMeasToneRecSumLstHr 30 }

avCmMeasToneRecSumLstHrCCMFCRPDenied        OBJECT-TYPE
    SYNTAX      Integer32 (0..9999)
    MAX-ACCESS  read-only
    STATUS      current
    DESCRIPTION
        "
        Fld OID Name:   avCmMeasToneRecSumLstHrCCMFCRPDenied
        Fld OID:        enterprises.6889.2.73.8.1.100.31
        Fld Form/Rpt:   TONE RECEIVER SUMMARY MEASUREMENTS
        Fld Format:     Single Field
        Fld(s) Name:    CC-MFCR Peak Denied
        Fld Descr:      An object containing the system-wide peak number of 
			requests that were denied at any one time because no 
			receivers of this type were available during the 
			measurement hour.
        "
    ::= { avCmMeasToneRecSumLstHr 31 }

avCmMeasToneRecSumLstHrDTMRPTTAvail        OBJECT-TYPE
    SYNTAX      Integer32 (0..999)
    MAX-ACCESS  read-only
    STATUS      current
    DESCRIPTION
        "
        Fld OID Name:   avCmMeasToneRecSumLstHrDTMRPTTAvail
        Fld OID:        enterprises.6889.2.73.8.1.100.32
        Fld Form/Rpt:   TONE RECEIVER SUMMARY MEASUREMENTS
        Fld Format:     Single Field
        Fld(s) Name:    DTMR-PT Total Avail
        Fld Descr:      An object containing the number of ports available for 
			the type of tone receiver. 
        "
    ::= { avCmMeasToneRecSumLstHr 32 }

avCmMeasToneRecSumLstHrGPTDPTTAvail        OBJECT-TYPE
    SYNTAX      Integer32 (0..999)
    MAX-ACCESS  read-only
    STATUS      current
    DESCRIPTION
        "
        Fld OID Name:   avCmMeasToneRecSumLstHrGPTDPTTAvail
        Fld OID:        enterprises.6889.2.73.8.1.100.33
        Fld Form/Rpt:   TONE RECEIVER SUMMARY MEASUREMENTS
        Fld Format:     Single Field
        Fld(s) Name:    GPTD-PT Total Avail
        Fld Descr:      An object containing the number of ports available for
                        the type of tone receiver.
        "
    ::= { avCmMeasToneRecSumLstHr 33 }


avCmMeasToneRecSumLstHrCLASPTTAvail        OBJECT-TYPE
    SYNTAX      Integer32 (0..999)
    MAX-ACCESS  read-only
    STATUS      current
    DESCRIPTION
        "
        Fld OID Name:   avCmMeasToneRecSumLstHrCLASPTTAvail
        Fld OID:        enterprises.6889.2.73.8.1.100.34
        Fld Form/Rpt:   TONE RECEIVER SUMMARY MEASUREMENTS
        Fld Format:     Single Field
        Fld(s) Name:    CLAS-PT Total Avail
        Fld Descr:      An object containing the number of ports available for
                        the type of tone receiver.
        "
    ::= { avCmMeasToneRecSumLstHr 34 }

avCmMeasToneRecSumLstHrETRPTTAvail        OBJECT-TYPE
    SYNTAX      Integer32 (0..999)
    MAX-ACCESS  read-only
    STATUS      current
    DESCRIPTION
        "
        Fld OID Name:   avCmMeasToneRecSumLstHrETRPTTAvail
        Fld OID:        enterprises.6889.2.73.8.1.100.35
        Fld Form/Rpt:   TONE RECEIVER SUMMARY MEASUREMENTS
        Fld Format:     Single Field
        Fld(s) Name:    ETR-PT Total Avail
        Fld Descr:      An object containing the number of ports available for
                        the type of tone receiver.
        "
    ::= { avCmMeasToneRecSumLstHr 35 }

-- ******************** avCmMeasToneRecSumToday Group *************************

-- MIB GROUP DESCRIPTION

-- MIB Group Name:
--		avCmMeasToneRecSumToday Group
-- OID:
--		enterprises.6889.2.73.8.1.101
-- Description:
--		The avCmMeasToneRecSumToday MIB Group uses the 
--		"list measurements tone-receiver summary today" command to 
--		retrieve tone-receiver data from the listed hour.
--		
-- Releases Supported:
--		CM6.3.100 and greater
-- Polling Type:
--		Performance/Utilization
-- Polling Interval:
--		No more than once an hour because the data is only updated
--		near the beginning of the hour.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements tone-receiver summary today
-- Form/Report Name:
--		1. TONE RECEIVER SUMMARY MEASUREMENTS
-- Reference Document:
--		1. A detailed description of the command and form can be
--		   found in document referenced by REF_DOC_4 in the
--		   DOCUMENT REFERENCE SECTION.
-- Command Permission/User-profile:
--		1. No special permissions needed.

avCmMeasToneRecSumToday	OBJECT IDENTIFIER ::= { avCmObjects 101 }

avCmMeasToneRecSumTodayRunDate	OBJECT-TYPE
    SYNTAX	SnmpAdminString (SIZE (0..28))
    MAX-ACCESS	read-only
    STATUS	current
    DESCRIPTION
	"
	Fld OID Name:	avCmMeasToneRecSumTodayRunDate
	Fld OID:	enterprises.6889.2.73.8.1.101.1
	Fld Form/Rpt:   TONE RECEIVER SUMMARY MEASUREMENTS
	Fld Format:	Single Field
	Fld(s) Name:	Date
	Fld Descr:	An object containing the Date the command was executed.
	"
    ::= { avCmMeasToneRecSumToday 1 }


avCmMeasToneRecSumTodayMeasHour   OBJECT-TYPE
    SYNTAX	Integer32 (0..9999)
    MAX-ACCESS  read-only
    STATUS      current
    DESCRIPTION
        "
        Fld OID Name:   avCmMeasToneRecSumTodayMeasHour
        Fld OID:        enterprises.6889.2.73.8.1.101.2
        Fld Form/Rpt:   TONE RECEIVER SUMMARY MEASUREMENTS
        Fld Format:     Single Field
        Fld(s) Name:    Hour
        Fld Descr:      An object containing the Hour the measurement was taken.
        "
    ::= { avCmMeasToneRecSumToday 2 }


avCmMeasToneRecSumTodayDTMFHour 	OBJECT-TYPE
    SYNTAX	Integer32 (0..9999)
    MAX-ACCESS	read-only
    STATUS	current
    DESCRIPTION
	"
	Fld OID Name:	avCmMeasToneRecSumTodayDTMFHour
	Fld OID:	enterprises.6889.2.73.8.1.101.3
	Fld Form/Rpt:   TONE RECEIVER SUMMARY MEASUREMENTS
	Fld Format:	Single Field
	Fld(s) Name:	DTMF Hour
	Fld Descr:	An object containing the hour the measurement was
			taken.
	"
    ::= { avCmMeasToneRecSumToday 3 }

avCmMeasToneRecSumTodayDTMFTReq	OBJECT-TYPE
    SYNTAX	Integer32 (0..999999)
    MAX-ACCESS	read-only
    STATUS	current
    DESCRIPTION
	"
	Fld OID Name:	avCmMeasToneRecSumTodayDTMFTReq
	Fld OID:	enterprises.6889.2.73.8.1.101.4
	Fld Form/Rpt:   TONE RECEIVER SUMMARY MEASUREMENTS
	Fld Format:	Single Field
	Fld(s) Name:	DTMF Total Request
	Fld Descr:	An object containing the system-wide total number of 
			requests for tone receivers of this type for the 
			measurement interval.
	"
    ::= { avCmMeasToneRecSumToday 4 }

avCmMeasToneRecSumTodayDTMFPReq   OBJECT-TYPE
    SYNTAX	Integer32 (0..99999)
    MAX-ACCESS	read-only
    STATUS	current
    DESCRIPTION
	"
	Fld OID Name:	avCmMeasToneRecSumTodayDTMFPReq
	Fld OID:	enterprises.6889.2.73.8.1.101.5
	Fld Form/Rpt:   TONE RECEIVER SUMMARY MEASUREMENTS
	Fld Format:	Single Field
	Fld(s) Name:	DTMF Peak Request
	Fld Descr:	An object containing the system-wide peak number of 
			simultaneous requests for tone receivers of this type 
			that occurred at any one time over the measurement 
			interval.
	"
    ::= { avCmMeasToneRecSumToday 5 }

avCmMeasToneRecSumTodayDTMFTQueued	OBJECT-TYPE
    SYNTAX	Integer32 (0..99999)
    MAX-ACCESS	read-only
    STATUS	current
    DESCRIPTION
	"
	Fld OID Name:	avCmMeasToneRecSumTodayDTMFTQueued
	Fld OID:	enterprises.6889.2.73.8.1.101.6
	Fld Form/Rpt:   TONE RECEIVER SUMMARY MEASUREMENTS
	Fld Format:	Single Field
	Fld(s) Name:	DTMF Total Queued
	Fld Descr:	An object containing the system-wide total number of 
			requests queued for tone receivers of this type during 
			the measurement interval.
	"
    ::= { avCmMeasToneRecSumToday 6 }

avCmMeasToneRecSumTodayDTMFPQueued	OBJECT-TYPE
    SYNTAX	Integer32 (0..99)
    MAX-ACCESS	read-only
    STATUS	current
    DESCRIPTION
	"
	Fld OID Name:	avCmMeasToneRecSumTodayDTMFPQueued
	Fld OID:	enterprises.6889.2.73.8.1.101.7
	Fld Form/Rpt:   TONE RECEIVER SUMMARY MEASUREMENTS
	Fld Format:	Single Field
	Fld(s) Name:	DTMF Peak Queued
	Fld Descr:	An object containing the system-wide peak number of 
			requests queued at any one time during the measurement 
			hour for tone receivers of this type.
	"
    ::= { avCmMeasToneRecSumToday 7 }

avCmMeasToneRecSumTodayDTMFTDenied	OBJECT-TYPE
    SYNTAX	Integer32 (0..9999)
    MAX-ACCESS	read-only
    STATUS	current
    DESCRIPTION
	"
	Fld OID Name:	avCmMeasToneRecSumTodayDTMFTDenied
	Fld OID:	enterprises.6889.2.73.8.1.101.8
	Fld Form/Rpt:   TONE RECEIVER SUMMARY MEASUREMENTS
	Fld Format:	Single Field
	Fld(s) Name:	DTMF Total Denied
	Fld Descr:	An object containing the system-wide total number of 
			requests that were denied because no receivers of this 
			type were available during the measurement hour.
	"
    ::= { avCmMeasToneRecSumToday 8 }

avCmMeasToneRecSumTodayDTMFPDenied	OBJECT-TYPE
    SYNTAX	Integer32 (0..9999)
    MAX-ACCESS	read-only
    STATUS	current
    DESCRIPTION
	"
	Fld OID Name:	avCmMeasToneRecSumTodayDTMFPDenied
	Fld OID:	enterprises.6889.2.73.8.1.101.9
	Fld Form/Rpt:   TONE RECEIVER SUMMARY MEASUREMENTS
	Fld Format:	Single Field
	Fld(s) Name:	DTMF Peak Denied
	Fld Descr:	An object containing the system-wide peak number of 
			requests that were denied at any one time because no 
			receivers of this type were available during the 
			measurement hour.
	"
    ::= { avCmMeasToneRecSumToday 9 }

avCmMeasToneRecSumTodayGPTDHour	OBJECT-TYPE
    SYNTAX	Integer32 (0..9999)
    MAX-ACCESS	read-only
    STATUS	current
    DESCRIPTION
	"
	Fld OID Name:	avCmMeasToneRecSumTodayGPTDHour
	Fld OID:	enterprises.6889.2.73.8.1.101.10
	Fld Form/Rpt:   TONE RECEIVER SUMMARY MEASUREMENTS
	Fld Format:	Single Field
	Fld(s) Name:	GPTD Hour
	Fld Descr:	An object containing the Hour the measurement was 
			taken.
	"
    ::= { avCmMeasToneRecSumToday 10 }

avCmMeasToneRecSumTodayGPTDTReq	OBJECT-TYPE
    SYNTAX	Integer32 (0..999999)
    MAX-ACCESS	read-only
    STATUS	current
    DESCRIPTION
	"
	Fld OID Name:	avCmMeasToneRecSumTodayGPTDTReq
	Fld OID:	enterprises.6889.2.73.8.1.101.11
	Fld Form/Rpt:   TONE RECEIVER SUMMARY MEASUREMENTS
	Fld Format:	Single Field
	Fld(s) Name:	GPTD Total Req
	Fld Descr:	An object containing the system-wide total number of 
			requests for tone receivers of this type for the 
			measurement interval.
	"
    ::= { avCmMeasToneRecSumToday 11 }

avCmMeasToneRecSumTodayGPTDPReq 	OBJECT-TYPE
    SYNTAX	Integer32 (0..999999)
    MAX-ACCESS	read-only
    STATUS	current
    DESCRIPTION
	"
	Fld OID Name:	avCmMeasToneRecSumTodayGPTDPReq
	Fld OID:	enterprises.6889.2.73.8.1.101.12
	Fld Form/Rpt:   TONE RECEIVER SUMMARY MEASUREMENTS
	Fld Format:	Single Field
	Fld(s) Name:	GPTD Peak Req
	Fld Descr:	An object containing the system-wide peak number of 
			simultaneous requests for tone receivers of this type 
			that occurred at any one time over the measurement 
			interval.
	"
    ::= { avCmMeasToneRecSumToday 12 }

avCmMeasToneRecSumTodayGPTDTDenied	OBJECT-TYPE
    SYNTAX	Integer32 (0..9999)
    MAX-ACCESS	read-only
    STATUS	current
    DESCRIPTION
	"
	Fld OID Name:	avCmMeasToneRecSumTodayGPTDTDenied
	Fld OID:	enterprises.6889.2.73.8.1.101.13
	Fld Form/Rpt:   TONE RECEIVER SUMMARY MEASUREMENTS
	Fld Format:	Single Field
	Fld(s) Name:	GPTD Total Denied
	Fld Descr:	An object containing the system-wide total number of 
			requests that were denied because no receivers of this 
			type were available during the measurement hour.
	"
    ::= { avCmMeasToneRecSumToday 13 }

avCmMeasToneRecSumTodayGPTDPDenied	OBJECT-TYPE
    SYNTAX	Integer32 (0..9999)
    MAX-ACCESS	read-only
    STATUS	current
    DESCRIPTION
	"
	Fld OID Name:	avCmMeasToneRecSumTodayGPTDPDenied
	Fld OID:	enterprises.6889.2.73.8.1.101.14
	Fld Form/Rpt:   TONE RECEIVER SUMMARY MEASUREMENTS
	Fld Format:	Single Field
	Fld(s) Name:	GPTD Peak Denied
	Fld Descr:      An object containing the system-wide peak number of 
			requests that were denied at any one time because no 
			receivers of this type were available during the 
			measurement hour.	
	"
    ::= { avCmMeasToneRecSumToday 14 }

avCmMeasToneRecSumTodayCCTTRHour        OBJECT-TYPE
    SYNTAX      Integer32 (0..9999)
    MAX-ACCESS  read-only
    STATUS      current
    DESCRIPTION
        "
        Fld OID Name:   avCmMeasToneRecSumTodayCCTTRHour
        Fld OID:        enterprises.6889.2.73.8.1.101.15
        Fld Form/Rpt:   TONE RECEIVER SUMMARY MEASUREMENTS
        Fld Format:     Single Field
        Fld(s) Name:    CC-TTR Hour 
        Fld Descr: 	An object containing the Hour the measurement was 
			taken.     
        "
    ::= { avCmMeasToneRecSumToday 15 }

avCmMeasToneRecSumTodayCCTTRTReq         OBJECT-TYPE
    SYNTAX      Integer32 (0..999999)
    MAX-ACCESS  read-only
    STATUS      current
    DESCRIPTION
        "
        Fld OID Name:   avCmMeasToneRecSumTodayCCTTRTReq 
        Fld OID:        enterprises.6889.2.73.8.1.101.16
        Fld Form/Rpt:   TONE RECEIVER SUMMARY MEASUREMENTS
        Fld Format:     Single Field
        Fld(s) Name:    CC-TTR  Total Req
        Fld Descr:      An object containing the system-wide total number of 
			requests for tone receivers of this type for the 
			measurement interval.
        "
    ::= { avCmMeasToneRecSumToday 16 }


avCmMeasToneRecSumTodayCCTTRPReq        OBJECT-TYPE
    SYNTAX      Integer32 (0..99999)
    MAX-ACCESS  read-only
    STATUS      current
    DESCRIPTION
        "
        Fld OID Name:   avCmMeasToneRecSumTodayCCTTRPReq 
        Fld OID:        enterprises.6889.2.73.8.1.101.17
        Fld Form/Rpt:   TONE RECEIVER SUMMARY MEASUREMENTS
        Fld Format:     Single Field
        Fld(s) Name:    CC-TTR  Peak Req
        Fld Descr:      An object containing the system-wide peak number of 
			simultaneous requests for tone receivers of this type 
			that occurred at any one time over the measurement 
			interval.
        "
    ::= { avCmMeasToneRecSumToday 17 }

avCmMeasToneRecSumTodayCCTTRTQueued	OBJECT-TYPE
    SYNTAX	Integer32 (0..99999)
    MAX-ACCESS	read-only
    STATUS	current
    DESCRIPTION
	"
	Fld OID Name:	avCmMeasToneRecSumTodayCCTTRTQueued
	Fld OID:	enterprises.6889.2.73.8.1.101.18
	Fld Form/Rpt:   TONE RECEIVER SUMMARY MEASUREMENTS
	Fld Format:	Single Field
	Fld(s) Name:	CC-TTR Total Queued
	Fld Descr:	An object containing the system-wide total number of 
			requests queued for tone receivers of this type during 
			the measurement interval.
	"
    ::= { avCmMeasToneRecSumToday 18 }

avCmMeasToneRecSumTodayCCTTRPQueued	OBJECT-TYPE
    SYNTAX	Integer32 (0..99)
    MAX-ACCESS	read-only
    STATUS	current
    DESCRIPTION
	"
	Fld OID Name:	avCmMeasToneRecSumTodayCCTTRPQueued
	Fld OID:	enterprises.6889.2.73.8.1.101.19
	Fld Form/Rpt:   TONE RECEIVER SUMMARY MEASUREMENTS
	Fld Format:	Single Field
	Fld(s) Name:	CC-TTR Peak Queued
	Fld Descr:	An object containing the system-wide peak number of 
			requests queued at any one time during the measurement 
			hour for tone receivers of this type.
	"
    ::= { avCmMeasToneRecSumToday 19 }

avCmMeasToneRecSumTodayCCTTRTDenied	     OBJECT-TYPE
    SYNTAX      Integer32 (0..9999)
    MAX-ACCESS  read-only
    STATUS      current
    DESCRIPTION
        "
        Fld OID Name:   avCmMeasToneRecSumTodayCCTTRTDenied
        Fld OID:        enterprises.6889.2.73.8.1.101.20
        Fld Form/Rpt:   TONE RECEIVER SUMMARY MEASUREMENTS
        Fld Format:     Single Field
        Fld(s) Name:    CC-TTR Total Denied
        Fld Descr:      An object containing the system-wide total number of 
			requests that were denied because no receivers of this 
			type were available during the measurement hour. 
        "
    ::= { avCmMeasToneRecSumToday 20 }

avCmMeasToneRecSumTodayCCTTRPDenied        OBJECT-TYPE
    SYNTAX      Integer32 (0..9999)
    MAX-ACCESS  read-only
    STATUS      current
    DESCRIPTION
        "
        Fld OID Name:   avCmMeasToneRecSumTodayCCTTRPDenied
        Fld OID:        enterprises.6889.2.73.8.1.101.21
        Fld Form/Rpt:   TONE RECEIVER SUMMARY MEASUREMENTS
        Fld Format:     Single Field
        Fld(s) Name:    CC-TTR Peak Denied
        Fld Descr:      An object containing the system-wide peak number of 
			requests that were denied at any one time because no 
			receivers of this type were available during the 
			measurement hour.
        "
    ::= { avCmMeasToneRecSumToday 21 }


avCmMeasToneRecSumTodayCCCPTRHour        OBJECT-TYPE
    SYNTAX      Integer32 (0..9999)
    MAX-ACCESS  read-only
    STATUS      current
    DESCRIPTION
        "
        Fld OID Name:   avCmMeasToneRecSumTodayCCCPTRHour
        Fld OID:        enterprises.6889.2.73.8.1.101.22
        Fld Form/Rpt:   TONE RECEIVER SUMMARY MEASUREMENTS
        Fld Format:     Single Field
        Fld(s) Name:    CC-CPTR Hour 
        Fld Descr: 	An object containing the Hour the measurement was 
			taken.     
        "
    ::= { avCmMeasToneRecSumToday 22 }

avCmMeasToneRecSumTodayCCCPTRTReq         OBJECT-TYPE
    SYNTAX      Integer32 (0..999999)
    MAX-ACCESS  read-only
    STATUS      current
    DESCRIPTION
        "
        Fld OID Name:   avCmMeasToneRecSumTodayCCCPTRTReq 
        Fld OID:        enterprises.6889.2.73.8.1.101.23
        Fld Form/Rpt:   TONE RECEIVER SUMMARY MEASUREMENTS
        Fld Format:     Single Field
        Fld(s) Name:    CC-CPTR  Total Req
        Fld Descr:      An object containing the system-wide total number of 
			requests for tone receivers of this type for the 
			measurement interval.
        "
    ::= { avCmMeasToneRecSumToday 23 }


avCmMeasToneRecSumTodayCCCPTRPReq        OBJECT-TYPE
    SYNTAX      Integer32 (0..99999)
    MAX-ACCESS  read-only
    STATUS      current
    DESCRIPTION
        "
        Fld OID Name:   avCmMeasToneRecSumTodayCCCPTRPReq 
        Fld OID:        enterprises.6889.2.73.8.1.101.24
        Fld Form/Rpt:   TONE RECEIVER SUMMARY MEASUREMENTS
        Fld Format:     Single Field
        Fld(s) Name:    CC-CPTR  Peak Req
        Fld Descr:      An object containing the system-wide peak number of 
			simultaneous requests for tone receivers of this type 
			that occurred at any one time over the measurement 
			interval.
        "
    ::= { avCmMeasToneRecSumToday 24 }

avCmMeasToneRecSumTodayCCCPTRTDenied     OBJECT-TYPE
    SYNTAX      Integer32 (0..9999)
    MAX-ACCESS  read-only
    STATUS      current
    DESCRIPTION
        "
        Fld OID Name:   avCmMeasToneRecSumTodayCCCPTRTDenied
        Fld OID:        enterprises.6889.2.73.8.1.101.25
        Fld Form/Rpt:   TONE RECEIVER SUMMARY MEASUREMENTS
        Fld Format:     Single Field
        Fld(s) Name:    CC-CPTR Total Denied
        Fld Descr:      An object containing the system-wide total number of 
			requests that were denied because no receivers of this 
			type were available during the measurement hour. 
        "
    ::= { avCmMeasToneRecSumToday 25 }

avCmMeasToneRecSumTodayCCCPTRPDenied        OBJECT-TYPE
    SYNTAX      Integer32 (0..9999)
    MAX-ACCESS  read-only
    STATUS      current
    DESCRIPTION
        "
        Fld OID Name:   avCmMeasToneRecSumTodayCCCPTRPDenied
        Fld OID:        enterprises.6889.2.73.8.1.101.26
        Fld Form/Rpt:   TONE RECEIVER SUMMARY MEASUREMENTS
        Fld Format:     Single Field
        Fld(s) Name:    CC-CPTR Peak Denied
        Fld Descr:      An object containing the system-wide peak number of 
			requests that were denied at any one time because no 
			receivers of this type were available during the 
			measurement hour.
        "
    ::= { avCmMeasToneRecSumToday 26 }


avCmMeasToneRecSumTodayCCMFCRHour        OBJECT-TYPE
    SYNTAX      Integer32 (0..9999)
    MAX-ACCESS  read-only
    STATUS      current
    DESCRIPTION
        "
        Fld OID Name:   avCmMeasToneRecSumTodayCCMFCRHour
        Fld OID:        enterprises.6889.2.73.8.1.101.27
        Fld Form/Rpt:   TONE RECEIVER SUMMARY MEASUREMENTS
        Fld Format:     Single Field
        Fld(s) Name:    CC-MFCR Hour 
        Fld Descr: 	An object containing the Hour the measurement was 
			taken.     
        "
    ::= { avCmMeasToneRecSumToday 27 }

avCmMeasToneRecSumTodayCCMFCRTReq         OBJECT-TYPE
    SYNTAX      Integer32 (0..999999)
    MAX-ACCESS  read-only
    STATUS      current
    DESCRIPTION
        "
        Fld OID Name:   avCmMeasToneRecSumTodayCCMFCRTReq 
        Fld OID:        enterprises.6889.2.73.8.1.101.28
        Fld Form/Rpt:   TONE RECEIVER SUMMARY MEASUREMENTS
        Fld Format:     Single Field
        Fld(s) Name:    CC-MFCR  Total Req
        Fld Descr:      An object containing the system-wide total number of 
			requests for tone receivers of this type for the 
			measurement interval.
        "
    ::= { avCmMeasToneRecSumToday 28 }


avCmMeasToneRecSumTodayCCMFCRPReq        OBJECT-TYPE
    SYNTAX      Integer32 (0..99999)
    MAX-ACCESS  read-only
    STATUS      current
    DESCRIPTION
        "
        Fld OID Name:   avCmMeasToneRecSumTodayCCMFCRPReq 
        Fld OID:        enterprises.6889.2.73.8.1.101.29
        Fld Form/Rpt:   TONE RECEIVER SUMMARY MEASUREMENTS
        Fld Format:     Single Field
        Fld(s) Name:    CC-MFCR  Peak Req
        Fld Descr:      An object containing the system-wide peak number of 
			simultaneous requests for tone receivers of this type 
			that occurred at any one time over the measurement 
			interval.
        "
    ::= { avCmMeasToneRecSumToday 29 }

avCmMeasToneRecSumTodayCCMFCRTDenied     OBJECT-TYPE
    SYNTAX      Integer32 (0..9999)
    MAX-ACCESS  read-only
    STATUS      current
    DESCRIPTION
        "
        Fld OID Name:   avCmMeasToneRecSumTodayCCMFCRTDenied
        Fld OID:        enterprises.6889.2.73.8.1.101.30
        Fld Form/Rpt:   TONE RECEIVER SUMMARY MEASUREMENTS
        Fld Format:     Single Field
        Fld(s) Name:    CC-MFCR Total Denied
        Fld Descr:      An object containing the system-wide total number of 
			requests that were denied because no receivers of this 
			type were available during the measurement hour. 
        "
    ::= { avCmMeasToneRecSumToday 30 }

avCmMeasToneRecSumTodayCCMFCRPDenied        OBJECT-TYPE
    SYNTAX      Integer32 (0..9999)
    MAX-ACCESS  read-only
    STATUS      current
    DESCRIPTION
        "
        Fld OID Name:   avCmMeasToneRecSumTodayCCMFCRPDenied
        Fld OID:        enterprises.6889.2.73.8.1.101.31
        Fld Form/Rpt:   TONE RECEIVER SUMMARY MEASUREMENTS
        Fld Format:     Single Field
        Fld(s) Name:    CC-MFCR Peak Denied
        Fld Descr:      An object containing the system-wide peak number of 
			requests that were denied at any one time because no 
			receivers of this type were available during the 
			measurement hour.
        "
    ::= { avCmMeasToneRecSumToday 31 }

avCmMeasToneRecSumTodayDTMRPTTAvail        OBJECT-TYPE
    SYNTAX      Integer32 (0..999)
    MAX-ACCESS  read-only
    STATUS      current
    DESCRIPTION
        "
        Fld OID Name:   avCmMeasToneRecSumTodayDTMRPTTAvail
        Fld OID:        enterprises.6889.2.73.8.1.101.32
        Fld Form/Rpt:   TONE RECEIVER SUMMARY MEASUREMENTS
        Fld Format:     Single Field
        Fld(s) Name:    DTMR-PT Total Avail
        Fld Descr:      An object containing the number of ports available for 
			the type of tone receiver. 
        "
    ::= { avCmMeasToneRecSumToday 32 }

avCmMeasToneRecSumTodayGPTDPTTAvail        OBJECT-TYPE
    SYNTAX      Integer32 (0..999)
    MAX-ACCESS  read-only
    STATUS      current
    DESCRIPTION
        "
        Fld OID Name:   avCmMeasToneRecSumTodayGPTDPTTAvail
        Fld OID:        enterprises.6889.2.73.8.1.101.33
        Fld Form/Rpt:   TONE RECEIVER SUMMARY MEASUREMENTS
        Fld Format:     Single Field
        Fld(s) Name:    GPTD-PT Total Avail
        Fld Descr:      An object containing the number of ports available for
                        the type of tone receiver.
        "
    ::= { avCmMeasToneRecSumToday 33 }


avCmMeasToneRecSumTodayCLASPTTAvail        OBJECT-TYPE
    SYNTAX      Integer32 (0..999)
    MAX-ACCESS  read-only
    STATUS      current
    DESCRIPTION
        "
        Fld OID Name:   avCmMeasToneRecSumTodayCLASPTTAvail
        Fld OID:        enterprises.6889.2.73.8.1.101.34
        Fld Form/Rpt:   TONE RECEIVER SUMMARY MEASUREMENTS
        Fld Format:     Single Field
        Fld(s) Name:    CLAS-PT Total Avail
        Fld Descr:      An object containing the number of ports available for
                        the type of tone receiver.
        "
    ::= { avCmMeasToneRecSumToday 34 }

avCmMeasToneRecSumTodayETRPTTAvail        OBJECT-TYPE
    SYNTAX      Integer32 (0..999)
    MAX-ACCESS  read-only
    STATUS      current
    DESCRIPTION
        "
        Fld OID Name:   avCmMeasToneRecSumTodayETRPTTAvail
        Fld OID:        enterprises.6889.2.73.8.1.101.35
        Fld Form/Rpt:   TONE RECEIVER SUMMARY MEASUREMENTS
        Fld Format:     Single Field
        Fld(s) Name:    ETR-PT Total Avail
        Fld Descr:      An object containing the number of ports available for
                        the type of tone receiver.
        "
    ::= { avCmMeasToneRecSumToday 35 }

-- ******************** avCmMeasToneRecSumYest Group *************************
-- MIB GROUP DESCRIPTION

-- MIB Group Name:
--		avCmMeasToneRecSumYest Group
-- OID:
--		enterprises.6889.2.73.8.1.102
-- Description:
--		The avCmMeasToneRecSumYest MIB Group uses the 
--		"list measurements tone-receiver summary yesterday" command to 
--		retrieve tone-receiver data from the listed hour.
--		
-- Releases Supported:
--		CM6.3.100 and greater
-- Polling Type:
--		Performance/Utilization
-- Polling Interval:
--		No more than once daily because the data is only updated
--		at midnight.
-- Default Caching Interval
-- 		600 seconds
-- Timeout Interval:
--		Initial Timeout should be set to 20 seconds.
-- Retry Interval:
--		Initial Retry should be set to 3.
-- Limitations:
--		Yellow/Medium - The data collected by this MIB Group
--		may have some impact on the system.
-- Command Type:
--		1. SAT
-- Command:
--		1. list measurements tone-receiver summary yesterday
-- Form/Report Name:
--		1. TONE RECEIVER SUMMARY MEASUREMENTS
-- Reference Document:
--		1. A detailed description of the command and form can be
--		   found in document referenced by REF_DOC_4 in the
--		   DOCUMENT REFERENCE SECTION.
-- Command Permission/User-profile:
--		1. No special permissions needed.

avCmMeasToneRecSumYest	OBJECT IDENTIFIER ::= { avCmObjects 102 }

avCmMeasToneRecSumYestRunDate	OBJECT-TYPE
    SYNTAX	SnmpAdminString (SIZE (0..28))
    MAX-ACCESS	read-only
    STATUS	current
    DESCRIPTION
	"
	Fld OID Name:	avCmMeasToneRecSumYestRunDate
	Fld OID:	enterprises.6889.2.73.8.1.102.1
	Fld Form/Rpt:   TONE RECEIVER SUMMARY MEASUREMENTS
	Fld Format:	Single Field
	Fld(s) Name:	Date
	Fld Descr:	An object containing the Date the command was executed.
	"
    ::= { avCmMeasToneRecSumYest 1 }


avCmMeasToneRecSumYestMeasHour   OBJECT-TYPE
    SYNTAX	Integer32 (0..9999)
    MAX-ACCESS  read-only
    STATUS      current
    DESCRIPTION
        "
        Fld OID Name:   avCmMeasToneRecSumYestMeasHour
        Fld OID:        enterprises.6889.2.73.8.1.102.2
        Fld Form/Rpt:   TONE RECEIVER SUMMARY MEASUREMENTS
        Fld Format:     Single Field
        Fld(s) Name:    Hour
        Fld Descr:      An object containing the Hour the measurement was taken.
        "
    ::= { avCmMeasToneRecSumYest 2 }


avCmMeasToneRecSumYestDTMFHour 	OBJECT-TYPE
    SYNTAX	Integer32 (0..9999)
    MAX-ACCESS	read-only
    STATUS	current
    DESCRIPTION
	"
	Fld OID Name:	avCmMeasToneRecSumYestDTMFHour
	Fld OID:	enterprises.6889.2.73.8.1.102.3
	Fld Form/Rpt:   TONE RECEIVER SUMMARY MEASUREMENTS
	Fld Format:	Single Field
	Fld(s) Name:	DTMF Hour
	Fld Descr:	An object containing the hour the measurement was
			taken.
	"
    ::= { avCmMeasToneRecSumYest 3 }

avCmMeasToneRecSumYestDTMFTReq	OBJECT-TYPE
    SYNTAX	Integer32 (0..999999)
    MAX-ACCESS	read-only
    STATUS	current
    DESCRIPTION
	"
	Fld OID Name:	avCmMeasToneRecSumYestDTMFTReq
	Fld OID:	enterprises.6889.2.73.8.1.102.4
	Fld Form/Rpt:   TONE RECEIVER SUMMARY MEASUREMENTS
	Fld Format:	Single Field
	Fld(s) Name:	DTMF Total Request
	Fld Descr:	An object containing the system-wide total number of 
			requests for tone receivers of this type for the 
			measurement interval.
	"
    ::= { avCmMeasToneRecSumYest 4 }

avCmMeasToneRecSumYestDTMFPReq   OBJECT-TYPE
    SYNTAX	Integer32 (0..99999)
    MAX-ACCESS	read-only
    STATUS	current
    DESCRIPTION
	"
	Fld OID Name:	avCmMeasToneRecSumYestDTMFPReq
	Fld OID:	enterprises.6889.2.73.8.1.102.5
	Fld Form/Rpt:   TONE RECEIVER SUMMARY MEASUREMENTS
	Fld Format:	Single Field
	Fld(s) Name:	DTMF Peak Request
	Fld Descr:	An object containing the system-wide peak number of 
			simultaneous requests for tone receivers of this type 
			that occurred at any one time over the measurement 
			interval.
	"
    ::= { avCmMeasToneRecSumYest 5 }

avCmMeasToneRecSumYestDTMFTQueued	OBJECT-TYPE
    SYNTAX	Integer32 (0..99999)
    MAX-ACCESS	read-only
    STATUS	current
    DESCRIPTION
	"
	Fld OID Name:	avCmMeasToneRecSumYestDTMFTQueued
	Fld OID:	enterprises.6889.2.73.8.1.102.6
	Fld Form/Rpt:   TONE RECEIVER SUMMARY MEASUREMENTS
	Fld Format:	Single Field
	Fld(s) Name:	DTMF Total Queued
	Fld Descr:	An object containing the system-wide total number of 
			requests queued for tone receivers of this type during 
			the measurement interval.
	"
    ::= { avCmMeasToneRecSumYest 6 }

avCmMeasToneRecSumYestDTMFPQueued	OBJECT-TYPE
    SYNTAX	Integer32 (0..99)
    MAX-ACCESS	read-only
    STATUS	current
    DESCRIPTION
	"
	Fld OID Name:	avCmMeasToneRecSumYestDTMFPQueued
	Fld OID:	enterprises.6889.2.73.8.1.102.7
	Fld Form/Rpt:   TONE RECEIVER SUMMARY MEASUREMENTS
	Fld Format:	Single Field
	Fld(s) Name:	DTMF Peak Queued
	Fld Descr:	An object containing the system-wide peak number of 
			requests queued at any one time during the measurement 
			hour for tone receivers of this type.
	"
    ::= { avCmMeasToneRecSumYest 7 }

avCmMeasToneRecSumYestDTMFTDenied	OBJECT-TYPE
    SYNTAX	Integer32 (0..9999)
    MAX-ACCESS	read-only
    STATUS	current
    DESCRIPTION
	"
	Fld OID Name:	avCmMeasToneRecSumYestDTMFTDenied
	Fld OID:	enterprises.6889.2.73.8.1.102.8
	Fld Form/Rpt:   TONE RECEIVER SUMMARY MEASUREMENTS
	Fld Format:	Single Field
	Fld(s) Name:	DTMF Total Denied
	Fld Descr:	An object containing the system-wide total number of 
			requests that were denied because no receivers of this 
			type were available during the measurement hour.
	"
    ::= { avCmMeasToneRecSumYest 8 }

avCmMeasToneRecSumYestDTMFPDenied	OBJECT-TYPE
    SYNTAX	Integer32 (0..9999)
    MAX-ACCESS	read-only
    STATUS	current
    DESCRIPTION
	"
	Fld OID Name:	avCmMeasToneRecSumYestDTMFPDenied
	Fld OID:	enterprises.6889.2.73.8.1.102.9
	Fld Form/Rpt:   TONE RECEIVER SUMMARY MEASUREMENTS
	Fld Format:	Single Field
	Fld(s) Name:	DTMF Peak Denied
	Fld Descr:	An object containing the system-wide peak number of 
			requests that were denied at any one time because no 
			receivers of this type were available during the 
			measurement hour.
	"
    ::= { avCmMeasToneRecSumYest 9 }

avCmMeasToneRecSumYestGPTDHour	OBJECT-TYPE
    SYNTAX	Integer32 (0..9999)
    MAX-ACCESS	read-only
    STATUS	current
    DESCRIPTION
	"
	Fld OID Name:	avCmMeasToneRecSumYestGPTDHour
	Fld OID:	enterprises.6889.2.73.8.1.102.10
	Fld Form/Rpt:   TONE RECEIVER SUMMARY MEASUREMENTS
	Fld Format:	Single Field
	Fld(s) Name:	GPTD Hour
	Fld Descr:	An object containing the Hour the measurement was 
			taken.
	"
    ::= { avCmMeasToneRecSumYest 10 }

avCmMeasToneRecSumYestGPTDTReq	OBJECT-TYPE
    SYNTAX	Integer32 (0..999999)
    MAX-ACCESS	read-only
    STATUS	current
    DESCRIPTION
	"
	Fld OID Name:	avCmMeasToneRecSumYestGPTDTReq
	Fld OID:	enterprises.6889.2.73.8.1.102.11
	Fld Form/Rpt:   TONE RECEIVER SUMMARY MEASUREMENTS
	Fld Format:	Single Field
	Fld(s) Name:	GPTD Total Req
	Fld Descr:	An object containing the system-wide total number of 
			requests for tone receivers of this type for the 
			measurement interval.
	"
    ::= { avCmMeasToneRecSumYest 11 }

avCmMeasToneRecSumYestGPTDPReq 	OBJECT-TYPE
    SYNTAX	Integer32 (0..999999)
    MAX-ACCESS	read-only
    STATUS	current
    DESCRIPTION
	"
	Fld OID Name:	avCmMeasToneRecSumYestGPTDPReq
	Fld OID:	enterprises.6889.2.73.8.1.102.12
	Fld Form/Rpt:   TONE RECEIVER SUMMARY MEASUREMENTS
	Fld Format:	Single Field
	Fld(s) Name:	GPTD Peak Req
	Fld Descr:	An object containing the system-wide peak number of 
			simultaneous requests for tone receivers of this type 
			that occurred at any one time over the measurement 
			interval.
	"
    ::= { avCmMeasToneRecSumYest 12 }

avCmMeasToneRecSumYestGPTDTDenied	OBJECT-TYPE
    SYNTAX	Integer32 (0..9999)
    MAX-ACCESS	read-only
    STATUS	current
    DESCRIPTION
	"
	Fld OID Name:	avCmMeasToneRecSumYestGPTDTDenied
	Fld OID:	enterprises.6889.2.73.8.1.102.13
	Fld Form/Rpt:   TONE RECEIVER SUMMARY MEASUREMENTS
	Fld Format:	Single Field
	Fld(s) Name:	GPTD Total Denied
	Fld Descr:	An object containing the system-wide total number of 
			requests that were denied because no receivers of this 
			type were available during the measurement hour.
	"
    ::= { avCmMeasToneRecSumYest 13 }

avCmMeasToneRecSumYestGPTDPDenied	OBJECT-TYPE
    SYNTAX	Integer32 (0..9999)
    MAX-ACCESS	read-only
    STATUS	current
    DESCRIPTION
	"
	Fld OID Name:	avCmMeasToneRecSumYestGPTDPDenied
	Fld OID:	enterprises.6889.2.73.8.1.102.14
	Fld Form/Rpt:   TONE RECEIVER SUMMARY MEASUREMENTS
	Fld Format:	Single Field
	Fld(s) Name:	GPTD Peak Denied
	Fld Descr:      An object containing the system-wide peak number of 
			requests that were denied at any one time because no 
			receivers of this type were available during the 
			measurement hour.	
	"
    ::= { avCmMeasToneRecSumYest 14 }

avCmMeasToneRecSumYestCCTTRHour        OBJECT-TYPE
    SYNTAX      Integer32 (0..9999)
    MAX-ACCESS  read-only
    STATUS      current
    DESCRIPTION
        "
        Fld OID Name:   avCmMeasToneRecSumYestCCTTRHour
        Fld OID:        enterprises.6889.2.73.8.1.102.15
        Fld Form/Rpt:   TONE RECEIVER SUMMARY MEASUREMENTS
        Fld Format:     Single Field
        Fld(s) Name:    CC-TTR Hour 
        Fld Descr: 	An object containing the Hour the measurement was 
			taken.     
        "
    ::= { avCmMeasToneRecSumYest 15 }

avCmMeasToneRecSumYestCCTTRTReq         OBJECT-TYPE
    SYNTAX      Integer32 (0..999999)
    MAX-ACCESS  read-only
    STATUS      current
    DESCRIPTION
        "
        Fld OID Name:   avCmMeasToneRecSumYestCCTTRTReq 
        Fld OID:        enterprises.6889.2.73.8.1.102.16
        Fld Form/Rpt:   TONE RECEIVER SUMMARY MEASUREMENTS
        Fld Format:     Single Field
        Fld(s) Name:    CC-TTR  Total Req
        Fld Descr:      An object containing the system-wide total number of 
			requests for tone receivers of this type for the 
			measurement interval.
        "
    ::= { avCmMeasToneRecSumYest 16 }


avCmMeasToneRecSumYestCCTTRPReq        OBJECT-TYPE
    SYNTAX      Integer32 (0..99999)
    MAX-ACCESS  read-only
    STATUS      current
    DESCRIPTION
        "
        Fld OID Name:   avCmMeasToneRecSumYestCCTTRPReq 
        Fld OID:        enterprises.6889.2.73.8.1.102.17
        Fld Form/Rpt:   TONE RECEIVER SUMMARY MEASUREMENTS
        Fld Format:     Single Field
        Fld(s) Name:    CC-TTR  Peak Req
        Fld Descr:      An object containing the system-wide peak number of 
			simultaneous requests for tone receivers of this type 
			that occurred at any one time over the measurement 
			interval.
        "
    ::= { avCmMeasToneRecSumYest 17 }

avCmMeasToneRecSumYestCCTTRTQueued	OBJECT-TYPE
    SYNTAX	Integer32 (0..99999)
    MAX-ACCESS	read-only
    STATUS	current
    DESCRIPTION
	"
	Fld OID Name:	avCmMeasToneRecSumYestCCTTRTQueued
	Fld OID:	enterprises.6889.2.73.8.1.102.18
	Fld Form/Rpt:   TONE RECEIVER SUMMARY MEASUREMENTS
	Fld Format:	Single Field
	Fld(s) Name:	CC-TTR Total Queued
	Fld Descr:	An object containing the system-wide total number of 
			requests queued for tone receivers of this type during 
			the measurement interval.
	"
    ::= { avCmMeasToneRecSumYest 18 }

avCmMeasToneRecSumYestCCTTRPQueued	OBJECT-TYPE
    SYNTAX	Integer32 (0..99)
    MAX-ACCESS	read-only
    STATUS	current
    DESCRIPTION
	"
	Fld OID Name:	avCmMeasToneRecSumYestCCTTRPQueued
	Fld OID:	enterprises.6889.2.73.8.1.102.19
	Fld Form/Rpt:   TONE RECEIVER SUMMARY MEASUREMENTS
	Fld Format:	Single Field
	Fld(s) Name:	CC-TTR Peak Queued
	Fld Descr:	An object containing the system-wide peak number of 
			requests queued at any one time during the measurement 
			hour for tone receivers of this type.
	"
    ::= { avCmMeasToneRecSumYest 19 }

avCmMeasToneRecSumYestCCTTRTDenied	     OBJECT-TYPE
    SYNTAX      Integer32 (0..9999)
    MAX-ACCESS  read-only
    STATUS      current
    DESCRIPTION
        "
        Fld OID Name:   avCmMeasToneRecSumYestCCTTRTDenied
        Fld OID:        enterprises.6889.2.73.8.1.102.20
        Fld Form/Rpt:   TONE RECEIVER SUMMARY MEASUREMENTS
        Fld Format:     Single Field
        Fld(s) Name:    CC-TTR Total Denied
        Fld Descr:      An object containing the system-wide total number of 
			requests that were denied because no receivers of this 
			type were available during the measurement hour. 
        "
    ::= { avCmMeasToneRecSumYest 20 }

avCmMeasToneRecSumYestCCTTRPDenied        OBJECT-TYPE
    SYNTAX      Integer32 (0..9999)
    MAX-ACCESS  read-only
    STATUS      current
    DESCRIPTION
        "
        Fld OID Name:   avCmMeasToneRecSumYestCCTTRPDenied
        Fld OID:        enterprises.6889.2.73.8.1.102.21
        Fld Form/Rpt:   TONE RECEIVER SUMMARY MEASUREMENTS
        Fld Format:     Single Field
        Fld(s) Name:    CC-TTR Peak Denied
        Fld Descr:      An object containing the system-wide peak number of 
			requests that were denied at any one time because no 
			receivers of this type were available during the 
			measurement hour.
        "
    ::= { avCmMeasToneRecSumYest 21 }


avCmMeasToneRecSumYestCCCPTRHour        OBJECT-TYPE
    SYNTAX      Integer32 (0..9999)
    MAX-ACCESS  read-only
    STATUS      current
    DESCRIPTION
        "
        Fld OID Name:   avCmMeasToneRecSumYestCCCPTRHour
        Fld OID:        enterprises.6889.2.73.8.1.102.22
        Fld Form/Rpt:   TONE RECEIVER SUMMARY MEASUREMENTS
        Fld Format:     Single Field
        Fld(s) Name:    CC-CPTR Hour 
        Fld Descr: 	An object containing the Hour the measurement was 
			taken.     
        "
    ::= { avCmMeasToneRecSumYest 22 }

avCmMeasToneRecSumYestCCCPTRTReq         OBJECT-TYPE
    SYNTAX      Integer32 (0..999999)
    MAX-ACCESS  read-only
    STATUS      current
    DESCRIPTION
        "
        Fld OID Name:   avCmMeasToneRecSumYestCCCPTRTReq 
        Fld OID:        enterprises.6889.2.73.8.1.102.23
        Fld Form/Rpt:   TONE RECEIVER SUMMARY MEASUREMENTS
        Fld Format:     Single Field
        Fld(s) Name:    CC-CPTR  Total Req
        Fld Descr:      An object containing the system-wide total number of 
			requests for tone receivers of this type for the 
			measurement interval.
        "
    ::= { avCmMeasToneRecSumYest 23 }


avCmMeasToneRecSumYestCCCPTRPReq        OBJECT-TYPE
    SYNTAX      Integer32 (0..99999)
    MAX-ACCESS  read-only
    STATUS      current
    DESCRIPTION
        "
        Fld OID Name:   avCmMeasToneRecSumYestCCCPTRPReq 
        Fld OID:        enterprises.6889.2.73.8.1.102.24
        Fld Form/Rpt:   TONE RECEIVER SUMMARY MEASUREMENTS
        Fld Format:     Single Field
        Fld(s) Name:    CC-CPTR  Peak Req
        Fld Descr:      An object containing the system-wide peak number of 
			simultaneous requests for tone receivers of this type 
			that occurred at any one time over the measurement 
			interval.
        "
    ::= { avCmMeasToneRecSumYest 24 }

avCmMeasToneRecSumYestCCCPTRTDenied     OBJECT-TYPE
    SYNTAX      Integer32 (0..9999)
    MAX-ACCESS  read-only
    STATUS      current
    DESCRIPTION
        "
        Fld OID Name:   avCmMeasToneRecSumYestCCCPTRTDenied
        Fld OID:        enterprises.6889.2.73.8.1.102.25
        Fld Form/Rpt:   TONE RECEIVER SUMMARY MEASUREMENTS
        Fld Format:     Single Field
        Fld(s) Name:    CC-CPTR Total Denied
        Fld Descr:      An object containing the system-wide total number of 
			requests that were denied because no receivers of this 
			type were available during the measurement hour. 
        "
    ::= { avCmMeasToneRecSumYest 25 }

avCmMeasToneRecSumYestCCCPTRPDenied        OBJECT-TYPE
    SYNTAX      Integer32 (0..9999)
    MAX-ACCESS  read-only
    STATUS      current
    DESCRIPTION
        "
        Fld OID Name:   avCmMeasToneRecSumYestCCCPTRPDenied
        Fld OID:        enterprises.6889.2.73.8.1.102.26
        Fld Form/Rpt:   TONE RECEIVER SUMMARY MEASUREMENTS
        Fld Format:     Single Field
        Fld(s) Name:    CC-CPTR Peak Denied
        Fld Descr:      An object containing the system-wide peak number of 
			requests that were denied at any one time because no 
			receivers of this type were available during the 
			measurement hour.
        "
    ::= { avCmMeasToneRecSumYest 26 }


avCmMeasToneRecSumYestCCMFCRHour        OBJECT-TYPE
    SYNTAX      Integer32 (0..9999)
    MAX-ACCESS  read-only
    STATUS      current
    DESCRIPTION
        "
        Fld OID Name:   avCmMeasToneRecSumYestCCMFCRHour
        Fld OID:        enterprises.6889.2.73.8.1.102.27
        Fld Form/Rpt:   TONE RECEIVER SUMMARY MEASUREMENTS
        Fld Format:     Single Field
        Fld(s) Name:    CC-MFCR Hour 
        Fld Descr: 	An object containing the Hour the measurement was 
			taken.     
        "
    ::= { avCmMeasToneRecSumYest 27 }

avCmMeasToneRecSumYestCCMFCRTReq         OBJECT-TYPE
    SYNTAX      Integer32 (0..999999)
    MAX-ACCESS  read-only
    STATUS      current
    DESCRIPTION
        "
        Fld OID Name:   avCmMeasToneRecSumYestCCMFCRTReq 
        Fld OID:        enterprises.6889.2.73.8.1.102.28
        Fld Form/Rpt:   TONE RECEIVER SUMMARY MEASUREMENTS
        Fld Format:     Single Field
        Fld(s) Name:    CC-MFCR  Total Req
        Fld Descr:      An object containing the system-wide total number of 
			requests for tone receivers of this type for the 
			measurement interval.
        "
    ::= { avCmMeasToneRecSumYest 28 }


avCmMeasToneRecSumYestCCMFCRPReq        OBJECT-TYPE
    SYNTAX      Integer32 (0..99999)
    MAX-ACCESS  read-only
    STATUS      current
    DESCRIPTION
        "
        Fld OID Name:   avCmMeasToneRecSumYestCCMFCRPReq 
        Fld OID:        enterprises.6889.2.73.8.1.102.29
        Fld Form/Rpt:   TONE RECEIVER SUMMARY MEASUREMENTS
        Fld Format:     Single Field
        Fld(s) Name:    CC-MFCR  Peak Req
        Fld Descr:      An object containing the system-wide peak number of 
			simultaneous requests for tone receivers of this type 
			that occurred at any one time over the measurement 
			interval.
        "
    ::= { avCmMeasToneRecSumYest 29 }

avCmMeasToneRecSumYestCCMFCRTDenied     OBJECT-TYPE
    SYNTAX      Integer32 (0..9999)
    MAX-ACCESS  read-only
    STATUS      current
    DESCRIPTION
        "
        Fld OID Name:   avCmMeasToneRecSumYestCCMFCRTDenied
        Fld OID:        enterprises.6889.2.73.8.1.102.30
        Fld Form/Rpt:   TONE RECEIVER SUMMARY MEASUREMENTS
        Fld Format:     Single Field
        Fld(s) Name:    CC-MFCR Total Denied
        Fld Descr:      An object containing the system-wide total number of 
			requests that were denied because no receivers of this 
			type were available during the measurement hour. 
        "
    ::= { avCmMeasToneRecSumYest 30 }

avCmMeasToneRecSumYestCCMFCRPDenied        OBJECT-TYPE
    SYNTAX      Integer32 (0..9999)
    MAX-ACCESS  read-only
    STATUS      current
    DESCRIPTION
        "
        Fld OID Name:   avCmMeasToneRecSumYestCCMFCRPDenied
        Fld OID:        enterprises.6889.2.73.8.1.102.31
        Fld Form/Rpt:   TONE RECEIVER SUMMARY MEASUREMENTS
        Fld Format:     Single Field
        Fld(s) Name:    CC-MFCR Peak Denied
        Fld Descr:      An object containing the system-wide peak number of 
			requests that were denied at any one time because no 
			receivers of this type were available during the 
			measurement hour.
        "
    ::= { avCmMeasToneRecSumYest 31 }

avCmMeasToneRecSumYestDTMRPTTAvail        OBJECT-TYPE
    SYNTAX      Integer32 (0..999)
    MAX-ACCESS  read-only
    STATUS      current
    DESCRIPTION
        "
        Fld OID Name:   avCmMeasToneRecSumYestDTMRPTTAvail
        Fld OID:        enterprises.6889.2.73.8.1.102.32
        Fld Form/Rpt:   TONE RECEIVER SUMMARY MEASUREMENTS
        Fld Format:     Single Field
        Fld(s) Name:    DTMR-PT Total Avail
        Fld Descr:      An object containing the number of ports available for 
			the type of tone receiver. 
        "
    ::= { avCmMeasToneRecSumYest 32 }

avCmMeasToneRecSumYestGPTDPTTAvail        OBJECT-TYPE
    SYNTAX      Integer32 (0..999)
    MAX-ACCESS  read-only
    STATUS      current
    DESCRIPTION
        "
        Fld OID Name:   avCmMeasToneRecSumYestGPTDPTTAvail
        Fld OID:        enterprises.6889.2.73.8.1.102.33
        Fld Form/Rpt:   TONE RECEIVER SUMMARY MEASUREMENTS
        Fld Format:     Single Field
        Fld(s) Name:    GPTD-PT Total Avail
        Fld Descr:      An object containing the number of ports available for
                        the type of tone receiver.
        "
    ::= { avCmMeasToneRecSumYest 33 }


avCmMeasToneRecSumYestCLASPTTAvail        OBJECT-TYPE
    SYNTAX      Integer32 (0..999)
    MAX-ACCESS  read-only
    STATUS      current
    DESCRIPTION
        "
        Fld OID Name:   avCmMeasToneRecSumYestCLASPTTAvail
        Fld OID:        enterprises.6889.2.73.8.1.102.34
        Fld Form/Rpt:   TONE RECEIVER SUMMARY MEASUREMENTS
        Fld Format:     Single Field
        Fld(s) Name:    CLAS-PT Total Avail
        Fld Descr:      An object containing the number of ports available for
                        the type of tone receiver.
        "
    ::= { avCmMeasToneRecSumYest 34 }

avCmMeasToneRecSumYestETRPTTAvail        OBJECT-TYPE
    SYNTAX      Integer32 (0..999)
    MAX-ACCESS  read-only
    STATUS      current
    DESCRIPTION
        "
        Fld OID Name:   avCmMeasToneRecSumYestETRPTTAvail
        Fld OID:        enterprises.6889.2.73.8.1.102.35
        Fld Form/Rpt:   TONE RECEIVER SUMMARY MEASUREMENTS
        Fld Format:     Single Field
        Fld(s) Name:    ETR-PT Total Avail
        Fld Descr:      An object containing the number of ports available for
                        the type of tone receiver.
        "
    ::= { avCmMeasToneRecSumYest 35 }

-- ******************** avCmSysParamCust Group *************************

-- MIB GROUP DESCRIPTION

-- MIB Group Name:
--		avCmSysParamCust Group
-- OID:
--		enterprises.6889.2.73.8.1.103
-- Description:
--		The avCmSysParamCust MIB Group uses the 
--		"display system-parameters customer-options" command to 
--		retrieve customer options data indicating whether a small
--		selection of features is activated.
--		
-- Releases Supported:
--		CM6.3.100 and greater
-- Polling Type:
--		Inventory and Configuration
-- Polling Interval:
--		No more than once daily.
-- Default Caching Interval
-- 		600 seconds
-- Timeout Interval:
--		Initial Timeout should be set to 20 seconds.
-- Retry Interval:
--		Initial Retry should be set to 3.
-- Limitations:
--              Green/Low - The data collected by this MIB Group
--              is minimal and therefore has a low impact on the system.
-- Command Type:
--		1. SAT
-- Command:
--		1. display system-parameters customer-options
-- Form/Report Name:
--		1. OPTIONAL FEATURES
-- Reference Document:
--		1. A detailed description of the command and form can be
--		   found in document referenced by REF_DOC_5 in the
--		   DOCUMENT REFERENCE SECTION.
-- Command Permission/User-profile:
--		1. No special permissions needed.

avCmSysParamCust	OBJECT IDENTIFIER ::= { avCmObjects 103 }

avCmSysParamCustPlat	OBJECT-TYPE
    SYNTAX	SnmpAdminString (SIZE (0..6))
    MAX-ACCESS	read-only
    STATUS	current
    DESCRIPTION
	"
	Fld OID Name:	avCmSysParamCustPlat
	Fld OID:	enterprises.6889.2.73.8.1.103.1
	Fld Form/Rpt:   OPTIONAL FEATURES
	Fld Format:	Single Field
	Fld(s) Name:	Platform
	Fld Descr:	An object containing the platform of the server. 
	"
    ::= { avCmSysParamCust 1 }


avCmSysParamCustESS   OBJECT-TYPE
    SYNTAX	SnmpAdminString (SIZE (0..2))
    MAX-ACCESS  read-only
    STATUS      current
    DESCRIPTION
        "
        Fld OID Name:   avCmSysParamCustESS
        Fld OID:        enterprises.6889.2.73.8.1.103.2
        Fld Form/Rpt:   OPTIONAL FEATURES
        Fld Format:     Single Field
        Fld(s) Name:    Enterprise Survivable Server
        Fld Descr:      An object containing whether the Enterprise Survivable 
			Server feature is enabled (enabled=y. disabled=n).
        "
    ::= { avCmSysParamCust 2 }


avCmSysParamCustLSP 	OBJECT-TYPE
    SYNTAX	SnmpAdminString (SIZE (0..2))
    MAX-ACCESS	read-only
    STATUS	current
    DESCRIPTION
	"
	Fld OID Name:	avCmSysParamCustLSP
	Fld OID:	enterprises.6889.2.73.8.1.103.3
	Fld Form/Rpt:   OPTIONAL FEATURES
	Fld Format:	Single Field
	Fld(s) Name:	Local Survivable Processor
	Fld Descr:	An object containing whether the Local Survivable 
			Processor feature is enabled (enabled=y. disabled=n).
	"
    ::= { avCmSysParamCust 3 }

avCmSysParamCustTenantPart	OBJECT-TYPE
    SYNTAX	SnmpAdminString (SIZE (0..2))
    MAX-ACCESS	read-only
    STATUS	current
    DESCRIPTION
	"
	Fld OID Name:	avCmSysParamCustTenantPart
	Fld OID:	enterprises.6889.2.73.8.1.103.4
	Fld Form/Rpt:   OPTIONAL FEATURES
	Fld Format:	Single Field
	Fld(s) Name:	Tenant Partitioning
	Fld Descr:	An object containing whether the Tenant Partitioning
                        feature is enabled (enabled=y. disabled=n).
	"
    ::= { avCmSysParamCust 4 }

avCmSysParamCustPortNetSup   OBJECT-TYPE
    SYNTAX	SnmpAdminString (SIZE (0..2))
    MAX-ACCESS	read-only
    STATUS	current
    DESCRIPTION
	"
	Fld OID Name:	avCmSysParamCustPortNetSup
	Fld OID:	enterprises.6889.2.73.8.1.103.5
	Fld Form/Rpt:   OPTIONAL FEATURES
	Fld Format:	Single Field
	Fld(s) Name:	Port Network Support
	Fld Descr:	An object containing whether the Port Network Support
                        feature is enabled (enabled=y. disabled=n).
	"
    ::= { avCmSysParamCust 5 }

--------------------------------------------------------------------
-- Conformance information
--------------------------------------------------------------------

avCmMIBCompliances	OBJECT IDENTIFIER ::= {avCmConformance 1}
avCmMIBGroups		OBJECT IDENTIFIER ::= {avCmConformance 2}

avCmMIBCompliance    MODULE-COMPLIANCE
    STATUS	 current
    DESCRIPTION
	"The compliance statement for Avaya Aura Communication Manager MIB
	  entities"
    MODULE
    MANDATORY-GROUPS { avCmVersionObjGrp, avCmServerAlarmObjGrp,
		       avCmConfigurationObjGrp, avCmServerInfoObjGrp,
		       avCmAlarmsObjGrp, avCmErrorsObjGrp,
		       avCmListStationObjGrp, avCmListStationRangeObjGrp,
		       avCmUpdateShowObjGrp, avCmListTrunkObjGrp, 
		       avCmListTrunkRangeObjGrp, avCmCapacityAsaiObjGrp, 
		       avCmCapacityBcmsObjGrp, avCmCapacityCallVecObjGrp,
		       avCmCapacityDialPlanObjGrp,
		       avCmCapacityHuntGrpsObjGrp,
		       avCmCapacityAnnounceObjGrp,
		       avCmCapacityTrunksObjGrp,
		       avCmCapacityVoiceTermObjGrp,
		       avCmCapacityLicObjGrp,
		       avCmCapacityUsageObjGrp,
		       avCmCapacityIPUsageObjGrp,
		       avCmCapacityCurrentUsageObjGrp,
		       avCmListMemTrunkObjGrp,
		       avCmListMemTrunkRangeObjGrp,
		       avCmStatusTrunkObjGrp,
		       avCmStatusTrunkRangeObjGrp,
		       avCmStatusTrunkMemObjGrp,
		       avCmStatusHealthObjGrp,
		       avCmStatusStationObjGrp,
		       avCmStatusStationRangeObjGrp,
		       avCmMeasOccSumObjGrp,
		       avCmMeasOccLstHrObjGrp,
		       avCmMeasOccBusIntvlObjGrp,
		       avCmMeasTrkGrpSumLstHrObjGrp,
		       avCmMeasTrkGrpSumTodayObjGrp,
		       avCmMeasTrkGrpSumYestObjGrp,
		       avCmMeasOutTrkLstHrObjGrp,
		       avCmMeasOutTrkTodayObjGrp,
		       avCmMeasOutTrkYestObjGrp,
		       avCmMeasLightUseTrkLstHrObjGrp,
		       avCmMeasLightUseTrkTodayObjGrp,
		       avCmMeasLightUseTrkYestObjGrp,
		       avCmMeasSecViolationSumObjGrp,
		       avCmListMedGatewayObjGrp,
		       avCmListConfigMedGatewayObjGrp,
		       avCmStatusMedGatewayObjGrp,
		       avCmListIpUnregisteredObjGrp,
		       avCmListSurvProcessObjGrp,
		       avCmDispSurvProcessObjGrp,
		       avCmListNodeNamesAllObjGrp,
		       avCmListNodeNamesV4ObjGrp,
		       avCmListNodeNamesV6ObjGrp,
		       avCmListAnnObjGrp,
		       avCmListIpUnregisteredRangeObjGrp,
		       avCmDispTimeObjGrp,
		       avCmMessagingAlarmObjGrp,
		       avCmInitCausesObjGrp,
		       avCmMeasAnnIntegAllLstHrObjGrp,
		       avCmMeasAnnIntegAllTodayObjGrp,
		       avCmMeasAnnIntegAllYestObjGrp,
		       avCmStatusMGAnnObjGrp,
		       avCmListIntegAnnObjGrp,
		       avCmMeasIpVoStatHrJitterObjGrp,
		       avCmMeasIpVoStatHrPkLosObjGrp,
		       avCmMeasIpVoStatHrRtdelObjGrp,
		       avCmMeasIpVoStatHrDataObjGrp,
		       avCmMeasIpVoStatSumJitterLstHrObjGrp,
		       avCmMeasIpVoStatSumJitterTodayObjGrp,
		       avCmMeasIpVoStatSumJitterYestObjGrp,
		       avCmMeasIpVoStatSumPkLosLstHrObjGrp,
		       avCmMeasIpVoStatSumPkLosTodayObjGrp,
		       avCmMeasIpVoStatSumPkLosYestObjGrp,
		       avCmMeasIpVoStatSumRtdelLstHrObjGrp,
		       avCmMeasIpVoStatSumRtdelTodayObjGrp,
		       avCmMeasIpVoStatSumRtdelYestObjGrp,
		       avCmMeasIpVoStatSumDataLstHrObjGrp,
		       avCmMeasIpVoStatSumDataTodayObjGrp,
		       avCmMeasIpVoStatSumDataYestObjGrp,
                       avCmMeasAnnAllLstHrObjGrp,
                       avCmMeasAnnAllTodayObjGrp,
                       avCmMeasAnnAllYestObjGrp,
		       avCmPlatCmdsObjGrp,
		       avCmListSigGrpObjGrp,
		       avCmStatusSigGrpObjGrp,
		       avCmListHuntGrpObjGrp,
		       avCmMeasHuntGrpLstHrObjGrp,
		       avCmMeasHuntGrpTodayObjGrp,
		       avCmMeasHuntGrpYestObjGrp,
		       avCmListIpInterfaceAllObjGrp,
		       avCmListIpInterfaceMedproObjGrp,
		       avCmStatusMedproBrdObjGrp,
		       avCmListIpServerIntfObjGrp,
		       avCmStatusLinkObjGrp,
		       avCmListIPNetRegMonitorObjGrp,
		       avCmStatIpNetRegionObjGrp,
		       avCmMeasToneRecLstHrObjGrp,
		       avCmMeasToneRecTodayObjGrp,
		       avCmMeasToneRecYestObjGrp,
		       avCmMeasToneRecSumLstHrObjGrp,
		       avCmMeasToneRecSumTodayObjGrp,
		       avCmMeasToneRecSumYestObjGrp,
		       avCmSysParamCustObjGrp
                       }
    ::= { avCmMIBCompliances 1 }

avCmVersionObjGrp     OBJECT-GROUP
    OBJECTS   { avCmVersionOperSystem, avCmVersionBuildDate,
		avCmVersionLoadNumber, avCmVersionRlsNumber,
		avCmVersionRlsString,  avCmVersionVMToolsVers,
		avCmVersionTransSaved, avCmVersionLicInstalled,
		avCmVersionMemConfig }
    STATUS	current
    DESCRIPTION
	"Avaya Aura Communication Manager avCmVersion MIB objects"
    ::= { avCmMIBGroups 1 }

avCmServerAlarmObjGrp     OBJECT-GROUP
    OBJECTS   { avCmServerAlarmID, avCmServerAlarmSource,
		avCmServerAlarmEventID, avCmServerAlarmLevel,
		avCmServerAlarmAck, avCmServerAlarmDate,
		avCmServerAlarmDescription }
    STATUS	current
    DESCRIPTION
	"Avaya Aura Communication Manager avCmServerAlarm MIB objects"
    ::= { avCmMIBGroups 2 }

avCmConfigurationObjGrp     OBJECT-GROUP
    OBJECTS   { avCmConfigurationBoardNumber, avCmConfigurationBoardType,
		avCmConfigurationCode, avCmConfigurationVintage,
		avCmConfigurationAssignedPorts }
    STATUS	current
    DESCRIPTION
	"Avaya Aura Communication Manager avCmConfiguration MIB objects"
    ::= { avCmMIBGroups 3 }

avCmServerInfoObjGrp     OBJECT-GROUP
    OBJECTS   { avCmServerInfoProductID, avCmServerInfoActiveName,
		avCmServerInfoActiveIPAddr, avCmServerInfoServer1Name,
		avCmServerInfoServer1IPAddr, avCmServerInfoServer1State,
		avCmServerInfoServer2Name, avCmServerInfoServer2IPAddr,
		avCmServerInfoServer2State, avCmServerInfoServerType,
		avCmServerInfoSurvRemoteConfig, avCmServerInfoSurvCoreConfig,
		avCmServerInfoStdbyRefresh }
    STATUS	current
    DESCRIPTION
	"Avaya Aura Communication Manager avCmServerInfo MIB objects"
    ::= { avCmMIBGroups 4 }

avCmAlarmsObjGrp     OBJECT-GROUP
    OBJECTS   { avCmAlarmsPort, avCmAlarmsMtceName, avCmAlarmsOnBrd,
		avCmAlarmsAltName, avCmAlarmsAlarmType, avCmAlarmsSvcState,
		avCmAlarmsAck, avCmAlarmsDateAlarmed, avCmAlarmsDateResolved }
    STATUS	current
    DESCRIPTION
	"Avaya Aura Communication Manager avCmAlarms MIB objects"
    ::= { avCmMIBGroups 5 }

avCmErrorsObjGrp     OBJECT-GROUP
    OBJECTS   { avCmErrorsPort, avCmErrorsMtceName, avCmErrorsAltName,
		avCmErrorsErrType, avCmErrorsAuxData,
		avCmErrorsFirstLastOccurrence, avCmErrorsErrCnt,
		avCmErrorsErrRt, avCmErrorsRtHr, avCmErrorsAlSt, avCmErrorsAc }
    STATUS	current
    DESCRIPTION
	"Avaya Aura Communication Manager avCmErrors MIB objects"
    ::= { avCmMIBGroups 6 }

avCmListStationObjGrp     OBJECT-GROUP
    OBJECTS   { avCmListStationExtension, avCmListStationType,
		avCmListStationName, avCmListStationPort }
    STATUS	current
    DESCRIPTION
	"Avaya Aura Communication Manager avCmListStation MIB objects"
    ::= { avCmMIBGroups 7 }

avCmListStationRangeObjGrp     OBJECT-GROUP
    OBJECTS   { avCmListStationRangeStartExt, avCmListStationRangeCount,
		avCmListStationRangeExtension, avCmListStationRangeType,
		avCmListStationRangeFloor, avCmListStationRangeBuilding,
		avCmListStationRangeJack, avCmListStationRangeCable,
		avCmListStationRangeRoom, avCmListStationRangeName,
		avCmListStationRangePort }
    STATUS	current
    DESCRIPTION
	"Avaya Aura Communication Manager avCmListStation MIB objects"
    ::= { avCmMIBGroups 8 }


avCmUpdateShowObjGrp     OBJECT-GROUP
    OBJECTS   { avCmUpdateShowID,
                avCmUpdateShowStatus,
                avCmUpdateShowType,
                avCmUpdateShowDescription }
    STATUS	current
    DESCRIPTION
	"Avaya Aura Communication Manager avCmUpdateShow MIB objects"
    ::= { avCmMIBGroups 9 }

avCmListTrunkObjGrp     OBJECT-GROUP
    OBJECTS   { avCmListTrunkGrpNumber,
                avCmListTrunkGrpType,
                avCmListTrunkGrpName,
                avCmListTrunkTAC,
                avCmListTrunkDirection,
                avCmListTrunkServiceType,
                avCmListTrunkCommType,
                avCmListTrunkTrunkType }
    STATUS	current
    DESCRIPTION
	"Avaya Aura Communication Manager avCmListTrunkObjGrp MIB objects"
    ::= { avCmMIBGroups 10 }

avCmListTrunkRangeObjGrp     OBJECT-GROUP
    OBJECTS   {
                avCmListTrunkRangeStartGrp,
                avCmListTrunkRangeCount,
                avCmListTrunkRangeGrpNumber,
                avCmListTrunkRangeTAC,
                avCmListTrunkRangeGrpType,
                avCmListTrunkRangeGrpName,
                avCmListTrunkRangeGrpNoMem,
                avCmListTrunkRangeSigGrp,
                avCmListTrunkRangeGrpSigType,
                avCmListTrunkRangeDirection,
                avCmListTrunkRangeServiceType,
                avCmListTrunkRangeCommType,
                avCmListTrunkRangeTrunkType,
                avCmListTrunkRangeMemAssignMeth,
                avCmListTrunkRangeCarMedium }
    STATUS      current
    DESCRIPTION
        "Avaya Aura Communication Manager avCmListTrunkRangeObjGrp MIB objects"
    ::= { avCmMIBGroups 11 }

avCmCapacityAsaiObjGrp     OBJECT-GROUP
    OBJECTS   { avCmCapacityAsaiActCtrlAsscUsed, 
		avCmCapacityAsaiActCtrlAsscAvail,
		avCmCapacityAsaiActCtrlAsscSysLim, 
		avCmCapacityAsaiNotifReqUsed, avCmCapacityAsaiNotifReqAvail,
		avCmCapacityAsaiNotifReqSysLim, 
		avCmCapacityAsaiSimActAdjCtrlCallUsed,
		avCmCapacityAsaiSimActAdjCtrlCallAvail,
		avCmCapacityAsaiSimActAdjCtrlCallSysLim }
    STATUS	current
    DESCRIPTION
	"Avaya Aura Communication Manager avCmCapacityAsai MIB objects"
    ::= { avCmMIBGroups 12 }

avCmCapacityBcmsObjGrp     OBJECT-GROUP
    OBJECTS   { avCmCapacityBcmsMeasAgentsUsed, 
		avCmCapacityBcmsMeasAgentsAvail,
		avCmCapacityBcmsMeasAgentsSysLim, 
		avCmCapacityBcmsMeasAcdMemUsed, avCmCapacityBcmsMeasAcdMemAvail,
		avCmCapacityBcmsMeasAcdMemSysLim, 
		avCmCapacityBcmsMeasSpliSkilUsed,
		avCmCapacityBcmsMeasSpliSkilAvail,
		avCmCapacityBcmsMeasSpliSkilSysLim,
                avCmCapacityBcmsMeasVdnUsed,
                avCmCapacityBcmsMeasVdnAvail,
                avCmCapacityBcmsMeasVdnSysLim }
    STATUS	current
    DESCRIPTION
	"Avaya Aura Communication Manager avCmCapacityBcms MIB objects"
    ::= { avCmMIBGroups 13 }

avCmCapacityCallVecObjGrp     OBJECT-GROUP
    OBJECTS   { avCmCapacityCallVecTotalVdnUsed, 
		avCmCapacityCallVecTotalVdnAvail,
		avCmCapacityCallVecTotalVdnSysLim, 
		avCmCapacityCallVecMeetMeVdnUsed, 
	        avCmCapacityCallVecMeetMeVdnAvail,
		avCmCapacityCallVecMeetMeVdnSysLim, 
		avCmCapacityCallVecMaxExpMeetMePtsUsed,
		avCmCapacityCallVecMaxExpMeetMePtsAvail,
		avCmCapacityCallVecMaxExpMeetMePtsSysLim,
                avCmCapacityCallVecTotalVectorsUsed,
                avCmCapacityCallVecTotalVectorsAvail,
                avCmCapacityCallVecTotalVectorsSysLim,
                avCmCapacityCallVecMeetMeVectorsUsed,
                avCmCapacityCallVecMeetMeVectorsAvail,
                avCmCapacityCallVecMeetMeVectorsSysLim,
                avCmCapacityCallVecBsrAppLocPairsUsed, 
                avCmCapacityCallVecBsrAppLocPairsAvail,
                avCmCapacityCallVecBsrAppLocPairsSysLim,
                avCmCapacityCallVecBkgrdBsrPollVdnUsed,
                avCmCapacityCallVecBkgrdBsrPollVdnAvail,
                avCmCapacityCallVecBkgrdBsrPollVdnSysLim,
                avCmCapacityCallVecVecComStepsUsed,
                avCmCapacityCallVecVecComStepsAvail,
                avCmCapacityCallVecVecComStepsSysLim,
                avCmCapacityCallVecPolicyRoutTblUsed, 
                avCmCapacityCallVecPolicyRoutTblAvail,
                avCmCapacityCallVecPolicyRoutTblSysLim,
                avCmCapacityCallVecPolicyRoutPtslUsed,
                avCmCapacityCallVecPolicyRoutPtsAvail,
                avCmCapacityCallVecPolicyRoutPtsSysLim }
    STATUS	current
    DESCRIPTION
	"Avaya Aura Communication Manager avCmCapacityCallVec MIB objects"
    ::= { avCmMIBGroups 14 }

avCmCapacityDialPlanObjGrp     OBJECT-GROUP
    OBJECTS   { avCmCapacityDialPlanExtUsed, 
		avCmCapacityDialPlanExtAvail,
		avCmCapacityDialPlanExtSysLim, 
		avCmCapacityDialPlanMiscExtUsed, 
		avCmCapacityDialPlanMiscExtAvail,
		avCmCapacityDialPlanMiscExtSysLim }
    STATUS	current
    DESCRIPTION
	"Avaya Aura Communication Manager avCmCapacityDialPlan MIB objects"
    ::= { avCmMIBGroups 15 }

avCmCapacityHuntGrpsObjGrp     OBJECT-GROUP
    OBJECTS   {
		avCmCapacityHuntGrpsSpSkUsed, 
		avCmCapacityHuntGrpsSpSkAvail,
		avCmCapacityHuntGrpsSpSkSysLim, 
		avCmCapacityHuntGrpsAdmLogAgtUsed, 
		avCmCapacityHuntGrpsAdmLogAgtAvail,
		avCmCapacityHuntGrpsAdmLogAgtSysLim,
		avCmCapacityHuntGrpsAdmLogAgtSkPrUsed,
		avCmCapacityHuntGrpsAdmLogAgtSkPrAvail,
		avCmCapacityHuntGrpsAdmLogAgtSkPrSysLim,
		avCmCapacityHuntGrpsLogAcdAgtUsed,
		avCmCapacityHuntGrpsLogAcdAgtAvail,
		avCmCapacityHuntGrpsLogAcdAgtSysLim,
		avCmCapacityHuntGrpsLogAdvocAgtUsed,
		avCmCapacityHuntGrpsLogAdvocAgtAvail,
		avCmCapacityHuntGrpsLogAdvocAgtSysLim,
		avCmCapacityHuntGrpsLogIPSoftAgtUsed,
		avCmCapacityHuntGrpsLogIPSoftAgtAvail,
		avCmCapacityHuntGrpsLogIPSoftAgtSysLim,
		avCmCapacityHuntGrpsLogSipEasAgtUsed,
		avCmCapacityHuntGrpsLogSipEasAgtAvail,
		avCmCapacityHuntGrpsLogSipEasAgtSysLim,
		avCmCapacityHuntGrpsGrpsMemPerSysUsed,
		avCmCapacityHuntGrpsGrpsMemPerSysAvail,
		avCmCapacityHuntGrpsGrpsMemPerSysSysLim,
		avCmCapacityHuntGrpsCmsMeasAcdMemUsed,
		avCmCapacityHuntGrpsCmsMeasAcdMemAvail,
		avCmCapacityHuntGrpsCmsMeasAcdMemSysLim
               }
    STATUS	current
    DESCRIPTION
	"Avaya Aura Communication Manager avCmCapacityHuntGrps MIB objects"
    ::= { avCmMIBGroups 16 }

avCmCapacityAnnounceObjGrp     OBJECT-GROUP
    OBJECTS   { 
		avCmCapacityAnnounceAdmAnnFileUsed, 
		avCmCapacityAnnounceAdmAnnFileAvail,
		avCmCapacityAnnounceAdmAnnFileSysLim, 
		avCmCapacityAnnounceTN2501ValBrdUsed, 
		avCmCapacityAnnounceTN2501ValBrdAvail,
		avCmCapacityAnnounceTN2501ValBrdSysLim,
		avCmCapacityAnnounceMGValSrcUsed,
		avCmCapacityAnnounceMGValSrcAvail,
		avCmCapacityAnnounceMGValSrcSysLim,
		avCmCapacityAnnounceTN2602Brds80ChUsed,
		avCmCapacityAnnounceTN2602Brds80ChAvail,
		avCmCapacityAnnounceTN2602Brds80ChSysLim,
		avCmCapacityAnnounceTN2602Brds320Used,
		avCmCapacityAnnounceTN2602Brds320Avail,
		avCmCapacityAnnounceTN2602Brds320SysLim,
		avCmCapacityAnnounceAvayaMedServUsed,
		avCmCapacityAnnounceAvayaMedServAvail,
		avCmCapacityAnnounceAvayaMedServSysLim 
		}
    STATUS	current
    DESCRIPTION
	"Avaya Aura Communication Manager avCmCapacityAnnounce MIB 
	 objects"
    ::= { avCmMIBGroups 17 }

avCmCapacityTrunksObjGrp OBJECT-GROUP
    OBJECTS   {
		avCmCapacityTrunksDS1CirPksUsed, 
		avCmCapacityTrunksDS1CirPksAvail,
		avCmCapacityTrunksDS1CirPksSysLim, 
		avCmCapacityTrunksDS1EchoCanUsed, 
		avCmCapacityTrunksDS1EchoCanAvail,
		avCmCapacityTrunksDS1EchoCanSysLim,
		avCmCapacityTrunksIchtIsdnSipTrkUsed,
		avCmCapacityTrunksIchtIsdnSipTrkAvail,
		avCmCapacityTrunksIchtIsdnSipTrkSysLim,
		avCmCapacityTrunksIsdnCbcTrkUsed,
		avCmCapacityTrunksIsdnCbcTrkAvail,
		avCmCapacityTrunksIsdnCbcTrkSysLim,
		avCmCapacityTrunksTrunkGrpsUsed,
		avCmCapacityTrunksTrunkGrpsAvail,
		avCmCapacityTrunksTrunkGrpsSysLim,
		avCmCapacityTrunksTrunkPtsUsed,
		avCmCapacityTrunksTrunkPtsAvail,
		avCmCapacityTrunksTrunkPtsSysLim,
		avCmCapacityTrunksH323TrksUsed,
		avCmCapacityTrunksH323TrksAvail,
		avCmCapacityTrunksH323TrksSysLim,
		avCmCapacityTrunksRemOffTrksUsed,
		avCmCapacityTrunksRemOffTrksAvail,
		avCmCapacityTrunksRemOffTrksSysLim,
		avCmCapacityTrunksSbsTrksUsed,
		avCmCapacityTrunksSbsTrksAvail,
		avCmCapacityTrunksSbsTrksSysLim,
		avCmCapacityTrunksSipTrksUsed,
		avCmCapacityTrunksSipTrksAvail,
		avCmCapacityTrunksSipTrksSysLim,
		avCmCapacityTrunksAdVidConfPtsUsed,
		avCmCapacityTrunksAdVidConfPtsAvail,
		avCmCapacityTrunksAdVidConfPtsSysLim
	        }
    STATUS	current
    DESCRIPTION
	"Avaya Aura Communication Manager avCMCapacityTrunks MIB objects"
    ::= { avCmMIBGroups 18 }

avCmCapacityVoiceTermObjGrp OBJECT-GROUP
    OBJECTS   {
		avCmCapacityVoiceTermStatWithPtUsed, 
		avCmCapacityVoiceTermStatWithOutPtUsed, 
		avCmCapacityVoiceTermOtherStatUsed,
		avCmCapacityVoiceTermTTIportsUsed,
		avCmCapacityVoiceTermAdmIPSoftUsed,
		avCmCapacityVoiceTermVidCapStatUsed,
		avCmCapacityVoiceTermVidCapStatAvail,
		avCmCapacityVoiceTermVidCapStatSysLim,
		avCmCapacityVoiceTermVidCapSoftUsed,
		avCmCapacityVoiceTermVidCapSoftAvail,
		avCmCapacityVoiceTermVidCapSoftSysLim,
		avCmCapacityVoiceTermBRIEndTrkPtsUsed,
		avCmCapacityVoiceTermBRIEndTrkPtsAvail,
		avCmCapacityVoiceTermBRIEndTrkPtsSysLim
	        }
    STATUS	current
    DESCRIPTION
	"Avaya Aura Communication Manager avCmCapacityVoiceTerm MIB objects"
    ::= { avCmMIBGroups 19 }

avCmCapacityLicObjGrp OBJECT-GROUP
    OBJECTS   {
		avCmCapacityLicStatTrkPtsUsed,
		avCmCapacityLicStatTrkPtsAvail,
		avCmCapacityLicStatTrkPtsLicLimit,
		avCmCapacityLicStatCapUsed,
		avCmCapacityLicStatCapAvail,
		avCmCapacityLicStatCapLicLimit,
		avCmCapacityLicXmobileStatUsed,
		avCmCapacityLicXmobileStatAvail,
		avCmCapacityLicXmobileStatLicLimit,
		avCmCapacityLicEC500Used,
	 	avCmCapacityLicIsdnDectUsed,
		avCmCapacityLicIpDectUsed,
		avCmCapacityLicPhsUsed,
		avCmCapacityLicOffPbxTelEC500Used,
		avCmCapacityLicOffPbxTelEC500Avail,
		avCmCapacityLicOffPbxTelEC500LicLimit,
		avCmCapacityLicOffPbxTelOPSUsed,
		avCmCapacityLicOffPbxTelOPSAvail,
		avCmCapacityLicOffPbxTelOPSLicLimit,
		avCmCapacityLicOffPbxTelPBFMCUsed,
		avCmCapacityLicOffPbxTelPBFMCAvail,
		avCmCapacityLicOffPbxTelPBFMCLicLimit,
		avCmCapacityLicOffPbxTelPVFMCUsed,
		avCmCapacityLicOffPbxTelPVFMCAvail,
		avCmCapacityLicOffPbxTelPVFMCLicLimit,
		avCmCapacityLicOffPbxTelSCCANUsed,
		avCmCapacityLicOffPbxTelSCCANAvail,
		avCmCapacityLicOffPbxTelSCCANLicLimit,
		avCmCapacityLicSurvProcUsed,
		avCmCapacityLicSurvProcAvail,
		avCmCapacityLicSurvProcLicLimit,
		avCmCapacityLicAvMedSerVoIPChUsed,
		avCmCapacityLicAvMedSerVoIPChAvail,
		avCmCapacityLicAvMedSerVoIPChLicLimit
	        }
    STATUS	current
    DESCRIPTION
	"Avaya Aura Communication Manager avCmCapacityLic MIB objects"
    ::= { avCmMIBGroups 20 }

avCmCapacityUsageObjGrp OBJECT-GROUP
    OBJECTS   {
		avCmCapacityUsageIPStatUsed, 
		avCmCapacityUsageIPStatAvail, 
		avCmCapacityUsageIPStatSysLim, 
		avCmCapacityUsageIPAttConUsed, 
		avCmCapacityUsageIPAttConAvail,	
		avCmCapacityUsageIPAttConSysLim, 
		avCmCapacityUsageRemOffStatUsed, 
		avCmCapacityUsageRemOffStatAvail, 
		avCmCapacityUsageRemOffStatSysLim, 
		avCmCapacityUsageUnauthH323StatUsed, 
		avCmCapacityUsageUnauthH323StatAvail, 
		avCmCapacityUsageUnauthH323StatSysLim, 
		avCmCapacityUsageAESServLicUsed 
	        }
    STATUS	current
    DESCRIPTION
	"Avaya Aura Communication Manager avCmCapacityUsage MIB objects"
    ::= { avCmMIBGroups 21 }

avCmCapacityIPUsageObjGrp OBJECT-GROUP
    OBJECTS   {
		avCmCapacityIPUsageTotalIpStatPtsUsed,
		avCmCapacityIPUsageTotalIpStatPtsAvail,
		avCmCapacityIPUsageTotalIpStatPtsSysLim
	        }
    STATUS	current
    DESCRIPTION
	"Avaya Aura Communication Manager avCmCapacityIPUsage MIB objects"
    ::= { avCmMIBGroups 22 }

avCmCapacityCurrentUsageObjGrp     OBJECT-GROUP
    OBJECTS   { 
		avCmCapacityCurrentUsageID, 
		avCmCapacityCurrentUsageRel,
		avCmCapacityCurrentUsageUsed, 
		avCmCapacityCurrentUsageAvail,
		avCmCapacityCurrentUsageLicLim
		 }
    STATUS	current
    DESCRIPTION
	"Avaya Aura Communication Manager avCmCapacityCurrentUsage MIB objects"
    ::= { avCmMIBGroups 23 }

avCmListMemTrunkObjGrp     OBJECT-GROUP
    OBJECTS   { 
                avCmListMemTrunkGrp,
                avCmListMemTrunkMemMember,
                avCmListMemTrunkPort,
                avCmListMemTrunkName,
                avCmListMemTrunkType,
                avCmListMemTrunkSigGrp
		 }
    STATUS	current
    DESCRIPTION
	"Avaya Aura Communication Manager avCmListMemTrunkObjGrp MIB objects"
    ::= { avCmMIBGroups 24 }


avCmListMemTrunkRangeObjGrp     OBJECT-GROUP
    OBJECTS   {
		avCmListMemTrunkRangeGrp,
		avCmListMemTrunkRangeStart,
		avCmListMemTrunkRangeCount,
                avCmListMemTrunkRangeMemMember,
                avCmListMemTrunkRangePort,
                avCmListMemTrunkRangeTnCode,
                avCmListMemTrunkRangeSfx,
                avCmListMemTrunkRangeName,
                avCmListMemTrunkRangeNight,
                avCmListMemTrunkRangeMode,
                avCmListMemTrunkRangeType,
                avCmListMemTrunkRangeAnsDelay,
                avCmListMemTrunkRangeSigGrp
                 }
    STATUS      current
    DESCRIPTION
        "Avaya Aura Communication Manager avCmListMemTrunkRangeObjGrp MIB 
	objects"
    ::= { avCmMIBGroups 25 }

avCmStatusTrunkObjGrp     OBJECT-GROUP
    OBJECTS   {
		avCmStatusTrunkGrp,
		avCmStatusTrunkMember,
                avCmStatusTrunkMemMember,
                avCmStatusTrunkPort,
                avCmStatusTrunkServiceState
                 }
    STATUS      current
    DESCRIPTION
        "Avaya Aura Communication Manager avCmStatusTrunkObjGrp MIB 
	objects"
    ::= { avCmMIBGroups 26 }

avCmStatusTrunkRangeObjGrp     OBJECT-GROUP
    OBJECTS   {
		avCmStatusTrunkRangeGrp,
		avCmStatusTrunkRangeCount,
                avCmStatusTrunkRangeMemMember,
                avCmStatusTrunkRangePort,
                avCmStatusTrunkRangeServiceState,
                avCmStatusTrunkRangeMtceBusy,
                avCmStatusTrunkRangeConnPorts1,
                avCmStatusTrunkRangeConnPorts2,
                avCmStatusTrunkRangeConnPorts3,
                avCmStatusTrunkRangeConnPorts4,
                avCmStatusTrunkRangeConnPorts5,
                avCmStatusTrunkRangeConnPorts6,
                avCmStatusTrunkRangeConnPorts7,
                avCmStatusTrunkRangeConnPorts8,
                avCmStatusTrunkRangeConnPorts9
                 }
    STATUS      current
    DESCRIPTION
        "Avaya Aura Communication Manager avCmStatusTrunkRangeObjGrp MIB 
	objects"
    ::= { avCmMIBGroups 27 }

avCmStatusTrunkMemObjGrp     OBJECT-GROUP
    OBJECTS   {
		avCmStatusTrunkMemGrp,
                avCmStatusTrunkMemMem,
                avCmStatusTrunkMemPort,
                avCmStatusTrunkMemServiceState,
                avCmStatusTrunkMemMtceBusy,
                avCmStatusTrunkMemSigGrpId,
                avCmStatusTrunkMemConnPorts1,
                avCmStatusTrunkMemConnPorts2,
                avCmStatusTrunkMemConnPorts3,
                avCmStatusTrunkMemConnPorts4,
                avCmStatusTrunkMemConnPorts5,
                avCmStatusTrunkMemConnPorts6,
                avCmStatusTrunkMemConnPorts7,
                avCmStatusTrunkMemConnPorts8,
                avCmStatusTrunkMemConnPorts9
                 }
    STATUS      current
    DESCRIPTION
        "Avaya Aura Communication Manager avCmStatusTrunkMemObjGrp MIB 
	objects"
    ::= { avCmMIBGroups 28 }

avCmStatusHealthObjGrp     OBJECT-GROUP
    OBJECTS   {
		avCmStatusHealthAlmMaj,
		avCmStatusHealthAlmMin,
		avCmStatusHealthAlmWrn,
		avCmStatusHealthBusyOutTrk,
		avCmStatusHealthBusyOutStn,
		avCmStatusHealthBusyOutOth,
		avCmStatusHealthOccupancySt,
		avCmStatusHealthOccupancySm,
		avCmStatusHealthOccupancyCp,
		avCmStatusHealthOccupancyIdl,
                avCmStatusHealthEntryTmRecOvrLd,
                avCmStatusHealthExitTmRecOvrLd,
                avCmStatusHealthLogins
                 }
    STATUS      current
    DESCRIPTION
        "Avaya Aura Communication Manager avCmStatusHealthObjGrp MIB 
	objects"
    ::= { avCmMIBGroups 29 }

avCmStatusStationObjGrp     OBJECT-GROUP
    OBJECTS   {
                avCmStatusStationExtension,
                avCmStatusStationConnType,
                avCmStatusStationServiceState,
                avCmStatusStationPort
                 }
    STATUS      current
    DESCRIPTION
        "Avaya Aura Communication Manager avCmStatusStationObjGrp MIB 
	objects"
    ::= { avCmMIBGroups 30 }


avCmStatusStationRangeObjGrp     OBJECT-GROUP
    OBJECTS   {
		avCmStatusStationRangeStartExt, 
		avCmStatusStationRangeCount,
                avCmStatusStationRangeExtension,
                avCmStatusStationRangeConnType,
                avCmStatusStationRangeServiceState,
                avCmStatusStationRangePort,
                avCmStatusStationRangeConnPort1,
                avCmStatusStationRangeConnPort2,
                avCmStatusStationRangeConnPort3,
                avCmStatusStationRangeConnPort4,
                avCmStatusStationRangeConnPort5,
                avCmStatusStationRangeConnPort6,
                avCmStatusStationRangeConnPort7,
                avCmStatusStationRangeConnPort8,
                avCmStatusStationRangeConnPort9,
                avCmStatusStationRangeConnPort10,
                avCmStatusStationRangeSACactive,
                avCmStatusStationRangeCFdestExt,
                avCmStatusStationRangeRingCutOff,
                avCmStatusStationRangeSerialNbr,
                avCmStatusStationRangePartID,
                avCmStatusStationRangeSwitchPort,
                avCmStatusStationRangeSwitchIPAddr,
                avCmStatusStationRangeSwitchIPPort,
                avCmStatusStationRangeSetIPAddr,
                avCmStatusStationRangeSetIPPort
                 }
    STATUS      current
    DESCRIPTION
        "Avaya Aura Communication Manager avCmStatusStationRangeObjGrp MIB 
	objects"
    ::= { avCmMIBGroups 31 }

avCmMeasOccSumObjGrp     OBJECT-GROUP
    OBJECTS   {
		avCmMeasOccSumRunDate,
		avCmMeasOccSumPeakHour,
                avCmMeasOccSumMeasHour,
                avCmMeasOccSumStatOcc,
                avCmMeasOccSumCPOcc,
                avCmMeasOccSumSMOcc,
		avCmMeasOccSumIdleOcc,
                avCmMeasOccSumTotCall,
                avCmMeasOccSumTandCall,
                avCmMeasOccSumTotConn,
		avCmMeasOccSumIntcomAtt,
                avCmMeasOccSumIncAtt,
                avCmMeasOccSumOutAtt,
                avCmMeasOccSumPnetAtt
                 }
    STATUS      current
    DESCRIPTION
        "Avaya Aura Communication Manager avCmMeasOccSumObjGrp MIB 
	objects"
    ::= { avCmMIBGroups 32 }


avCmMeasOccLstHrObjGrp     OBJECT-GROUP
    OBJECTS   {
		avCmMeasOccLstHrRunDate,
                avCmMeasOccLstHrMeasMinute,
                avCmMeasOccLstHrStatOcc,
                avCmMeasOccLstHrCPOcc,
                avCmMeasOccLstHrSMOcc,
		avCmMeasOccLstHrIdleOcc,
                avCmMeasOccLstHrTotCall,
                avCmMeasOccLstHrTandCall,
                avCmMeasOccLstHrTotConn,
		avCmMeasOccLstHrIntcomAtt,
                avCmMeasOccLstHrIncAtt,
                avCmMeasOccLstHrOutAtt,
                avCmMeasOccLstHrPnetAtt
                 }
    STATUS      current
    DESCRIPTION
        "Avaya Aura Communication Manager avCmMeasOccLstHrObjGrp MIB 
	objects"
    ::= { avCmMIBGroups 33 }

avCmMeasOccBusIntvlObjGrp     OBJECT-GROUP
    OBJECTS   {
		avCmMeasOccBusIntvlRunDate,
                avCmMeasOccBusIntvlDateofOcc,
                avCmMeasOccBusIntvlStatOcc,
                avCmMeasOccBusIntvlCPOcc,
                avCmMeasOccBusIntvlSMOcc,
		avCmMeasOccBusIntvlIdleOcc,
                avCmMeasOccBusIntvlTotCall,
                avCmMeasOccBusIntvlTandCall,
                avCmMeasOccBusIntvlTotConn,
		avCmMeasOccBusIntvlIntcomAtt,
                avCmMeasOccBusIntvlIncAtt,
                avCmMeasOccBusIntvlOutAtt,
                avCmMeasOccBusIntvlPnetAtt
                 }
    STATUS      current
    DESCRIPTION
        "Avaya Aura Communication Manager avCmMeasOccBusIntvlObjGrp MIB 
	objects"
    ::= { avCmMIBGroups 34 }

avCmMeasTrkGrpSumLstHrObjGrp     OBJECT-GROUP
    OBJECTS   {
		avCmMeasTrkGrpSumLstHrTrunkGroup,
		avCmMeasTrkGrpSumLstHrRunDate,
		avCmMeasTrkGrpSumLstHrMeasHour,
		avCmMeasTrkGrpSumLstHrGroupSize,
		avCmMeasTrkGrpSumLstHrTotalUsage,
		avCmMeasTrkGrpSumLstHrTotalSeize,
		avCmMeasTrkGrpSumLstHrIncSeize,
		avCmMeasTrkGrpSumLstHrGrpOvflow,
		avCmMeasTrkGrpSumLstHrQueSiz,
		avCmMeasTrkGrpSumLstHrCallQued,
		avCmMeasTrkGrpSumLstHrQueOvf,
		avCmMeasTrkGrpSumLstHrQueAbd,
		avCmMeasTrkGrpSumLstHrOutSrv,
		avCmMeasTrkGrpSumLstHrPercentAtb,
		avCmMeasTrkGrpSumLstHrPercentOutBlk
                 }
    STATUS      current
    DESCRIPTION
        "Avaya Aura Communication Manager avCmMeasTrkGrpSumLstHrObjGrp MIB 
	objects"
    ::= { avCmMIBGroups 35 }

avCmMeasTrkGrpSumTodayObjGrp     OBJECT-GROUP
    OBJECTS   {
                avCmMeasTrkGrpSumTodayTrunkGroup,
                avCmMeasTrkGrpSumTodayRunDate,
                avCmMeasTrkGrpSumTodayPeakHour,
                avCmMeasTrkGrpSumTodayMeasHour,
                avCmMeasTrkGrpSumTodayGroupSize,
                avCmMeasTrkGrpSumTodayTotalUsage,
                avCmMeasTrkGrpSumTodayTotalSeize,
                avCmMeasTrkGrpSumTodayIncSeize,
                avCmMeasTrkGrpSumTodayGrpOvflow,
                avCmMeasTrkGrpSumTodayQueSiz,
                avCmMeasTrkGrpSumTodayCallQued,
                avCmMeasTrkGrpSumTodayQueOvf,
                avCmMeasTrkGrpSumTodayQueAbd,
                avCmMeasTrkGrpSumTodayOutSrv,
                avCmMeasTrkGrpSumTodayPercentAtb,
                avCmMeasTrkGrpSumTodayPercentOutBlk
                 }
    STATUS      current
    DESCRIPTION
        "Avaya Aura Communication Manager avCmMeasTrkGrpSumTodayObjGrp MIB 
	objects"
    ::= { avCmMIBGroups 36 }

avCmMeasTrkGrpSumYestObjGrp     OBJECT-GROUP
    OBJECTS   {
                avCmMeasTrkGrpSumYestTrunkGroup,
                avCmMeasTrkGrpSumYestRunDate,
                avCmMeasTrkGrpSumYestMeasHour,
                avCmMeasTrkGrpSumYestPeakHour,
                avCmMeasTrkGrpSumYestGroupSize,
                avCmMeasTrkGrpSumYestTotalUsage,
                avCmMeasTrkGrpSumYestTotalSeize,
                avCmMeasTrkGrpSumYestIncSeize,
                avCmMeasTrkGrpSumYestGrpOvflow,
                avCmMeasTrkGrpSumYestQueSiz,
                avCmMeasTrkGrpSumYestCallQued,
                avCmMeasTrkGrpSumYestQueOvf,
                avCmMeasTrkGrpSumYestQueAbd,
                avCmMeasTrkGrpSumYestOutSrv,
                avCmMeasTrkGrpSumYestPercentAtb,
                avCmMeasTrkGrpSumYestPercentOutBlk
                 }
    STATUS      current
    DESCRIPTION
        "Avaya Aura Communication Manager avCmMeasTrkGrpSumYestObjGrp MIB 
	objects"
    ::= { avCmMIBGroups 37 }

avCmMeasOutTrkLstHrObjGrp     OBJECT-GROUP
    OBJECTS   {
                avCmMeasOutTrkLstHrTrunkGroup,
                avCmMeasOutTrkLstHrRunDate,
                avCmMeasOutTrkLstHrGrpSize,
                avCmMeasOutTrkLstHrGrpMbr,
                avCmMeasOutTrkLstHrOutages
                 }
    STATUS      current
    DESCRIPTION
        "Avaya Aura Communication Manager avCmMeasOutTrkLstHrObjGrp MIB 
	objects"
    ::= { avCmMIBGroups 38 }

avCmMeasOutTrkTodayObjGrp     OBJECT-GROUP
    OBJECTS   {
                avCmMeasOutTrkTodayTrunkGroup,
                avCmMeasOutTrkTodayRunDate,
                avCmMeasOutTrkTodayGrpSize,
                avCmMeasOutTrkTodayGrpMbr,
                avCmMeasOutTrkTodayOutages
                 }
    STATUS      current
    DESCRIPTION
        "Avaya Aura Communication Manager avCmMeasOutTrkTodayObjGrp MIB
        objects"
    ::= { avCmMIBGroups 39 }

avCmMeasOutTrkYestObjGrp     OBJECT-GROUP
    OBJECTS   {
                avCmMeasOutTrkYestTrunkGroup,
                avCmMeasOutTrkYestRunDate,
                avCmMeasOutTrkYestGrpSize,
                avCmMeasOutTrkYestGrpMbr,
                avCmMeasOutTrkYestOutages
                 }
    STATUS      current
    DESCRIPTION
        "Avaya Aura Communication Manager avCmMeasOutTrkYestObjGrp MIB
        objects"
    ::= { avCmMIBGroups 40 }

avCmMeasLightUseTrkLstHrObjGrp     OBJECT-GROUP
    OBJECTS   {
                avCmMeasLightUseTrkLstHrTrunkGroup,
                avCmMeasLightUseTrkLstHrRunDate,
                avCmMeasLightUseTrkLstHrGrpSize,
                avCmMeasLightUseTrkLstHrGrpMbr,
                avCmMeasLightUseTrkLstHrCallsCarried

                 }
    STATUS      current
    DESCRIPTION
        "Avaya Aura Communication Manager avCmMeasLightUseTrkLstHrObjGrp MIB
        objects"
    ::= { avCmMIBGroups 41 }

avCmMeasLightUseTrkTodayObjGrp     OBJECT-GROUP
    OBJECTS   {
                avCmMeasLightUseTrkTodayTrunkGroup,
                avCmMeasLightUseTrkTodayRunDate,
                avCmMeasLightUseTrkTodayGrpSize,
                avCmMeasLightUseTrkTodayGrpMbr,
                avCmMeasLightUseTrkTodayCallsCarried

                 }
    STATUS      current
    DESCRIPTION
        "Avaya Aura Communication Manager avCmMeasLightUseTrkTodayObjGrp MIB
        objects"
    ::= { avCmMIBGroups 42 }


avCmMeasLightUseTrkYestObjGrp     OBJECT-GROUP
    OBJECTS   {
                avCmMeasLightUseTrkYestTrunkGroup,
                avCmMeasLightUseTrkYestRunDate,
                avCmMeasLightUseTrkYestGrpSize,
                avCmMeasLightUseTrkYestGrpMbr,
                avCmMeasLightUseTrkYestCallsCarried

                 }
    STATUS      current
    DESCRIPTION
        "Avaya Aura Communication Manager avCmMeasLightUseTrkYestObjGrp MIB
        objects"
    ::= { avCmMIBGroups 43 }

avCmMeasSecViolationSumObjGrp     OBJECT-GROUP
    OBJECTS   {
		avCmMeasSecViolationSumPortType,
		avCmMeasSecViolationSumRunDate,
		avCmMeasSecViolationSumCountSince,
		avCmMeasSecViolationSumValidBC,
		avCmMeasSecViolationSumInvalidBC,
		avCmMeasSecViolationSumBC,
		avCmMeasSecViolationSumValidStnSecCode,
		avCmMeasSecViolationSumInvalidStnSecCode,
		avCmMeasSecViolationSumValidTrkSecCode,
		avCmMeasSecViolationSumInvalidTrkSecCode,
		avCmMeasSecViolationSumTotValidSecCode,
		avCmMeasSecViolationSumTotInvalidSecCode,
		avCmMeasSecViolationSumTotSecCode,
		avCmMeasSecViolationSumValidStnAC,
		avCmMeasSecViolationSumInvalidStnAC,
		avCmMeasSecViolationSumValidTrkAC,
		avCmMeasSecViolationSumInvalidTrkAC,
		avCmMeasSecViolationSumValidRemAccAC,
		avCmMeasSecViolationSumInvalidRemAccAC,
		avCmMeasSecViolationSumValidAtdAC,
		avCmMeasSecViolationSumInvalidAtdAC,
		avCmMeasSecViolationSumValidTotAC,
		avCmMeasSecViolationSumInvalidTotAC,
		avCmMeasSecViolationSumInvalidTotAC,
		avCmMeasSecViolationSumTotAC
                 }
    STATUS      current
    DESCRIPTION
        "Avaya Aura Communication Manager avCmMeasSecViolationSumObjGrp MIB
        objects"
    ::= { avCmMIBGroups 44 }

avCmListMedGatewayObjGrp     OBJECT-GROUP
    OBJECTS   {
                avCmListMedGatewayNumber,
                avCmListMedGatewayName,
                avCmListMedGatewaySerNum,
                avCmListMedGatewayFWVersHWVint,
                avCmListMedGatewayRecRule,
                avCmListMedGatewayIPV4Address,
                avCmListMedGatewayIPV6Address,
                avCmListMedGatewayContrlAddr,
                avCmListMedGatewayType,
                avCmListMedGatewayRegion,
                avCmListMedGatewayRegistered
                 }
    STATUS      current
    DESCRIPTION
        "Avaya Aura Communication Manager avCmListMedGatewayObjGrp MIB
        objects"
    ::= { avCmMIBGroups 45 }

avCmListConfigMedGatewayObjGrp     OBJECT-GROUP
    OBJECTS   {
                avCmListConfigMedGatewayBoardNumber,
                avCmListConfigMedGatewayBoardType,
                avCmListConfigMedGatewayCode,
                avCmListConfigMedGatewayVintage,
                avCmListConfigMedGatewayAssignedPorts
                 }
    STATUS      current
    DESCRIPTION
        "Avaya Aura Communication Manager avCmListConfigMedGatewayObjGrp MIB
        objects"
    ::= { avCmMIBGroups 46 }

avCmStatusMedGatewayObjGrp     OBJECT-GROUP
    OBJECTS   {
		avCmStatusMedGatewayAlmMajor,
		avCmStatusMedGatewayAlmMinor,
		avCmStatusMedGatewayAlmWarning,
		avCmStatusMedGatewayBusyOutTrunks,
		avCmStatusMedGatewayBusyOutStations,
		avCmStatusMedGatewayH248LinksDown,
		avCmStatusMedGatewayH248LinksUp,
		avCmStatusMedGatewayNbrLogins,
		avCmStatusMedGatewayAlarms1,
		avCmStatusMedGatewayAlarms2,
		avCmStatusMedGatewayAlarms3,
		avCmStatusMedGatewayAlarms4,
		avCmStatusMedGatewayAlarms5,
		avCmStatusMedGatewayAlarms6,
		avCmStatusMedGatewayAlarms7,
		avCmStatusMedGatewayAlarms8,
		avCmStatusMedGatewayAlarms9,
		avCmStatusMedGatewayAlarms10,
		avCmStatusMedGatewayAlarms11,
		avCmStatusMedGatewayAlarms12,
		avCmStatusMedGatewayAlarms13,
		avCmStatusMedGatewayAlarms14,
		avCmStatusMedGatewayAlarms15,
		avCmStatusMedGatewayAlarms16,
		avCmStatusMedGatewayAlarms17,
		avCmStatusMedGatewayAlarms18,
		avCmStatusMedGatewayAlarms19,
		avCmStatusMedGatewayAlarms20,
		avCmStatusMedGatewayAlarms21,
		avCmStatusMedGatewayAlarms22,
		avCmStatusMedGatewayAlarms23,
		avCmStatusMedGatewayAlarms24,
		avCmStatusMedGatewayAlarms25,
		avCmStatusMedGatewayAlarms26,
		avCmStatusMedGatewayAlarms27,
		avCmStatusMedGatewayAlarms28,
		avCmStatusMedGatewayAlarms29,
		avCmStatusMedGatewayAlarms30,
		avCmStatusMedGatewayAlarms31,
		avCmStatusMedGatewayAlarms32,
		avCmStatusMedGatewayAlarms33,
		avCmStatusMedGatewayAlarms34,
		avCmStatusMedGatewayAlarms35,
		avCmStatusMedGatewayAlarms36,
		avCmStatusMedGatewayAlarms37,
		avCmStatusMedGatewayAlarms38,
		avCmStatusMedGatewayAlarms39,
		avCmStatusMedGatewayAlarms40,
		avCmStatusMedGatewayAlarms41,
		avCmStatusMedGatewayAlarms42,
		avCmStatusMedGatewayAlarms43,
		avCmStatusMedGatewayAlarms44,
		avCmStatusMedGatewayAlarms45,
		avCmStatusMedGatewayAlarms46,
		avCmStatusMedGatewayAlarms47,
		avCmStatusMedGatewayAlarms48,
		avCmStatusMedGatewayAlarms49,
		avCmStatusMedGatewayAlarms50,
		avCmStatusMedGatewayAlarms51,
		avCmStatusMedGatewayAlarms52,
		avCmStatusMedGatewayAlarms53,
		avCmStatusMedGatewayAlarms54,
		avCmStatusMedGatewayAlarms55,
		avCmStatusMedGatewayAlarms56,
		avCmStatusMedGatewayAlarms57,
		avCmStatusMedGatewayAlarms58,
		avCmStatusMedGatewayAlarms59,
		avCmStatusMedGatewayAlarms60,
		avCmStatusMedGatewayAlarms61,
		avCmStatusMedGatewayAlarms62,
		avCmStatusMedGatewayAlarms63,
		avCmStatusMedGatewayAlarms64,
		avCmStatusMedGatewayAlarms65,
		avCmStatusMedGatewayAlarms66,
		avCmStatusMedGatewayAlarms67,
		avCmStatusMedGatewayAlarms68,
		avCmStatusMedGatewayAlarms69,
		avCmStatusMedGatewayAlarms70,
		avCmStatusMedGatewayAlarms71,
		avCmStatusMedGatewayAlarms72,
		avCmStatusMedGatewayAlarms73,
		avCmStatusMedGatewayAlarms74,
		avCmStatusMedGatewayAlarms75,
		avCmStatusMedGatewayAlarms76,
		avCmStatusMedGatewayAlarms77,
		avCmStatusMedGatewayAlarms78,
		avCmStatusMedGatewayAlarms79,
		avCmStatusMedGatewayAlarms80,
		avCmStatusMedGatewayAlarms81,
		avCmStatusMedGatewayAlarms82,
		avCmStatusMedGatewayAlarms83,
		avCmStatusMedGatewayAlarms84,
		avCmStatusMedGatewayAlarms85,
		avCmStatusMedGatewayAlarms86,
		avCmStatusMedGatewayAlarms87,
		avCmStatusMedGatewayAlarms88,
		avCmStatusMedGatewayAlarms89,
		avCmStatusMedGatewayAlarms90,
		avCmStatusMedGatewayAlarms91,
		avCmStatusMedGatewayAlarms92,
		avCmStatusMedGatewayAlarms93,
		avCmStatusMedGatewayAlarms94,
		avCmStatusMedGatewayAlarms95,
		avCmStatusMedGatewayAlarms96,
		avCmStatusMedGatewayAlarms97,
		avCmStatusMedGatewayAlarms98,
		avCmStatusMedGatewayAlarms99,
		avCmStatusMedGatewayAlarms100,
		avCmStatusMedGatewayAlarms101,
		avCmStatusMedGatewayAlarms102,
		avCmStatusMedGatewayAlarms103,
		avCmStatusMedGatewayAlarms104,
		avCmStatusMedGatewayAlarms105,
		avCmStatusMedGatewayAlarms106,
		avCmStatusMedGatewayAlarms107,
		avCmStatusMedGatewayAlarms108,
		avCmStatusMedGatewayAlarms109,
		avCmStatusMedGatewayAlarms110,
		avCmStatusMedGatewayAlarms111,
		avCmStatusMedGatewayAlarms112,
		avCmStatusMedGatewayAlarms113,
		avCmStatusMedGatewayAlarms114,
		avCmStatusMedGatewayAlarms115,
		avCmStatusMedGatewayAlarms116,
		avCmStatusMedGatewayAlarms117,
		avCmStatusMedGatewayAlarms118,
		avCmStatusMedGatewayAlarms119,
		avCmStatusMedGatewayAlarms120,
		avCmStatusMedGatewayAlarms121,
		avCmStatusMedGatewayAlarms122,
		avCmStatusMedGatewayAlarms123,
		avCmStatusMedGatewayAlarms124,
		avCmStatusMedGatewayAlarms125,
		avCmStatusMedGatewayAlarms126,
		avCmStatusMedGatewayAlarms127,
		avCmStatusMedGatewayAlarms128,
		avCmStatusMedGatewayAlarms129,
		avCmStatusMedGatewayAlarms130,
		avCmStatusMedGatewayAlarms131,
		avCmStatusMedGatewayAlarms132,
		avCmStatusMedGatewayAlarms133,
		avCmStatusMedGatewayAlarms134,
		avCmStatusMedGatewayAlarms135,
		avCmStatusMedGatewayAlarms136,
		avCmStatusMedGatewayAlarms137,
		avCmStatusMedGatewayAlarms138,
		avCmStatusMedGatewayAlarms139,
		avCmStatusMedGatewayAlarms140,
		avCmStatusMedGatewayAlarms141,
		avCmStatusMedGatewayAlarms142,
		avCmStatusMedGatewayAlarms143,
		avCmStatusMedGatewayAlarms144,
		avCmStatusMedGatewayAlarms145,
		avCmStatusMedGatewayAlarms146,
		avCmStatusMedGatewayAlarms147,
		avCmStatusMedGatewayAlarms148,
		avCmStatusMedGatewayAlarms149,
		avCmStatusMedGatewayAlarms150,
		avCmStatusMedGatewayAlarms151,
		avCmStatusMedGatewayAlarms152,
		avCmStatusMedGatewayAlarms153,
		avCmStatusMedGatewayAlarms154,
		avCmStatusMedGatewayAlarms155,
		avCmStatusMedGatewayAlarms156,
		avCmStatusMedGatewayAlarms157,
		avCmStatusMedGatewayAlarms158,
		avCmStatusMedGatewayAlarms159,
		avCmStatusMedGatewayAlarms160,
		avCmStatusMedGatewayAlarms161,
		avCmStatusMedGatewayAlarms162,
		avCmStatusMedGatewayAlarms163,
		avCmStatusMedGatewayAlarms164,
		avCmStatusMedGatewayAlarms147,
		avCmStatusMedGatewayAlarms148,
		avCmStatusMedGatewayAlarms149,
		avCmStatusMedGatewayAlarms150,
		avCmStatusMedGatewayAlarms151,
		avCmStatusMedGatewayAlarms152,
		avCmStatusMedGatewayAlarms153,
		avCmStatusMedGatewayAlarms154,
		avCmStatusMedGatewayAlarms155,
		avCmStatusMedGatewayAlarms156,
		avCmStatusMedGatewayAlarms157,
		avCmStatusMedGatewayAlarms158,
		avCmStatusMedGatewayAlarms159,
		avCmStatusMedGatewayAlarms160,
		avCmStatusMedGatewayAlarms161,
		avCmStatusMedGatewayAlarms162,
		avCmStatusMedGatewayAlarms163,
		avCmStatusMedGatewayAlarms164,
		avCmStatusMedGatewayAlarms165,
		avCmStatusMedGatewayAlarms166,
		avCmStatusMedGatewayAlarms167,
		avCmStatusMedGatewayAlarms168,
		avCmStatusMedGatewayAlarms169,
		avCmStatusMedGatewayAlarms170,
		avCmStatusMedGatewayAlarms171,
		avCmStatusMedGatewayAlarms172,
		avCmStatusMedGatewayAlarms173,
		avCmStatusMedGatewayAlarms174,
		avCmStatusMedGatewayAlarms175,
		avCmStatusMedGatewayAlarms176,
		avCmStatusMedGatewayAlarms177,
		avCmStatusMedGatewayAlarms178,
		avCmStatusMedGatewayAlarms179,
		avCmStatusMedGatewayAlarms180,
		avCmStatusMedGatewayAlarms181,
		avCmStatusMedGatewayAlarms182,
		avCmStatusMedGatewayAlarms183,
		avCmStatusMedGatewayAlarms184,
		avCmStatusMedGatewayAlarms185,
		avCmStatusMedGatewayAlarms186,
		avCmStatusMedGatewayAlarms187,
		avCmStatusMedGatewayAlarms188,
		avCmStatusMedGatewayAlarms189,
		avCmStatusMedGatewayAlarms190,
		avCmStatusMedGatewayAlarms191,
		avCmStatusMedGatewayAlarms192,
		avCmStatusMedGatewayAlarms193,
		avCmStatusMedGatewayAlarms194,
		avCmStatusMedGatewayAlarms195,
		avCmStatusMedGatewayAlarms196,
		avCmStatusMedGatewayAlarms197,
		avCmStatusMedGatewayAlarms198,
		avCmStatusMedGatewayAlarms199,
		avCmStatusMedGatewayAlarms200,
		avCmStatusMedGatewayAlarms201,
		avCmStatusMedGatewayAlarms202,
		avCmStatusMedGatewayAlarms203,
		avCmStatusMedGatewayAlarms204,
		avCmStatusMedGatewayAlarms205,
		avCmStatusMedGatewayAlarms206,
		avCmStatusMedGatewayAlarms207,
		avCmStatusMedGatewayAlarms208,
		avCmStatusMedGatewayAlarms209,
		avCmStatusMedGatewayAlarms210,
		avCmStatusMedGatewayAlarms211,
		avCmStatusMedGatewayAlarms212,
		avCmStatusMedGatewayAlarms213,
		avCmStatusMedGatewayAlarms214,
		avCmStatusMedGatewayAlarms215,
		avCmStatusMedGatewayAlarms216,
		avCmStatusMedGatewayAlarms217,
		avCmStatusMedGatewayAlarms218,
		avCmStatusMedGatewayAlarms219,
		avCmStatusMedGatewayAlarms220,
		avCmStatusMedGatewayAlarms221,
		avCmStatusMedGatewayAlarms222,
		avCmStatusMedGatewayAlarms223,
		avCmStatusMedGatewayAlarms224,
		avCmStatusMedGatewayAlarms225,
		avCmStatusMedGatewayAlarms226,
		avCmStatusMedGatewayAlarms227,
		avCmStatusMedGatewayAlarms228,
		avCmStatusMedGatewayAlarms229,
		avCmStatusMedGatewayAlarms230,
		avCmStatusMedGatewayAlarms231,
		avCmStatusMedGatewayAlarms232,
		avCmStatusMedGatewayAlarms233,
		avCmStatusMedGatewayAlarms234,
		avCmStatusMedGatewayAlarms235,
		avCmStatusMedGatewayAlarms236,
		avCmStatusMedGatewayAlarms237,
		avCmStatusMedGatewayAlarms238,
		avCmStatusMedGatewayAlarms239,
		avCmStatusMedGatewayAlarms240,
		avCmStatusMedGatewayAlarms241,
		avCmStatusMedGatewayAlarms242,
		avCmStatusMedGatewayAlarms243,
		avCmStatusMedGatewayAlarms244,
		avCmStatusMedGatewayAlarms245,
		avCmStatusMedGatewayAlarms246,
		avCmStatusMedGatewayAlarms247,
		avCmStatusMedGatewayAlarms248,
		avCmStatusMedGatewayAlarms249,
		avCmStatusMedGatewayAlarms250
                 }
    STATUS      current
    DESCRIPTION
        "Avaya Aura Communication Manager avCmStatusMedGatewayObjGrp MIB
        objects"
    ::= { avCmMIBGroups 47 }


avCmListIpUnregisteredObjGrp     OBJECT-GROUP
    OBJECTS   {
		avCmListIpUnregisteredExtension,
		avCmListIpUnregisteredPort,
		avCmListIpUnregisteredRegistered
                 }
    STATUS      current
    DESCRIPTION
        "Avaya Aura Communication Manager avCmListIpUnregisteredObjGrp MIB
        objects"
    ::= { avCmMIBGroups 48 }

avCmListSurvProcessObjGrp     OBJECT-GROUP
    OBJECTS   {
		avCmListSurvProcessNumber,
		avCmListSurvProcessName,
		avCmListSurvProcessType,
		avCmListSurvProcessReg,
		avCmListSurvProcessAct,
		avCmListSurvProcessTransUpdated,
		avCmListSurvProcessNetRgn,
		avCmListSurvProcessIpAddress,
		avCmListSurvProcessIPV6Name,
		avCmListSurvProcessIPV6Address
                 }
    STATUS      current
    DESCRIPTION
        "Avaya Aura Communication Manager avCmListSurvProcessObjGrp MIB
        objects"
    ::= { avCmMIBGroups 49 }

avCmDispSurvProcessObjGrp     OBJECT-GROUP
    OBJECTS   {
                avCmDispSurvProcessNodeName,
                avCmDispSurvProcessType,
                avCmDispSurvProcessClusterId,
                avCmDispSurvProcessActivesrvIP,
                avCmDispSurvProcessAID,
                avCmDispSurvProcessAnodename,
                avCmDispSurvProcessAIP,
                avCmDispSurvProcessBID,
                avCmDispSurvProcessBnodename,
                avCmDispSurvProcessBIP,
                avCmDispSurvProcessSystemPref,
                avCmDispSurvProcessPriorityscore,
                avCmDispSurvProcessLocalPref,
                avCmDispSurvProcessLocalOnly,
                avCmDispSurvProcessV6NodeName,
                avCmDispSurvProcessV6IP,
                avCmDispSurvProcessAV6NodeName,
                avCmDispSurvProcessAV6IP,
                avCmDispSurvProcessBV6NodeName,
                avCmDispSurvProcessBV6IP
                 }
    STATUS      current
    DESCRIPTION
        "Avaya Aura Communication Manager avCmDispSurvProcessObjGrp MIB
        objects"
    ::= { avCmMIBGroups 50 }

avCmListNodeNamesAllObjGrp     OBJECT-GROUP
    OBJECTS   {
		avCmListNodeNamesAllName,
		avCmListNodeNamesAllType,
		avCmListNodeNamesAllIPAddress 
                }
    STATUS      current
    DESCRIPTION
        "Avaya Aura Communication Manager avCmListNodeNamesAllObjGrp MIB
        objects"
    ::= { avCmMIBGroups 51 }


avCmListNodeNamesV4ObjGrp     OBJECT-GROUP
    OBJECTS   {
                avCmListNodeNamesV4Name,
                avCmListNodeNamesV4Type,
                avCmListNodeNamesV4IPAddress
                }
    STATUS      current
    DESCRIPTION
        "Avaya Aura Communication Manager avCmListNodeNamesV4ObjGrp MIB
        objects"
    ::= { avCmMIBGroups 52 }


avCmListNodeNamesV6ObjGrp     OBJECT-GROUP
    OBJECTS   {
                avCmListNodeNamesV6Name,
                avCmListNodeNamesV6Type,
                avCmListNodeNamesV6IPAddress
                }
    STATUS      current
    DESCRIPTION
        "Avaya Aura Communication Manager avCmListNodeNamesV6ObjGrp MIB
        objects"
    ::= { avCmMIBGroups 53 }


avCmListAnnObjGrp     OBJECT-GROUP
    OBJECTS   {
		avCmListAnnExtension,
		avCmListAnnType,
		avCmListAnnName,
		avCmListAnnSource,
		avCmListAnnNumFiles
                }
    STATUS      current
    DESCRIPTION
        "Avaya Aura Communication Manager avCmavCmListAnnObjGrp MIB
        objects"
    ::= { avCmMIBGroups 54 }


avCmListIpUnregisteredRangeObjGrp     OBJECT-GROUP
    OBJECTS   {
                avCmListIpUnregisteredRangeStartExt,
                avCmListIpUnregisteredRangeCount,
                avCmListIpUnregisteredRangeExtension,
                avCmListIpUnregisteredRangePort,
                avCmListIpUnregisteredRangeRegistered
                 }
    STATUS      current
    DESCRIPTION
        "Avaya Aura Communication Manager avCmListIpUnregisteredRangeObjGrp MIB
        objects"
    ::= { avCmMIBGroups 55 }


avCmDispTimeObjGrp     OBJECT-GROUP
    OBJECTS   {
		avCmDispTimeDayOfWeek,
		avCmDispTimeMonth,
		avCmDispTimeDayOfTheMonth,
		avCmDispTimeYear,
		avCmDispTimeHour,
		avCmDispTimeMinute,
		avCmDispTimeSecond,
		avCmDispTimeType,
		avCmDispTimeDSTRule
                 }
    STATUS      current
    DESCRIPTION
        "Avaya Aura Communication Manager avCmDispTimeObjGrp MIB
        objects"
    ::= { avCmMIBGroups 56 }


avCmMessagingAlarmObjGrp     OBJECT-GROUP
    OBJECTS   {
                avCmMessagingAlarmID,
                avCmMessagingAlarmApp,
                avCmMessagingAlarmSource,
                avCmMessagingAlarmEventID,
                avCmMessagingAlarmLevel,
                avCmMessagingAlarmAck,
                avCmMessagingAlarmLoc,
                avCmMessagingAlarmDate,
                avCmMessagingAlarmDescription

                 }
    STATUS      current
    DESCRIPTION
        "Avaya Aura Communication Manager avCmMessagingAlarmObjGrp MIB
        objects"
    ::= { avCmMIBGroups 57 }

avCmInitCausesObjGrp     OBJECT-GROUP
    OBJECTS   {
                avCmInitCausesTime,
                avCmInitCausesCause,
                avCmInitCausesAction,
                avCmInitCausesEscalated,
                avCmInitCausesMode
                 }
    STATUS      current
    DESCRIPTION
        "Avaya Aura Communication Manager avCmInitCausesObjGrp MIB
        objects"
    ::= { avCmMIBGroups 58 }

avCmMeasAnnIntegAllLstHrObjGrp     OBJECT-GROUP
    OBJECTS   {
                avCmMeasAnnIntegAllLstHrExtension,
                avCmMeasAnnIntegAllLstHrRunDate,
                avCmMeasAnnIntegAllLstHrSource,
                avCmMeasAnnIntegAllLstHrPlayPorts,
                avCmMeasAnnIntegAllLstHrMaxCallrsPeriod,
                avCmMeasAnnIntegAllLstHrAllPortsBusyPeriod,
                avCmMeasAnnIntegAllLstHrName,
                avCmMeasAnnIntegAllLstHrMeasHour,
                avCmMeasAnnIntegAllLstHrPlayRequests,
                avCmMeasAnnIntegAllLstHrCallsQueued,
                avCmMeasAnnIntegAllLstHrASP,
                avCmMeasAnnIntegAllLstHrPSP,
                avCmMeasAnnIntegAllLstHrQueueDrops,
                avCmMeasAnnIntegAllLstHrMportPlays,
                avCmMeasAnnIntegAllLstHrMxPorts,
                avCmMeasAnnIntegAllLstHrMaxCallers
                 }
    STATUS      current
    DESCRIPTION
        "Avaya Aura Communication Manager avCmMeasAnnIntegAllLstHrObjGrp MIB
        objects"
    ::= { avCmMIBGroups 59 }

avCmMeasAnnIntegAllTodayObjGrp     OBJECT-GROUP
    OBJECTS   {
                avCmMeasAnnIntegAllTodayExtension,
                avCmMeasAnnIntegAllTodayRunDate,
                avCmMeasAnnIntegAllTodaySource,
                avCmMeasAnnIntegAllTodayPlayPorts,
                avCmMeasAnnIntegAllTodayMaxCallrsPeriod,
                avCmMeasAnnIntegAllTodayAllPortsBusyPeriod,
                avCmMeasAnnIntegAllTodayName,
                avCmMeasAnnIntegAllTodayMeasHour,
                avCmMeasAnnIntegAllTodayPlayRequests,
                avCmMeasAnnIntegAllTodayCallsQueued,
                avCmMeasAnnIntegAllTodayASP,
                avCmMeasAnnIntegAllTodayPSP,
                avCmMeasAnnIntegAllTodayQueueDrops,
                avCmMeasAnnIntegAllTodayMportPlays,
                avCmMeasAnnIntegAllTodayMxPorts,
                avCmMeasAnnIntegAllTodayMaxCallers
                 }
    STATUS      current
    DESCRIPTION
        "Avaya Aura Communication Manager avCmMeasAnnIntegAllTodayObjGrp MIB
        objects"
    ::= { avCmMIBGroups 60 }

avCmMeasAnnIntegAllYestObjGrp     OBJECT-GROUP
    OBJECTS   {
                avCmMeasAnnIntegAllYestExtension,
                avCmMeasAnnIntegAllYestRunDate,
                avCmMeasAnnIntegAllYestSource,
                avCmMeasAnnIntegAllYestPlayPorts,
                avCmMeasAnnIntegAllYestMaxCallrsPeriod,
                avCmMeasAnnIntegAllYestAllPortsBusyPeriod,
                avCmMeasAnnIntegAllYestName,
                avCmMeasAnnIntegAllYestMeasHour,
                avCmMeasAnnIntegAllYestPlayRequests,
                avCmMeasAnnIntegAllYestCallsQueued,
                avCmMeasAnnIntegAllYestASP,
                avCmMeasAnnIntegAllYestPSP,
                avCmMeasAnnIntegAllYestQueueDrops,
                avCmMeasAnnIntegAllYestMportPlays,
                avCmMeasAnnIntegAllYestMxPorts,
                avCmMeasAnnIntegAllYestMaxCallers 
                 }
    STATUS      current
    DESCRIPTION
        "Avaya Aura Communication Manager avCmMeasAnnIntegAllYestObjGrp MIB
        objects"
    ::= { avCmMIBGroups 61 }

avCmStatusMGAnnObjGrp     OBJECT-GROUP
    OBJECTS   {
                avCmStatusMGAnnMGNum,
                avCmStatusMGAnnMGType,
                avCmStatusMGAnnEnabled,
                avCmStatusMGAnnStorUsedTotal,
                avCmStatusMGAnnStorUsedUsed,
                avCmStatusMGAnnStorUsedAvail,
                avCmStatusMGAnnCfStatIns,
                avCmStatusMGAnnCfStatAct,
                avCmStatusMGAnnCfStatErr
                 }
    STATUS      current
    DESCRIPTION
        "Avaya Aura Communication Manager avCmStatusMGAnnObjGrp MIB
        objects"
    ::= { avCmMIBGroups 62 }


avCmListIntegAnnObjGrp     OBJECT-GROUP
    OBJECTS   {
                avCmListIntegAnnSource,
                avCmListIntegAnnTimeRem,
                avCmListIntegAnnKbps,
                avCmListIntegAnnIntNum,
                avCmListIntegAnnGrpNum,
                avCmListIntegAnnExtension,
                avCmListIntegAnnName,
                avCmListIntegAnnLength,
                avCmListIntegAnnSize
                 }
    STATUS      current
    DESCRIPTION
        "Avaya Aura Communication Manager avCmListIntegAnnObjGrp MIB
        objects"
    ::= { avCmMIBGroups 63 }


avCmMeasIpVoStatHrJitterObjGrp     OBJECT-GROUP
    OBJECTS   {
                avCmMeasIpVoStatHrJitterRegion,
                avCmMeasIpVoStatHrJitterMeasHour,
                avCmMeasIpVoStatHrJitterRunTime,
                avCmMeasIpVoStatHrJitterBoardLoc,
                avCmMeasIpVoStatHrJitterCallingNum,
                avCmMeasIpVoStatHrJitterCalledNum,
                avCmMeasIpVoStatHrJitterCodec,
                avCmMeasIpVoStatHrJitterPktSize,
                avCmMeasIpVoStatHrJitterTimeCall,
                avCmMeasIpVoStatHrJitterBufSize,
                avCmMeasIpVoStatHrJitterBufOrn,
                avCmMeasIpVoStatHrJitterBufUrn,
                avCmMeasIpVoStatHrJitterAvgJitter,
                avCmMeasIpVoStatHrJitterPeakJitter,
                avCmMeasIpVoStatHrJitterFarIpAddr
                 }
    STATUS      current
    DESCRIPTION
        "Avaya Aura Communication Manager avCmMeasIpVoStatHrJitterObjGrp MIB
        objects"
    ::= { avCmMIBGroups 64 }

avCmMeasIpVoStatHrPkLosObjGrp     OBJECT-GROUP
    OBJECTS   {
                avCmMeasIpVoStatHrPkLosRegion,
                avCmMeasIpVoStatHrPkLosMeasHour,
                avCmMeasIpVoStatHrPkLosRunTime,
                avCmMeasIpVoStatHrPkLosBoardLoc,
                avCmMeasIpVoStatHrPkLosCallingNum,
                avCmMeasIpVoStatHrPkLosCalledNum,
                avCmMeasIpVoStatHrPkLosCodec,
                avCmMeasIpVoStatHrPkLosDstReg,
                avCmMeasIpVoStatHrPkLosTimeCall,
                avCmMeasIpVoStatHrPkLosUDPPort,
                avCmMeasIpVoStatHrPkLosPktSize,
                avCmMeasIpVoStatHrPkLosTotnumLosPkts,
                avCmMeasIpVoStatHrPkLosPktLossPerc,
                avCmMeasIpVoStatHrPkLosSilSup,
                avCmMeasIpVoStatHrPkLosFEAddr
                 }
    STATUS      current
    DESCRIPTION
        "Avaya Aura Communication Manager avCmMeasIpVoStatHrPkLosObjGrp MIB
        objects"
    ::= { avCmMIBGroups 65 }

avCmMeasIpVoStatHrRtdelObjGrp     OBJECT-GROUP
    OBJECTS   {
                avCmMeasIpVoStatHrRtdelRegion,
                avCmMeasIpVoStatHrRtdelMeasHour,
                avCmMeasIpVoStatHrRtdelRunTime,
                avCmMeasIpVoStatHrRtdelBoardLoc,
                avCmMeasIpVoStatHrRtdelCallingNum,
                avCmMeasIpVoStatHrRtdelCalledNum,
                avCmMeasIpVoStatHrRtdelCodec,
                avCmMeasIpVoStatHrRtdelPktSize,
                avCmMeasIpVoStatHrRtdelDstReg,
                avCmMeasIpVoStatHrRtdelAvg,
                avCmMeasIpVoStatHrRtdelPeak,
                avCmMeasIpVoStatHrRtdelTimeCall,
                avCmMeasIpVoStatHrRtdelDataCall,
                avCmMeasIpVoStatHrRtdelEncryp,
                avCmMeasIpVoStatHrRtdelEC,
                avCmMeasIpVoStatHrRtdelFEAddr
                 }
    STATUS      current
    DESCRIPTION
        "Avaya Aura Communication Manager avCmMeasIpVoStatHrRtdelObjGrp MIB
        objects"
    ::= { avCmMIBGroups 66 }

avCmMeasIpVoStatHrDataObjGrp     OBJECT-GROUP
    OBJECTS   {
                avCmMeasIpVoStatHrDataRegion,
                avCmMeasIpVoStatHrDataMeasHour,
                avCmMeasIpVoStatHrDataRunTime,
                avCmMeasIpVoStatHrDataBoardLoc,
                avCmMeasIpVoStatHrDataCallingNum,
                avCmMeasIpVoStatHrDataCalledNum,
                avCmMeasIpVoStatHrDataCodec,
                avCmMeasIpVoStatHrDataDataType,
                avCmMeasIpVoStatHrDataPktSize,
                avCmMeasIpVoStatHrDataLossPerc,
                avCmMeasIpVoStatHrDataPeakJitter,
                avCmMeasIpVoStatHrDataPeakDly,
                avCmMeasIpVoStatHrDataEC,
                avCmMeasIpVoStatHrDataFarIpAddr
                 }
    STATUS      current
    DESCRIPTION
        "Avaya Aura Communication Manager avCmMeasIpVoStatHrDataObjGrp MIB
        objects"
    ::= { avCmMIBGroups 67 }


avCmMeasIpVoStatSumJitterLstHrObjGrp     OBJECT-GROUP
    OBJECTS   {
		avCmMeasIpVoStatSumJitterLstHrRegion,
		avCmMeasIpVoStatSumJitterLstHrMeasHour,
		avCmMeasIpVoStatSumJitterLstHrRunTime,
		avCmMeasIpVoStatSumJitterLstHrBoardLoc,
		avCmMeasIpVoStatSumJitterLstHrCallingNum,
		avCmMeasIpVoStatSumJitterLstHrCalledNum,
		avCmMeasIpVoStatSumJitterLstHrDstReg,
		avCmMeasIpVoStatSumJitterLstHrCodec,
		avCmMeasIpVoStatSumJitterLstHrPktSize,
		avCmMeasIpVoStatSumJitterLstHrTimeCall,
		avCmMeasIpVoStatSumJitterLstHrBufSize,
		avCmMeasIpVoStatSumJitterLstHrBufOrn,
		avCmMeasIpVoStatSumJitterLstHrBufUrn,
		avCmMeasIpVoStatSumJitterLstHrAvgJitter,
		avCmMeasIpVoStatSumJitterLstHrPeakJitter,
		avCmMeasIpVoStatSumJitterLstHrFarIpAddr
                 }
    STATUS      current
    DESCRIPTION
    "Avaya Aura Communication Manager avCmMeasIpVoStatSumJitterLstHrObjGrp MIB
        objects"
    ::= { avCmMIBGroups 68 }

avCmMeasIpVoStatSumJitterTodayObjGrp     OBJECT-GROUP
    OBJECTS   {
                avCmMeasIpVoStatSumJitterTodayRegion,
                avCmMeasIpVoStatSumJitterTodayMeasHour,
                avCmMeasIpVoStatSumJitterTodayRunTime,
                avCmMeasIpVoStatSumJitterTodayBoardLoc,
                avCmMeasIpVoStatSumJitterTodayCallingNum,
                avCmMeasIpVoStatSumJitterTodayCalledNum,
                avCmMeasIpVoStatSumJitterTodayDstReg,
                avCmMeasIpVoStatSumJitterTodayCodec,
                avCmMeasIpVoStatSumJitterTodayPktSize,
                avCmMeasIpVoStatSumJitterTodayTimeCall,
                avCmMeasIpVoStatSumJitterTodayBufSize,
                avCmMeasIpVoStatSumJitterTodayBufOrn,
                avCmMeasIpVoStatSumJitterTodayBufUrn,
                avCmMeasIpVoStatSumJitterTodayAvgJitter,
                avCmMeasIpVoStatSumJitterTodayPeakJitter,
                avCmMeasIpVoStatSumJitterTodayFarIpAddr
                 }
    STATUS      current
    DESCRIPTION
    "Avaya Aura Communication Manager avCmMeasIpVoStatSumJitterTodayObjGrp MIB
        objects"
    ::= { avCmMIBGroups 69 }

avCmMeasIpVoStatSumJitterYestObjGrp     OBJECT-GROUP
    OBJECTS   {
                avCmMeasIpVoStatSumJitterYestRegion,
                avCmMeasIpVoStatSumJitterYestMeasHour,
                avCmMeasIpVoStatSumJitterYestRunTime,
                avCmMeasIpVoStatSumJitterYestBoardLoc,
                avCmMeasIpVoStatSumJitterYestCallingNum,
                avCmMeasIpVoStatSumJitterYestCalledNum,
                avCmMeasIpVoStatSumJitterYestDstReg,
                avCmMeasIpVoStatSumJitterYestCodec,
                avCmMeasIpVoStatSumJitterYestPktSize,
                avCmMeasIpVoStatSumJitterYestTimeCall,
                avCmMeasIpVoStatSumJitterYestBufSize,
                avCmMeasIpVoStatSumJitterYestBufOrn,
                avCmMeasIpVoStatSumJitterYestBufUrn,
                avCmMeasIpVoStatSumJitterYestAvgJitter,
                avCmMeasIpVoStatSumJitterYestPeakJitter,
                avCmMeasIpVoStatSumJitterYestFarIpAddr
                 }
    STATUS      current
    DESCRIPTION
    "Avaya Aura Communication Manager avCmMeasIpVoStatSumJitterYestObjGrp MIB
        objects"
    ::= { avCmMIBGroups 70 }

avCmMeasIpVoStatSumPkLosLstHrObjGrp     OBJECT-GROUP
    OBJECTS   {
                avCmMeasIpVoStatSumPkLosLstHrRegion,
                avCmMeasIpVoStatSumPkLosLstHrMeasHour,
                avCmMeasIpVoStatSumPkLosLstHrRunTime,
                avCmMeasIpVoStatSumPkLosLstHrBoardLoc,
                avCmMeasIpVoStatSumPkLosLstHrCallingNum,
                avCmMeasIpVoStatSumPkLosLstHrCalledNum,
                avCmMeasIpVoStatSumPkLosLstHrDstReg,
                avCmMeasIpVoStatSumPkLosLstHrCodec,
                avCmMeasIpVoStatSumPkLosLstHrTimeCall,
                avCmMeasIpVoStatSumPkLosLstHrUDPPort,
                avCmMeasIpVoStatSumPkLosLstHrPktSize,
                avCmMeasIpVoStatSumPkLosLstHrTotnumLosPkts,
                avCmMeasIpVoStatSumPkLosLstHrPktLossPerc,
                avCmMeasIpVoStatSumPkLosLstHrSilSup,
                avCmMeasIpVoStatSumPkLosLstHrFEAddr
                 }
    STATUS      current
    DESCRIPTION
    "Avaya Aura Communication Manager avCmMeasIpVoStatSumPkLosLstHrObjGrp MIB
        objects"
    ::= { avCmMIBGroups 71 }

avCmMeasIpVoStatSumPkLosTodayObjGrp     OBJECT-GROUP
    OBJECTS   {
                avCmMeasIpVoStatSumPkLosTodayRegion,
                avCmMeasIpVoStatSumPkLosTodayMeasHour,
                avCmMeasIpVoStatSumPkLosTodayRunTime,
                avCmMeasIpVoStatSumPkLosTodayBoardLoc,
                avCmMeasIpVoStatSumPkLosTodayCallingNum,
                avCmMeasIpVoStatSumPkLosTodayCalledNum,
                avCmMeasIpVoStatSumPkLosTodayDstReg,
                avCmMeasIpVoStatSumPkLosTodayCodec,
                avCmMeasIpVoStatSumPkLosTodayTimeCall,
                avCmMeasIpVoStatSumPkLosTodayUDPPort,
                avCmMeasIpVoStatSumPkLosTodayPktSize,
                avCmMeasIpVoStatSumPkLosTodayTotnumLosPkts,
                avCmMeasIpVoStatSumPkLosTodayPktLossPerc,
                avCmMeasIpVoStatSumPkLosTodaySilSup,
                avCmMeasIpVoStatSumPkLosTodayFEAddr
                 }
    STATUS      current
    DESCRIPTION
    "Avaya Aura Communication Manager avCmMeasIpVoStatSumPkLosTodayObjGrp MIB
        objects"
    ::= { avCmMIBGroups 72 }
avCmMeasIpVoStatSumPkLosYestObjGrp     OBJECT-GROUP
    OBJECTS   {
                avCmMeasIpVoStatSumPkLosYestRegion,
                avCmMeasIpVoStatSumPkLosYestMeasHour,
                avCmMeasIpVoStatSumPkLosYestRunTime,
                avCmMeasIpVoStatSumPkLosYestBoardLoc,
                avCmMeasIpVoStatSumPkLosYestCallingNum,
                avCmMeasIpVoStatSumPkLosYestCalledNum,
                avCmMeasIpVoStatSumPkLosYestDstReg,
                avCmMeasIpVoStatSumPkLosYestCodec,
                avCmMeasIpVoStatSumPkLosYestTimeCall,
                avCmMeasIpVoStatSumPkLosYestUDPPort,
                avCmMeasIpVoStatSumPkLosYestPktSize,
                avCmMeasIpVoStatSumPkLosYestTotnumLosPkts,
                avCmMeasIpVoStatSumPkLosYestPktLossPerc,
                avCmMeasIpVoStatSumPkLosYestSilSup,
                avCmMeasIpVoStatSumPkLosYestFEAddr
                 }
    STATUS      current
    DESCRIPTION
    "Avaya Aura Communication Manager avCmMeasIpVoStatSumPkLosYestObjGrp MIB
        objects"
    ::= { avCmMIBGroups 73 }

avCmMeasIpVoStatSumRtdelLstHrObjGrp     OBJECT-GROUP
    OBJECTS   {
                avCmMeasIpVoStatSumRtdelLstHrRegion,
                avCmMeasIpVoStatSumRtdelLstHrMeasHour,
                avCmMeasIpVoStatSumRtdelLstHrRunTime,
                avCmMeasIpVoStatSumRtdelLstHrBoardLoc,
                avCmMeasIpVoStatSumRtdelLstHrCallingNum,
                avCmMeasIpVoStatSumRtdelLstHrCalledNum,
		avCmMeasIpVoStatSumRtdelLstHrPktSize,
                avCmMeasIpVoStatSumRtdelLstHrDstReg,
                avCmMeasIpVoStatSumRtdelLstHrCodec,
                avCmMeasIpVoStatSumRtdelLstHrAvg,
                avCmMeasIpVoStatSumRtdelLstHrPeak,
                avCmMeasIpVoStatSumRtdelLstHrTimeCall,
                avCmMeasIpVoStatSumRtdelLstHrDataCall,
                avCmMeasIpVoStatSumRtdelLstHrEncryp,
                avCmMeasIpVoStatSumRtdelLstHrEC,
                avCmMeasIpVoStatSumRtdelLstHrFEAddr
                 }
    STATUS      current
    DESCRIPTION
    "Avaya Aura Communication Manager avCmMeasIpVoStatSumRtdelLstHrObjGrp MIB
        objects"
    ::= { avCmMIBGroups 74 }

avCmMeasIpVoStatSumRtdelTodayObjGrp     OBJECT-GROUP
    OBJECTS   {
                avCmMeasIpVoStatSumRtdelTodayRegion,
                avCmMeasIpVoStatSumRtdelTodayMeasHour,
                avCmMeasIpVoStatSumRtdelTodayRunTime,
                avCmMeasIpVoStatSumRtdelTodayBoardLoc,
                avCmMeasIpVoStatSumRtdelTodayCallingNum,
                avCmMeasIpVoStatSumRtdelTodayCalledNum,
                avCmMeasIpVoStatSumRtdelTodayPktSize,
                avCmMeasIpVoStatSumRtdelTodayDstReg,
                avCmMeasIpVoStatSumRtdelTodayCodec,
                avCmMeasIpVoStatSumRtdelTodayAvg,
                avCmMeasIpVoStatSumRtdelTodayPeak,
                avCmMeasIpVoStatSumRtdelTodayTimeCall,
                avCmMeasIpVoStatSumRtdelTodayDataCall,
                avCmMeasIpVoStatSumRtdelTodayEncryp,
                avCmMeasIpVoStatSumRtdelTodayEC,
                avCmMeasIpVoStatSumRtdelTodayFEAddr
                 }
    STATUS      current
    DESCRIPTION
    "Avaya Aura Communication Manager avCmMeasIpVoStatSumRtdelTodayObjGrp MIB
        objects"
    ::= { avCmMIBGroups 75 }

avCmMeasIpVoStatSumRtdelYestObjGrp     OBJECT-GROUP
    OBJECTS   {
                avCmMeasIpVoStatSumRtdelYestRegion,
                avCmMeasIpVoStatSumRtdelYestMeasHour,
                avCmMeasIpVoStatSumRtdelYestRunTime,
                avCmMeasIpVoStatSumRtdelYestBoardLoc,
                avCmMeasIpVoStatSumRtdelYestCallingNum,
                avCmMeasIpVoStatSumRtdelYestCalledNum,
                avCmMeasIpVoStatSumRtdelYestPktSize,
                avCmMeasIpVoStatSumRtdelYestDstReg,
                avCmMeasIpVoStatSumRtdelYestCodec,
                avCmMeasIpVoStatSumRtdelYestAvg,
                avCmMeasIpVoStatSumRtdelYestPeak,
                avCmMeasIpVoStatSumRtdelYestTimeCall,
                avCmMeasIpVoStatSumRtdelYestDataCall,
                avCmMeasIpVoStatSumRtdelYestEncryp,
                avCmMeasIpVoStatSumRtdelYestEC,
                avCmMeasIpVoStatSumRtdelYestFEAddr
                 }
    STATUS      current
    DESCRIPTION
    "Avaya Aura Communication Manager avCmMeasIpVoStatSumRtdelYestObjGrp MIB
        objects"
    ::= { avCmMIBGroups 76 }

avCmMeasIpVoStatSumDataLstHrObjGrp     OBJECT-GROUP
    OBJECTS   {
                avCmMeasIpVoStatSumDataLstHrRegion,
                avCmMeasIpVoStatSumDataLstHrMeasHour,
                avCmMeasIpVoStatSumDataLstHrRunTime,
                avCmMeasIpVoStatSumDataLstHrBoardLoc,
                avCmMeasIpVoStatSumDataLstHrCallingNum,
                avCmMeasIpVoStatSumDataLstHrCalledNum,
                avCmMeasIpVoStatSumDataLstHrDstReg,
                avCmMeasIpVoStatSumDataLstHrCodec,
                avCmMeasIpVoStatSumDataLstHrDataType,
                avCmMeasIpVoStatSumDataLstHrPktSize,
                avCmMeasIpVoStatSumDataLstHrLossPerc,
                avCmMeasIpVoStatSumDataLstHrPeakJitter,
                avCmMeasIpVoStatSumDataLstHrPeakDly,
                avCmMeasIpVoStatSumDataLstHrEC,
                avCmMeasIpVoStatSumDataLstHrFEAddr
                 }
    STATUS      current
    DESCRIPTION
    "Avaya Aura Communication Manager avCmMeasIpVoStatSumDataLstHrObjGrp MIB
        objects"
    ::= { avCmMIBGroups 77 }

avCmMeasIpVoStatSumDataTodayObjGrp     OBJECT-GROUP
    OBJECTS   {
                avCmMeasIpVoStatSumDataTodayRegion,
                avCmMeasIpVoStatSumDataTodayMeasHour,
                avCmMeasIpVoStatSumDataTodayRunTime,
                avCmMeasIpVoStatSumDataTodayBoardLoc,
                avCmMeasIpVoStatSumDataTodayCallingNum,
                avCmMeasIpVoStatSumDataTodayCalledNum,
                avCmMeasIpVoStatSumDataTodayPktSize,
                avCmMeasIpVoStatSumDataTodayDstReg,
                avCmMeasIpVoStatSumDataTodayCodec,
                avCmMeasIpVoStatSumDataTodayDataType,
                avCmMeasIpVoStatSumDataTodayPktSize,
                avCmMeasIpVoStatSumDataTodayLossPerc,
                avCmMeasIpVoStatSumDataTodayPeakJitter,
                avCmMeasIpVoStatSumDataTodayPeakDly,
                avCmMeasIpVoStatSumDataTodayEC,
                avCmMeasIpVoStatSumDataTodayFEAddr
                 }
    STATUS      current
    DESCRIPTION
    "Avaya Aura Communication Manager avCmMeasIpVoStatSumDataTodayObjGrp MIB
        objects"
    ::= { avCmMIBGroups 78 }

avCmMeasIpVoStatSumDataYestObjGrp     OBJECT-GROUP
    OBJECTS   {
                avCmMeasIpVoStatSumDataYestRegion,
                avCmMeasIpVoStatSumDataYestMeasHour,
                avCmMeasIpVoStatSumDataYestRunTime,
                avCmMeasIpVoStatSumDataYestBoardLoc,
                avCmMeasIpVoStatSumDataYestCallingNum,
                avCmMeasIpVoStatSumDataYestCalledNum,
                avCmMeasIpVoStatSumDataYestPktSize,
                avCmMeasIpVoStatSumDataYestDstReg,
                avCmMeasIpVoStatSumDataYestCodec,
                avCmMeasIpVoStatSumDataYestDataType,
                avCmMeasIpVoStatSumDataYestPktSize,
                avCmMeasIpVoStatSumDataYestLossPerc,
                avCmMeasIpVoStatSumDataYestPeakJitter,
                avCmMeasIpVoStatSumDataYestPeakDly,
                avCmMeasIpVoStatSumDataYestEC,
                avCmMeasIpVoStatSumDataYestFEAddr
                 }
    STATUS      current
    DESCRIPTION
    "Avaya Aura Communication Manager avCmMeasIpVoStatSumDataYestObjGrp MIB
        objects"
    ::= { avCmMIBGroups 79 }


avCmMeasAnnAllLstHrObjGrp     OBJECT-GROUP
    OBJECTS   {
                avCmMeasAnnAllLstHrExtension,
                avCmMeasAnnAllLstHrRunDate,
                avCmMeasAnnAllLstHrName,
                avCmMeasAnnAllLstHrMeasHour,
                avCmMeasAnnAllLstHrPlayRequests,
                avCmMeasAnnAllLstHrCallsQueued,
                avCmMeasAnnAllLstHrASP,
                avCmMeasAnnAllLstHrPSP,
                avCmMeasAnnAllLstHrQueueDrops,
                avCmMeasAnnAllLstHrMportPlays,
                avCmMeasAnnAllLstHrMxPorts,
                avCmMeasAnnAllLstHrMaxCallers
                 }
    STATUS      current
    DESCRIPTION
        "Avaya Aura Communication Manager avCmMeasAnnAllLstHrObjGrp MIB
        objects"
    ::= { avCmMIBGroups 80 }


avCmMeasAnnAllTodayObjGrp     OBJECT-GROUP
    OBJECTS   {
                avCmMeasAnnAllTodayExtension,
                avCmMeasAnnAllTodayRunDate,
                avCmMeasAnnAllTodayName,
                avCmMeasAnnAllTodayMeasHour,
                avCmMeasAnnAllTodayPlayRequests,
                avCmMeasAnnAllTodayCallsQueued,
                avCmMeasAnnAllTodayASP,
                avCmMeasAnnAllTodayPSP,
                avCmMeasAnnAllTodayQueueDrops,
                avCmMeasAnnAllTodayMportPlays,
                avCmMeasAnnAllTodayMxPorts,
                avCmMeasAnnAllTodayMaxCallers
                 }
    STATUS      current
    DESCRIPTION
        "Avaya Aura Communication Manager avCmMeasAnnAllTodayObjGrp MIB
        objects"
    ::= { avCmMIBGroups 81 }

avCmMeasAnnAllYestObjGrp     OBJECT-GROUP
    OBJECTS   {
                avCmMeasAnnAllYestExtension,
                avCmMeasAnnAllYestRunDate,
                avCmMeasAnnAllYestName,
                avCmMeasAnnAllYestMeasHour,
                avCmMeasAnnAllYestPlayRequests,
                avCmMeasAnnAllYestCallsQueued,
                avCmMeasAnnAllYestASP,
                avCmMeasAnnAllYestPSP,
                avCmMeasAnnAllYestQueueDrops,
                avCmMeasAnnAllYestMportPlays,
                avCmMeasAnnAllYestMxPorts,
                avCmMeasAnnAllYestMaxCallers
                 }
    STATUS      current
    DESCRIPTION
        "Avaya Aura Communication Manager avCmMeasAnnAllYestObjGrp MIB
        objects"
    ::= { avCmMIBGroups 82 }

avCmPlatCmdsObjGrp     OBJECT-GROUP
    OBJECTS   {
                avCmPlatCmdsDate,
                avCmPlatCmdsTime,
                avCmPlatCmdsSeqNumber,
                avCmPlatCmdsPriority,
                avCmPlatCmdsServerName,
                avCmPlatCmdsLoginId,
                avCmPlatCmdsCommand
                 }
    STATUS      current
    DESCRIPTION
        "Avaya Aura Communication Manager avCmPlatCmdsObjGrp MIB
        objects"
    ::= { avCmMIBGroups 83 }

avCmListSigGrpObjGrp     OBJECT-GROUP
    OBJECTS   {
                avCmListSigGrpGrpNumber,
                avCmListSigGrpGrpType,
                avCmListSigGrpFAS,
                avCmListSigGrpTrkBrds,
                avCmListSigGrpPriDChannel,
                avCmListSigGrpSecDChannel,
                avCmListSigGrpMaxNCATSC,
                avCmListSigGrpMaxCATSC,
                avCmListSigGrpNoAdmdNCATSCs,
                avCmListSigGrpNearNode,
                avCmListSigGrpFarNode
                 }
    STATUS      current
    DESCRIPTION
        "Avaya Aura Communication Manager avCmListSigGrpObjGrp MIB
        objects"
    ::= { avCmMIBGroups 84 }

avCmStatusSigGrpObjGrp     OBJECT-GROUP
    OBJECTS   {
                avCmStatusSigGrpGrpNumber,
                avCmStatusSigGrpGrpType,
                avCmStatusSigGrpGrpState
                 }
    STATUS      current
    DESCRIPTION
        "Avaya Aura Communication Manager avCmStatusSigGrpObjGrp MIB
        objects"
    ::= { avCmMIBGroups 85 }

avCmListHuntGrpObjGrp     OBJECT-GROUP
    OBJECTS   {
                avCmListHuntGrpGrpNumber,
                avCmListHuntGrpGrpName,
                avCmListHuntGrpGrpExt,
                avCmListHuntGrpGrpType,
                avCmListHuntGrpGrpAcdMeas,
                avCmListHuntGrpGrpVec,
                avCmListHuntGrpGrpMch,
                avCmListHuntGrpGrpQue,
                avCmListHuntGrpGrpNoMem,
                avCmListHuntGrpCovPath,
                avCmListHuntGrpNotifCtgAdj,
                avCmListHuntGrpDomCtrl,
                avCmListHuntGrpMsgCtr,
		avCmListHuntGrpMsgCtrName
                 }
    STATUS      current
    DESCRIPTION
        "Avaya Aura Communication Manager avCmListHuntGrpObjGrp MIB
        objects"
    ::= { avCmMIBGroups 86 }

avCmMeasHuntGrpLstHrObjGrp     OBJECT-GROUP
    OBJECTS   {
		avCmMeasHuntGrpLstHrHuntGrpNo,
		avCmMeasHuntGrpLstHrRunDate,
		avCmMeasHuntGrpLstHrGrpName,
		avCmMeasHuntGrpLstHrGroupSiz,
		avCmMeasHuntGrpLstHrMeasHour,
		avCmMeasHuntGrpLstHrTotalUsage, 
		avCmMeasHuntGrpLstHrCallsAns,
		avCmMeasHuntGrpLstHrGrpQue,
		avCmMeasHuntGrpLstHrCallsQue,
		avCmMeasHuntGrpLstHrQueOvfl,
		avCmMeasHuntGrpLstHrTimeAvail,
		avCmMeasHuntGrpLstHrSpeedAns,
		avCmMeasHuntGrpLstHrTyp,
		avCmMeasHuntGrpLstHrAban
                 }
    STATUS      current
    DESCRIPTION
        "Avaya Aura Communication Manager avCmMeasHuntGrpLstHrObjGrp MIB
        objects"
    ::= { avCmMIBGroups 87 }

avCmMeasHuntGrpTodayObjGrp     OBJECT-GROUP
    OBJECTS   {
                avCmMeasHuntGrpTodayHuntGrpNo,
                avCmMeasHuntGrpTodayRunDate,
                avCmMeasHuntGrpTodayGrpName,
                avCmMeasHuntGrpTodayGroupSiz,
                avCmMeasHuntGrpTodayMeasHour,
                avCmMeasHuntGrpTodayTotalUsage,
                avCmMeasHuntGrpTodayCallsAns,
                avCmMeasHuntGrpTodayGrpQue,
                avCmMeasHuntGrpTodayCallsQue,
                avCmMeasHuntGrpTodayQueOvfl,
                avCmMeasHuntGrpTodayTimeAvail,
                avCmMeasHuntGrpTodaySpeedAns,
                avCmMeasHuntGrpTodayTyp,
                avCmMeasHuntGrpTodayAban
                 }
    STATUS      current
    DESCRIPTION
        "Avaya Aura Communication Manager avCmMeasHuntGrpTodayObjGrp MIB
        objects"
    ::= { avCmMIBGroups 88 }

avCmMeasHuntGrpYestObjGrp     OBJECT-GROUP
    OBJECTS   {
                avCmMeasHuntGrpYestHuntGrpNo,
                avCmMeasHuntGrpYestRunDate,
                avCmMeasHuntGrpYestGrpName,
                avCmMeasHuntGrpYestGroupSiz,
                avCmMeasHuntGrpYestMeasHour,
                avCmMeasHuntGrpYestTotalUsage,
                avCmMeasHuntGrpYestCallsAns,
                avCmMeasHuntGrpYestGrpQue,
                avCmMeasHuntGrpYestCallsQue,
                avCmMeasHuntGrpYestQueOvfl,
                avCmMeasHuntGrpYestTimeAvail,
                avCmMeasHuntGrpYestSpeedAns,
                avCmMeasHuntGrpYestTyp,
                avCmMeasHuntGrpYestAban
                 }
    STATUS      current
    DESCRIPTION
        "Avaya Aura Communication Manager avCmMeasHuntGrpYestObjGrp MIB
        objects"
    ::= { avCmMIBGroups 89 }

avCmListIpInterfaceAllObjGrp     OBJECT-GROUP
    OBJECTS   {
		avCmListIpInterfaceAllOn,
		avCmListIpInterfaceAllType,
		avCmListIpInterfaceAllSlot,
		avCmListIpInterfaceAllCode,
		avCmListIpInterfaceAllSfx,
		avCmListIpInterfaceAllNodeName,
		avCmListIpInterfaceAllMask, 
		avCmListIpInterfaceAllNetRgn,
		avCmListIpInterfaceAllVlan,
		avCmListIpInterfaceMedproVirtualNode,
		avCmListIpInterfaceAllIpAddress,
		avCmListIpInterfaceAllGatewayNode,
		avCmListIpInterfaceAllOn2,
		avCmListIpInterfaceAllType2,
		avCmListIpInterfaceAllSlot2,
		avCmListIpInterfaceAllCode2,
		avCmListIpInterfaceAllSfx2,
		avCmListIpInterfaceAllNodeName2,
		avCmListIpInterfaceAllMask2, 
		avCmListIpInterfaceAllNetRgn2,
		avCmListIpInterfaceAllVlan2,
		avCmListIpInterfaceMedproVirtualNode2,
		avCmListIpInterfaceAllIpAddress2,
		avCmListIpInterfaceAllGatewayNode2
                 }
    STATUS      current
    DESCRIPTION
        "Avaya Aura Communication Manager avCmListIpInterfaceAllObjGrp MIB
        objects"
    ::= { avCmMIBGroups 90 }

avCmListIpInterfaceMedproObjGrp     OBJECT-GROUP
    OBJECTS   {
		avCmListIpInterfaceMedproOn,
		avCmListIpInterfaceMedproType,
		avCmListIpInterfaceMedproSlot,
		avCmListIpInterfaceMedproCode,
		avCmListIpInterfaceMedproSfx,
		avCmListIpInterfaceMedproNodeName,
		avCmListIpInterfaceMedproMask, 
		avCmListIpInterfaceMedproNetRgn,
		avCmListIpInterfaceMedproVlan,
		avCmListIpInterfaceMedproVirtualNode,
		avCmListIpInterfaceMedproIpAddress,
		avCmListIpInterfaceMedproGatewayNode,
		avCmListIpInterfaceMedproOn2,
		avCmListIpInterfaceMedproType2,
		avCmListIpInterfaceMedproSlot2,
		avCmListIpInterfaceMedproCode2,
		avCmListIpInterfaceMedproSfx2,
		avCmListIpInterfaceMedproNodeName2,
		avCmListIpInterfaceMedproMask2, 
		avCmListIpInterfaceMedproNetRgn2,
		avCmListIpInterfaceMedproVlan2,
		avCmListIpInterfaceMedproVirtualNode2,
		avCmListIpInterfaceMedproIpAddress2,
		avCmListIpInterfaceMedproGatewayNode2
                 }
    STATUS      current
    DESCRIPTION
        "Avaya Aura Communication Manager avCmListIpInterfaceMedproObjGrp MIB
        objects"
    ::= { avCmMIBGroups 91 }

avCmStatusMedproBrdObjGrp     OBJECT-GROUP
    OBJECTS   {
		avCmStatusMedproBrdBoardLoc,
		avCmStatusMedproBrdState,
		avCmStatusMedproBrdNodeName,
		avCmStatusMedproBrdIpAddess,
		avCmStatusMedproBrdSubnetMask,
		avCmStatusMedproBrdGatewayAddr,
		avCmStatusMedproBrdMACAddress,
		avCmStatusMedproBrdEtherEnabled ,
		avCmStatusMedproBrdDSPChanStatus1,
		avCmStatusMedproBrdDSPChanStatus2,
		avCmStatusMedproBrdDSPChanStatus3,
		avCmStatusMedproBrdDSPChanStatus4,
		avCmStatusMedproBrdDupDSPChanStatus5,
		avCmStatusMedproBrdDupDSPChanStatus6,
		avCmStatusMedproBrdDupDSPChanStatus7,
		avCmStatusMedproBrdDupDSPChanStatus8,
		avCmStatusMedproBrdNetworkRegion,
		avCmStatusMedproBrdDupNetworkRegion,
		avCmStatusMedproBrdStandbyRefreshed,
		avCmStatusMedproBrdSharedIP ,
		avCmStatusMedproBrdSharedVirtMAC,
		avCmStatusMedproBrdDupBoardLoc,
		avCmStatusMedproBrdDupState,
		avCmStatusMedproBrdDupNodeName,
		avCmStatusMedproBrdDupIpAddess,
		avCmStatusMedproBrdDupSubnetMask,
		avCmStatusMedproBrdDupGatewayAddr,
		avCmStatusMedproBrdDupMACAddress,
		avCmStatusMedproBrdDupEtherEnabled,
		avCmStatusMedproBrdLinkMPCL,
		avCmStatusMedproBrdLinkEth,
		avCmStatusMedproBrdLinkPeer,
		avCmStatusMedproBrdAlarmMaj,
		avCmStatusMedproBrdAlarmMin,
		avCmStatusMedproBrdAlarmWrn,
		avCmStatusMedproBrdDupLinkMPCL,
		avCmStatusMedproBrdDupLinkEth,
		avCmStatusMedproBrdDupLinkPeer,
		avCmStatusMedproBrdDupAlarmMaj,
		avCmStatusMedproBrdDupAlarmMin,
		avCmStatusMedproBrdDupAlarmWrn,
		avCmStatusMedproBrdLocked,
		avCmStatusMedproBrdIPV6Address,
		avCmStatusMedproBrdIPV6SubnetMask,
		avCmStatusMedproBrdIPV6GatewayAddr,
		avCmStatusMedproBrdIPV6NodeName,
		avCmStatusMedproBrdIPV6EtherEnable
                 }
    STATUS      current
    DESCRIPTION
        "Avaya Aura Communication Manager avCmStatusMedproBrdObjGrp MIB
        objects"
    ::= { avCmMIBGroups 92 }


avCmListIpServerIntfObjGrp     OBJECT-GROUP
    OBJECTS   {
		avCmListIpServerIntfPortNtwkNum,
		avCmListIpServerIntfPriBdLoc,
		avCmListIpServerIntfPrimaryIPAddress,
		avCmListIpServerIntfPrimaryHostName,
		avCmListIpServerIntfPrimaryDHCPID,
		avCmListIpServerIntfServState,
		avCmListIpServerIntfControlState, 
		avCmListIpServerIntfStateOfHealthCPEG,
		avCmListIpServerIntfSecondaryBdLoc,
		avCmListIpServerIntfSecondaryIPAddress,
		avCmListIpServerIntfSecondaryHostName,
		avCmListIpServerIntfSecondaryDHCPID,
		avCmListIpServerIntfSecondaryServState,
		avCmListIpServerIntfSecondaryControlState,
		avCmListIpServerIntfSecondaryStateOfHealth
                 }
    STATUS      current
    DESCRIPTION
        "Avaya Aura Communication Manager avCmListIpServerIntfObjGrp MIB
        objects"
    ::= { avCmMIBGroups 93 }

avCmStatusLinkObjGrp     OBJECT-GROUP
    OBJECTS   {
		avCmStatusLinkNum,
		avCmStatusLinkStatus,
		avCmStatusLinkType,
		avCmStatusLinkName,
		avCmStatusLinkServicePortLoc,
		avCmStatusLinkDataExt,
		avCmStatusLinkServiceState,
		avCmStatusLinkNodeName,
		avCmStatusLinkSourceIpAddress,
		avCmStatusLinkBroadcastAddress,
		avCmStatusLinkPhysicalAddress,
		avCmStatusLinkEthEnabled,
		avCmStatusLinkEthMaintBusy,
		avCmStatusLinkEthActiveChannels,
		avCmStatusLinkPPPEnabled,
		avCmStatusLinkPPPMaintBusy,
		avCmStatusLinkPPPActiveChannels,
		avCmStatusLinkAssocClanModem,
		avCmStatusLinkConnSpeed,
                avCmStatusLinkV6Status,
                avCmStatusLinkV6Type,
		avCmStatusLinkV6ServicePortLoc,
		avCmStatusLinkV6NodeName,
		avCmStatusLinkV6SourceIpAddress,
		avCmStatusLinkV6BroadcastAddress,
		avCmStatusLinkV6EthEnabled,
		avCmStatusLinkV6EthMaintBusy,
		avCmStatusLinkV6EthActiveChannels
                 }
    STATUS      current
    DESCRIPTION
        "Avaya Aura Communication Manager avCmStatusLinkObjGrp MIB
        objects"
    ::= { avCmMIBGroups 94 }

avCmListIPNetRegMonitorObjGrp     OBJECT-GROUP
    OBJECTS   {
                avCmListIPNetRegMonitorRegion,
                avCmListIPNetRegMonitorName,
                avCmListIPNetRegMonitorPortNoIPv4,
                avCmListIPNetRegMonitorRTCPMonIPv4Addr,
                avCmListIPNetRegMonitorServiceReportPer,
                avCmListIPNetRegMonitorCodecSet,
                avCmListIPNetRegMonitorUDPPortRangeMin,
                avCmListIPNetRegMonitorUDPPortRangeMax,
                avCmListIPNetRegMonitorPortNoIPv6,
                avCmListIPNetRegMonitorRTCPMonIPv6Addr
                 }
    STATUS      current
    DESCRIPTION
        "Avaya Aura Communication Manager avCmListIPNetRegMonitorObjGrp MIB
        objects"
    ::= { avCmMIBGroups 95 }


avCmStatIpNetRegionObjGrp     OBJECT-GROUP
    OBJECTS   {
                avCmStatIpNetRegionSrcRgn,
                avCmStatIpNetRegionDstRgn,
                avCmStatIpNetRegionConnType,
                avCmStatIpNetRegionConnStat,
                avCmStatIpNetRegionBWlimit,
                avCmStatIpNetRegionBWUnits,
                avCmStatIpNetRegionBWUsedbitsTx,
                avCmStatIpNetRegionBWUsedbitsRx,
                avCmStatIpNetRegionNumofConsTx,
                avCmStatIpNetRegionNumofConsRx,
                avCmStatIpNetRegionDenialCount
                 }
    STATUS      current
    DESCRIPTION
        "Avaya Aura Communication Manager StatIpNetRegionObjGrp MIB
        objects"
    ::= { avCmMIBGroups 96 }


avCmMeasToneRecLstHrObjGrp     OBJECT-GROUP
    OBJECTS   {
		avCmMeasToneRecLstHrPNNumber,
		avCmMeasToneRecLstHrRunDate,
		avCmMeasToneRecLstHrMeasHour,
		avCmMeasToneRecLstHrDTMFPnReq,
		avCmMeasToneRecLstHrDTMFPnAlloc,
		avCmMeasToneRecLstHrDTMFPkAlloc,
		avCmMeasToneRecLstHrDTMFTotOffPN,
		avCmMeasToneRecLstHrDTMFPkOffPN,
		avCmMeasToneRecLstHrGPTDPnReq,
		avCmMeasToneRecLstHrGPTDPnAlloc,
		avCmMeasToneRecLstHrGPTDPkAlloc,
		avCmMeasToneRecLstHrGPTDTotOffPN,
		avCmMeasToneRecLstHrGPTDPkOffPN,
		avCmMeasToneRecLstHrCCTTRPnReq,
		avCmMeasToneRecLstHrCCTTRPnAlloc,
		avCmMeasToneRecLstHrCCTRPkAlloc,
		avCmMeasToneRecLstHrCCTTRTotOffPN,
		avCmMeasToneRecLstHrCCTTRPkOffPN,
		avCmMeasToneRecLstHrCCCPTRPnReq,
		avCmMeasToneRecLstHrCCCPTRPnAlloc,
		avCmMeasToneRecLstHrCCCPTRPkAlloc,
		avCmMeasToneRecLstHrCCCPTRTotOffPN,
		avCmMeasToneRecLstHrCCCPTRPkOffPN,
		avCmMeasToneRecLstHrCCMFCRPnReq,
		avCmMeasToneRecLstHrCCMFCRPnAlloc,
		avCmMeasToneRecLstHrCCMFCRPkAlloc,
		avCmMeasToneRecLstHrCCMFCRTotOffPN,
		avCmMeasToneRecLstHrCCMFCRPkOffPN
                 }
    STATUS      current
    DESCRIPTION
        "Avaya Aura Communication Manager avCmMeasToneRecLstHrObjGrp MIB
        objects"
    ::= { avCmMIBGroups 97 }

avCmMeasToneRecTodayObjGrp     OBJECT-GROUP
    OBJECTS   {
		avCmMeasToneRecTodayPNNumber,
		avCmMeasToneRecTodayRunDate,
		avCmMeasToneRecTodayMeasHour,
		avCmMeasToneRecTodayDTMFPnReq,
		avCmMeasToneRecTodayDTMFPnAlloc,
		avCmMeasToneRecTodayDTMFPkAlloc ,
		avCmMeasToneRecTodayDTMFTotOffPN,
		avCmMeasToneRecTodayDTMFPkOffPN,
		avCmMeasToneRecTodayGPTDPnReq,
		avCmMeasToneRecTodayGPTDPnAlloc,
		avCmMeasToneRecTodayGPTDPkAlloc,
		avCmMeasToneRecTodayGPTDTotOffPN,
		avCmMeasToneRecTodayGPTDPkOffPN,
		avCmMeasToneRecTodayCCTTRPnReq,
		avCmMeasToneRecTodayCCTTRPnAlloc,
		avCmMeasToneRecTodayCCTRPkAlloc,
		avCmMeasToneRecTodayCCTTRTotOffPN,
		avCmMeasToneRecTodayCCTTRPkOffPN,
		avCmMeasToneRecTodayCCCPTRPnReq,
		avCmMeasToneRecTodayCCCPTRPnAlloc,
		avCmMeasToneRecTodayCCCPTRPkAlloc,
		avCmMeasToneRecTodayCCCPTRTotOffPN,
		avCmMeasToneRecTodayCCCPTRPkOffPN,
		avCmMeasToneRecTodayCCMFCRPnReq,
		avCmMeasToneRecTodayCCMFCRPnAlloc,
		avCmMeasToneRecTodayCCMFCRPkAlloc,
		avCmMeasToneRecTodayCCMFCRTotOffPN,
		avCmMeasToneRecTodayCCMFCRPkOffPN
                 }
    STATUS      current
    DESCRIPTION
        "Avaya Aura Communication Manager avCmMeasToneRecTodayObjGrp MIB
        objects"
    ::= { avCmMIBGroups 98 }

avCmMeasToneRecYestObjGrp     OBJECT-GROUP
    OBJECTS   {
		avCmMeasToneRecYestPNNumber,
		avCmMeasToneRecYestRunDate,
		avCmMeasToneRecYestMeasHour,
		avCmMeasToneRecYestDTMFPnReq,
		avCmMeasToneRecYestDTMFPnAlloc,
		avCmMeasToneRecYestDTMFPkAlloc ,
		avCmMeasToneRecYestDTMFTotOffPN,
		avCmMeasToneRecYestDTMFPkOffPN,
		avCmMeasToneRecYestGPTDPnReq,
		avCmMeasToneRecYestGPTDPnAlloc,
		avCmMeasToneRecYestGPTDPkAlloc,
		avCmMeasToneRecYestGPTDTotOffPN,
		avCmMeasToneRecYestGPTDPkOffPN,
		avCmMeasToneRecYestCCTTRPnReq,
		avCmMeasToneRecYestCCTTRPnAlloc,
		avCmMeasToneRecYestCCTRPkAlloc,
		avCmMeasToneRecYestCCTTRTotOffPN,
		avCmMeasToneRecYestCCTTRPkOffPN,
		avCmMeasToneRecYestCCCPTRPnReq,
		avCmMeasToneRecYestCCCPTRPnAlloc,
		avCmMeasToneRecYestCCCPTRPkAlloc,
		avCmMeasToneRecYestCCCPTRTotOffPN,
		avCmMeasToneRecYestCCCPTRPkOffPN,
		avCmMeasToneRecYestCCMFCRPnReq,
		avCmMeasToneRecYestCCMFCRPnAlloc,
		avCmMeasToneRecYestCCMFCRPkAlloc,
		avCmMeasToneRecYestCCMFCRTotOffPN,
		avCmMeasToneRecYestCCMFCRPkOffPN
                 }
    STATUS      current
    DESCRIPTION
        "Avaya Aura Communication Manager avCmMeasToneRecYestObjGrp MIB
        objects"
    ::= { avCmMIBGroups 99 }

avCmMeasToneRecSumLstHrObjGrp     OBJECT-GROUP
    OBJECTS   {
		avCmMeasToneRecSumLstHrRunDate,
		avCmMeasToneRecSumLstHrMeasHour,
		avCmMeasToneRecSumLstHrDTMFHour,
		avCmMeasToneRecSumLstHrDTMFTReq,
		avCmMeasToneRecSumLstHrDTMFPReq,
		avCmMeasToneRecSumLstHrDTMFTQueued,
		avCmMeasToneRecSumLstHrDTMFPQueued,
		avCmMeasToneRecSumLstHrDTMFTDenied,
		avCmMeasToneRecSumLstHrDTMFPDenied,
		avCmMeasToneRecSumLstHrGPTDHour,
		avCmMeasToneRecSumLstHrGPTDTReq,
		avCmMeasToneRecSumLstHrGPTDPReq,
		avCmMeasToneRecSumLstHrGPTDTDenied,
		avCmMeasToneRecSumLstHrGPTDPDenied,
		avCmMeasToneRecSumLstHrCCTTRHour,
		avCmMeasToneRecSumLstHrCCTTRTReq,
		avCmMeasToneRecSumLstHrCCTTRPReq,
		avCmMeasToneRecSumLstHrCCTTRTQueued,
		avCmMeasToneRecSumLstHrCCTTRPQueued,
		avCmMeasToneRecSumLstHrCCTTRTDenied,
		avCmMeasToneRecSumLstHrCCTTRPDenied,
		avCmMeasToneRecSumLstHrCCCPTRHour,
		avCmMeasToneRecSumLstHrCCCPTRTReq,
		avCmMeasToneRecSumLstHrCCCPTRPReq,
		avCmMeasToneRecSumLstHrCCCPTRTDenied,
		avCmMeasToneRecSumLstHrCCCPTRPDenied,
		avCmMeasToneRecSumLstHrCCMFCRHour,
		avCmMeasToneRecSumLstHrCCMFCRTReq,
		avCmMeasToneRecSumLstHrCCMFCRPReq,
		avCmMeasToneRecSumLstHrCCMFCRTDenied,
		avCmMeasToneRecSumLstHrCCMFCRPDenied,
		avCmMeasToneRecSumLstHrDTMRPTTAvail,
		avCmMeasToneRecSumLstHrGPTDPTTAvail,
		avCmMeasToneRecSumLstHrCLASPTTAvail,
		avCmMeasToneRecSumLstHrETRPTTAvail
                 }
    STATUS      current
    DESCRIPTION
        "Avaya Aura Communication Manager avCmMeasToneRecSumLstHrObjGrp MIB
        objects"
    ::= { avCmMIBGroups 100 }

avCmMeasToneRecSumTodayObjGrp     OBJECT-GROUP
    OBJECTS   {
		avCmMeasToneRecSumTodayRunDate,
		avCmMeasToneRecSumTodayMeasHour,
		avCmMeasToneRecSumTodayDTMFHour,
		avCmMeasToneRecSumTodayDTMFTReq,
		avCmMeasToneRecSumTodayDTMFPReq,
		avCmMeasToneRecSumTodayDTMFTQueued,
		avCmMeasToneRecSumTodayDTMFPQueued,
		avCmMeasToneRecSumTodayDTMFTDenied,
		avCmMeasToneRecSumTodayDTMFPDenied,
		avCmMeasToneRecSumTodayGPTDHour,
		avCmMeasToneRecSumTodayGPTDTReq,
		avCmMeasToneRecSumTodayGPTDPReq,
		avCmMeasToneRecSumTodayGPTDTDenied,
		avCmMeasToneRecSumTodayGPTDPDenied,
		avCmMeasToneRecSumTodayCCTTRHour,
		avCmMeasToneRecSumTodayCCTTRTReq,
		avCmMeasToneRecSumTodayCCTTRPReq,
		avCmMeasToneRecSumTodayCCTTRTQueued,
		avCmMeasToneRecSumTodayCCTTRPQueued,
		avCmMeasToneRecSumTodayCCTTRTDenied,
		avCmMeasToneRecSumTodayCCTTRPDenied,
		avCmMeasToneRecSumTodayCCCPTRHour,
		avCmMeasToneRecSumTodayCCCPTRTReq,
		avCmMeasToneRecSumTodayCCCPTRPReq,
		avCmMeasToneRecSumTodayCCCPTRTDenied,
		avCmMeasToneRecSumTodayCCCPTRPDenied,
		avCmMeasToneRecSumTodayCCMFCRHour,
		avCmMeasToneRecSumTodayCCMFCRTReq,
		avCmMeasToneRecSumTodayCCMFCRPReq,
		avCmMeasToneRecSumTodayCCMFCRTDenied,
		avCmMeasToneRecSumTodayCCMFCRPDenied,
		avCmMeasToneRecSumTodayDTMRPTTAvail,
		avCmMeasToneRecSumTodayGPTDPTTAvail,
		avCmMeasToneRecSumTodayCLASPTTAvail,
		avCmMeasToneRecSumTodayETRPTTAvail
                 }
    STATUS      current
    DESCRIPTION
        "Avaya Aura Communication Manager avCmMeasToneRecSumTodayObjGrp MIB
        objects"
    ::= { avCmMIBGroups 101 }

avCmMeasToneRecSumYestObjGrp     OBJECT-GROUP
    OBJECTS   {
		avCmMeasToneRecSumYestRunDate,
		avCmMeasToneRecSumYestMeasHour,
		avCmMeasToneRecSumYestDTMFHour,
		avCmMeasToneRecSumYestDTMFTReq,
		avCmMeasToneRecSumYestDTMFPReq,
		avCmMeasToneRecSumYestDTMFTQueued,
		avCmMeasToneRecSumYestDTMFPQueued,
		avCmMeasToneRecSumYestDTMFTDenied,
		avCmMeasToneRecSumYestDTMFPDenied,
		avCmMeasToneRecSumYestGPTDHour,
		avCmMeasToneRecSumYestGPTDTReq,
		avCmMeasToneRecSumYestGPTDPReq,
		avCmMeasToneRecSumYestGPTDTDenied,
		avCmMeasToneRecSumYestGPTDPDenied,
		avCmMeasToneRecSumYestCCTTRHour,
		avCmMeasToneRecSumYestCCTTRTReq,
		avCmMeasToneRecSumYestCCTTRPReq,
		avCmMeasToneRecSumYestCCTTRTQueued,
		avCmMeasToneRecSumYestCCTTRPQueued,
		avCmMeasToneRecSumYestCCTTRTDenied,
		avCmMeasToneRecSumYestCCTTRPDenied,
		avCmMeasToneRecSumYestCCCPTRHour,
		avCmMeasToneRecSumYestCCCPTRTReq,
		avCmMeasToneRecSumYestCCCPTRPReq,
		avCmMeasToneRecSumYestCCCPTRTDenied,
		avCmMeasToneRecSumYestCCCPTRPDenied,
		avCmMeasToneRecSumYestCCMFCRHour,
		avCmMeasToneRecSumYestCCMFCRTReq,
		avCmMeasToneRecSumYestCCMFCRPReq,
		avCmMeasToneRecSumYestCCMFCRTDenied,
		avCmMeasToneRecSumYestCCMFCRPDenied,
		avCmMeasToneRecSumYestDTMRPTTAvail,
		avCmMeasToneRecSumYestGPTDPTTAvail,
		avCmMeasToneRecSumYestCLASPTTAvail,
		avCmMeasToneRecSumYestETRPTTAvail
                 }
    STATUS      current
    DESCRIPTION
        "Avaya Aura Communication Manager avCmMeasToneRecSumYestObjGrp MIB
        objects"
    ::= { avCmMIBGroups 102 }

avCmSysParamCustObjGrp     OBJECT-GROUP
    OBJECTS   {
		avCmSysParamCustPlat,
		avCmSysParamCustESS,
		avCmSysParamCustLSP,
		avCmSysParamCustTenantPart,
		avCmSysParamCustPortNetSup
                 }
    STATUS      current
    DESCRIPTION
        "Avaya Aura Communication Manager avCmSysParamCustObjGrp MIB
        objects"
    ::= { avCmMIBGroups 103 }

END
