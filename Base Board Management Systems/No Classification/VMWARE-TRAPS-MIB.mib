VMWARE-TRAPS-MIB DEFINITIONS ::= BEGIN

IMPORTS
   TRAP-TYPE 
      FROM RFC-1215
   OBJECT-TYPE 
      FROM RFC1155-SMI
   DisplayString 
      FROM RFC1213-MIB;
 
vmware             OBJECT IDENTIFIER ::= { enterprises 6876 }
vmwSystem          OBJECT IDENTIFIER ::= { vmware 1 }
vmwVirtMachines    OBJECT IDENTIFIER ::= { vmware 2 }
vmwResources       OBJECT IDENTIFIER ::= { vmware 3 }
vmwProductSpecific OBJECT IDENTIFIER ::= { vmware 4 }
vmwTraps           OBJECT IDENTIFIER ::= { vmware 50 }
vmwOID             OBJECT IDENTIFIER ::= { vmware 60 }
vmwExperimental    OBJECT IDENTIFIER ::= { vmware 700 }

--  This file contains the MIB for VMware specific traps 
--  with NMS Annotations (comments where #<Ann> immediately
--  follows the comment marker with no spaces between).
--  All traps are of the SNMPv1 type. 

vmPoweredOn TRAP-TYPE 
   ENTERPRISE vmware 
   VARIABLES { vmID, vmConfigFile }
   DESCRIPTION 
      "This trap is sent when a virtual machine is powered ON from a suspended 
       or a powered off state."
      --#TYPE      "Virtual machine powered ON."
      --#SUMMARY   "Powered ON %s (id=%d)."
      --#ARGUMENTS { 1, 0 }
      --#SEVERITY  INFORMATIONAL 
      --#TIMEINDEX 2
      --#STATE     OPERATIONAL
   ::= 1 

vmPoweredOff TRAP-TYPE 
   ENTERPRISE vmware 
   VARIABLES { vmID, vmConfigFile }
   DESCRIPTION 
      "This trap is sent when a virtual machine is powered OFF." 
      --#TYPE      "Virtual machine powered OFF."
      --#SUMMARY   "Powered OFF %s (id=%d)."
      --#ARGUMENTS { 1, 0 }
      --#SEVERITY  INFORMATIONAL 
      --#TIMEINDEX 2
      --#STATE     NONOPERATIONAL
   ::= 2 

vmHBLost TRAP-TYPE 
   ENTERPRISE vmware 
   VARIABLES { vmID, vmConfigFile }
   DESCRIPTION 
      "This trap is sent when a virtual machine detects a loss in guest heartbeat." 
      --#TYPE      "Virtual machine heartbeat lost."
      --#SUMMARY   "Heartbeat lost for %s (id=%d) ."
      --#ARGUMENTS { 1, 0 }
      --#SEVERITY  MAJOR 
      --#TIMEINDEX 2
      --#STATE     DEGRADED
   ::= 3 

vmHBDetected TRAP-TYPE 
   ENTERPRISE vmware 
   VARIABLES { vmID, vmConfigFile }
   DESCRIPTION 
      "This trap is sent when a virtual machine detects or regains the guest heartbeat." 
      --#TYPE      "Virtual machine heartbeat detected."
      --#SUMMARY   "Heartbeat detected for %s (id=%d) ."
      --#ARGUMENTS { 1, 0 }
      --#SEVERITY  INFORMATIONAL 
      --#TIMEINDEX 2
      --#STATE     OPERATIONAL
   ::= 4 

vmSuspended TRAP-TYPE 
   ENTERPRISE vmware 
   VARIABLES { vmID, vmConfigFile }
   DESCRIPTION 
      "This trap is sent when a virtual machine is suspended." 
      --#TYPE      "Virtual machine suspended."
      --#SUMMARY   "Suspended %s (id=%d)."
      --#ARGUMENTS { 1, 0 }
      --#SEVERITY  INFORMATIONAL 
      --#TIMEINDEX 2
      --#STATE     NONOPERATIONAL
   ::= 5 

-- Accompanying variables for traps

vmID OBJECT-TYPE
   SYNTAX     INTEGER 
   ACCESS     read-only 
   STATUS     mandatory
   DESCRIPTION
      "This is the ID of the affected vm generating the trap. If the vmID
      is non-existent, (such as for a power-off trap) -1 is returned."
   ::= { vmwTraps 101 }

vmConfigFile OBJECT-TYPE
   SYNTAX     DisplayString 
   ACCESS     read-only 
   STATUS     mandatory
   DESCRIPTION
      "This is the config file of the affected vm generating the trap."
   ::= { vmwTraps 102 }

END
