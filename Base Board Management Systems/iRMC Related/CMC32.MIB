-- RITTAL-WERK Herborn
-- CMC-MIB Version 3.3
-- ComputerMultiControl
--*********************************************************************
--Release History
--Date: August 25, 1997 (Version 1.0)
--Revised by MHai
--Tested with HP OpenView for Windows
--Date: September 3, 1997
--Revised MHai  included PEN 2606
--Date: August 5, 1998
--Revised MHai  included Table
--Date: October 27, 1998
--Changed "ENTERPRISE" of trap-definition to cmc (rittal 1) Version 3.0
--Date: December 23, 1998
--Included Tables (values, status, trap-receiver, relay)
--Variables added (trapControl...) Version 3.1
--Date: March 23, 1999
--Removed 2nd definition of DisplayString  Version 3.2
--Date: May 12, 1999
--Revised MHai  Variables added to trap-definition
--*********************************************************************


          CMC-MIB DEFINITIONS ::= BEGIN

          IMPORTS
-----------------------------------------------------------------------
           enterprises FROM RFC1155-SMI
           DisplayString FROM RFC1213-MIB
-----------------------------------------------------------------------
           OBJECT-TYPE FROM RFC-1212
           TRAP-TYPE FROM RFC-1215;
-----------------------------------------------------------------------

        rittal    	OBJECT IDENTIFIER ::= { enterprises 2606 }
        cmc             OBJECT IDENTIFIER ::= { rittal 1 }
        values    	OBJECT IDENTIFIER ::= { cmc 1 }
             table1          OBJECT IDENTIFIER ::= { values 6 }
        status    	OBJECT IDENTIFIER ::= { cmc 2 }
             table           OBJECT IDENTIFIER ::= { status 17 }
        set       	OBJECT IDENTIFIER ::= { cmc 3 }
             relayControl    OBJECT IDENTIFIER ::= { set 5 }
        setpoints 	OBJECT IDENTIFIER ::= { cmc 4 }
        trapControl  	OBJECT IDENTIFIER ::= { cmc 5 }
             traps           OBJECT IDENTIFIER ::= { trapControl 4 }

		
--          DisplayString ::= OCTET STRING
--          IPADDRESS ::= OCTET STRING


-- values-group--------------------------------------------------------
	  valueTemperature1 OBJECT-TYPE
	      SYNTAX  INTEGER 
	      ACCESS  read-only
	      STATUS  mandatory
              DESCRIPTION
              "Actual value of temperature 1 in deg C"
              ::= { values 1 }

	  valueTemperature2 OBJECT-TYPE
              SYNTAX  INTEGER 
	      ACCESS  read-only
	      STATUS  mandatory
              DESCRIPTION
              "Actual value of temperature 2 in deg C"
              ::= { values 2 }

	  valuePowerSupply   OBJECT-TYPE
              SYNTAX  INTEGER 
	      ACCESS  read-only
	      STATUS  mandatory
              DESCRIPTION
              "Actual value of power supply in V"
              ::= { values 3 }

          valueAnalogAux1  OBJECT-TYPE
	      SYNTAX  INTEGER
	      ACCESS  read-only
	      STATUS  mandatory
              DESCRIPTION
              "Actual value of aux. analog input 1
              (4-20mA = 0-100%)"
              ::= { values 4 }

          valueAnalogAux2  OBJECT-TYPE
	      SYNTAX  INTEGER
	      ACCESS  read-only
	      STATUS  mandatory
              DESCRIPTION 
              "Actual value of aux. analog input 2
              (4-20mA = 0-100%)"
              ::= { values 5 }
-----------------------------------------------------------------------
--values-table-group

          valuesNumber            OBJECT-TYPE
              SYNTAX  INTEGER 
              ACCESS  read-only
	      STATUS  mandatory
              DESCRIPTION
              "Number of value-table entries"
              ::= { table1 1 }

          valuesTable          OBJECT-TYPE
              SYNTAX  SEQUENCE OF ValuesEntry
              ACCESS  not-accessible
	      STATUS  mandatory
              DESCRIPTION
              "Headline of value-table"
              ::= { table1 2 }

          valuesEntry            OBJECT-TYPE
              SYNTAX  ValuesEntry
              ACCESS  not-accessible
	      STATUS  mandatory
              DESCRIPTION
              "Entries of value-table"
              INDEX   { valuesIndex }
              ::= { valuesTable 1 }

              ValuesEntry ::=
              SEQUENCE {
              valuesIndex
                INTEGER,
              valuesText
		DisplayString (SIZE (0..31)),                
              valuesValue
                INTEGER,
              valuesStatus
                INTEGER,
              valuesMaxValue
                INTEGER,
              valuesMinValue
                INTEGER
              }

             valuesIndex OBJECT-TYPE
             SYNTAX INTEGER
             ACCESS read-only
             STATUS mandatory
             DESCRIPTION
             "Index for the list of value entries. Its value ranges
              between 1 and the value of valuesNumber." 
             ::= { valuesEntry 1 }

             valuesText  OBJECT-TYPE
             SYNTAX DisplayString (SIZE (0..31))
             ACCESS read-write
             STATUS mandatory
             DESCRIPTION
             "Text of the entry in the value-table"
             ::= { valuesEntry 2 }
              
             valuesValue OBJECT-TYPE
             SYNTAX INTEGER
             ACCESS read-only
             STATUS mandatory
             DESCRIPTION
             "Actual value of the value-table"
             ::= { valuesEntry 3 }

             valuesStatus OBJECT-TYPE
             SYNTAX INTEGER  {
             valueOK(1),
             value-too-low(2),
             value-too-high(3),
             valueERROR(4),
             not-avail(5)
             }
             ACCESS read-only
             STATUS mandatory
             DESCRIPTION
             "Status of the value"
             ::= { valuesEntry 4 }

             valuesMaxValue OBJECT-TYPE
             SYNTAX INTEGER
             ACCESS read-write
             STATUS mandatory
             DESCRIPTION
             "Value for max. alarm"
             ::= { valuesEntry 5 }

             valuesMinValue OBJECT-TYPE
             SYNTAX INTEGER
             ACCESS read-write
             STATUS mandatory
             DESCRIPTION
             "Value for min. alarm"
             ::= { valuesEntry 6 }



--status-group---------------------------------------------------------

	  statusTemperature1 OBJECT-TYPE
	      SYNTAX  DisplayString (SIZE (0..31))
	      ACCESS  read-only
	      STATUS  mandatory
              DESCRIPTION
              "Status temperature 1, OK/ too low/ too high
              (see setpoints of temperature 1)"
              ::= { status 1 }

	  statusTemperature2 OBJECT-TYPE
	      SYNTAX  DisplayString (SIZE (0..31))
	      ACCESS  read-only
	      STATUS  mandatory
              DESCRIPTION
              "Status temperature 2, OK/ too low/ too high
              (see setpoints of temperature 2)"
              ::= { status 2 }

	  statusFan1  OBJECT-TYPE
	      SYNTAX    DisplayString (SIZE (0..31))
	      ACCESS  read-only
	      STATUS  mandatory
              DESCRIPTION
              "Status fan 1, Stop/ running/ fault"
              ::= { status 3 }

	  statusFan2  OBJECT-TYPE
	      SYNTAX    DisplayString (SIZE (0..31))
	      ACCESS  read-only
	      STATUS  mandatory
              DESCRIPTION
              "Status fan 2, Stop/ running/ fault"
              ::= { status 4 }

	  statusHeating  OBJECT-TYPE
	      SYNTAX    DisplayString (SIZE (0..31))
	      ACCESS  read-only
	      STATUS  mandatory
              DESCRIPTION
              "Status heating, On/Off"
              ::= { status 5 }

	  statusPowerSupply  OBJECT-TYPE
	      SYNTAX    DisplayString (SIZE (0..31))
	      ACCESS  read-only
	      STATUS  mandatory
              DESCRIPTION
              "Status power supply, OK/ too low/ too high
              (see setpoints of power supply)"
              ::= { status 6 }

          statusAnalogAux1  OBJECT-TYPE
	      SYNTAX    DisplayString (SIZE (0..31))
	      ACCESS  read-only
	      STATUS  mandatory
              DESCRIPTION
              "Status aux analog input 1, OK/ too low/ too high"
              ::= { status 7 }

          statusAnalogAux2 OBJECT-TYPE
	      SYNTAX    DisplayString (SIZE (0..31))
	      ACCESS read-only
	      STATUS mandatory
              DESCRIPTION
              "Status aux analog input 2, OK/ too low/ too high"
              ::= { status 8 }

	  statusDoor  OBJECT-TYPE
	      SYNTAX    DisplayString (SIZE (0..31))
	      ACCESS  read-only
	      STATUS  mandatory
              DESCRIPTION
              "Status door, open/closed/locked"
              ::= { status 9 }

	  statusUps1  OBJECT-TYPE
	      SYNTAX  DisplayString (SIZE (0..31))
	      ACCESS  read-only
	      STATUS  mandatory
              DESCRIPTION
              "Status UPS 1, OK/ fault"
              ::= { status 10 }

	  statusUps2  OBJECT-TYPE
	      SYNTAX  DisplayString (SIZE (0..31))
	      ACCESS    read-only
	      STATUS    mandatory
              DESCRIPTION
              "Status UPS 2, OK/ fault"
              ::= { status 11 }

	  statusSmokeSensor  OBJECT-TYPE
	      SYNTAX  DisplayString (SIZE (0..31))
	      ACCESS    read-only
	      STATUS    mandatory
              DESCRIPTION
              "Status smoke-sensor, OK/ smoke"
              ::= { status 12 }

	  statusVibrationSensor  OBJECT-TYPE
	      SYNTAX  DisplayString (SIZE (0..31))
	      ACCESS  read-only
	      STATUS    mandatory
              DESCRIPTION
              "Status vibration sensor, OK/ vibration"
              ::= { status 13 }

	  statusMessage OBJECT-TYPE
	      SYNTAX  DisplayString (SIZE (0..31))
	      ACCESS    read-only
	      STATUS    mandatory
              DESCRIPTION
              "Message from CMC"
              ::= { status 14 }

	  valueOperatingTime    OBJECT-TYPE
	      SYNTAX  DisplayString (SIZE (0..31))
	      ACCESS  read-only
	      STATUS  mandatory
              DESCRIPTION
              "Operating time CMC-unit"
              ::= { status 15 }

	  statusUnit          OBJECT-TYPE
              SYNTAX  INTEGER {
              unitCelsius(1),
              unitFahrenheit(2)
              }
	      ACCESS  read-only
	      STATUS  mandatory
              DESCRIPTION
              "Unit of temperature-values, Celsius or Fahrenheit"
              ::= { status 16 }


------------------------------------------------------------------------
--status-table-group

          statusNumber            OBJECT-TYPE
              SYNTAX  INTEGER 
              ACCESS  read-only
	      STATUS  mandatory
              DESCRIPTION
              "Number of status-table entries"
              ::= { table 1 }

          statusTable          OBJECT-TYPE
              SYNTAX  SEQUENCE OF StatusEntry
              ACCESS  not-accessible
	      STATUS  mandatory
              DESCRIPTION
              "Headline of table"
              ::= { table 2 }

          statusEntry            OBJECT-TYPE
              SYNTAX  StatusEntry
              ACCESS  not-accessible
	      STATUS  mandatory
              DESCRIPTION
              "A list of status entries.  The number of
              entries is given by the value of statusNumber." 
              INDEX   { statusIndex }
              ::= { statusTable 1 }

              StatusEntry ::=
              SEQUENCE {
              statusIndex
                INTEGER,
              statusText
		DisplayString (SIZE (0..31)),
              statusStatus
                INTEGER              
              }

             statusIndex OBJECT-TYPE
             SYNTAX INTEGER
             ACCESS read-only
             STATUS mandatory
             DESCRIPTION
             "Index fo the list of status entries. Its value ranges
              between 1 and the value of statusNumber." 
             ::= { statusEntry 1 }

             statusText OBJECT-TYPE
             SYNTAX DisplayString (SIZE (0..31))
             ACCESS read-write
             STATUS mandatory
             DESCRIPTION
             "Text of the entry in the status-table"
             ::= { statusEntry 2 }

             statusStatus OBJECT-TYPE
             SYNTAX INTEGER  {
             statusOK(1),
             alarm(2),
             security(3),
             not-avail(4)
             }
             ACCESS read-only
             STATUS mandatory
             DESCRIPTION
             "Status of the table entry"
             ::= { statusEntry 3 }


--******************************************************************************

--set-group-------------------------------------------------------------

	  statusAccess  OBJECT-TYPE
	      SYNTAX  DisplayString (SIZE (0..31))
	      ACCESS    read-write
	      STATUS    mandatory
              DESCRIPTION
              "Status access"
              ::= { set 1 }

	  setDoor  OBJECT-TYPE
              SYNTAX    INTEGER {
              lockDoor(1),
              openDoorTime(2),
              openDoorAccess(3),
              openDoor(4)
              }
              ACCESS  read-write
	      STATUS  mandatory
              DESCRIPTION
              "Set door, see table"
              ::= { set 2 }

	  setMessage  OBJECT-TYPE
	      SYNTAX  DisplayString (SIZE (0..31))
	      ACCESS    read-write
	      STATUS    mandatory
              DESCRIPTION
              "Set message"
              ::= { set 3 }

	  setFault        OBJECT-TYPE
              SYNTAX  INTEGER {
              clearFault(1),
              setFault(2)
              }
	      ACCESS  read-write
	      STATUS  mandatory
              DESCRIPTION
              "Set fault, see table"
              ::= { set 4 }


--relayControl-group-----------------------------------------------------------------

          relaytableMaxNum            OBJECT-TYPE
              SYNTAX  INTEGER 
              ACCESS  read-only
	      STATUS  mandatory
              DESCRIPTION
              "Number of table entries"
              ::= { relayControl 1 }

          relayTable          OBJECT-TYPE
              SYNTAX  SEQUENCE OF RelayEntry
              ACCESS  not-accessible
	      STATUS  mandatory
              DESCRIPTION
              "Headline of table for relay control"
              ::= { relayControl 2 }

          relayEntry            OBJECT-TYPE
              SYNTAX  RelayEntry
              ACCESS  not-accessible
	      STATUS  mandatory
              DESCRIPTION
              "Entries"
              INDEX   { relaytableIndex }
              ::= { relayTable 1 }

              RelayEntry ::=
              SEQUENCE {
              relaytableIndex
                INTEGER,
              relaytableText
		DisplayString (SIZE (0..31)),
              relaytableStatus
                INTEGER              
              }

             relaytableIndex OBJECT-TYPE
             SYNTAX INTEGER
             ACCESS read-only
             STATUS mandatory
             DESCRIPTION
             "Index for the relay-table. Its value ranges
              between 1 and relaytableMaxNum"
             ::= { relayEntry 1 }

             relaytableText OBJECT-TYPE
             SYNTAX DisplayString (SIZE (0..31))
             ACCESS read-write
             STATUS mandatory
             DESCRIPTION
             "Description-Text for each relay in the table"
             ::= { relayEntry 2 }

             relaytableStatus OBJECT-TYPE
             SYNTAX INTEGER  {
             relayOFF(1),
             relayON(2),
             not-avail(3)
             }
             ACCESS read-write
             STATUS mandatory
             DESCRIPTION
             "Status of relays in the table"
             ::= { relayEntry 3 }



--setpoints-group-------------------------------------------------------------

          setpointFan1        OBJECT-TYPE
              SYNTAX  INTEGER 
	      ACCESS  read-write
	      STATUS  mandatory
              DESCRIPTION
              "Setpoint Fan 1 in C, Fan 1 will start
               if temperature 1 exceeds this value"
              ::= { setpoints 1 }

          setpointFan2        OBJECT-TYPE
              SYNTAX  INTEGER 
	      ACCESS  read-write
	      STATUS  mandatory
              DESCRIPTION
              "Setpoint Fan 2 in C, Fan 2 will start
               if temperature 2 exceeds this value"
              ::= { setpoints 2 }

          setpointHeating     OBJECT-TYPE
              SYNTAX  INTEGER 
	      ACCESS  read-write
	      STATUS  mandatory
              DESCRIPTION
              "Setpoint heating in C, heating will start
               if lowest value of temperature 1 and 2 falls below this value"
              ::= { setpoints 3 }

          setpointHighTemperature1        OBJECT-TYPE
              SYNTAX  INTEGER 
	      ACCESS  read-write
	      STATUS  mandatory
              DESCRIPTION
              "Setpoint high value alarm temperature 1"
              ::= { setpoints 4 }

          setpointLowTemperature1        OBJECT-TYPE
              SYNTAX  INTEGER 
	      ACCESS  read-write
	      STATUS  mandatory
              DESCRIPTION
              "Setpoint low value alarm temperature 1"
              ::= { setpoints 5 }

          setpointHighTemperature2        OBJECT-TYPE
              SYNTAX  INTEGER 
	      ACCESS  read-write
	      STATUS  mandatory
              DESCRIPTION
              "Setpoint high value alarm temperature 2"
              ::= { setpoints 6 }

          setpointLowTemperature2        OBJECT-TYPE
              SYNTAX  INTEGER 
	      ACCESS  read-write
	      STATUS  mandatory
              DESCRIPTION
              "Setpoint low value alarm temperature 2"
              ::= { setpoints 7 }

          setpointHighVoltage            OBJECT-TYPE
              SYNTAX  INTEGER 
	      ACCESS  read-write
	      STATUS  mandatory
              DESCRIPTION
              "Setpoint high value supply voltage alarm"
              ::= { setpoints 8 }

          setpointLowVoltage            OBJECT-TYPE
              SYNTAX  INTEGER
	      ACCESS  read-write
	      STATUS  mandatory
              DESCRIPTION
              "Setpoint low value supply voltage alarm"
              ::= { setpoints 9 }

          setpointLowAux1               OBJECT-TYPE
              SYNTAX  INTEGER 
	      ACCESS  read-write
	      STATUS  mandatory
              DESCRIPTION
              "Setpoint low value Aux input 1 alarm"
              ::= { setpoints 10 }

          setpointHighAux1              OBJECT-TYPE
              SYNTAX  INTEGER 
	      ACCESS  read-write
	      STATUS  mandatory
              DESCRIPTION
              "Setpoint high value Aux input 1 alarm"
              ::= { setpoints 11 }

          setpointLowAux2               OBJECT-TYPE
              SYNTAX  INTEGER 
	      ACCESS  read-write
	      STATUS  mandatory
              DESCRIPTION
              "Setpoint low value Aux input 2 alarm"
              ::= { setpoints 12 }

          setpointHighAux2              OBJECT-TYPE
              SYNTAX  INTEGER 
	      ACCESS  read-write
	      STATUS  mandatory
              DESCRIPTION
              "Setpoint high value Aux input alarm"
              ::= { setpoints 13 }

--------------------------------------------------------------------------


--******************************************************************************
--trapControl-group

	     setTrapRepeat OBJECT-TYPE
             SYNTAX INTEGER {
		disableTrapRepeat(1),
		enableTrapRepeat(2)
		}
             ACCESS read-write
             STATUS mandatory
             DESCRIPTION
             "Enable/disable repeating of traps. If enabled, traps will
              be repeated after a repeat time, set in setTrapRepeatTime.
              Repeating can be stopped by setting setTrapQuit to quitTrap"
             ::= { trapControl 1 }

	     setTrapRepeatTime OBJECT-TYPE
             SYNTAX INTEGER 
             ACCESS read-write
             STATUS mandatory
             DESCRIPTION
             "Time value (sec) for trap-repeating, if setTrapRepeat is enabled"
             ::= { trapControl 2 }

	     setTrapQuit OBJECT-TYPE
             SYNTAX INTEGER {
		quitTrap(1),
		quitTrapOK(2),
		noTrapToQuit(3),
		trapToQuit(4)
	        }
             ACCESS read-write
             STATUS mandatory
             DESCRIPTION
             "Quit trap to stop repeating."
             ::= { trapControl 3 }


--******************************************************************************
--trapTable-group

          traptableNumber            OBJECT-TYPE
              SYNTAX  INTEGER 
              ACCESS  read-only
	      STATUS  mandatory
              DESCRIPTION
              "Number of trapTable entries. The number of trap-receiver"
              ::= { traps 1 }

          trapTable          OBJECT-TYPE
              SYNTAX  SEQUENCE OF TrapTableEntry
              ACCESS  not-accessible
	      STATUS  mandatory
              DESCRIPTION
              "A list of trap-receiver entries"
              ::= { traps 2 }

          trapTableEntry            OBJECT-TYPE
              SYNTAX  TrapTableEntry
              ACCESS  not-accessible
	      STATUS  mandatory
              DESCRIPTION
              "Entries of trapTable"
              INDEX   { trapIndex }
              ::= { trapTable 1 }

              TrapTableEntry ::=
              SEQUENCE {
              trapIndex
                INTEGER,
              trapStatus
                INTEGER,
              trapIPaddress
                DisplayString
              }

             trapIndex OBJECT-TYPE
             SYNTAX INTEGER
             ACCESS read-only
             STATUS mandatory
             DESCRIPTION
             "Index for the trap-receiver-table. Its value ranges between
              1 and the value of traptableNumber "
             ::= { trapTableEntry 1 }

             trapStatus OBJECT-TYPE
             SYNTAX INTEGER  {
             enabled(1),
             disabled(2)
             }
             ACCESS read-write
             STATUS mandatory
             DESCRIPTION
             "Enable or disable trap receiver"
             ::= { trapTableEntry 2 }

             trapIPaddress OBJECT-TYPE
             SYNTAX DisplayString (SIZE (0..31))
             ACCESS read-write
             STATUS mandatory
             DESCRIPTION
             "IP-address of trap-receiver"
             ::= { trapTableEntry 3 }

--******************************************************************************
--Traps
          alarmTemperature1 TRAP-TYPE
              ENTERPRISE cmc
              VARIABLES { sysDescr, sysContact, sysName,
                          sysLocation, statusMessage }
              DESCRIPTION
              "Alarm temperature 1, temperature 1 exceeds high-setpoint
              or falls below low-setpoint of temperature 1"
--
--#TYPE		"Temperature-alarm"
--#SUMMARY	"Location: %s, Message: %s from: %s, contact %s"
--#ARGUMENTS	{3,4,2,1}
--#SEVERITY	CRITICAL
--#TIMEINDEX	6
--#STATE	OPERATIONAL
--			
              ::= 1

          alarmTemperature2 TRAP-TYPE
              ENTERPRISE cmc
              VARIABLES { sysDescr, sysContact, sysName,
                          sysLocation, statusMessage }  
              DESCRIPTION 
              "Alarm temperature 2, temperature 2 exceeds high-setpoint
              or falls below low-setpoint of temperature 2"
--
--#TYPE		"Temperature-alarm"
--#SUMMARY	"Location: %s, Message: %s from: %s, contact %s"
--#ARGUMENTS	{3,4,2,1}
--#SEVERITY	CRITICAL
--#TIMEINDEX	6
--#STATE	OPERATIONAL
--
              ::= 2

          alarmFan1 TRAP-TYPE
              ENTERPRISE cmc
              VARIABLES { sysDescr, sysContact, sysName,
                          sysLocation, statusMessage }  
              DESCRIPTION
              "Alarm fan 1, no current to fan 1"
--
--#TYPE		"Fan-alarm"
--#SUMMARY	"Location: %s, Message: %s from: %s, contact %s"
--#ARGUMENTS	{3,4,2,1}
--#SEVERITY	MAJOR
--#TIMEINDEX	6
--#STATE	NONOPERATIONAL
--
              ::= 3

          alarmFan2 TRAP-TYPE
              ENTERPRISE cmc
              VARIABLES { sysDescr, sysContact, sysName,
                          sysLocation, statusMessage }  
              DESCRIPTION
              "Alarm fan 2, no current to fan 2"
--
--#TYPE		"Fan-alarm"
--#SUMMARY	"Location: %s, Message: %s from: %s, contact %s"
--#ARGUMENTS	{3,4,2,1}
--#SEVERITY	MAJOR
--#TIMEINDEX	6
--#STATE	NONOPERATIONAL
--
              ::= 4

          alarmVoltage TRAP-TYPE
              ENTERPRISE cmc
              VARIABLES { sysDescr, sysContact, sysName,
                          sysLocation, statusMessage }  
              DESCRIPTION
              "Alarm supply-voltage, voltage exceeds high-setpoint
              or falls below low-setpoint of supply-voltage"
--
--#TYPE		"Voltage-alarm"
--#SUMMARY	"Location: %s, Message: %s from: %s, contact %s"
--#ARGUMENTS	{3,4,2,1}
--#SEVERITY	MAJOR
--#TIMEINDEX	6
--#STATE	OPERATIONAL
--
              ::= 5

          alarmSmoke TRAP-TYPE
              ENTERPRISE cmc
              VARIABLES { sysDescr, sysContact, sysName,
                          sysLocation, statusMessage }  
              DESCRIPTION
              "Alarm smoke-sensor"
--
--#TYPE		"Smoke-alarm"
--#SUMMARY	"Location: %s, Message: %s from: %s, contact %s"
--#ARGUMENTS	{3,4,2,1}
--#SEVERITY	CRITICAL
--#TIMEINDEX	6
--#STATE	OPERATIONAL
--
              ::= 6

          alarmVibration TRAP-TYPE
              ENTERPRISE cmc
              VARIABLES { sysDescr, sysContact, sysName,
                          sysLocation, statusMessage }  
              DESCRIPTION
              "Alarm vibration-sensor"
--
--#TYPE		"Vibration-alarm"
--#SUMMARY	"Location: %s, Message: %s from: %s, contact %s"
--#ARGUMENTS	{3,4,2,1}
--#SEVERITY	CRITICAL
--#TIMEINDEX	6
--#STATE	OPERATIONAL
--
              ::= 7

          alarmUPS1 TRAP-TYPE
              ENTERPRISE cmc
              VARIABLES { sysDescr, sysContact, sysName,
                          sysLocation, statusMessage }  
              DESCRIPTION
              "Alarm UPS1"
--
--#TYPE		"UPS-alarm"
--#SUMMARY	"Location: %s, Message: %s from: %s, contact %s"
--#ARGUMENTS	{3,4,2,1}
--#SEVERITY	MINOR
--#TIMEINDEX	6
--#STATE	OPERATIONAL
--
              ::= 8

          alarmUPS2 TRAP-TYPE
              ENTERPRISE cmc
              VARIABLES { sysDescr, sysContact, sysName,
                          sysLocation, statusMessage }  
              DESCRIPTION
              "Alarm UPS2"
--
--#TYPE		"UPS-alarm"
--#SUMMARY	"Location: %s, Message: %s from: %s, contact %s"
--#ARGUMENTS	{3,4,2,1}
--#SEVERITY	MINOR
--#TIMEINDEX	6
--#STATE	OPERATIONAL
--
              ::= 9

          alarmDoor TRAP-TYPE
              ENTERPRISE cmc
              VARIABLES { sysDescr, sysContact, sysName,
                          sysLocation, statusMessage }  
              DESCRIPTION
              "Alarm Door/Door lock"
--
--#TYPE		"Door-alarm"
--#SUMMARY	"Location: %s, Message: %s from: %s, contact %s"
--#ARGUMENTS	{3,4,2,1}
--#SEVERITY	MAJOR
--#TIMEINDEX	6
--#STATE	OPERATIONAL
--
              ::= 10

          alarmAnalogAux1 TRAP-TYPE
              ENTERPRISE cmc
              VARIABLES { sysDescr, sysContact, sysName,
                          sysLocation, statusMessage }  
              DESCRIPTION
              "Alarm Analog Input Aux1 (4-20mA),
              value not OK"
--
--#TYPE		"AnalogAux-alarm"
--#SUMMARY	"Location: %s, Message: %s from: %s, contact %s"
--#ARGUMENTS	{3,4,2,1}
--#SEVERITY	MINOR
--#TIMEINDEX	6
--#STATE	OPERATIONAL
--
              ::= 11

          alarmAnalogAux2 TRAP-TYPE
              ENTERPRISE cmc
              VARIABLES { sysDescr, sysContact, sysName,
                          sysLocation, statusMessage }  
              DESCRIPTION
              "Alarm Analog Input Aux2 (4-20mA),
              value not OK"
--
--#TYPE		"AnalogAux-alarm"
--#SUMMARY	"Location: %s, Message: %s from: %s, contact %s"
--#ARGUMENTS	{3,4,2,1}
--#SEVERITY	MINOR
--#TIMEINDEX	6
--#STATE	OPERATIONAL
--
              ::= 12

          msgAccess    	    TRAP-TYPE
              ENTERPRISE cmc
              VARIABLES { sysDescr, sysContact, sysName,
                          sysLocation, statusMessage,statusAccess }  
              DESCRIPTION
              "Access message"
--
--#TYPE		"Access"
--#SUMMARY	"Location: %s, Message: %s by %s from: %s, contact %s"
--#ARGUMENTS	{3,4,5,2,1}
--#SEVERITY	MINOR
--#TIMEINDEX	6
--#STATE	OPERATIONAL
--
              ::= 13

	  okTrap            TRAP-TYPE
              ENTERPRISE cmc
              VARIABLES { sysDescr, sysContact, sysName,
                          sysLocation, statusMessage } 
              DESCRIPTION
              "Trap for OK- message. This trap is send, if a detected 
               alarm is gone" 
--
--#TYPE		"OK-Trap"
--#SUMMARY	"No Alarm in: %s, Message: %s from: %s"
--#ARGUMENTS	{3,4,2}
--#SEVERITY	INFORMATIONAL
--#TIMEINDEX	6
--#STATE	OPERATIONAL
--
              ::= 14

          alarm1            TRAP-TYPE
              ENTERPRISE cmc
              VARIABLES { sysDescr, sysContact, sysName,
                          sysLocation, statusMessage }   
              DESCRIPTION
              "Trap 1"
--
--#TYPE		"Alarm 1"
--#SUMMARY	"Location: %s, Message: %s from: %s, contact %s"
--#ARGUMENTS	{3,4,2,1}
--#SEVERITY	MAJOR
--#TIMEINDEX	6
--#STATE	OPERATIONAL
--
              ::= 21

          alarm2            TRAP-TYPE
              ENTERPRISE cmc
              VARIABLES { sysDescr, sysContact, sysName,
                          sysLocation, statusMessage }   
              DESCRIPTION 
              "Trap 2"
--
--#TYPE		"Alarm 2"
--#SUMMARY	"Location: %s, Message: %s from: %s, contact %s"
--#ARGUMENTS	{3,4,2,1}
--#SEVERITY	MAJOR
--#TIMEINDEX	6
--#STATE	OPERATIONAL
--
              ::= 22

          alarm3         TRAP-TYPE
              ENTERPRISE cmc
              VARIABLES { sysDescr, sysContact, sysName,
                          sysLocation, statusMessage }   
              DESCRIPTION
              "Trap 3 "
--
--#TYPE		"Alarm 3"
--#SUMMARY	"Location: %s, Message: %s from: %s, contact %s"
--#ARGUMENTS	{3,4,2,1}
--#SEVERITY	MAJOR
--#TIMEINDEX	6
--#STATE	OPERATIONAL
--
              ::= 23

          alarm4         TRAP-TYPE
              ENTERPRISE cmc
              VARIABLES { sysDescr, sysContact, sysName,
                          sysLocation, statusMessage }   
              DESCRIPTION
              "Trap 4"
--
--#TYPE		"Alarm 4"
--#SUMMARY	"Location: %s, Message: %s from: %s, contact %s"
--#ARGUMENTS	{3,4,2,1}
--#SEVERITY	MAJOR
--#TIMEINDEX	6
--#STATE	OPERATIONAL
--
              ::= 24

          alarm5         TRAP-TYPE
              ENTERPRISE cmc
              VARIABLES { sysDescr, sysContact, sysName,
                          sysLocation, statusMessage }   
              DESCRIPTION
              "Trap 5"
--
--#TYPE		"Alarm 5"
--#SUMMARY	"Location: %s, Message: %s from: %s, contact %s"
--#ARGUMENTS	{3,4,2,1}
--#SEVERITY	MAJOR
--#TIMEINDEX	6
--#STATE	OPERATIONAL
--
              ::= 25

          alarm6         TRAP-TYPE
              ENTERPRISE cmc
              VARIABLES { sysDescr, sysContact, sysName,
                          sysLocation, statusMessage }   
              DESCRIPTION
              "Trap 6"
--
--#TYPE		"Alarm 6"
--#SUMMARY	"Location: %s, Message: %s from: %s, contact %s"
--#ARGUMENTS	{3,4,2,1}
--#SEVERITY	MAJOR
--#TIMEINDEX	6
--#STATE	OPERATIONAL
--
              ::= 26

          alarm7         TRAP-TYPE
              ENTERPRISE cmc
              VARIABLES { sysDescr, sysContact, sysName,
                          sysLocation, statusMessage }   
              DESCRIPTION
              "Trap 7"
--
--#TYPE		"Alarm 7"
--#SUMMARY	"Location: %s, Message: %s from: %s, contact %s"
--#ARGUMENTS	{3,4,2,1}
--#SEVERITY	MAJOR
--#TIMEINDEX	6
--#STATE	OPERATIONAL
--
              ::= 27

          alarm8         TRAP-TYPE
              ENTERPRISE cmc
              VARIABLES { sysDescr, sysContact, sysName,
                          sysLocation, statusMessage }   
              DESCRIPTION
              "Trap 8"
--
--#TYPE		"Alarm 8"
--#SUMMARY	"Location: %s, Message: %s from: %s, contact %s"
--#ARGUMENTS	{3,4,2,1}
--#SEVERITY	MAJOR
--#TIMEINDEX	6
--#STATE	OPERATIONAL
--
              ::= 28

          alarm9         TRAP-TYPE
              ENTERPRISE cmc
              VARIABLES { sysDescr, sysContact, sysName,
                          sysLocation, statusMessage }   
              DESCRIPTION
              "Trap 9"
--
--#TYPE		"Alarm 9"
--#SUMMARY	"Location: %s, Message: %s from: %s, contact %s"
--#ARGUMENTS	{3,4,2,1}
--#SEVERITY	MAJOR
--#TIMEINDEX	6
--#STATE	OPERATIONAL
--
              ::= 29

          alarm10        TRAP-TYPE
              ENTERPRISE cmc
              VARIABLES { sysDescr, sysContact, sysName,
                          sysLocation, statusMessage }   
              DESCRIPTION
              "Trap 10"
--
--#TYPE		"Alarm 10"
--#SUMMARY	"Location: %s, Message: %s from: %s, contact %s"
--#ARGUMENTS	{3,4,2,1}
--#SEVERITY	MAJOR
--#TIMEINDEX	6
--#STATE	OPERATIONAL
--
              ::= 30

          alarm11        TRAP-TYPE
              ENTERPRISE cmc
              VARIABLES { sysDescr, sysContact, sysName,
                          sysLocation, statusMessage }   
              DESCRIPTION
              "Trap 11"
--
--#TYPE		"Alarm 11"
--#SUMMARY	"Location: %s, Message: %s from: %s, contact %s"
--#ARGUMENTS	{3,4,2,1}
--#SEVERITY	MAJOR
--#TIMEINDEX	6
--#STATE	OPERATIONAL
--
              ::= 31

          alarm12        TRAP-TYPE
              ENTERPRISE cmc
              VARIABLES { sysDescr, sysContact, sysName,
                          sysLocation, statusMessage }   
              DESCRIPTION
              "Trap 12"
--
--#TYPE		"Alarm 12"
--#SUMMARY	"Location: %s, Message: %s from: %s, contact %s"
--#ARGUMENTS	{3,4,2,1}
--#SEVERITY	MAJOR
--#TIMEINDEX	6
--#STATE	OPERATIONAL
--
              ::= 32

          alarm13        TRAP-TYPE
              ENTERPRISE cmc
              VARIABLES { sysDescr, sysContact, sysName,
                          sysLocation, statusMessage }   
              DESCRIPTION
              "Trap 13"
--
--#TYPE		"Alarm 13"
--#SUMMARY	"Location: %s, Message: %s from: %s, contact %s"
--#ARGUMENTS	{3,4,2,1}
--#SEVERITY	MAJOR
--#TIMEINDEX	6
--#STATE	OPERATIONAL
--
              ::= 33

          alarm14        TRAP-TYPE
              ENTERPRISE cmc
              VARIABLES { sysDescr, sysContact, sysName,
                          sysLocation, statusMessage }   
              DESCRIPTION
              "Trap 14"
--
--#TYPE		"Alarm 14"
--#SUMMARY	"Location: %s, Message: %s from: %s, contact %s"
--#ARGUMENTS	{3,4,2,1}
--#SEVERITY	MAJOR
--#TIMEINDEX	6
--#STATE	OPERATIONAL
--
              ::= 34

          alarm15        TRAP-TYPE
              ENTERPRISE cmc
              VARIABLES { sysDescr, sysContact, sysName,
                          sysLocation, statusMessage }   
              DESCRIPTION
              "Trap 15"
--
--#TYPE		"Alarm 15"
--#SUMMARY	"Location: %s, Message: %s from: %s, contact %s"
--#ARGUMENTS	{3,4,2,1}
--#SEVERITY	MAJOR
--#TIMEINDEX	6
--#STATE	OPERATIONAL
--
              ::= 35

          alarm16        TRAP-TYPE
              ENTERPRISE cmc
              VARIABLES { sysDescr, sysContact, sysName,
                          sysLocation, statusMessage }   
              DESCRIPTION
              "Trap 16"
--
--#TYPE		"Alarm 16"
--#SUMMARY	"Location: %s, Message: %s from: %s, contact %s"
--#ARGUMENTS	{3,4,2,1}
--#SEVERITY	MAJOR
--#TIMEINDEX	6
--#STATE	OPERATIONAL
--
              ::= 36

          alarm17        TRAP-TYPE
              ENTERPRISE cmc
              VARIABLES { sysDescr, sysContact, sysName,
                          sysLocation, statusMessage }   
              DESCRIPTION
              "Trap 17"
--
--#TYPE		"Alarm 17"
--#SUMMARY	"Location: %s, Message: %s from: %s, contact %s"
--#ARGUMENTS	{3,4,2,1}
--#SEVERITY	MAJOR
--#TIMEINDEX	6
--#STATE	OPERATIONAL
--
              ::= 37

          alarm18        TRAP-TYPE
              ENTERPRISE cmc
              VARIABLES { sysDescr, sysContact, sysName,
                          sysLocation, statusMessage }   
              DESCRIPTION
              "Trap 18"
--
--#TYPE		"Alarm 18"
--#SUMMARY	"Location: %s, Message: %s from: %s, contact %s"
--#ARGUMENTS	{3,4,2,1}
--#SEVERITY	MAJOR
--#TIMEINDEX	6
--#STATE	OPERATIONAL
--
              ::= 38

          alarm19        TRAP-TYPE
              ENTERPRISE cmc
              VARIABLES { sysDescr, sysContact, sysName,
                          sysLocation, statusMessage }   
              DESCRIPTION
              "Trap 19"
--
--#TYPE		"Alarm 19"
--#SUMMARY	"Location: %s, Message: %s from: %s, contact %s"
--#ARGUMENTS	{3,4,2,1}
--#SEVERITY	MAJOR
--#TIMEINDEX	6
--#STATE	OPERATIONAL
--
              ::= 39

          alarm20        TRAP-TYPE
              ENTERPRISE cmc
              VARIABLES { sysDescr, sysContact, sysName,
                          sysLocation, statusMessage }   
              DESCRIPTION
              "Trap 20"
--
--#TYPE		"Alarm 20"
--#SUMMARY	"Location: %s, Message: %s from: %s, contact %s"
--#ARGUMENTS	{3,4,2,1}
--#SEVERITY	MAJOR
--#TIMEINDEX	6
--#STATE	OPERATIONAL
--
              ::= 40

          alarm21        TRAP-TYPE
              ENTERPRISE cmc
              VARIABLES { sysDescr, sysContact, sysName,
                          sysLocation, statusMessage }   
              DESCRIPTION
              "Trap 21"
--
--#TYPE		"Alarm 21"
--#SUMMARY	"Location: %s, Message: %s from: %s, contact %s"
--#ARGUMENTS	{3,4,2,1}
--#SEVERITY	MAJOR
--#TIMEINDEX	6
--#STATE	OPERATIONAL
--
              ::= 41

          alarm22        TRAP-TYPE
              ENTERPRISE cmc
              VARIABLES { sysDescr, sysContact, sysName,
                          sysLocation, statusMessage }   
              DESCRIPTION
              "Trap 22"
--
--#TYPE		"Alarm 22"
--#SUMMARY	"Location: %s, Message: %s from: %s, contact %s"
--#ARGUMENTS	{3,4,2,1}
--#SEVERITY	MAJOR
--#TIMEINDEX	6
--#STATE	OPERATIONAL
--
              ::= 42

          alarm23        TRAP-TYPE
              ENTERPRISE cmc
              VARIABLES { sysDescr, sysContact, sysName,
                          sysLocation, statusMessage }   
              DESCRIPTION
              "Trap 23"
--
--#TYPE		"Alarm 23"
--#SUMMARY	"Location: %s, Message: %s from: %s, contact %s"
--#ARGUMENTS	{3,4,2,1}
--#SEVERITY	MAJOR
--#TIMEINDEX	6
--#STATE	OPERATIONAL
--
              ::= 43

          alarm24        TRAP-TYPE
              ENTERPRISE cmc
              VARIABLES { sysDescr, sysContact, sysName,
                          sysLocation, statusMessage }   
              DESCRIPTION
              "Trap 24"
--
--#TYPE		"Alarm 24"
--#SUMMARY	"Location: %s, Message: %s from: %s, contact %s"
--#ARGUMENTS	{3,4,2,1}
--#SEVERITY	MAJOR
--#TIMEINDEX	6
--#STATE	OPERATIONAL
--
              ::= 44

          alarm25        TRAP-TYPE
              ENTERPRISE cmc
              VARIABLES { sysDescr, sysContact, sysName,
                          sysLocation, statusMessage }   
              DESCRIPTION
              "Trap 25"
--
--#TYPE		"Alarm 25"
--#SUMMARY	"Location: %s, Message: %s from: %s, contact %s"
--#ARGUMENTS	{3,4,2,1}
--#SEVERITY	MAJOR
--#TIMEINDEX	6
--#STATE	OPERATIONAL
--
              ::= 45

          alarm26        TRAP-TYPE
              ENTERPRISE cmc
              VARIABLES { sysDescr, sysContact, sysName,
                          sysLocation, statusMessage }   
              DESCRIPTION
              "Trap 26"
--
--#TYPE		"Alarm 26"
--#SUMMARY	"Location: %s, Message: %s from: %s, contact %s"
--#ARGUMENTS	{3,4,2,1}
--#SEVERITY	MAJOR
--#TIMEINDEX	6
--#STATE	OPERATIONAL
--
              ::= 46

          alarm27        TRAP-TYPE
              ENTERPRISE cmc
              VARIABLES { sysDescr, sysContact, sysName,
                          sysLocation, statusMessage }   
              DESCRIPTION
              "Trap 27"
--
--#TYPE		"Alarm 27"
--#SUMMARY	"Location: %s, Message: %s from: %s, contact %s"
--#ARGUMENTS	{3,4,2,1}
--#SEVERITY	MAJOR
--#TIMEINDEX	6
--#STATE	OPERATIONAL
--
              ::= 47

          alarm28        TRAP-TYPE
              ENTERPRISE cmc
              VARIABLES { sysDescr, sysContact, sysName,
                          sysLocation, statusMessage }   
              DESCRIPTION
              "Trap 28"
--
--#TYPE		"Alarm 28"
--#SUMMARY	"Location: %s, Message: %s from: %s, contact %s"
--#ARGUMENTS	{3,4,2,1}
--#SEVERITY	MAJOR
--#TIMEINDEX	6
--#STATE	OPERATIONAL
--
              ::= 48

          alarm29        TRAP-TYPE
              ENTERPRISE cmc
              VARIABLES { sysDescr, sysContact, sysName,
                          sysLocation, statusMessage }  
              DESCRIPTION
              "Trap 29"
--
--#TYPE		"Alarm 29"
--#SUMMARY	"Location: %s, Message: %s from: %s, contact %s"
--#ARGUMENTS	{3,4,2,1}
--#SEVERITY	MAJOR
--#TIMEINDEX	6
--#STATE	OPERATIONAL
--
              ::= 49

          alarm30        TRAP-TYPE
              ENTERPRISE cmc
              VARIABLES { sysDescr, sysContact, sysName,
                          sysLocation, statusMessage }   
              DESCRIPTION
              "Trap 30"
--
--#TYPE		"Alarm 30"
--#SUMMARY	"Location: %s, Message: %s from: %s, contact %s"
--#ARGUMENTS	{3,4,2,1}
--#SEVERITY	MAJOR
--#TIMEINDEX	6
--#STATE	OPERATIONAL
--
              ::= 50

          alarm31        TRAP-TYPE
              ENTERPRISE cmc
              VARIABLES { sysDescr, sysContact, sysName,
                          sysLocation, statusMessage }   
              DESCRIPTION
              "Trap 31"
--
--#TYPE		"Alarm 31"
--#SUMMARY	"Location: %s, Message: %s from: %s, contact %s"
--#ARGUMENTS	{3,4,2,1}
--#SEVERITY	MAJOR
--#TIMEINDEX	6
--#STATE	OPERATIONAL
--
              ::= 51

          alarm32        TRAP-TYPE
              ENTERPRISE cmc
              VARIABLES { sysDescr, sysContact, sysName,
                          sysLocation, statusMessage }   
              DESCRIPTION
              "Trap 32"
--
--#TYPE		"Alarm 32"
--#SUMMARY	"Location: %s, Message: %s from: %s, contact %s"
--#ARGUMENTS	{3,4,2,1}
--#SEVERITY	MAJOR
--#TIMEINDEX	6
--#STATE	OPERATIONAL
--
              ::= 52

          alarm33        TRAP-TYPE
              ENTERPRISE cmc
              VARIABLES { sysDescr, sysContact, sysName,
                          sysLocation, statusMessage }  
              DESCRIPTION
              "Trap 33"
--
--#TYPE		"Alarm 33"
--#SUMMARY	"Location: %s, Message: %s from: %s, contact %s"
--#ARGUMENTS	{3,4,2,1}
--#SEVERITY	MAJOR
--#TIMEINDEX	6
--#STATE	OPERATIONAL
--
              ::= 53

          alarm34        TRAP-TYPE
              ENTERPRISE cmc
              VARIABLES { sysDescr, sysContact, sysName,
                          sysLocation, statusMessage }   
              DESCRIPTION
              "Trap 34"
--
--#TYPE		"Alarm 34"
--#SUMMARY	"Location: %s, Message: %s from: %s, contact %s"
--#ARGUMENTS	{3,4,2,1}
--#SEVERITY	MAJOR
--#TIMEINDEX	6
--#STATE	OPERATIONAL
--
              ::= 54

          alarm35        TRAP-TYPE
              ENTERPRISE cmc
              VARIABLES { sysDescr, sysContact, sysName,
                          sysLocation, statusMessage }   
              DESCRIPTION
              "Trap 35"
--
--#TYPE		"Alarm 35"
--#SUMMARY	"Location: %s, Message: %s from: %s, contact %s"
--#ARGUMENTS	{3,4,2,1}
--#SEVERITY	MAJOR
--#TIMEINDEX	6
--#STATE	OPERATIONAL
--
              ::= 55


	    END
