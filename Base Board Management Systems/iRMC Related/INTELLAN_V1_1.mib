-- Automatically generated from file 
-- Wed Mar 08 11:19:25 W. Europe Standard Time 2006

INTEL-LAN-ADAPTERS-MIB DEFINITIONS ::= BEGIN

IMPORTS
        enterprises, Gauge, Counter, IpAddress, TimeTicks FROM RFC1155-SMI
        OBJECT-TYPE 	  FROM RFC1212
        TRAP-TYPE 	  FROM RFC1215;

intel OBJECT IDENTIFIER ::= {enterprises 343}

products OBJECT IDENTIFIER ::= {intel 2}

nic-products OBJECT IDENTIFIER ::= {products 7}

intel-lan-adapters OBJECT IDENTIFIER ::= {nic-products 2}

InterfaceIndex ::= INTEGER

DisplayString ::= OCTET STRING

PhysAddress ::= OCTET STRING

component-description OBJECT IDENTIFIER ::= {intel-lan-adapters 1}

company 	OBJECT-TYPE
	SYNTAX DisplayString
	ACCESS read-only
	STATUS mandatory
	DESCRIPTION
		"Company that provided this MIB - Intel(R) Corporation."
	::= { component-description 1 }

description 	OBJECT-TYPE
	SYNTAX DisplayString
	ACCESS read-only
	STATUS mandatory
	DESCRIPTION
		"Description of this component - 
		 Intel(R) Network Adapter(s), Advanced Management."
	::= { component-description 2 }

operatingSystem 	OBJECT-TYPE
	SYNTAX DisplayString
	ACCESS read-only
	STATUS mandatory
	DESCRIPTION
		"Operating System of the server on which the SNMP agent is executed."
	::= { component-description 3 }

mibVersion1-4-3 	OBJECT-TYPE
	SYNTAX DisplayString
	ACCESS read-only
	STATUS mandatory
	DESCRIPTION
		"Version of this MIB - the empty string is always returned."
	::= { component-description 4 }

mibVersionSupported 	OBJECT-TYPE
	SYNTAX DisplayString
	ACCESS read-only
	STATUS mandatory
	DESCRIPTION
		"Version of the MIB supported by the agent.
		 1.x.y indicates that every MIB version of that template is supported by the agent."
	::= { component-description 5 }

agentExtensionVersion 	OBJECT-TYPE
	SYNTAX DisplayString
	ACCESS read-only
	STATUS mandatory
	DESCRIPTION
		"Version of the SNMP extension agent."
	::= { component-description 6 }

status 	OBJECT-TYPE
	SYNTAX INTEGER {
                               enabled (1),
                               disabled (2)
                        }
	ACCESS read-only
	STATUS mandatory
	DESCRIPTION
		"Indicates status and functionality of the adapter(s) -
		 whether the base driver and ANS are loaded."
	::= { component-description 7 }

adaptersTables OBJECT IDENTIFIER ::= {intel-lan-adapters 2}

genericAdaptersAttrTables OBJECT IDENTIFIER ::= {adaptersTables 1}

genericAdaptersAttrTable 	OBJECT-TYPE
	SYNTAX SEQUENCE OF GenericAdapterAttrEntry
	ACCESS not-accessible
	STATUS mandatory
	DESCRIPTION
		"Attributes common to all kinds of adapters."
	::= { genericAdaptersAttrTables 1 }

genericAdapterAttrEntry 	OBJECT-TYPE
	SYNTAX GenericAdapterAttrEntry
	ACCESS not-accessible
	STATUS mandatory
	DESCRIPTION
		"Attributes common to all kinds of adapters. 
		 There is one 'entry' for each physical or virtual adapter."
	INDEX {
		adapterIndex
	}
	::= { genericAdaptersAttrTable 1 }

GenericAdapterAttrEntry ::= SEQUENCE {
	adapterIndex             InterfaceIndex,
	adapterName              DisplayString,
	adapterType              INTEGER,
	adapterDriverLoadStatus  INTEGER
	}

adapterIndex 	OBJECT-TYPE
	SYNTAX InterfaceIndex
	ACCESS read-only
	STATUS mandatory
	DESCRIPTION
		"A unique value, greater than or equal to zero, for each interface."
	::= { genericAdapterAttrEntry 1 }

adapterName 	OBJECT-TYPE
	SYNTAX DisplayString
	ACCESS read-only
	STATUS mandatory
	DESCRIPTION
		"Name of the adapter interface.
		 There is a unique name for each instance."
	::= { genericAdapterAttrEntry 2 }

adapterType 	OBJECT-TYPE
	SYNTAX INTEGER {
                               standAlone (0),
                               teamMember (1),
                               virtual (2)
                        }
	ACCESS read-only
	STATUS mandatory
	DESCRIPTION
		"Type of adapter (member, stand-alone, or virtual)."
	::= { genericAdapterAttrEntry 3 }

adapterDriverLoadStatus 	OBJECT-TYPE
	SYNTAX INTEGER {
                               loaded (0),
                               notLoaded (1)
                        }
	ACCESS read-only
	STATUS mandatory
	DESCRIPTION
		"Load status of the driver:
		 -'loaded' if the driver is loaded on the NIC; 'notLoaded' otherwise.
		 A status of 'notLoaded' means that the NIC is missing (via 'hotRemove')
		 or the driver is not fully loaded for some reason."
	::= { genericAdapterAttrEntry 4 }

genericAdaptersDriversAttrTable 	OBJECT-TYPE
	SYNTAX SEQUENCE OF GenericAdapterDriverAttrEntry
	ACCESS not-accessible
	STATUS mandatory
	DESCRIPTION
		"Attributes common to all kinds of adapter drivers."
	::= { genericAdaptersAttrTables 2 }

genericAdapterDriverAttrEntry 	OBJECT-TYPE
	SYNTAX GenericAdapterDriverAttrEntry
	ACCESS not-accessible
	STATUS mandatory
	DESCRIPTION
		"Attributes common to all kinds of adapter drivers.
		 There is one 'entry' for each adapter driver"
	INDEX {
		adapterIndex
	}
	::= { genericAdaptersDriversAttrTable 1 }

GenericAdapterDriverAttrEntry ::= SEQUENCE {
	adapterDriverName     DisplayString,
	adapterDriverInfo     DisplayString,
	adapterDriverVersion  DisplayString,
	adapterDriverPath     DisplayString,
	adapterDriverDate     DisplayString,
	adapterDriverSize     DisplayString,
	adapterIpAddress      DisplayString
	}

adapterDriverName 	OBJECT-TYPE
	SYNTAX DisplayString
	ACCESS read-only
	STATUS mandatory
	DESCRIPTION
		"Name of the adapter driver."
	::= { genericAdapterDriverAttrEntry 1 }

adapterDriverInfo 	OBJECT-TYPE
	SYNTAX DisplayString
	ACCESS read-only
	STATUS mandatory
	DESCRIPTION
		"Additional information about the adapter. Includes name of the NIC."
	::= { genericAdapterDriverAttrEntry 2 }

adapterDriverVersion 	OBJECT-TYPE
	SYNTAX DisplayString
	ACCESS read-only
	STATUS mandatory
	DESCRIPTION
		"Adapter driver version number."
	::= { genericAdapterDriverAttrEntry 3 }

adapterDriverPath 	OBJECT-TYPE
	SYNTAX DisplayString
	ACCESS read-only
	STATUS mandatory
	DESCRIPTION
		"Adapter driver path name."
	::= { genericAdapterDriverAttrEntry 4 }

adapterDriverDate 	OBJECT-TYPE
	SYNTAX DisplayString
	ACCESS read-only
	STATUS mandatory
	DESCRIPTION
		"Adapter driver creation date (in mm/dd/yy format)."
	::= { genericAdapterDriverAttrEntry 5 }

adapterDriverSize 	OBJECT-TYPE
	SYNTAX DisplayString
	ACCESS read-only
	STATUS mandatory
	DESCRIPTION
		"Adapter driver file size."
	::= { genericAdapterDriverAttrEntry 6 }

adapterIpAddress 	OBJECT-TYPE
	SYNTAX DisplayString
	ACCESS read-only
	STATUS mandatory
	DESCRIPTION
		"Adapter IP address"
	::= { genericAdapterDriverAttrEntry 7 }

genericAdaptersTrafficStatsAttrTable 	OBJECT-TYPE
	SYNTAX SEQUENCE OF GenericAdapterTrafficStatsAttrEntry
	ACCESS not-accessible
	STATUS mandatory
	DESCRIPTION
		"Traffic stats common to all kinds of adapters."
	::= { genericAdaptersAttrTables 3 }

genericAdapterTrafficStatsAttrEntry 	OBJECT-TYPE
	SYNTAX GenericAdapterTrafficStatsAttrEntry
	ACCESS not-accessible
	STATUS mandatory
	DESCRIPTION
		"Traffic stats common to all kinds of adapters.
		 There is one 'entry' for each adapter instance."
	INDEX {
		adapterIndex
	}
	::= { genericAdaptersTrafficStatsAttrTable 1 }

GenericAdapterTrafficStatsAttrEntry ::= SEQUENCE {
	adapterRxPackets    Counter,
	adapterTxPackets    Counter,
	adapterRxBytes      Counter,
	adapterTxBytes      Counter,
	adapterRxErrors     Counter,
	adapterTxErrors     Counter,
	adapterRxDropped    Counter,
	adapterTxDropped    Counter,
	adapterRxMulticast  Counter,
	adapterCollisions   Counter
	}

adapterRxPackets 	OBJECT-TYPE
	SYNTAX Counter
	ACCESS read-only
	STATUS mandatory
	DESCRIPTION
		"Total number of packets received."
	::= { genericAdapterTrafficStatsAttrEntry 1 }

adapterTxPackets 	OBJECT-TYPE
	SYNTAX Counter
	ACCESS read-only
	STATUS mandatory
	DESCRIPTION
		"Total number of packets transmitted."
	::= { genericAdapterTrafficStatsAttrEntry 2 }

adapterRxBytes 	OBJECT-TYPE
	SYNTAX Counter
	ACCESS read-only
	STATUS mandatory
	DESCRIPTION
		"Total number of bytes received."
	::= { genericAdapterTrafficStatsAttrEntry 3 }

adapterTxBytes 	OBJECT-TYPE
	SYNTAX Counter
	ACCESS read-only
	STATUS mandatory
	DESCRIPTION
		"Total number of bytes transmitted."
	::= { genericAdapterTrafficStatsAttrEntry 4 }

adapterRxErrors 	OBJECT-TYPE
	SYNTAX Counter
	ACCESS read-only
	STATUS mandatory
	DESCRIPTION
		"Total number of packets received with errors
		 (packets that failed to reach the protocol)."
	::= { genericAdapterTrafficStatsAttrEntry 5 }

adapterTxErrors 	OBJECT-TYPE
	SYNTAX Counter
	ACCESS read-only
	STATUS mandatory
	DESCRIPTION
		"Total number of packets that failed to transmit."
	::= { genericAdapterTrafficStatsAttrEntry 6 }

adapterRxDropped 	OBJECT-TYPE
	SYNTAX Counter
	ACCESS read-only
	STATUS mandatory
	DESCRIPTION
		"Total number of receive packets dropped due to overrun."
	::= { genericAdapterTrafficStatsAttrEntry 7 }

adapterTxDropped 	OBJECT-TYPE
	SYNTAX Counter
	ACCESS read-only
	STATUS mandatory
	DESCRIPTION
		"Total number of transmit packets dropped due to successive collisions."
	::= { genericAdapterTrafficStatsAttrEntry 8 }

adapterRxMulticast 	OBJECT-TYPE
	SYNTAX Counter
	ACCESS read-only
	STATUS mandatory
	DESCRIPTION
		"Total number of Multicast packets received."
	::= { genericAdapterTrafficStatsAttrEntry 9 }

adapterCollisions 	OBJECT-TYPE
	SYNTAX Counter
	ACCESS read-only
	STATUS mandatory
	DESCRIPTION
		"Total number of single collisions."
	::= { genericAdapterTrafficStatsAttrEntry 10 }

physicalAdaptersAttrTables OBJECT IDENTIFIER ::= {adaptersTables 2}

physicalAdaptersAttrTable 	OBJECT-TYPE
	SYNTAX SEQUENCE OF PhysicalAdapterAttrEntry
	ACCESS not-accessible
	STATUS mandatory
	DESCRIPTION
		"Attributes common to all Physical Adapters."
	::= { physicalAdaptersAttrTables 1 }

physicalAdapterAttrEntry 	OBJECT-TYPE
	SYNTAX PhysicalAdapterAttrEntry
	ACCESS not-accessible
	STATUS mandatory
	DESCRIPTION
		"Attributes common to all Physical Adapters.
		 There is one 'entry' for each standalone or member adapter."
	INDEX {
		physicalAdapterIndex
	}
	::= { physicalAdaptersAttrTable 1 }

PhysicalAdapterAttrEntry ::= SEQUENCE {
	physicalAdapterIndex                     InterfaceIndex,
	physicalAdapterLinkStatus                INTEGER,
	physicalAdapterLinkStatusChangesCounter  Counter,
	physicalAdapterSpeed                     Gauge,
	physicalAdapterDplxMode                  INTEGER,
	physicalAdapterAutoNegotiation           INTEGER,
	physicalAdapterPciBus                    INTEGER,
	physicalAdapterPciSlot                   INTEGER,
	physicalAdapterIrq                       INTEGER,
	physicalAdapterCurrentNA                 PhysAddress,
	physicalAdapterPermanentNA               PhysAddress,
	physicalAdapterOnlineDiagStatus          INTEGER,
	physicalAdapterExpressTeamed             INTEGER,
	physicalAdapterExpressTeamBundleId       INTEGER
	}

physicalAdapterIndex 	OBJECT-TYPE
	SYNTAX InterfaceIndex
	ACCESS read-only
	STATUS mandatory
	DESCRIPTION
		"A unique value, greater than or equal to zero, for each interface."
	::= { physicalAdapterAttrEntry 1 }

physicalAdapterLinkStatus 	OBJECT-TYPE
	SYNTAX INTEGER {
                               not-available (-1),
                               link-up (0),
                               link-down (1)
                        }
	ACCESS read-only
	STATUS mandatory
	DESCRIPTION
		"Physical adapter link status. Appears only if available -
		 that is, only if the driver is compliant with SNMP;
		 otherwise, NO_SUCH_NAME is returned."
	::= { physicalAdapterAttrEntry 2 }

physicalAdapterLinkStatusChangesCounter 	OBJECT-TYPE
	SYNTAX Counter
	ACCESS read-write
	STATUS mandatory
	DESCRIPTION
		"Number of changes in physical adapter link status. 
		 Any change ('up-to-down' or 'down- to-up') is counted.
		 This value can be reset (to zero) by the user; no other value is permitted.
		 This value appears only if it is available - 
		 that is, only if the driver is compliant with SNMP; 
		 otherwise, NO_SUCH_NAME is returned."
	::= { physicalAdapterAttrEntry 3 }

physicalAdapterSpeed 	OBJECT-TYPE
	SYNTAX Gauge
	ACCESS read-only
	STATUS mandatory
	DESCRIPTION
		"Physical adapter speed (in Mbps).
		 Appears only for an SNMP-compliant adapter with link up."
	::= { physicalAdapterAttrEntry 4 }

physicalAdapterDplxMode 	OBJECT-TYPE
	SYNTAX INTEGER {
                               not-available (0),
                               half (1),
                               full (2)
                        }
	ACCESS read-only
	STATUS mandatory
	DESCRIPTION
		"Physical Adapter Duplex Mode.
		 Appears only for an SNMP-compliant adapter with link up."
	::= { physicalAdapterAttrEntry 5 }

physicalAdapterAutoNegotiation 	OBJECT-TYPE
	SYNTAX INTEGER {
                               on (0),
                               off (1)
                        }
	ACCESS read-only
	STATUS mandatory
	DESCRIPTION
		"Physical adapter autonegotiation mode.
		 This value appears only if it is available -
		 that is, only if the driver is compliant with SNMP;
		 otherwise, NO_SUCH_NAME is returned."
	::= { physicalAdapterAttrEntry 6 }

physicalAdapterPciBus 	OBJECT-TYPE
	SYNTAX INTEGER
	ACCESS read-only
	STATUS mandatory
	DESCRIPTION
		"Physical adapter PCI bus number."
	::= { physicalAdapterAttrEntry 7 }

physicalAdapterPciSlot 	OBJECT-TYPE
	SYNTAX INTEGER
	ACCESS read-only
	STATUS mandatory
	DESCRIPTION
		"Physical adapter PCI slot number."
	::= { physicalAdapterAttrEntry 8 }

physicalAdapterIrq 	OBJECT-TYPE
	SYNTAX INTEGER
	ACCESS read-only
	STATUS mandatory
	DESCRIPTION
		"Physical adapter Interrupt Request number."
	::= { physicalAdapterAttrEntry 9 }

physicalAdapterCurrentNA 	OBJECT-TYPE
	SYNTAX PhysAddress
	ACCESS read-only
	STATUS mandatory
	DESCRIPTION
		"Current MAC address of the physical adapter(in hex notation)."
	::= { physicalAdapterAttrEntry 10 }

physicalAdapterPermanentNA 	OBJECT-TYPE
	SYNTAX PhysAddress
	ACCESS read-only
	STATUS mandatory
	DESCRIPTION
		"Permanent MAC address of the physical adapter(in hex notation)."
	::= { physicalAdapterAttrEntry 11 }

physicalAdapterOnlineDiagStatus 	OBJECT-TYPE
	SYNTAX INTEGER {
                               not-available (-1),
                               failed (0),
                               passed (1)
                        }
	ACCESS read-only
	STATUS mandatory
	DESCRIPTION
		"The Online Diagnostics Status of the Physical Adapter. 
		 Online Diagnostics consist of Link Test and other Hardware Tests."
	::= { physicalAdapterAttrEntry 12 }

physicalAdapterExpressTeamed 	OBJECT-TYPE
	SYNTAX INTEGER {
                               not-available (0),
                               primary (1),
                               secondary (2)
                        }
	ACCESS read-only
	STATUS mandatory
	DESCRIPTION
		"Physical Adapter Express team status.
		 Appears only for an adapter with express teaming capability."
	::= { physicalAdapterAttrEntry 13 }

physicalAdapterExpressTeamBundleId 	OBJECT-TYPE
	SYNTAX INTEGER
	ACCESS read-only
	STATUS mandatory
	DESCRIPTION
		"Unique value to identify the express team in the system."
	::= { physicalAdapterAttrEntry 14 }

physicalAdaptersAttrOffloadTable 	OBJECT-TYPE
	SYNTAX SEQUENCE OF PhysicalAdapterAttrOffloadEntry
	ACCESS not-accessible
	STATUS mandatory
	DESCRIPTION
		"Attributes of offloading-enabled physical adapters.
		 There is one 'entry' for each SNMP-compliant physical adapter."
	::= { physicalAdaptersAttrTables 2 }

physicalAdapterAttrOffloadEntry 	OBJECT-TYPE
	SYNTAX PhysicalAdapterAttrOffloadEntry
	ACCESS not-accessible
	STATUS mandatory
	DESCRIPTION
		"Attributes of offloading-enabled physical adapters.
		 There is one 'entry' for each SNMP-compliant physical adapter."
	INDEX {
		physicalAdapterIndex
	}
	::= { physicalAdaptersAttrOffloadTable 1 }

PhysicalAdapterAttrOffloadEntry ::= SEQUENCE {
	physicalAdapterTcpRxChecksumOffLoadEnable        INTEGER,
	physicalAdapterTcpRxChecksumBad                  Counter,
	physicalAdapterTcpTxChecksumOffLoadEnable        INTEGER,
	physicalAdapterIpv4RxChecksumOffLoadEnable       INTEGER,
	physicalAdapterIpv4TxChecksumOffLoadEnable       INTEGER,
	physicalAdapterIpv4TCPSegmentationOffLoadEnable  INTEGER
	}

physicalAdapterTcpRxChecksumOffLoadEnable 	OBJECT-TYPE
	SYNTAX INTEGER {
                               enabled (0),
                               disabled (1)
                        }
	ACCESS read-only
	STATUS mandatory
	DESCRIPTION
		"When enabled, TCP for 'receive' checksums are performed in hardware."
	::= { physicalAdapterAttrOffloadEntry 1 }

physicalAdapterTcpRxChecksumBad 	OBJECT-TYPE
	SYNTAX Counter
	ACCESS read-only
	STATUS mandatory
	DESCRIPTION
		"Number of bad 'receive' checksums."
	::= { physicalAdapterAttrOffloadEntry 2 }

physicalAdapterTcpTxChecksumOffLoadEnable 	OBJECT-TYPE
	SYNTAX INTEGER {
                               enabled (0),
                               disabled (1)
                        }
	ACCESS read-only
	STATUS mandatory
	DESCRIPTION
		"When enabled, TCP for 'transmit' checksums are performed in hardware."
	::= { physicalAdapterAttrOffloadEntry 3 }

physicalAdapterIpv4RxChecksumOffLoadEnable 	OBJECT-TYPE
	SYNTAX INTEGER {
                               enabled (0),
                               disabled (1)
                        }
	ACCESS read-only
	STATUS mandatory
	DESCRIPTION
		"When enabled, IPv4 for 'receive' checksums are performed in hardware."
	::= { physicalAdapterAttrOffloadEntry 4 }

physicalAdapterIpv4TxChecksumOffLoadEnable 	OBJECT-TYPE
	SYNTAX INTEGER {
                               enabled (0),
                               disabled (1)
                        }
	ACCESS read-only
	STATUS mandatory
	DESCRIPTION
		"When enabled, IPv4 for 'receive' checksums are performed in hardware."
	::= { physicalAdapterAttrOffloadEntry 5 }

physicalAdapterIpv4TCPSegmentationOffLoadEnable 	OBJECT-TYPE
	SYNTAX INTEGER {
                               disabled (0),
                               enabled (1)
                        }
	ACCESS read-only
	STATUS mandatory
	DESCRIPTION
		"When enabled, TCP Segmentation is performed in hardware."
	::= { physicalAdapterAttrOffloadEntry 6 }

virtualAdaptersAttrTables OBJECT IDENTIFIER ::= {adaptersTables 3}

virtualAdaptersAttrTable 	OBJECT-TYPE
	SYNTAX SEQUENCE OF VirtualAdapterAttrEntry
	ACCESS not-accessible
	STATUS mandatory
	DESCRIPTION
		"Attributes common to all iANS-virtual adapters."
	::= { virtualAdaptersAttrTables 1 }

virtualAdapterAttrEntry 	OBJECT-TYPE
	SYNTAX VirtualAdapterAttrEntry
	ACCESS not-accessible
	STATUS mandatory
	DESCRIPTION
		"Attributes common to all iANS-virtual adapters.
		 There is one 'entry' for each virtual adapter"
	INDEX {
		virtualAdapterIndex
	}
	::= { virtualAdaptersAttrTable 1 }

VirtualAdapterAttrEntry ::= SEQUENCE {
	virtualAdapterIndex  InterfaceIndex,
	virtualAdapterAnsId  INTEGER
	}

virtualAdapterIndex 	OBJECT-TYPE
	SYNTAX InterfaceIndex
	ACCESS read-only
	STATUS mandatory
	DESCRIPTION
		"A unique value, greater than or equal to zero, for each interface."
	::= { virtualAdapterAttrEntry 1 }

virtualAdapterAnsId 	OBJECT-TYPE
	SYNTAX INTEGER
	ACCESS read-only
	STATUS mandatory
	DESCRIPTION
		"ID of the team to which the adapter belongs."
	::= { virtualAdapterAttrEntry 2 }

virtualAdaptersVlanAttrTable 	OBJECT-TYPE
	SYNTAX SEQUENCE OF VirtualAdapterVlanAttrEntry
	ACCESS not-accessible
	STATUS mandatory
	DESCRIPTION
		"Attributes common to all iANS-virtual adapters VLANs."
	::= { virtualAdaptersAttrTables 2 }

virtualAdapterVlanAttrEntry 	OBJECT-TYPE
	SYNTAX VirtualAdapterVlanAttrEntry
	ACCESS not-accessible
	STATUS mandatory
	DESCRIPTION
		"VLAN attributes.Appears for virtual adapters that support VLANs only.
		 There is one 'entry' for each VLAN."
	INDEX {
		virtualAdapterIndex
	}
	::= { virtualAdaptersVlanAttrTable 1 }

VirtualAdapterVlanAttrEntry ::= SEQUENCE {
	virtualAdapterVlanId  INTEGER
	}

virtualAdapterVlanId 	OBJECT-TYPE
	SYNTAX INTEGER {
                               none (0)
                        }
	ACCESS read-only
	STATUS mandatory
	DESCRIPTION
		"ID for this virtual adapter VLAN."
	::= { virtualAdapterVlanAttrEntry 1 }

ansAttrTables OBJECT IDENTIFIER ::= {adaptersTables 4}

ansAttrTable 	OBJECT-TYPE
	SYNTAX SEQUENCE OF AnsAttrEntry
	ACCESS not-accessible
	STATUS mandatory
	DESCRIPTION
		"ANS attributes."
	::= { ansAttrTables 1 }

ansAttrEntry 	OBJECT-TYPE
	SYNTAX AnsAttrEntry
	ACCESS not-accessible
	STATUS mandatory
	DESCRIPTION
		"ANS attributes. There is one 'entry'  for each team"
	INDEX {
		ansId
	}
	::= { ansAttrTable 1 }

AnsAttrEntry ::= SEQUENCE {
	ansId                       INTEGER,
	ansNumberOfMembers          INTEGER,
	ansNumberOfVirtualAdapters  INTEGER
	}

ansId 	OBJECT-TYPE
	SYNTAX INTEGER
	ACCESS read-only
	STATUS mandatory
	DESCRIPTION
		"ANS ID. A unique value."
	::= { ansAttrEntry 1 }

ansNumberOfMembers 	OBJECT-TYPE
	SYNTAX INTEGER
	ACCESS read-only
	STATUS mandatory
	DESCRIPTION
		"Number of member adapters in the team."
	::= { ansAttrEntry 2 }

ansNumberOfVirtualAdapters 	OBJECT-TYPE
	SYNTAX INTEGER
	ACCESS read-only
	STATUS mandatory
	DESCRIPTION
		"Number of virtual adapters in the team."
	::= { ansAttrEntry 3 }

ansVlansAttrTable 	OBJECT-TYPE
	SYNTAX SEQUENCE OF AnsVlanAttrEntry
	ACCESS not-accessible
	STATUS mandatory
	DESCRIPTION
		"ANS attributes."
	::= { ansAttrTables 2 }

ansVlanAttrEntry 	OBJECT-TYPE
	SYNTAX AnsVlanAttrEntry
	ACCESS not-accessible
	STATUS mandatory
	DESCRIPTION
		"ANS VLAN attributes.
		 Appears only if VLAN is active. There is one 'entry'  for each Vlan."
	INDEX {
		ansId
	}
	::= { ansVlansAttrTable 1 }

AnsVlanAttrEntry ::= SEQUENCE {
	ansVlanTaggingType  INTEGER,
	ansVlanGvrpSupport  INTEGER
	}

ansVlanTaggingType 	OBJECT-TYPE
	SYNTAX INTEGER {
                               none (0),
                               tag-802-1Q (1),
                               tag-802-1P (2),
                               tag-802-3AC (3),
                               tag-iSL (4)
                        }
	ACCESS read-only
	STATUS mandatory
	DESCRIPTION
		"Tagging type of the VLAN adapter."
	::= { ansVlanAttrEntry 1 }

ansVlanGvrpSupport 	OBJECT-TYPE
	SYNTAX INTEGER {
                               enabled (0),
                               disabled (1)
                        }
	ACCESS read-only
	STATUS mandatory
	DESCRIPTION
		"Indicates whether GVRP is enabled."
	::= { ansVlanAttrEntry 2 }

ansTeamsAttrTable 	OBJECT-TYPE
	SYNTAX SEQUENCE OF AnsTeamAttrEntry
	ACCESS not-accessible
	STATUS mandatory
	DESCRIPTION
		"ANS team attributes."
	::= { ansAttrTables 3 }

ansTeamAttrEntry 	OBJECT-TYPE
	SYNTAX AnsTeamAttrEntry
	ACCESS not-accessible
	STATUS mandatory
	DESCRIPTION
		"ANS team attributes. Appears only when adapter teaming exist.
		 There is one 'entry' for each team."
	INDEX {
		ansId
	}
	::= { ansTeamsAttrTable 1 }

AnsTeamAttrEntry ::= SEQUENCE {
	ansTeamName                   DisplayString,
	ansTeamMode                   INTEGER,
	ansTeamLinkState              INTEGER,
	ansTeamSpeed                  Gauge,
	ansTeamProbesState            INTEGER,
	ansTeamProbesMode             INTEGER,
	ansTeamLoadBalanceRefresh     INTEGER,
	ansTeamProbesSendTime         INTEGER,
	ansTeamPreferredPrimaryIndex  INTEGER,
	ansTeamCurrentPrimaryIndex    INTEGER,
	ansTeamPreviousPrimaryIndex   INTEGER,
	ansTeamFailoverCounter        Counter,
	ansTeamSlaCompatible          INTEGER,
	ansTeamAggrSelectionMode      INTEGER,
	ansTeamRlbSupport             INTEGER
	}

ansTeamName 	OBJECT-TYPE
	SYNTAX DisplayString
	ACCESS read-only
	STATUS mandatory
	DESCRIPTION
		"Unique ANS team name"
	::= { ansTeamAttrEntry 1 }

ansTeamMode 	OBJECT-TYPE
	SYNTAX INTEGER {
                               none (6),
                               adapter-fault-tolerance (0),
                               adaptive-load-balancing (1),
                               static-link-aggregation (2),
                               iEEE-802-3ad (4),
                               switch-fault-tolerance (5)
                        }
	ACCESS read-only
	STATUS mandatory
	DESCRIPTION
		"Team mode."
	::= { ansTeamAttrEntry 2 }

ansTeamLinkState 	OBJECT-TYPE
	SYNTAX INTEGER {
                               up (0),
                               down (1)
                        }
	ACCESS read-only
	STATUS mandatory
	DESCRIPTION
		"Team link state.
		 Aggregation of the link state of all team members ( 0 = some up)."
	::= { ansTeamAttrEntry 3 }

ansTeamSpeed 	OBJECT-TYPE
	SYNTAX Gauge
	ACCESS read-only
	STATUS mandatory
	DESCRIPTION
		"Team speed.Speed of the current primary member (in Mbps)."
	::= { ansTeamAttrEntry 4 }

ansTeamProbesState 	OBJECT-TYPE
	SYNTAX INTEGER {
                               probes-enabled (0),
                               probes-disabled (1)
                        }
	ACCESS read-only
	STATUS mandatory
	DESCRIPTION
		"If enabled, the ANS uses probes to check on its members."
	::= { ansTeamAttrEntry 5 }

ansTeamProbesMode 	OBJECT-TYPE
	SYNTAX INTEGER {
                               broadcast (0),
                               multicast (1),
                               not-available (2)
                        }
	ACCESS read-only
	STATUS mandatory
	DESCRIPTION
		"Mode of probe usage."
	::= { ansTeamAttrEntry 6 }

ansTeamLoadBalanceRefresh 	OBJECT-TYPE
	SYNTAX INTEGER {
                               not-available (0)
                        }
	ACCESS read-only
	STATUS mandatory
	DESCRIPTION
		"In seconds. If available, the number of seconds that passes before 
		 the software resets or refreshes the current load across team members."
	::= { ansTeamAttrEntry 7 }

ansTeamProbesSendTime 	OBJECT-TYPE
	SYNTAX INTEGER {
                               not-available (0)
                        }
	ACCESS read-only
	STATUS mandatory
	DESCRIPTION
		"In seconds. If available,
		 the interval in seconds during which probe packets are sent."
	::= { ansTeamAttrEntry 8 }

ansTeamPreferredPrimaryIndex 	OBJECT-TYPE
	SYNTAX INTEGER {
                               not-available (-1)
                        }
	ACCESS read-only
	STATUS mandatory
	DESCRIPTION
		"Index of the preferred primary member adapter. "
	::= { ansTeamAttrEntry 9 }

ansTeamCurrentPrimaryIndex 	OBJECT-TYPE
	SYNTAX INTEGER {
                               not-available (-1)
                        }
	ACCESS read-only
	STATUS mandatory
	DESCRIPTION
		"Index of the current primary member adapter."
	::= { ansTeamAttrEntry 10 }

ansTeamPreviousPrimaryIndex 	OBJECT-TYPE
	SYNTAX INTEGER {
                               not-available (-1)
                        }
	ACCESS read-only
	STATUS mandatory
	DESCRIPTION
		"Index of the previous primary member adapter."
	::= { ansTeamAttrEntry 11 }

ansTeamFailoverCounter 	OBJECT-TYPE
	SYNTAX Counter
	ACCESS read-write
	STATUS mandatory
	DESCRIPTION
		"Failover counter - 
		 that is, the number of failovers the team suffered.
		 This value can be reset by the user - 
		 that is, it can be set to zero only; no other value is permitted."
	::= { ansTeamAttrEntry 12 }

ansTeamSlaCompatible 	OBJECT-TYPE
	SYNTAX INTEGER {
                               not-available (-1),
                               yes (0),
                               no (1)
                        }
	ACCESS read-only
	STATUS mandatory
	DESCRIPTION
		"Indicates compatibility with Static Link Aggregation mode 
		 when in IEEE 802.3AD mode."
	::= { ansTeamAttrEntry 13 }

ansTeamAggrSelectionMode 	OBJECT-TYPE
	SYNTAX INTEGER {
                               not-available (-1),
                               bandwidth (0),
                               count (1)
                        }
	ACCESS read-only
	STATUS mandatory
	DESCRIPTION
		"Indicates aggregation selection mode when in IEEE 802.3AD mode."
	::= { ansTeamAttrEntry 14 }

ansTeamRlbSupport 	OBJECT-TYPE
	SYNTAX INTEGER {
                               not-available (-1),
                               enabled (0),
                               disabled (1)
                        }
	ACCESS read-only
	STATUS mandatory
	DESCRIPTION
		"Indicates whether 'receive load balancing support' is enabled 
		 when in AdaptiveLoadBalancing teaming mode.
		 (If disabled, only the transmission is balanced.)"
	::= { ansTeamAttrEntry 15 }

ansMembersAttrTables OBJECT IDENTIFIER ::= {adaptersTables 5}

ansMembersAttrTable 	OBJECT-TYPE
	SYNTAX SEQUENCE OF AnsMemberAttrEntry
	ACCESS not-accessible
	STATUS mandatory
	DESCRIPTION
		"Attributes common to all iANS-TeamMember Adapters."
	::= { ansMembersAttrTables 1 }

ansMemberAttrEntry 	OBJECT-TYPE
	SYNTAX AnsMemberAttrEntry
	ACCESS not-accessible
	STATUS mandatory
	DESCRIPTION
		"Attributes common to all iANS-TeamMember Adapters. 
		 There is one 'entry' for each team member adapter."
	INDEX {
		ansMemberIndex
	}
	::= { ansMembersAttrTable 1 }

AnsMemberAttrEntry ::= SEQUENCE {
	ansMemberIndex  InterfaceIndex,
	ansMemberAnsId  INTEGER
	}

ansMemberIndex 	OBJECT-TYPE
	SYNTAX InterfaceIndex
	ACCESS read-only
	STATUS mandatory
	DESCRIPTION
		"A unique value for each member. The value is non-negative and identical
		 to the value of the physical adapter associated with this member."
	::= { ansMemberAttrEntry 1 }

ansMemberAnsId 	OBJECT-TYPE
	SYNTAX INTEGER
	ACCESS read-only
	STATUS mandatory
	DESCRIPTION
		"ID of the ANS to which the Adapter belongs."
	::= { ansMemberAttrEntry 2 }

ansTeamMembersAttrTable 	OBJECT-TYPE
	SYNTAX SEQUENCE OF AnsTeamMemberAttrEntry
	ACCESS not-accessible
	STATUS mandatory
	DESCRIPTION
		"Attributes common to all iANS-TeamMember Adapters."
	::= { ansMembersAttrTables 2 }

ansTeamMemberAttrEntry 	OBJECT-TYPE
	SYNTAX AnsTeamMemberAttrEntry
	ACCESS not-accessible
	STATUS mandatory
	DESCRIPTION
		"Attributes of iANS-TeamMember Adapters related to adapter teaming.
		 Appears only if adapter teaming exists."
	INDEX {
		ansMemberIndex
	}
	::= { ansTeamMembersAttrTable 1 }

AnsTeamMemberAttrEntry ::= SEQUENCE {
	ansTeamMemberState           INTEGER,
	ansTeamMemberFailureCounter  Counter,
	ansTeamMemberPriority        INTEGER
	}

ansTeamMemberState 	OBJECT-TYPE
	SYNTAX INTEGER {
                               active (0),
                               disabled (1),
                               standby (2),
                               active-secondary (3)
                        }
	ACCESS read-only
	STATUS mandatory
	DESCRIPTION
		"iANS-TeamMember adapter state."
	::= { ansTeamMemberAttrEntry 1 }

ansTeamMemberFailureCounter 	OBJECT-TYPE
	SYNTAX Counter
	ACCESS read-write
	STATUS mandatory
	DESCRIPTION
		"Failure counter - that is, the number of failovers from this member.
		 This value can be reset by the user - 
		 that is, it can be set to zero only; no other value is permitted."
	::= { ansTeamMemberAttrEntry 2 }

ansTeamMemberPriority 	OBJECT-TYPE
	SYNTAX INTEGER {
                               none (0),
                               primary (1),
                               secondary (2)
                        }
	ACCESS read-only
	STATUS mandatory
	DESCRIPTION
		"Priority of the team member."
	::= { ansTeamMemberAttrEntry 3 }

events OBJECT IDENTIFIER ::= {intel-lan-adapters 3}

physicalAdaptersEvents OBJECT IDENTIFIER ::= {events 1}

physicalAdaptersTraps OBJECT IDENTIFIER ::= {physicalAdaptersEvents 1}

physicalAdapterLinkUpTrap 	TRAP-TYPE
	ENTERPRISE physicalAdaptersTraps
	VARIABLES {
		physicalAdapterIndex
	}
	DESCRIPTION
		"Adapter has reached a linkup state."
	::= 1

physicalAdapterLinkDownTrap 	TRAP-TYPE
	ENTERPRISE physicalAdaptersTraps
	VARIABLES {
		physicalAdapterIndex
	}
	DESCRIPTION
		"Adapter has reached a link down state."
	::= 2

physicalAdapterAddedTrap 	TRAP-TYPE
	ENTERPRISE physicalAdaptersTraps
	VARIABLES {
		physicalAdapterIndex
	}
	DESCRIPTION
		"Adapter has been installed."
	::= 3

physicalAdapterRemovedTrap 	TRAP-TYPE
	ENTERPRISE physicalAdaptersTraps
	VARIABLES {
		physicalAdapterIndex
	}
	DESCRIPTION
		"Adapter has been uninstalled."
	::= 4

physicalAdapterOnlineDiagPassedTrap 	TRAP-TYPE
	ENTERPRISE physicalAdaptersTraps
	VARIABLES {
		physicalAdapterIndex
	}
	DESCRIPTION
		"Adapter's online diagnostics passed."
	::= 5

physicalAdapterOnlineDiagFailedTrap 	TRAP-TYPE
	ENTERPRISE physicalAdaptersTraps
	VARIABLES {
		physicalAdapterIndex
	}
	DESCRIPTION
		"Adapter's online diagnostics failed.  Online diagnostics might fail because of link loss or other hardware issues."
	::= 6

physicalAdapterLinkUpDownTrapEnable 	OBJECT-TYPE
	SYNTAX INTEGER {
                               disabled (0),
                               enabled (1)
                        }
	ACCESS read-write
	STATUS mandatory
	DESCRIPTION
		"Indicates whether a physical adapter's link up and link down traps are enabled.
		 The user can set this value."
	::= { physicalAdaptersEvents 2 }

physicalAdapterAddedRemovedTrapEnable 	OBJECT-TYPE
	SYNTAX INTEGER {
                               disabled (0),
                               enabled (1)
                        }
	ACCESS read-write
	STATUS mandatory
	DESCRIPTION
		"Indicates whether a physical adapter's 'added' and 'removed' traps are enabled. 
		 The user can set this value."
	::= { physicalAdaptersEvents 3 }

physicalAdapterOnlineDiagPassedFailedTrapEnable 	OBJECT-TYPE
	SYNTAX INTEGER {
                               disabled (0),
                               enabled (1)
                        }
	ACCESS read-write
	STATUS mandatory
	DESCRIPTION
		"Indicates whether physicalAdapterOnlineDiag 'passed' and 'failed' are enabled."
	::= { physicalAdaptersEvents 4 }



END
