-- Automatically generated from file 
-- Fri Aug 05 12:51:16 W. Europe Standard Time 2005

FSC-HPI-MIB DEFINITIONS ::= BEGIN

IMPORTS
        enterprises, Gauge, Counter, IpAddress, TimeTicks FROM RFC1155-SMI
        OBJECT-TYPE 	  FROM RFC1212
        TRAP-TYPE 	  FROM RFC1215;

sni OBJECT IDENTIFIER ::= {enterprises 231}

sniProductMibs OBJECT IDENTIFIER ::= {sni 2}

fscHpi OBJECT IDENTIFIER ::= {sniProductMibs 60}

fscHpiBMIB OBJECT IDENTIFIER ::= {fscHpi 6}

DisplayString ::= OCTET STRING

TruthValue ::= INTEGER {
	true (1),
	false (2)
	}

RowStatus ::= INTEGER {
	active (1),
	notInService (2),
	notReady (3),
	createAndGo (4),
	createAndWait (5),
	destroy (6)
	}

RowPointer ::= OBJECT IDENTIFIER

SaHpiDomainCapabilities ::= OCTET STRING

SaHpiTextType ::= INTEGER {
	undefined (0),
	unicode (1),
	bcdplus (2),
	ascii6 (3),
	text (4),
	binary (5)
	}

SaHpiTextLanguage ::= INTEGER {
	undefined (0),
	unknown (1),
	afar (2),
	abkhazian (3),
	afrikaans (4),
	amharic (5),
	arabic (6),
	assamese (7),
	aymara (8),
	azerbaijani (9),
	bashkir (10),
	byelorussian (11),
	bulgarian (12),
	bihari (13),
	bislama (14),
	bengali (15),
	tibetan (16),
	breton (17),
	catalan (18),
	corsican (19),
	czech (20),
	welsh (21),
	danish (22),
	german (23),
	bhutani (24),
	greek (25),
	english (26),
	esperanto (27),
	spanish (28),
	estonian (29),
	basque (30),
	persian (31),
	finnish (32),
	fiji (33),
	faeroese (34),
	french (35),
	frisian (36),
	irish (37),
	scotsgaelic (38),
	galician (39),
	guarani (40),
	gujarati (41),
	hausa (42),
	hindi (43),
	croatian (44),
	hungarian (45),
	armenian (46),
	interlingua (47),
	interlingue (48),
	inupiak (49),
	indonesian (50),
	icelandic (51),
	italian (52),
	hebrew (53),
	japanese (54),
	yiddish (55),
	javanese (56),
	georgian (57),
	kazakh (58),
	greenlandic (59),
	cambodian (60),
	kannada (61),
	korean (62),
	kashmiri (63),
	kurdish (64),
	kirghiz (65),
	latin (66),
	lingala (67),
	laothian (68),
	lithuanian (69),
	latvianlettish (70),
	malagasy (71),
	maori (72),
	macedonian (73),
	malayalam (74),
	mongolian (75),
	moldavian (76),
	marathi (77),
	malay (78),
	maltese (79),
	burmese (80),
	nauru (81),
	nepali (82),
	dutch (83),
	norwegian (84),
	occitan (85),
	afanoromo (86),
	oriya (87),
	punjabi (88),
	polish (89),
	pashtopushto (90),
	portuguese (91),
	quechua (92),
	rhaetoromance (93),
	kirundi (94),
	romanian (95),
	russian (96),
	kinyarwanda (97),
	sanskrit (98),
	sindhi (99),
	sangro (100),
	serbocroatian (101),
	singhalese (102),
	slovak (103),
	slovenian (104),
	samoan (105),
	shona (106),
	somali (107),
	albanian (108),
	serbian (109),
	siswati (110),
	sesotho (111),
	sudanese (112),
	swedish (113),
	swahili (114),
	tamil (115),
	telugu (116),
	tajik (117),
	thai (118),
	tigrinya (119),
	turkmen (120),
	tagalog (121),
	setswana (122),
	tonga (123),
	turkish (124),
	tsonga (125),
	tatar (126),
	twi (127),
	ukrainian (128),
	urdu (129),
	uzbek (130),
	vietnamese (131),
	volapuk (132),
	wolof (133),
	xhosa (134),
	yoruba (135),
	chinese (136),
	zulu (137)
	}

SaHpiText ::= OCTET STRING

SaHpiTime ::= OCTET STRING

SaHpiGuid ::= OCTET STRING

SaHpiEntryId ::= Gauge

SaHpiSeverity ::= INTEGER {
	undefined (0),
	critical (1),
	major (2),
	minor (3),
	informational (4),
	ok (5),
	debug (81)
	}

SaHpiCondition ::= INTEGER {
	undefined (0),
	sensor (1),
	resource (2),
	oem (3),
	user (4)
	}

SaHpiEntityPath ::= OCTET STRING

SaHpiEventState ::= OCTET STRING

SaHpiManufacturerId ::= Gauge

SaHpiEntityType ::= INTEGER {
	undefined (0),
	unspecified (1),
	other (2),
	unknown (3),
	processor (4),
	diskBay (5),
	peripheralBay (6),
	sysMgmntModule (7),
	systemBoard (8),
	memoryModule (9),
	processorModule (10),
	powerSupply (11),
	addInCard (12),
	frontPanelBoard (13),
	backPanelBoard (14),
	powerSystemBoard (15),
	driveBackplane (16),
	sysExpansionBoard (17),
	otherSystemBoard (18),
	processorBoard (19),
	powerUnit (20),
	powerModule (21),
	powerMgmnt (22),
	chassisBackPanelBoard (23),
	systemChassis (24),
	subChassis (25),
	otherChassisBoard (26),
	diskDriveBayv (27),
	peripheralBay2 (28),
	deviceBay (29),
	coolingDevice (30),
	coolingUnit (31),
	interconnect (32),
	memoryDevice (33),
	sysMgmntSoftware (34),
	bios (35),
	operatingSystem (36),
	systemBus (37),
	group (38),
	remote (39),
	externalEnvironment (40),
	battery (41),
	chassisSpecific (145),
	boardSetSpecific (177),
	oemSysintSpecific (209),
	root (65536),
	rack (65537),
	subrack (65538),
	compactpciChassis (65539),
	advancedtcaChassis (65540),
	rackMountedServer (65541),
	systemBlade (65542),
	switch (65543),
	switchBlade (65544),
	sbcBlade (65545),
	ioBlade (65546),
	diskBlade (65547),
	diskBrive (65548),
	fan (65549),
	powerDistributionUnit (65550),
	specProcBlade (65551),
	ioSubboard (65552),
	sbcSubboard (65553),
	alarmManager (65554),
	shelfManager (65555),
	displayPanel (65556),
	subboardCarrierBlade (65557),
	physicalSlot (65558),
	frontBoard (161),
	rearTransitionModule (193),
	powerFiltering (239),
	shelfManagementController (241),
	filtrationUnit (242),
	shelfFRUInformation (243)
	}

SaHpiCapabilities ::= OCTET STRING

SaHpiHsCapabilities ::= OCTET STRING

SaHpiHotSwapState ::= INTEGER {
	undefined (0),
	inactive (1),
	insertionPending (2),
	active (3),
	extractionPending (4),
	notPresent (5)
	}

SaHpiSensorType ::= INTEGER {
	undefined (0),
	temperature (2),
	voltage (3),
	current (4),
	fan (5),
	physicalSecurity (6),
	platformViolation (7),
	processor (8),
	powerSupply (9),
	powerUnit (10),
	coolingDevice (11),
	otherUnitsBasedSensor (12),
	memory (13),
	driveSlot (14),
	postMemoryResize (15),
	systemFwProgress (16),
	eventLoggingDisabled (17),
	reserved1 (18),
	systemEvent (19),
	criticalInterrupt (20),
	button (21),
	moduleBoard (22),
	microcontrollerCoProcessor (23),
	addinCard (24),
	chassis (25),
	chipSet (26),
	otherFru (27),
	cableInterconnect (28),
	terminator (29),
	systemBootInitiated (30),
	bootError (31),
	osBoot (32),
	osCriticalStop (33),
	slotConnector (34),
	systemACPIPowerState (35),
	reserved2 (36),
	platformAlert (37),
	entityPresence (38),
	monitorAsicIC (39),
	lan (40),
	managementSubsystemHealth (41),
	battery (42),
	operational (161),
	oemSensor (193)
	}

SaHpiEventCategory ::= INTEGER {
	undefined (0),
	unspecified (1),
	threshold (2),
	usage (3),
	state (4),
	predFail (5),
	limit (6),
	performance (7),
	severity (8),
	presence (9),
	enable (10),
	availability (11),
	redundancy (12),
	sensorSpecific (127),
	generic (128)
	}

SaHpiSensorReadingType ::= INTEGER {
	undefined (0),
	int64 (1),
	uint64 (2),
	float64 (3),
	buffer (4)
	}

SaHpiSensorReadingValue ::= OCTET STRING

SaHpiWatchdogPreTimerAction ::= INTEGER {
	undefined (0),
	none (1),
	smi (2),
	nmi (3),
	messageInterrupt (4),
	oem (16)
	}

SaHpiWatchdogTimerUse ::= INTEGER {
	undefined (0),
	none (1),
	biosFrb2 (2),
	biosPost (3),
	osLoad (4),
	smsOs (5),
	oem (6),
	unspecified (16)
	}

SaHpiInstrumentId ::= Gauge

SaHpiSensorRangeFlags ::= OCTET STRING

SaHpiSensorUnits ::= INTEGER {
	undefined (0),
	unspecified (1),
	degreesC (2),
	degreesF (3),
	degreesK (4),
	volts (5),
	amps (6),
	watts (7),
	joules (8),
	coulombs (9),
	va (10),
	nits (11),
	lumen (12),
	lux (13),
	candela (14),
	kpa (15),
	psi (16),
	newton (17),
	cfm (18),
	rpm (19),
	hz (20),
	microsecond (21),
	millisecond (22),
	second (23),
	minute (24),
	hour (25),
	day (26),
	week (27),
	mil (28),
	inches (29),
	feet (30),
	cuInches (31),
	cuFeet (32),
	mm (33),
	cm (34),
	m (35),
	cuCm (36),
	cuM (37),
	liters (38),
	fluidOunce (39),
	radians (40),
	steradians (41),
	revolutions (42),
	cycles (43),
	gravities (44),
	ounce (45),
	pound (46),
	ftLbs (47),
	ozInches (48),
	gauss (49),
	gilberts (50),
	henry (51),
	millihenry (52),
	farad (53),
	microfarad (54),
	ohms (55),
	siemens (56),
	mole (57),
	becquerel (58),
	ppm (59),
	reserved (60),
	decibels (61),
	dba (62),
	dbc (63),
	gray (64),
	sievert (65),
	colorTempDegK (66),
	bit (67),
	kilobit (68),
	megabit (69),
	gigabit (70),
	byte (71),
	kilobyte (72),
	megabyte (73),
	gigabyte (74),
	word (75),
	dword (76),
	qword (77),
	line (78),
	hit (79),
	miss (80),
	retry (81),
	reset (82),
	overrun (83),
	underrun (84),
	collision (85),
	packets (86),
	messages (87),
	characters (88),
	errors (89),
	correctableErrors (90),
	uncorrectableErrors (91)
	}

SaHpiSensorModUnitUse ::= INTEGER {
	undefined (0),
	none (1),
	basicOverModifier (2),
	basicTimesModifier (3)
	}

Double ::= OCTET STRING

SaHpiSensorThdMask ::= OCTET STRING

SaHpiThresholdEvents ::= OCTET STRING

SaHpiUsageEvents ::= OCTET STRING

SaHpiStateEvents ::= OCTET STRING

SaHpiPredFailEvents ::= OCTET STRING

SaHpiLimitEvents ::= OCTET STRING

SaHpiPerformanceEvents ::= OCTET STRING

SaHpiSeverityEvents ::= OCTET STRING

SaHpiPresenceEvents ::= OCTET STRING

SaHpiEnableEvents ::= OCTET STRING

SaHpiAvailabilityEvents ::= OCTET STRING

SaHpiRedundancyEvents ::= OCTET STRING

SaHpiGenericEvents ::= OCTET STRING

hpiAdministration OBJECT IDENTIFIER ::= {fscHpiBMIB 1}

hpiHpiVersion 	OBJECT-TYPE
	SYNTAX DisplayString
	ACCESS read-only
	STATUS mandatory
	DESCRIPTION
		"The interface version is the version of the actual interface and 
		 not the version of the implementation. It is a 24 bit value where
		 the most significant 8 bits represent the compatibility level
		 (with letters represented as the corresponding numbers);
		 the next 8 bits represent the major version number; and
		 the least significant 8 bits represent the minor version number."
	::= { hpiAdministration 1 }

hpiAgentVersion 	OBJECT-TYPE
	SYNTAX DisplayString
	ACCESS read-only
	STATUS mandatory
	DESCRIPTION
		"The Agent Implementation Version"
	::= { hpiAdministration 2 }

hpiSNMPResourceId 	OBJECT-TYPE
	SYNTAX Gauge
	ACCESS read-only
	STATUS mandatory
	DESCRIPTION
		"This columnar node provides the Resource Id of the domain the
		 HPI-MIB SNMP implementation is running on.  This is to help prevent
		 powering down the machine providing the SNMP service."
	::= { hpiAdministration 3 }

hpiDiscover 	OBJECT-TYPE
	SYNTAX TruthValue
	ACCESS read-write
	STATUS mandatory
	DESCRIPTION
		"This columnar node forces the discovery of all resources and
		 associated domains by the underlying management service."
	::= { hpiAdministration 4 }

hpiDiscoveryStatus 	OBJECT-TYPE
	SYNTAX INTEGER {
                               undefined (0),
                               start (1),
                               working (2),
                               done (3),
                               stopped (4)
                        }
	ACCESS read-only
	STATUS mandatory
	DESCRIPTION
		"The Status of the HPI Resource Discovery."
	::= { hpiAdministration 10 }

hpiDiscoveryTime 	OBJECT-TYPE
	SYNTAX Gauge
	ACCESS read-only
	STATUS mandatory
	DESCRIPTION
		"The time in seconds needed for Discovery"
	::= { hpiAdministration 11 }

hpiDiscoveryAutoUpdateTime 	OBJECT-TYPE
	SYNTAX Gauge
	ACCESS read-write
	STATUS mandatory
	DESCRIPTION
		"The time in seconds between two HPI Resource Discoveries.
		 A value of 0 means 'no auto discovery'."
	::= { hpiAdministration 12 }

hpiReconnect 	OBJECT-TYPE
	SYNTAX TruthValue
	ACCESS read-write
	STATUS mandatory
	DESCRIPTION
		""
	::= { hpiAdministration 20 }

hpiDomain OBJECT IDENTIFIER ::= {fscHpiBMIB 2}

hpiDomainEntryCount 	OBJECT-TYPE
	SYNTAX Counter
	ACCESS read-only
	STATUS mandatory
	DESCRIPTION
		"The number of Domain entries present in the system."
	::= { hpiDomain 1 }

hpiDomainTable 	OBJECT-TYPE
	SYNTAX SEQUENCE OF HpiDomainEntry
	ACCESS not-accessible
	STATUS mandatory
	DESCRIPTION
		"This table represents the management attributes common to all Domains
		 within the managed platform. The logical domain ID and the entity ID
		 are used to address an entity."
	::= { hpiDomain 2 }

hpiDomainEntry 	OBJECT-TYPE
	SYNTAX HpiDomainEntry
	ACCESS not-accessible
	STATUS mandatory
	DESCRIPTION
		"Domain Info:
		 
		 This structure is used to store the information regarding the domain
		 including information regarding the domain reference table (DRT) and
		 the resource presence table (RPT).
		 
		 The DomainTag field is an informational value that supplies an
		 HPI User with naming information for the domain.
		 
		 NOTE: Regarding timestamps - If the implementation cannot supply an
		 absolute timestamp, then it may supply a timestamp relative to some
		 system-defined  epoch, such as system boot.
		 The value SAHPI_TIME_UNSPECIFIED indicates that the time of the
		 update cannot be determined. Otherwise, If the value is less
		 than or equal to SAHPI_TIME_MAX_RELATIVE, then it is relative; if it is
		 greater than SAHPI_TIME_MAX_RELATIVE, then it is absolute.
		 
		 The GUID is used to uniquely identify a domain. A GUID value of zero
		 is not valid and indicates that the domain does not have an
		 associated GUID."
	INDEX {
		hpiDomainId
	}
	::= { hpiDomainTable 1 }

HpiDomainEntry ::= SEQUENCE {
	hpiDomainId                               Gauge,
	hpiDomainCapabilities                     SaHpiDomainCapabilities,
	hpiDomainIsPeer                           TruthValue,
	hpiDomainTagTextType                      SaHpiTextType,
	hpiDomainTagTextLanguage                  SaHpiTextLanguage,
	hpiDomainTag                              SaHpiText,
	hpiDomainReferenceUpdateCount             Gauge,
	hpiDomainReferenceUpdateTimestamp         SaHpiTime,
	hpiDomainResourcePresenceUpdateCount      Gauge,
	hpiDomainResourcePresenceUpdateTimestamp  SaHpiTime,
	hpiDomainAlarmUpdateCount                 Gauge,
	hpiDomainAlarmUpdateTimestamp             SaHpiTime,
	hpiDomainActiveAlarms                     Gauge,
	hpiDomainCriticalAlarms                   Gauge,
	hpiDomainMajorAlarms                      Gauge,
	hpiDomainMinorAlarms                      Gauge,
	hpiDomainAlarmUserLimit                   Gauge,
	hpiDomainAlarmOverflow                    TruthValue,
	hpiDomainGuid                             SaHpiGuid
	}

hpiDomainId 	OBJECT-TYPE
	SYNTAX Gauge
	ACCESS not-accessible
	STATUS mandatory
	DESCRIPTION
		"The SAHPI_UNSPECIFIED_DOMAIN_ID value is used to specify the
		 default domain.
		 SAHPI_UNSPECIFIED_DOMAIN_ID  0xFFFFFFFF(4294967295) "
	::= { hpiDomainEntry 1 }

hpiDomainCapabilities 	OBJECT-TYPE
	SYNTAX SaHpiDomainCapabilities
	ACCESS read-only
	STATUS mandatory
	DESCRIPTION
		"This definition defines the capabilities of a given domain.
		 A domain may support any number of capabilities.
		 autoinsertReadOnly
		 Indicates that the domain auto insert timeout value is
		 read-only and may not be modified using the
		 hpiHotSwapAutoInsertTimeoutSet columnar object."
	::= { hpiDomainEntry 2 }

hpiDomainIsPeer 	OBJECT-TYPE
	SYNTAX TruthValue
	ACCESS read-only
	STATUS mandatory
	DESCRIPTION
		"Indicates that this domain participates in a peer relationship.
		 true = Domain is peer.  false = Domain is not peer."
	::= { hpiDomainEntry 3 }

hpiDomainTagTextType 	OBJECT-TYPE
	SYNTAX SaHpiTextType
	ACCESS read-write
	STATUS mandatory
	DESCRIPTION
		"Information tag associated with domain.
		 See Definition for SaHpiTextType for more details."
	::= { hpiDomainEntry 4 }

hpiDomainTagTextLanguage 	OBJECT-TYPE
	SYNTAX SaHpiTextLanguage
	ACCESS read-write
	STATUS mandatory
	DESCRIPTION
		"Information tag associated with domain.
		 See Definition for SaHpiTextLanguage for more details."
	::= { hpiDomainEntry 5 }

hpiDomainTag 	OBJECT-TYPE
	SYNTAX SaHpiText
	ACCESS read-write
	STATUS mandatory
	DESCRIPTION
		"Information tag associated with domain.
		 The type of date is specified
		 by hpiResourceTagTextType and hpiResourceTagLanguage."
	::= { hpiDomainEntry 6 }

hpiDomainReferenceUpdateCount 	OBJECT-TYPE
	SYNTAX Gauge
	ACCESS read-only
	STATUS mandatory
	DESCRIPTION
		"This count is incremented any time the table is changed.
		 It rolls over to zero when the maximum value (2^32) is reached."
	::= { hpiDomainEntry 7 }

hpiDomainReferenceUpdateTimestamp 	OBJECT-TYPE
	SYNTAX SaHpiTime
	ACCESS read-only
	STATUS mandatory
	DESCRIPTION
		"This timestamp is set any time the DRT table is changed.
		 Refer to SaHpiTime for full description."
	::= { hpiDomainEntry 8 }

hpiDomainResourcePresenceUpdateCount 	OBJECT-TYPE
	SYNTAX Gauge
	ACCESS read-only
	STATUS mandatory
	DESCRIPTION
		"This count is incremented any time the RPT is changed.
		 It rolls over to zero when the maximum (2^32) value is reached "
	::= { hpiDomainEntry 9 }

hpiDomainResourcePresenceUpdateTimestamp 	OBJECT-TYPE
	SYNTAX SaHpiTime
	ACCESS read-only
	STATUS mandatory
	DESCRIPTION
		"This timestamp is set any time the RPT table is changed.
		 Refer to SaHpiTime for full description."
	::= { hpiDomainEntry 10 }

hpiDomainAlarmUpdateCount 	OBJECT-TYPE
	SYNTAX Gauge
	ACCESS read-only
	STATUS mandatory
	DESCRIPTION
		"This count is incremented any time the DAT is changed.
		 It rolls over to zero when the maximum value (2^32) is reached "
	::= { hpiDomainEntry 11 }

hpiDomainAlarmUpdateTimestamp 	OBJECT-TYPE
	SYNTAX SaHpiTime
	ACCESS read-only
	STATUS mandatory
	DESCRIPTION
		"This timestamp is set any time the DAT is changed.
		 Refer to SaHpiTime for full description."
	::= { hpiDomainEntry 12 }

hpiDomainActiveAlarms 	OBJECT-TYPE
	SYNTAX Gauge
	ACCESS read-only
	STATUS mandatory
	DESCRIPTION
		"Count of active alarms in the DAT."
	::= { hpiDomainEntry 13 }

hpiDomainCriticalAlarms 	OBJECT-TYPE
	SYNTAX Gauge
	ACCESS read-only
	STATUS mandatory
	DESCRIPTION
		"Count of active critical alarms in the DAT."
	::= { hpiDomainEntry 14 }

hpiDomainMajorAlarms 	OBJECT-TYPE
	SYNTAX Gauge
	ACCESS read-only
	STATUS mandatory
	DESCRIPTION
		"Count of active major alarms in the DAT."
	::= { hpiDomainEntry 15 }

hpiDomainMinorAlarms 	OBJECT-TYPE
	SYNTAX Gauge
	ACCESS read-only
	STATUS mandatory
	DESCRIPTION
		"Count of active minor alarms in the DAT."
	::= { hpiDomainEntry 16 }

hpiDomainAlarmUserLimit 	OBJECT-TYPE
	SYNTAX Gauge
	ACCESS read-only
	STATUS mandatory
	DESCRIPTION
		"Maximum User Alarms that can be added to DAT.
		 0 = no fixed limit."
	::= { hpiDomainEntry 17 }

hpiDomainAlarmOverflow 	OBJECT-TYPE
	SYNTAX TruthValue
	ACCESS read-only
	STATUS mandatory
	DESCRIPTION
		"Set to True if there are one or more non-User Alarms
		 that are missing from the DAT because of space limitations."
	::= { hpiDomainEntry 18 }

hpiDomainGuid 	OBJECT-TYPE
	SYNTAX SaHpiGuid
	ACCESS read-only
	STATUS mandatory
	DESCRIPTION
		"The GUID is used to uniquely identify a domain.
		 A GUID value of zero is not valid and indicates that the domain
		 does not have an associated GUID.
		 
		 GUID - Globally Unique Identifier
		 
		 The format if the ID follows that specified by the Wired for
		 Management Baseline, Version 2.0 specification.  HPI uses
		 version 1 of the GUID format, with a 3-bit variant field of
		 10x (where x indicates 'don't care')"
	::= { hpiDomainEntry 19 }

hpiDomainReferenceEntryCount 	OBJECT-TYPE
	SYNTAX Counter
	ACCESS read-only
	STATUS mandatory
	DESCRIPTION
		"The number of DRT entries present in the hpiDomainReferenceTable."
	::= { hpiDomain 3 }

hpiDomainReferenceTable 	OBJECT-TYPE
	SYNTAX SEQUENCE OF HpiDomainReferenceEntry
	ACCESS not-accessible
	STATUS mandatory
	DESCRIPTION
		"A table, provided by an HPI implementation, of additional domains
		 related to the current domain."
	::= { hpiDomain 4 }

hpiDomainReferenceEntry 	OBJECT-TYPE
	SYNTAX HpiDomainReferenceEntry
	ACCESS not-accessible
	STATUS mandatory
	DESCRIPTION
		"The Domain Reference Table (DRT) which provides information about
		 other domains associated with the domain. The two hpiDomainId are
		 used to uniquely identify a domain and a corresponding domain which
		 can be off peer or tiered domain architecture.
		 The DRT contains an entry for each associated domain, and HPI MIB 
		 Users may read these entries to discover the presence of additional 
		 domains within a 'System'. The discovered domains can, in turn, be 
		 used to discover additional resources and domains. 
		 The DRT is automatically built and maintained by the HPI 
		 implementation.  Domain entries in the DRT may change over time 
		 if the 'System' configuration changes.
		 
		 There are two types of domain references:
		 
		 - A peer domain architecture, which consists of two or more domains 
		 that are expected to contain the same resources and domain references.      
		 Each domain in a peer relationship contains an RPT listing all 
		 resources present in each domain.
		 
		 - A tiered (child) domain architecture is used when all the resources 
		 in a'system' cannot be accessed in a single domain.  A 'parent'
		 domain references one or more 'child' domains in its DRT.  The 
		 'child' domains may be simple domains containing only resources, 
		 or they may themselves be a 'parent' to other 'child' domains. 
		 Domains in a tiered relationship are disjointed and do not contain 
		 the same resources.
		 
		 Note:
		 When a domain is added to the DRT (SAHPI_DOMAIN_REF_ADDED) and when 
		 a domain is removed from the DRT (SAHPI_DOMAIN_REF_REMOVED) an event 
		 is generated."
	INDEX {
		hpiDomainId,
		hpiDomainReferenceDomain
	}
	::= { hpiDomainReferenceTable 1 }

HpiDomainReferenceEntry ::= SEQUENCE {
	hpiDomainReferenceDomain  Gauge,
	hpiDomainReferenceIsPeer  TruthValue
	}

hpiDomainReferenceDomain 	OBJECT-TYPE
	SYNTAX Gauge
	ACCESS not-accessible
	STATUS mandatory
	DESCRIPTION
		""
	::= { hpiDomainReferenceEntry 1 }

hpiDomainReferenceIsPeer 	OBJECT-TYPE
	SYNTAX TruthValue
	ACCESS read-only
	STATUS mandatory
	DESCRIPTION
		"Indicates that this domain participates in a peer relationship.
		 true = Domain is peer.  false = Domain is not peer (is a child) "
	::= { hpiDomainReferenceEntry 2 }

hpiDomainAlarmEntryCount 	OBJECT-TYPE
	SYNTAX Counter
	ACCESS read-only
	STATUS mandatory
	DESCRIPTION
		"The number of DomainAlarm entries present in the system."
	::= { hpiDomain 5 }

hpiDomainAlarmTable 	OBJECT-TYPE
	SYNTAX SEQUENCE OF HpiDomainAlarmEntry
	ACCESS not-accessible
	STATUS mandatory
	DESCRIPTION
		"This table represents the management attributes common to all Domains
		 within the managed platform.  The logical domain ID and the entity ID
		 are used to address an entity."
	::= { hpiDomain 6 }

hpiDomainAlarmEntry 	OBJECT-TYPE
	SYNTAX HpiDomainAlarmEntry
	ACCESS not-accessible
	STATUS mandatory
	DESCRIPTION
		"This table is used to store alarm information."
	INDEX {
		hpiDomainId,
		hpiDomainAlarmId
	}
	::= { hpiDomainAlarmTable 1 }

HpiDomainAlarmEntry ::= SEQUENCE {
	hpiDomainAlarmId                    SaHpiEntryId,
	hpiDomainAlarmTimestamp             SaHpiTime,
	hpiDomainAlarmSeverity              SaHpiSeverity,
	hpiDomainAlarmAcknowledged          TruthValue,
	hpiDomainAlarmCondType              SaHpiCondition,
	hpiDomainAlarmCondEntityPath        SaHpiEntityPath,
	hpiDomainAlarmCondSensorNum         Gauge,
	hpiDomainAlarmCondSensorEventState  SaHpiEventState,
	hpiDomainAlarmCondName              OCTET STRING,
	hpiDomainAlarmCondMid               SaHpiManufacturerId,
	hpiDomainAlarmCondDataType          SaHpiTextType,
	hpiDomainAlarmCondDataLanguage      SaHpiTextLanguage,
	hpiDomainAlarmCondData              SaHpiText,
	hpiDomainAlarmInstanceStatus        INTEGER
	}

hpiDomainAlarmId 	OBJECT-TYPE
	SYNTAX SaHpiEntryId
	ACCESS not-accessible
	STATUS mandatory
	DESCRIPTION
		"DomainAlarm Id"
	::= { hpiDomainAlarmEntry 1 }

hpiDomainAlarmTimestamp 	OBJECT-TYPE
	SYNTAX SaHpiTime
	ACCESS read-only
	STATUS mandatory
	DESCRIPTION
		"Time when alarm was added to the DAT table.
		 Refer to SaHpiTime for full description."
	::= { hpiDomainAlarmEntry 2 }

hpiDomainAlarmSeverity 	OBJECT-TYPE
	SYNTAX SaHpiSeverity
	ACCESS read-write
	STATUS mandatory
	DESCRIPTION
		"Severity of alarm.
		 (Only used with DAT and Annunciator functions.  This is not a valid
		 severity for events or alarms)
		 
		 Note: Enumerated values are increased by one value compared to
		 SAI-HPI-B spec."
	::= { hpiDomainAlarmEntry 3 }

hpiDomainAlarmAcknowledged 	OBJECT-TYPE
	SYNTAX TruthValue
	ACCESS read-write
	STATUS mandatory
	DESCRIPTION
		"
		 An HPI User acknowledges an alarm to indicate that it is aware of the alarm 
		 and to influence platform-specific alarm annunciation that may be provided  
		 by the implementation.  Typically, an implementation ignores acknowledged   
		 alarms when announcing an alarm on annunciation devices such as audible     
		 sirens and dry contact closures.  However, alarm annunciation is            
		 implementation-specific.                                                    
		                                                                             
		 An acknowledged alarm will have the Acknowledged field in the alarm entry   
		 set to True.                                                                
		                                                                             
		 DomainAlarms are acknowledged by one of two ways: a single alarm entry by DomainAlarmId
		 regardless of severity or as a group of alarm entries by Severity
		 regardless of DomainAlarmId.                                                      
		                                                                             
		 To acknowledge all alarms contained within the DAT, set the Severity
		 parameter to allSeverities(256), and set the DomainAlarmId parameter to         
		 SAHPI_ENTRY_UNSPECIFIED.                                                    
		                                                                             
		 To acknowledge all alarms of a specific severity contained within the DAT,
		 set the Severity parameter to the appropriate value, and set the DomainAlarmId
		 parameter to SAHPI_ENTRY_UNSPECIFIED.                                       
		                                                                             
		 To acknowledge a single alarm entry, set the DomainAlarmId parameter to a value   
		 other than SAHPI_ENTRY_UNSPECIFIED.  The DomainAlarmId must be a valid identifier 
		 for an alarm entry present in the DAT at the time of the function call.     
		                                                                             
		 If an alarm has been previously acknowledged, acknowledging it again has no 
		 effect.  However, this is not an error.                                     
		                                                                             
		 If the DomainAlarmId parameter has a value other than SAHPI_ENTRY_UNSPECIFIED,    
		 the Severity parameter is ignored.
		                                                                             
		 If the DomainAlarmId parameter is passed as SAHPI_ENTRY_UNSPECIFIED, and no       
		 alarms are present that meet the requested Severity, this function will
		 have no effect.  However, this is not an error.                             
		                                                                             
		 SAHPI_ENTRY_UNSPECIFIED is defined as the same value as SAHPI_FIRST_ENTRY,  
		 so using either symbol will have the same effect.  However,                 
		 SAHPI_ENTRY_UNSPECIFIED should be used with this function for clarity.      
		 "
	::= { hpiDomainAlarmEntry 4 }

hpiDomainAlarmCondType 	OBJECT-TYPE
	SYNTAX SaHpiCondition
	ACCESS read-only
	STATUS mandatory
	DESCRIPTION
		"Enumeration of status condition type.
		 This is read-only because creation is allowed for user Alarms only"
	::= { hpiDomainAlarmEntry 5 }

hpiDomainAlarmCondEntityPath 	OBJECT-TYPE
	SYNTAX SaHpiEntityPath
	ACCESS read-write
	STATUS mandatory
	DESCRIPTION
		"Entity assoc. with status condition:
		 If resource manages a FRU, entity path of the FRU.
		 If resource manages a single entity, entity path of that entity.
		 If resource manages multiple entities, the entity path
		 of the 'primary' entity managed by the resource.
		 
		 Must be set to the same value in every domain which
		 contains this resource.
		 
		 This object converts HPI's hpiEntityPathT structure
		 and an OpenHPI canonical string. The canonical string is
		 formed by removing the SAHPI_ENT_ prefix from the
		 HPI types, and creating tuples for the entity types.
		 
		 Order of significance is inverted to make entity paths
		 look more like Unix directory structure. It is also assumed
		 that {ROOT,0} exists implicitly before all of these entries.
		 
		 For example:
		     {SYSTEM_CHASSIS,2}{PROCESSOR_BOARD,0} "
	::= { hpiDomainAlarmEntry 6 }

hpiDomainAlarmCondSensorNum 	OBJECT-TYPE
	SYNTAX Gauge
	ACCESS read-only
	STATUS mandatory
	DESCRIPTION
		"Sensor associated with status Only valid if Type is
		 SAHPI_STATUS_COND_TYPE_SENSOR.
		 This is read-only because creation is allowed for user Alarms only"
	::= { hpiDomainAlarmEntry 7 }

hpiDomainAlarmCondSensorEventState 	OBJECT-TYPE
	SYNTAX SaHpiEventState
	ACCESS read-only
	STATUS mandatory
	DESCRIPTION
		"Sensor event state.  Only valid if hpiDomainAlarmCondType
		 is sensor(1).
		 This is read-only because creation is allowed for user Alarms only"
	::= { hpiDomainAlarmEntry 8 }

hpiDomainAlarmCondName 	OBJECT-TYPE
	SYNTAX OCTET STRING
	ACCESS read-write
	STATUS mandatory
	DESCRIPTION
		"AIS compatible identifier associated with Status condition.
		 
		 The Service Availability(TM) Forum Application Interface
		 Specification standardizes the interface between Service
		 Availability(TM) Forum compliant High Availability (HA)
		 middleware and service applications. http://www.saforum.org"
	::= { hpiDomainAlarmEntry 9 }

hpiDomainAlarmCondMid 	OBJECT-TYPE
	SYNTAX SaHpiManufacturerId
	ACCESS read-write
	STATUS mandatory
	DESCRIPTION
		"Manufacturer Id associated with status condition,
		 required when hpiDomainAlarmCondStatusCondType is oem(3)."
	::= { hpiDomainAlarmEntry 10 }

hpiDomainAlarmCondDataType 	OBJECT-TYPE
	SYNTAX SaHpiTextType
	ACCESS read-write
	STATUS mandatory
	DESCRIPTION
		"Optional data associated with status condition. 
		 For more details, see textual definition"
	::= { hpiDomainAlarmEntry 11 }

hpiDomainAlarmCondDataLanguage 	OBJECT-TYPE
	SYNTAX SaHpiTextLanguage
	ACCESS read-write
	STATUS mandatory
	DESCRIPTION
		"Optional data associated with status condition. 
		 For more details, see textual definition"
	::= { hpiDomainAlarmEntry 12 }

hpiDomainAlarmCondData 	OBJECT-TYPE
	SYNTAX SaHpiText
	ACCESS read-write
	STATUS mandatory
	DESCRIPTION
		"Optional data associated with status condition.
		 The type of date is specified by hpiDomainAlarmCondDomainAlarmaTextType and
		 hpiDomainAlarmCondDomainAlarmaTextLanguage."
	::= { hpiDomainAlarmEntry 13 }

hpiDomainAlarmInstanceStatus 	OBJECT-TYPE
	SYNTAX INTEGER {
                               undefined (0),
                               active (1),
                               toCreate (2),
                               toDelete (3)
                        }
	ACCESS read-write
	STATUS mandatory
	DESCRIPTION
		"This columnar node contains the status of the row and also
		 perform add and delete operations."
	::= { hpiDomainAlarmEntry 14 }

hpiResourceEntryCount 	OBJECT-TYPE
	SYNTAX Counter
	ACCESS read-only
	STATUS mandatory
	DESCRIPTION
		"The number of RPT entries present in the system.
		 This field is used to determine if new resources have been added
		 or existing removed. "
	::= { hpiDomain 7 }

hpiResourceTable 	OBJECT-TYPE
	SYNTAX SEQUENCE OF HpiResourceEntry
	ACCESS not-accessible
	STATUS mandatory
	DESCRIPTION
		"The logical domain ID and the entity ID are used to address an entity."
	::= { hpiDomain 8 }

hpiResourceEntry 	OBJECT-TYPE
	SYNTAX HpiResourceEntry
	ACCESS not-accessible
	STATUS mandatory
	DESCRIPTION
		"This structure is used to store the RPT entry information.
		 The ResourceCapabilities field definies the capabilities of
		 the resource.  This field must be non-zero for all valid
		 resources.   The ResourceTag field is an informational value
		 that supplies the caller with naming  information for the
		 resource. This should be set to the  user-visible  name for a
		 resource, which can be used to identify the resource in
		 messages to a human operator.  For example, it could be set to
		 match a physical printed label attached to the primary  entity
		 which the resource manages. See section 5.2.6,
		 SaHpiResourceTagSet(), on page 33."
	INDEX {
		hpiDomainId,
		hpiResourceId
	}
	::= { hpiResourceTable 1 }

HpiResourceEntry ::= SEQUENCE {
	hpiResourceId                    Gauge,
	hpiResourceEntityType            SaHpiEntityType,
	hpiResourceEntityPath            SaHpiEntityPath,
	hpiResourceCapabilities          SaHpiCapabilities,
	hpiResourceSeverity              SaHpiSeverity,
	hpiResourceFailed                TruthValue,
	hpiResourceInfoResourceRev       Gauge,
	hpiResourceInfoSpecificVer       Gauge,
	hpiResourceInfoDeviceSupport     Gauge,
	hpiResourceInfoManufacturerId    SaHpiManufacturerId,
	hpiResourceInfoProductId         Gauge,
	hpiResourceInfoFirmwareMajorRev  Gauge,
	hpiResourceInfoFirmwareMinorRev  Gauge,
	hpiResourceInfoAuxFirmwareRev    Gauge,
	hpiResourceInfoGuid              SaHpiGuid,
	hpiResourceTagType               SaHpiTextType,
	hpiResourceTagLanguage           SaHpiTextLanguage,
	hpiResourceTag                   SaHpiText,
	hpiResourceText                  DisplayString,
	hpiResourceParamControl          INTEGER,
	hpiResourceResetState            INTEGER,
	hpiResourcePowerState            INTEGER
	}

hpiResourceId 	OBJECT-TYPE
	SYNTAX Gauge
	ACCESS not-accessible
	STATUS mandatory
	DESCRIPTION
		"Resource identifier.
		 The SAHPI_UNSPECIFIED_RESOURCE_ID value is used to specify the Domain
		 Event Log and to specify that there is no resource for such things as HPI
		 User events/alarms.
		 Note:
		 SAHPI_UNSPECIFIED_RESOURCE_ID 0xFFFFFFFF"
	::= { hpiResourceEntry 1 }

hpiResourceEntityType 	OBJECT-TYPE
	SYNTAX SaHpiEntityType
	ACCESS read-only
	STATUS mandatory
	DESCRIPTION
		"experimental"
	::= { hpiResourceEntry 2 }

hpiResourceEntityPath 	OBJECT-TYPE
	SYNTAX SaHpiEntityPath
	ACCESS read-only
	STATUS mandatory
	DESCRIPTION
		"If resource manages a FRU, entity path of the FRU.
		 If resource manages a single entity, entity path of that entity.
		 If resource manages multiple entities, the entity path
		 of the 'primary' entity managed by the resource.
		 
		 Must be set to the same value in every domain which contains this
		 resource.
		 
		 This object converts HPI's hpiEntityPathT structure and an OpenHPI
		 canonical string. The canonical string is formed by removing the
		 SAHPI_ENT_ prefix from the HPI types, and creating tuples for the
		 entity types.
		 
		 Order of significance is inverted to make entity paths
		 look more like Unix directory structure. It is also assumed
		 that {ROOT,0} exists implicitly before all of these entries.
		 
		 For example:
		     {SYSTEM_CHASSIS,2}{PROCESSOR_BOARD,0} "
	::= { hpiResourceEntry 3 }

hpiResourceCapabilities 	OBJECT-TYPE
	SYNTAX SaHpiCapabilities
	ACCESS read-only
	STATUS mandatory
	DESCRIPTION
		"
		 Resource Capabilities
		 
		 This definition defines the capabilities of a given resource.
		 One resource may support any number of capabilities using this
		 string (each capability is seperated by a delimeter).
		 
		 Because each entry in an RPT will have the
		 RESOURCE string, no value  is not a valid value for the
		 capability flag, and is thus used to indicate 'no RPT
		 entry present' in some function calls.
		 
		 RESOURCE
		 EVT_DEASSERTS
		 
		 Indicates that all sensors on the resource have the property that their
		 Assertion and Deassertion event enable flags are the same. That is,
		 for all event states whose assertion triggers an event, it is
		 guaranteed that the deassertion of that event will also
		 trigger an event.
		 
		 Thus, an HPI User may track the state of sensors on the
		 resource by monitoring events rather than polling for state changes.
		 
		 AGGREGATE_STATUS
		 CONFIGURATION
		 MANAGED_HOTSWAP
		 
		 Indicates that the resource supports the full managed hot swap model.
		 Since hot swap only makes sense for field-replaceable units, the
		 FRU capability string must also be set for this columnar object.
		 
		 WATCHDOG
		 CONTROL
		 FRU
		 
		 Indicates that the resource is a field-replaceable unit; i.e., it is
		 capable of being removed and replaced in a live system. If
		 MANAGED_HOTSWAP is also set, the resource supports
		 the full hot swap model.  If MANAGED_HOTSWAP is not
		 set, the resource supports the simplified hot swap model.
		 
		 ANNUNCIATOR
		 POWER
		 RESET
		 INVENTORY_DATA
		 EVENT_LOG
		 RDR
		 
		 Indicates that a resource data record (RDR) repository is supplied
		 by the resource. Since the existence of an RDR is mandatory for all
		 management instruments, this capability must be asserted if the
		 resource contains any sensors, controls, watchdog timers, or inventory
		 data repositories.
		 
		 SENSOR
		 "
	::= { hpiResourceEntry 4 }

hpiResourceSeverity 	OBJECT-TYPE
	SYNTAX SaHpiSeverity
	ACCESS read-write
	STATUS mandatory
	DESCRIPTION
		"Indicates the criticality that should be raised when the resource
		 is not responding.
		 
		 Note: The enumerated named have +1 added as opposed to the SA HPI
		 spec for the same constants.  "
	::= { hpiResourceEntry 6 }

hpiResourceFailed 	OBJECT-TYPE
	SYNTAX TruthValue
	ACCESS read-only
	STATUS mandatory
	DESCRIPTION
		"true = Resource Not Functional.  false = Resource Functional "
	::= { hpiResourceEntry 7 }

hpiResourceInfoResourceRev 	OBJECT-TYPE
	SYNTAX Gauge
	ACCESS read-only
	STATUS mandatory
	DESCRIPTION
		"hpiResourceInfo contains static configuration data
		 concerning the management controller associated with
		 the resource, or the resource itself.
		 
		 Note this information is used to describe the resource;
		 that is, the piece of infrastructure which manages an
		 entity (or multiple entities) - NOT the entities for
		 which the resource probvides management. The purpose of the
		 hpiResourceInfoT structure is to provide information
		 that the HPI user may need in order to interact
		 correctly with the resource (e.g., recognize a
		 specific management controller which may have defined
		 OEM fields in sensors, OEM controls, etc.
		 
		 All of the fields in the following structure may or
		 may not be used by a given resource."
	::= { hpiResourceEntry 8 }

hpiResourceInfoSpecificVer 	OBJECT-TYPE
	SYNTAX Gauge
	ACCESS read-only
	STATUS mandatory
	DESCRIPTION
		"
		 hpiResourceInfo contains static configuration data
		 concerning the management controller associated with 
		 the resource, or the resource itself.
		 
		 Note this information is used to describe the resource;
		 that is, the piece of infrastructure which manages an 
		 entity (or multiple entities) - NOT the entities for
		 which the resource provides management. The purpose of the 
		 hpiResourceInfoT structure is to provide information
		 that the HPI user may need in order to interact 
		 correctly with the resource (e.g., recognize a
		 specific management controller which may have defined 
		 OEM fields in sensors, OEM controls, etc.
		 
		 All of the fields in the following structure may or
		 may not be used by a given resource."
	::= { hpiResourceEntry 9 }

hpiResourceInfoDeviceSupport 	OBJECT-TYPE
	SYNTAX Gauge
	ACCESS read-only
	STATUS mandatory
	DESCRIPTION
		"
		 hpiResourceInfo contains static configuration data
		 concerning the management controller associated with
		 the resource, or the resource itself. 
		 
		 Note this information is used to describe the resource; 
		 that is, the piece of infrastructure which manages an
		 entity (or multiple entities) - NOT the entities for 
		 which the resource provides management. The purpose of the
		 hpiResourceInfoT structure is to provide information
		 that the HPI user may need in order to interact
		 correctly with the resource (e.g., recognize a 
		 specific management controller which may have defined
		 OEM fields in sensors, OEM controls, etc.
		 
		 All of the fields in the following structure may or 
		 may not be used by a given resource."
	::= { hpiResourceEntry 10 }

hpiResourceInfoManufacturerId 	OBJECT-TYPE
	SYNTAX SaHpiManufacturerId
	ACCESS read-only
	STATUS mandatory
	DESCRIPTION
		"
		 hpiResourceInfo contains static configuration data
		 concerning the management controller associated with 
		 the resource, or the resource itself.
		 
		 Note this information is used to describe the resource;
		 that is, the piece of infrastructure which manages an 
		 entity (or multiple entities) - NOT the entities for
		 which the resource provides management. The purpose of the 
		 hpiResourceInfoT structure is to provide information
		 that the HPI user may need in order to interact 
		 correctly with the resource (e.g., recognize a
		 specific management controller which may have defined 
		 OEM fields in sensors, OEM controls, etc.
		 
		 All of the fields in the following structure may or
		 may not be used by a given resource."
	::= { hpiResourceEntry 11 }

hpiResourceInfoProductId 	OBJECT-TYPE
	SYNTAX Gauge
	ACCESS read-only
	STATUS mandatory
	DESCRIPTION
		"
		 hpiResourceInfo contains static configuration data
		 concerning the management controller associated with
		 the resource, or the resource itself. 
		 
		 Note this information is used to describe the resource; 
		 that is, the piece of infrastructure which manages an
		 entity (or multiple entities) - NOT the entities for 
		 which the resource provides management. The purpose of the
		 hpiResourceInfoT structure is to provide information
		 that the HPI user may need in order to interact
		 correctly with the resource (e.g., recognize a
		 specific management controller which may have defined
		 OEM fields in sensors, OEM controls, etc.
		 
		 All of the fields in the following structure may or 
		 may not be used by a given resource."
	::= { hpiResourceEntry 12 }

hpiResourceInfoFirmwareMajorRev 	OBJECT-TYPE
	SYNTAX Gauge
	ACCESS read-only
	STATUS mandatory
	DESCRIPTION
		"
		 hpiResourceInfo contains static configuration data
		 concerning the management controller associated with 
		 the resource, or the resource itself.
		 
		 Note this information is used to describe the resource;
		 that is, the piece of infrastructure which manages an 
		 entity (or multiple entities) - NOT the entities for
		 which the resource provides management. The purpose of the 
		 hpiResourceInfoT structure is to provide information
		 that the HPI user may need in order to interact 
		 correctly with the resource (e.g., recognize a
		 specific management controller which may have defined 
		 OEM fields in sensors, OEM controls, etc.
		 
		 All of the fields in the following structure may or
		 may not be used by a given resource."
	::= { hpiResourceEntry 13 }

hpiResourceInfoFirmwareMinorRev 	OBJECT-TYPE
	SYNTAX Gauge
	ACCESS read-only
	STATUS mandatory
	DESCRIPTION
		"
		 hpiResourceInfo contains static configuration data
		 concerning the management controller associated with
		 the resource, or the resource itself.
		 
		 Note this information is used to describe the resource;
		 that is, the piece of infrastructure which manages an
		 entity (or multiple entities) - NOT the entities for
		 which the resource provides management. The purpose of the
		 hpiResourceInfoT structure is to provide information
		 that the HPI user may need in order to interact
		 correctly with the resource (e.g., recognize a
		 specific management controller which may have defined
		 OEM fields in sensors, OEM controls, etc.
		 
		 All of the fields in the following structure may or
		 may not be used by a given resource."
	::= { hpiResourceEntry 14 }

hpiResourceInfoAuxFirmwareRev 	OBJECT-TYPE
	SYNTAX Gauge
	ACCESS read-only
	STATUS mandatory
	DESCRIPTION
		"
		 hpiResourceInfo contains static configuration data
		 concerning the management controller associated with
		 the resource, or the resource itself.
		 
		 Note this information is used to describe the resource;
		 that is, the piece of infrastructure which manages an
		 entity (or multiple entities) - NOT the entities for
		 which the resource provides management. The purpose of the
		 hpiResourceInfoT structure is to provide information
		 That the HPI user may need in order to interact
		 correctly with the resource (e.g., recognize a
		 specific management controller which may have defined
		 OEM fields in sensors, OEM controls, etc.
		 
		 All of the fields in the following structure may or
		 may not be used by a given resource."
	::= { hpiResourceEntry 15 }

hpiResourceInfoGuid 	OBJECT-TYPE
	SYNTAX SaHpiGuid
	ACCESS read-only
	STATUS mandatory
	DESCRIPTION
		"
		 GUID - Globally Unique Identifier
		 
		 The format if the ID follows that specified by the Wired for Management
		 Baseline, Version 2.0 specification.  HPI uses version 1 of the GUID
		 format, with a 3-bit variant field of 10x (where x indicates 'don't care')"
	::= { hpiResourceEntry 16 }

hpiResourceTagType 	OBJECT-TYPE
	SYNTAX SaHpiTextType
	ACCESS read-write
	STATUS mandatory
	DESCRIPTION
		"See Definition."
	::= { hpiResourceEntry 17 }

hpiResourceTagLanguage 	OBJECT-TYPE
	SYNTAX SaHpiTextLanguage
	ACCESS read-write
	STATUS mandatory
	DESCRIPTION
		"See Definition."
	::= { hpiResourceEntry 18 }

hpiResourceTag 	OBJECT-TYPE
	SYNTAX SaHpiText
	ACCESS read-write
	STATUS mandatory
	DESCRIPTION
		"Resource tag. The type of date is specified
		 by hpiResourceTagTextType and hpiResourceTagLanguage."
	::= { hpiResourceEntry 19 }

hpiResourceText 	OBJECT-TYPE
	SYNTAX DisplayString
	ACCESS read-only
	STATUS mandatory
	DESCRIPTION
		"Resource tag. The type of date is specified
		 by hpiResourceTagTextType and hpiResourceTagLanguage."
	::= { hpiResourceEntry 20 }

hpiResourceParamControl 	OBJECT-TYPE
	SYNTAX INTEGER {
                               undefined (0),
                               default (1),
                               save (2),
                               restore (3)
                        }
	ACCESS read-write
	STATUS mandatory
	DESCRIPTION
		"This object allows the user to save and restore parameters
		 associated with a specific resource. Valid actions for this
		 function include:
		 undefined(0)    - resource has no concept of    configurations.
		 restoreDefaultParm(1) - Restores the factory default settings
		             for a specific resource. Factory defaults
		             include sensor thresholds and configurations,
		             and resource- specific configuration parameters.
		 savaParm(2) - Stores the resource configuration parameters in
		             non-volatile storage. Resource configuration
		             parameters stored in non-volatile storage will
		             survive power cycles and resource resets.
		 restoreParm(3) - Restores resource configuration parameters
		             from non-volatile storage. Resource
		             configuration parameters include sensor
		             thresholds and sensor configurations, as well
		             as resource-specific.
		 
		 Note: Enumerated values are increased by one value compared to
		 SAI-HPI-B spec."
	::= { hpiResourceEntry 21 }

hpiResourceResetState 	OBJECT-TYPE
	SYNTAX INTEGER {
                               undefined (0),
                               coldReset (1),
                               warmReset (2),
                               assert (3),
                               deassert (4),
                               unsupported (5)
                        }
	ACCESS read-write
	STATUS mandatory
	DESCRIPTION
		"This function gets the reset state of an entity, allowing the HPI
		 User to determine if the entity is being held with its reset asserted.
		 If a resource manages multiple entities, this function will address
		 the entity which is identified in the RPT entry for the resource.
		 
		 coldReset(1) and warmReset(2) are pulsed resets, and are not valid
		 values to be returned in hpiResetAction.
		 If the entity is not being held in reset (using resetAssert(3)),
		 the appropriate value is resetDeAssert(4).
		 
		 Note: Enumerated values are increased by one value compared to
		 SAI-HPI-B spec."
	::= { hpiResourceEntry 22 }

hpiResourcePowerState 	OBJECT-TYPE
	SYNTAX INTEGER {
                               undefined (0),
                               off (1),
                               on (2),
                               cycle (3),
                               unsupported (4)
                        }
	ACCESS read-write
	STATUS mandatory
	DESCRIPTION
		"This function gets the power state of an entity, allowing the
		 HPI User to determine if the entity is currently powered on or
		 off. If a resource manages multiple entities, this function will
		 address the entity which is identified in the RPT entry for the
		 resource.
		 
		 cycle(3) is a pulsed power operation and is not a valid return
		 for the power state.
		 
		 This function controls the hardware power on a FRU entity
		 regardless of what hot-swap state the resource is in. For
		 example, it is legal (and may be desirable) to cycle power
		 on the FRU even while it is in ACTIVE state in order to attempt
		 to clear a fault condition. Similarly, a resource could be
		 instructed to power on a FRU even while it is in INACTIVE state,
		 for example, in order to run off-line diagnostics.
		 Not all resources supporting hot swap will necessarily support
		 this function. In particular, resources that use the simplified
		 hot swap model may not have the ability to control FRU power.
		 This function may also be supported for non-FRU entities if power
		 control is available for those entities.
		 Note: Enumerated values are increased by one value compared to
		    SAI-HPI-B spec."
	::= { hpiResourceEntry 23 }

hpiHotSwap OBJECT IDENTIFIER ::= {hpiDomain 11}

hpiAutoInsertTable 	OBJECT-TYPE
	SYNTAX SEQUENCE OF HpiAutoInsertEntry
	ACCESS not-accessible
	STATUS mandatory
	DESCRIPTION
		"In support of hpiAutoInsertTimeoutGet(), hpiAutoInsertTimeoutSet()"
	::= { hpiHotSwap 1 }

hpiAutoInsertEntry 	OBJECT-TYPE
	SYNTAX HpiAutoInsertEntry
	ACCESS not-accessible
	STATUS mandatory
	DESCRIPTION
		"Table of domains with a timeout for how long to wait before
		 the default auto-insertion policy is invoked on a resource within
		 a specific domain."
	INDEX {
		hpiDomainId
	}
	::= { hpiAutoInsertTable 1 }

HpiAutoInsertEntry ::= SEQUENCE {
	hpiAutoInsertTimeout  SaHpiTime
	}

hpiAutoInsertTimeout 	OBJECT-TYPE
	SYNTAX SaHpiTime
	ACCESS read-write
	STATUS mandatory
	DESCRIPTION
		"This function allows the HPI SNMP Manager to configure a timeout for
		 how long to wait before the default auto-insertion policy is invoked
		 on a resource within a specific domain.
		 
		 This columnar node accepts a parameter instructing each resource to impose
		 a delay before performing its default hot swap policy for
		 auto-insertion.  The parameter may be set to
		     SAHPI_TIMEOUT_IMMEDIATE
		 ( see SaHpiTime Textual-Convention for further details)
		 to direct resources to proceed immediately to auto-insertion, or to
		     SAHPI_TIMEOUT_BLOCK
		 ( see SaHpiTime Textual-Convention for further details)
		 to prevent auto-insertion from ever occurring.
		 If the parameter is set to another value, then it defines the number
		 of nanoseconds between the time a hot swap event with
		 hpiHotSwapState == insertionPending(5) is generated, and the time
		 that the auto-insertion policy will be invoked for that resource.
		 If, during this time period, a hpiHotSwapPolicyCancel function
		 call is processed, the timer will be stopped, and the auto-insertion
		 policy will not be invoked.  Each domain maintains a single
		 auto-insert timeout value and it is applied to all contained resources
		 upon insertion, which support managed hot swap. Once the auto-insertion
		 process begins, the HPI SNMP Manager will not be allowed to take control of
		 the insertion process; hence, the timeout should be set appropriately
		 to allow for this condition.  Note that the timeout period begins
		 when the hot swap event with hpiHotSwapState == insertionPending(5)
		 is initially generated."
	::= { hpiAutoInsertEntry 1 }

hpiHotSwapEntryCount 	OBJECT-TYPE
	SYNTAX Counter
	ACCESS read-only
	STATUS mandatory
	DESCRIPTION
		"The number of HotSwap entries present in the system."
	::= { hpiHotSwap 2 }

hpiHotSwapTable 	OBJECT-TYPE
	SYNTAX SEQUENCE OF HpiHotSwapEntry
	ACCESS not-accessible
	STATUS mandatory
	DESCRIPTION
		"This table represents management attributes common to all hot swappable
		 resources in the managed platform.  The entries in this table are
		 straight from the HPI spec.  This table builds upon information present
		 in the hpiResourceTable."
	::= { hpiHotSwap 3 }

hpiHotSwapEntry 	OBJECT-TYPE
	SYNTAX HpiHotSwapEntry
	ACCESS not-accessible
	STATUS mandatory
	DESCRIPTION
		"An entry describing a particular hot swappable entity."
	INDEX {
		hpiDomainId,
		hpiResourceId
	}
	::= { hpiHotSwapTable 1 }

HpiHotSwapEntry ::= SEQUENCE {
	hpiHotSwapCapabilities     SaHpiHsCapabilities,
	hpiHotSwapIndicator        INTEGER,
	hpiHotSwapState            SaHpiHotSwapState,
	hpiHotSwapExtractTimeout   SaHpiTime,
	hpiHotSwapActionRequest    INTEGER,
	hpiHotSwapPolicyCancel     INTEGER,
	hpiHotSwapResourceRequest  INTEGER
	}

hpiHotSwapCapabilities 	OBJECT-TYPE
	SYNTAX SaHpiHsCapabilities
	ACCESS read-only
	STATUS mandatory
	DESCRIPTION
		""
	::= { hpiHotSwapEntry 1 }

hpiHotSwapIndicator 	OBJECT-TYPE
	SYNTAX INTEGER {
                               undefined (0),
                               off (1),
                               on (2)
                        }
	ACCESS read-write
	STATUS mandatory
	DESCRIPTION
		"A FRU associated with a hot-swappable resource may include
		 a hot swap indicator such as a blue LED. This indicator signifies
		 that the FRU is ready for removal.
		 This columnar node allows the HPI SNMP Manager to retrieve and set the
		 state of this indicator.
		 When retrieving the values, the valid states are either
		 hpiHotSwapIndicator == off(1)
		     or
		 hpiHotSwapIndicator == on(2).
		 This columnar node will return information, regardless of
		 what hot swap state the resource is in.
		 When setting the values,  valid states include
		 hpiHotSwapIndicator == off(1)
		     or
		 hpiHotSwapIndicator == on(2).
		 This function will set the indicator regardless of what hot swap
		 state the resource is in, though it is recommended that this
		 function be used only in conjunction with moving the resource to
		 the appropriate hot swap state."
	::= { hpiHotSwapEntry 2 }

hpiHotSwapState 	OBJECT-TYPE
	SYNTAX SaHpiHotSwapState
	ACCESS read-only
	STATUS mandatory
	DESCRIPTION
		"Refer to the textual convention for full details."
	::= { hpiHotSwapEntry 3 }

hpiHotSwapExtractTimeout 	OBJECT-TYPE
	SYNTAX SaHpiTime
	ACCESS read-write
	STATUS mandatory
	DESCRIPTION
		"This function allows the HPI User to configure a timeout for how
		 long to wait before the default auto-extraction policy is invoked.
		 This function accepts a parameter instructing the resource to impose
		 a delay before performing its default hot swap policy for
		 auto-extraction. The parameter may be set to SAHPI_TIMEOUT_IMMEDIATE
		 to direct the resource to proceed immediately to auto-extraction, or
		 to SAHPI_TIMEOUT_BLOCK to prevent auto-extraction from ever occurring
		 on a resource. If the parameter is set to another value, then it
		 defines the number of nanoseconds between the time a hot swap event
		 with hpiHotSwapState = extractionPending(5) is generated and the
		 time that the auto-extraction policy will be invoked for the
		 resource. If, during this time period, a hpiHotSwapPolicyCancel
		 function call is processed, the timer will be stopped, and the
		 auto-extraction policy will not be invoked.
		 
		 Once the auto-extraction process begins, the HPI User will not be
		 allowed to take control of the extraction process; hence, the
		 timeout should be set appropriately to allow for this condition.
		 
		 Note that the timeout period begins when the hot swap event with
		 hpiHotSwapState = extractionPending(4) is initially generated."
	::= { hpiHotSwapEntry 4 }

hpiHotSwapActionRequest 	OBJECT-TYPE
	SYNTAX INTEGER {
                               undefined (0),
                               insertion (1),
                               extraction (2)
                        }
	ACCESS read-write
	STATUS mandatory
	DESCRIPTION
		"A resource supporting hot swap typically requires a physical
		 action on the associated FRU to invoke an insertion or extraction
		 process. An insertion process is invoked by physically inserting
		 the FRU into a chassis. Physically opening an ejector latch or
		 pressing a button invokes the extraction process.
		 
		 This columnar node allows the HPI User to invoke an insertion or
		 extraction process via software.
		 
		 Note: Enumerated values are increased by one value compared to
		 SAI-HPI-B spec."
	::= { hpiHotSwapEntry 5 }

hpiHotSwapPolicyCancel 	OBJECT-TYPE
	SYNTAX INTEGER {
                               undefined (0),
                               cancel (1)
                        }
	ACCESS read-write
	STATUS mandatory
	DESCRIPTION
		"A resource supporting hot swap typically supports default policies for
		 insertion and extraction. On insertion, the default policy may be for
		 the resource to turn the associated FRU~s local power on and to
		 de-assert reset. On extraction, the default policy may be for the
		 resource to immediately power off the FRU and turn on a hot swap
		 indicator. This function allows an HPI User, after receiving a hot
		 swap event with hpiHotSwapState equal to INSERTION_PENDING or
		 EXTRACTION_PENDING, to prevent the default policy from being executed.
		 
		 Once the resource transitions to either the ACTIVE or INACTIVE state,
		 the default policies will once again execute, unless cancelled using
		 hpiHotSwapPolicyCancel.
		 
		 The default policy cannot be canceled once it has begun to execute.
		 
		 Because a resource that supports the simplified hot swap model will
		 never transition into INSERTION PENDING or EXTRACTION PENDING states,
		 this function is not applicable to those resources.
		 
		 Note: Enumerated values are increased by one value compared to
		 SAI-HPI-B spec."
	::= { hpiHotSwapEntry 6 }

hpiHotSwapResourceRequest 	OBJECT-TYPE
	SYNTAX INTEGER {
                               undefined (0),
                               setActive (1),
                               setInActive (2)
                        }
	ACCESS read-write
	STATUS mandatory
	DESCRIPTION
		"Depending on the values, the user can:
		 
		 - use this function to request a resource to return to the ACTIVE state 
		 from the EXTRACTION PENDING state in order to reject an extraction request.
		 Because a resource that supports the simplified hot swap model will never 
		 transition into INSERTION PENDING or EXTRACTION PENDING states, this 
		 function is not applicable to those resources.
		 
		 - use this function to request a resource to return to the INACTIVE state 
		 from the INSERTION PENDING state to abort a hot-swap insertion action.
		 Because a resource that supports the simplified hot swap model will never 
		 transition into INSERTION PENDING or EXTRACTION PENDING states, this 
		 function is not applicable to those resources.
		 
		 Note: Enumerated values are increased by one value compared to
		 SAI-HPI-B spec."
	::= { hpiHotSwapEntry 7 }

hpiEvents OBJECT IDENTIFIER ::= {fscHpiBMIB 3}

events OBJECT IDENTIFIER ::= {hpiEvents 1}

hpiEventInfoTable OBJECT IDENTIFIER ::= {events 1}

hpiEventEntryCount 	OBJECT-TYPE
	SYNTAX Counter
	ACCESS read-only
	STATUS mandatory
	DESCRIPTION
		"The number of events present in this table.
		 hpiEventCount represents the total of types currently in the
		 system.  hpiDomainEventCount represents the subset of events
		 that are Domain events.  The same relationship exists for
		 ResourceEvent,  SensorEvent,  SensorEnableChangeEvent,
		 HotSwapEvent,  WatchdogEvent,  HpiSwEvent,  OemEvent,  UserEvent."
	::= { events 3 }

hpiEventTable 	OBJECT-TYPE
	SYNTAX SEQUENCE OF HpiEventEntry
	ACCESS not-accessible
	STATUS mandatory
	DESCRIPTION
		"Event Master table. "
	::= { events 4 }

hpiEventEntry 	OBJECT-TYPE
	SYNTAX HpiEventEntry
	ACCESS not-accessible
	STATUS mandatory
	DESCRIPTION
		"This table presents the list of all events which are present in the
		 HPI system. The implementation decides how to manipulate the events
		 as they reach a large number. This table is used as a master event
		 table which an index that points to the specific sub-table which has
		 more details on the event.
		 Each time a new event is surfaced in the HPI system this table
		 increases by a new row and its respective sub-event table too
		 (hpiResourceEventTable, hpiOEMEventTable, etc). Futhermore
		 based on the type of event, an notification is generated as well."
	INDEX {
		hpiDomainId,
		hpiResourceId,
		hpiEventSeverity,
		hpiEventTimeStamp
	}
	::= { hpiEventTable 1 }

HpiEventEntry ::= SEQUENCE {
	hpiEventSeverity   INTEGER,
	hpiEventTimeStamp  SaHpiTime,
	hpiEventSource     INTEGER,
	hpiEventTime       OCTET STRING,
	hpiEventType       INTEGER
	}

hpiEventSeverity 	OBJECT-TYPE
	SYNTAX INTEGER {
                               undefined (0),
                               critical (1),
                               major (2),
                               minor (3),
                               informational (4),
                               ok (5),
                               debug (241)
                        }
	ACCESS read-only
	STATUS mandatory
	DESCRIPTION
		"Severity of event.
		 Note: Enumerated values are increased by one value compared to
		 SAI-HPI-B spec."
	::= { hpiEventEntry 1 }

hpiEventTimeStamp 	OBJECT-TYPE
	SYNTAX SaHpiTime
	ACCESS read-only
	STATUS mandatory
	DESCRIPTION
		"Refer to textual convention for SaHpiTime for more details.
		 The value is Equal to TIME_UNSPECIFIED if time is not available;
		 Absolute time if greater than TIME_MAX_RELATIVE, Relative time
		 if less than or equal to TIME_MAX_RELATIVE."
	::= { hpiEventEntry 2 }

hpiEventSource 	OBJECT-TYPE
	SYNTAX INTEGER {
                               unspecified (-1)
                        }
	ACCESS read-only
	STATUS mandatory
	DESCRIPTION
		""
	::= { hpiEventEntry 3 }

hpiEventTime 	OBJECT-TYPE
	SYNTAX OCTET STRING
	ACCESS read-only
	STATUS mandatory
	DESCRIPTION
		"Refer to textual convention for SaHpiTime for more details.
		 The value is Equal to TIME_UNSPECIFIED if time is not available;
		 Absolute time if greater than TIME_MAX_RELATIVE, Relative time
		 if less than or equal to TIME_MAX_RELATIVE."
	::= { hpiEventEntry 4 }

hpiEventType 	OBJECT-TYPE
	SYNTAX INTEGER {
                               undefined (0),
                               resource (1),
                               domain (2),
                               sensor (3),
                               sensorEnableChange (4),
                               hotswap (5),
                               watchdog (6),
                               hpiSw (7),
                               oem (8),
                               user (9)
                        }
	ACCESS read-only
	STATUS mandatory
	DESCRIPTION
		"Event type.
		 Note: The enumerated named have +1 added as opposed to the
		 SA HPI spec for the same constants.  "
	::= { hpiEventEntry 5 }

hpiResourceEventEntryCount 	OBJECT-TYPE
	SYNTAX Counter
	ACCESS read-only
	STATUS mandatory
	DESCRIPTION
		"This columnar node represents the subset of events that
		 are Resource Events."
	::= { events 6 }

hpiResourceEventTable 	OBJECT-TYPE
	SYNTAX SEQUENCE OF HpiResourceEventEntry
	ACCESS not-accessible
	STATUS mandatory
	DESCRIPTION
		"Event table. "
	::= { events 7 }

hpiResourceEventEntry 	OBJECT-TYPE
	SYNTAX HpiResourceEventEntry
	ACCESS not-accessible
	STATUS mandatory
	DESCRIPTION
		"Resource events."
	INDEX {
		hpiDomainId,
		hpiResourceId,
		hpiEventSeverity,
		hpiEventTimeStamp
	}
	::= { hpiResourceEventTable 1 }

HpiResourceEventEntry ::= SEQUENCE {
	hpiResourceEventType  INTEGER
	}

hpiResourceEventType 	OBJECT-TYPE
	SYNTAX INTEGER {
                               undefined (0),
                               resourceFailure (1),
                               resourceRestored (2),
                               resourceAdded (3)
                        }
	ACCESS read-only
	STATUS mandatory
	DESCRIPTION
		"Resource events are sent to indicate the failure or
		 subsequent restoration of a resource.  Resource events can also be
		 used to announce the addition of a non-FRU resource to the RPT table.
		 Note: Enumerated values are increased by one value compared to
		 SAI-HPI-B spec."
	::= { hpiResourceEventEntry 1 }

hpiDomainEventEntryCount 	OBJECT-TYPE
	SYNTAX Counter
	ACCESS read-only
	STATUS mandatory
	DESCRIPTION
		"hpiDomainEventEntryCount represents the subset of events
		 that are Domain events."
	::= { events 9 }

hpiDomainEventTable 	OBJECT-TYPE
	SYNTAX SEQUENCE OF HpiDomainEventEntry
	ACCESS not-accessible
	STATUS mandatory
	DESCRIPTION
		"Event table. "
	::= { events 10 }

hpiDomainEventEntry 	OBJECT-TYPE
	SYNTAX HpiDomainEventEntry
	ACCESS not-accessible
	STATUS mandatory
	DESCRIPTION
		"Domain events."
	INDEX {
		hpiDomainId,
		hpiResourceId,
		hpiEventSeverity,
		hpiEventTimeStamp
	}
	::= { hpiDomainEventTable 1 }

HpiDomainEventEntry ::= SEQUENCE {
	hpiDomainEventType    INTEGER,
	hpiDomainEventDomain  Gauge
	}

hpiDomainEventType 	OBJECT-TYPE
	SYNTAX INTEGER {
                               undefined (0),
                               domainRefAdded (1),
                               domainRefRemoved (2)
                        }
	ACCESS read-only
	STATUS mandatory
	DESCRIPTION
		"Domain events are used to announce the addition of domain
		 references and the removal of domain references to the DRT."
	::= { hpiDomainEventEntry 1 }

hpiDomainEventDomain 	OBJECT-TYPE
	SYNTAX Gauge
	ACCESS read-only
	STATUS mandatory
	DESCRIPTION
		"Domain Id of domain added to or removed from DRT."
	::= { hpiDomainEventEntry 2 }

hpiSensorEventEntryCount 	OBJECT-TYPE
	SYNTAX Counter
	ACCESS read-only
	STATUS mandatory
	DESCRIPTION
		"This columnar node represents the subset of events that
		 are Sensor Events."
	::= { events 12 }

hpiSensorEventTable 	OBJECT-TYPE
	SYNTAX SEQUENCE OF HpiSensorEventEntry
	ACCESS not-accessible
	STATUS mandatory
	DESCRIPTION
		"Event table. "
	::= { events 13 }

hpiSensorEventEntry 	OBJECT-TYPE
	SYNTAX HpiSensorEventEntry
	ACCESS not-accessible
	STATUS mandatory
	DESCRIPTION
		"Sensor events."
	INDEX {
		hpiDomainId,
		hpiResourceId,
		hpiEventSeverity,
		hpiEventTimeStamp
	}
	::= { hpiSensorEventTable 1 }

HpiSensorEventEntry ::= SEQUENCE {
	hpiSensorEventNum                   Gauge,
	hpiSensorEventType                  SaHpiSensorType,
	hpiSensorEventCategory              SaHpiEventCategory,
	hpiSensorEventAssertion             TruthValue,
	hpiSensorEventState                 SaHpiEventState,
	hpiSensorEventOptionalData          OCTET STRING,
	hpiSensorEventTriggerReadingType    SaHpiSensorReadingType,
	hpiSensorEventTriggerReading        SaHpiSensorReadingValue,
	hpiSensorEventTriggerThresholdType  SaHpiSensorReadingType,
	hpiSensorEventTriggerThreshold      SaHpiSensorReadingValue,
	hpiSensorEventPreviousState         SaHpiEventState,
	hpiSensorEventCurrentState          SaHpiEventState,
	hpiSensorEventOem                   Gauge,
	hpiSensorEventSpecific              Gauge
	}

hpiSensorEventNum 	OBJECT-TYPE
	SYNTAX Gauge
	ACCESS read-only
	STATUS mandatory
	DESCRIPTION
		""
	::= { hpiSensorEventEntry 1 }

hpiSensorEventType 	OBJECT-TYPE
	SYNTAX SaHpiSensorType
	ACCESS read-only
	STATUS mandatory
	DESCRIPTION
		"Refer to the textual convention for more
		 details."
	::= { hpiSensorEventEntry 2 }

hpiSensorEventCategory 	OBJECT-TYPE
	SYNTAX SaHpiEventCategory
	ACCESS read-only
	STATUS mandatory
	DESCRIPTION
		"Event category: See TEXTUAL-CONVENTION, SaHpiEventCategory."
	::= { hpiSensorEventEntry 3 }

hpiSensorEventAssertion 	OBJECT-TYPE
	SYNTAX TruthValue
	ACCESS read-only
	STATUS mandatory
	DESCRIPTION
		"Sensor Events and Sensor Event States:
		 Each Event State may be asserted or deasserted.  The set of Event
		 States a sensor may support is defined by the sensor's
		 'Event Category.'  A particular sensor, however, does not have to
		 support all the Event States defined for its event category.
		 The specific Event States that a particular sensor supports are
		 indicated in the 'Events' field in the sensor's RDR. A sensor is
		 not required to support any Event States. If no Event States are
		 supported by a sensor, the 'Events' field will be 0x0000.  A sensor
		 may not support any Event States that are not defined for its event
		 category. Each Event State is independent, although in some event
		 categories the meaning assigned to the Event States will imply that
		 certain Event States will be mutually exclusive.  For example, a
		 sensor that uses the SAHPI_EC_LIMIT event category should only have
		 one of the two Event States, SAHPI_ES_LIMIT_NOT_EXCEEDED or
		 SAHPI_ES_LIMIT_EXCEEDED asserted at any one time. Except where mutual
		 exclusion is implied, however, sensors may have multiple Event States
		 asserted simultaneously. For example, the event category
		 SAHPI_EC_THRESHOLD uses six different event states to report the
		 relationship between the value currently measured by the sensor and up
		 to six different 'threshold' values.  Each threshold is independently
		 examined, and each Event State that represents a threshold that has
		 been 'crossed' will be asserted.  Threshold values must be configured
		 so that 'Minor', 'Major' and 'Critical' thresholds are increasingly
		 extreme readings, such that when a 'Major' threshold has been crossed,
		 the corresponding 'Minor' threshold will also have been crossed, and
		 thus both Event States will be asserted. When a sensor Event State is
		 asserted or deasserted, an event may be generated by the resource.
		 The generated event identifies the sensor and the event state
		 being asserted or deasserted.  The HPI implementation may assign event
		 severity levels for each event state assertion or deassertion on an
		 individual sensor basis."
	::= { hpiSensorEventEntry 4 }

hpiSensorEventState 	OBJECT-TYPE
	SYNTAX SaHpiEventState
	ACCESS read-only
	STATUS mandatory
	DESCRIPTION
		"Refer to the textual convention for more details."
	::= { hpiSensorEventEntry 5 }

hpiSensorEventOptionalData 	OBJECT-TYPE
	SYNTAX OCTET STRING
	ACCESS read-only
	STATUS mandatory
	DESCRIPTION
		""
	::= { hpiSensorEventEntry 6 }

hpiSensorEventTriggerReadingType 	OBJECT-TYPE
	SYNTAX SaHpiSensorReadingType
	ACCESS read-only
	STATUS mandatory
	DESCRIPTION
		"Refer to the textual convention for more details."
	::= { hpiSensorEventEntry 7 }

hpiSensorEventTriggerReading 	OBJECT-TYPE
	SYNTAX SaHpiSensorReadingValue
	ACCESS read-only
	STATUS mandatory
	DESCRIPTION
		"Refer to the textual convention for more details."
	::= { hpiSensorEventEntry 8 }

hpiSensorEventTriggerThresholdType 	OBJECT-TYPE
	SYNTAX SaHpiSensorReadingType
	ACCESS read-only
	STATUS mandatory
	DESCRIPTION
		"Refer to the textual convention for more details."
	::= { hpiSensorEventEntry 9 }

hpiSensorEventTriggerThreshold 	OBJECT-TYPE
	SYNTAX SaHpiSensorReadingValue
	ACCESS read-only
	STATUS mandatory
	DESCRIPTION
		"Refer to the textual convention for more details."
	::= { hpiSensorEventEntry 10 }

hpiSensorEventPreviousState 	OBJECT-TYPE
	SYNTAX SaHpiEventState
	ACCESS read-only
	STATUS mandatory
	DESCRIPTION
		"Refer to the textual convention for more details."
	::= { hpiSensorEventEntry 11 }

hpiSensorEventCurrentState 	OBJECT-TYPE
	SYNTAX SaHpiEventState
	ACCESS read-only
	STATUS mandatory
	DESCRIPTION
		"Refer to SaHpiEventState textual convention for more details."
	::= { hpiSensorEventEntry 12 }

hpiSensorEventOem 	OBJECT-TYPE
	SYNTAX Gauge
	ACCESS read-only
	STATUS mandatory
	DESCRIPTION
		"Reserved for OEM use."
	::= { hpiSensorEventEntry 13 }

hpiSensorEventSpecific 	OBJECT-TYPE
	SYNTAX Gauge
	ACCESS read-only
	STATUS mandatory
	DESCRIPTION
		""
	::= { hpiSensorEventEntry 14 }

hpiSensorEnableChangeEventEntryCount 	OBJECT-TYPE
	SYNTAX Counter
	ACCESS read-only
	STATUS mandatory
	DESCRIPTION
		"This columnar node represents the subset of events that
		 are Sensor Enable ChangeEvents."
	::= { events 15 }

hpiSensorEnableChangeEventTable 	OBJECT-TYPE
	SYNTAX SEQUENCE OF HpiSensorEnableChangeEventEntry
	ACCESS not-accessible
	STATUS mandatory
	DESCRIPTION
		"Event table. "
	::= { events 16 }

hpiSensorEnableChangeEventEntry 	OBJECT-TYPE
	SYNTAX HpiSensorEnableChangeEventEntry
	ACCESS not-accessible
	STATUS mandatory
	DESCRIPTION
		"Sensor Enable Change events."
	INDEX {
		hpiDomainId,
		hpiResourceId,
		hpiEventSeverity,
		hpiEventTimeStamp
	}
	::= { hpiSensorEnableChangeEventTable 1 }

HpiSensorEnableChangeEventEntry ::= SEQUENCE {
	hpiSensorEnableChangeEventNum             Gauge,
	hpiSensorEnableChangeEventType            SaHpiSensorType,
	hpiSensorEnableChangeEventCategory        SaHpiEventCategory,
	hpiSensorEnableChangeEventEnabled         TruthValue,
	hpiSensorEnableChangeEventEventsEnabled   TruthValue,
	hpiSensorEnableChangeEventAssertEvents    SaHpiEventState,
	hpiSensorEnableChangeEventDeassertEvents  SaHpiEventState,
	hpiSensorEnableChangeEventOptionalData    OCTET STRING,
	hpiSensorEnableChangeEventCurrentState    SaHpiEventState
	}

hpiSensorEnableChangeEventNum 	OBJECT-TYPE
	SYNTAX Gauge
	ACCESS read-only
	STATUS mandatory
	DESCRIPTION
		""
	::= { hpiSensorEnableChangeEventEntry 1 }

hpiSensorEnableChangeEventType 	OBJECT-TYPE
	SYNTAX SaHpiSensorType
	ACCESS read-only
	STATUS mandatory
	DESCRIPTION
		"Refer to the textual convention for more
		 details."
	::= { hpiSensorEnableChangeEventEntry 2 }

hpiSensorEnableChangeEventCategory 	OBJECT-TYPE
	SYNTAX SaHpiEventCategory
	ACCESS read-only
	STATUS mandatory
	DESCRIPTION
		"Refer to the textual convention for more details."
	::= { hpiSensorEnableChangeEventEntry 3 }

hpiSensorEnableChangeEventEnabled 	OBJECT-TYPE
	SYNTAX TruthValue
	ACCESS read-only
	STATUS mandatory
	DESCRIPTION
		"Current sensor enable status."
	::= { hpiSensorEnableChangeEventEntry 4 }

hpiSensorEnableChangeEventEventsEnabled 	OBJECT-TYPE
	SYNTAX TruthValue
	ACCESS read-only
	STATUS mandatory
	DESCRIPTION
		"Current event enable status."
	::= { hpiSensorEnableChangeEventEntry 5 }

hpiSensorEnableChangeEventAssertEvents 	OBJECT-TYPE
	SYNTAX SaHpiEventState
	ACCESS read-only
	STATUS mandatory
	DESCRIPTION
		"Refer to the textual convention for more details."
	::= { hpiSensorEnableChangeEventEntry 6 }

hpiSensorEnableChangeEventDeassertEvents 	OBJECT-TYPE
	SYNTAX SaHpiEventState
	ACCESS read-only
	STATUS mandatory
	DESCRIPTION
		"Refer to the textual convention for more details."
	::= { hpiSensorEnableChangeEventEntry 7 }

hpiSensorEnableChangeEventOptionalData 	OBJECT-TYPE
	SYNTAX OCTET STRING
	ACCESS read-only
	STATUS mandatory
	DESCRIPTION
		""
	::= { hpiSensorEnableChangeEventEntry 8 }

hpiSensorEnableChangeEventCurrentState 	OBJECT-TYPE
	SYNTAX SaHpiEventState
	ACCESS read-only
	STATUS mandatory
	DESCRIPTION
		"Current set of asserted Event states."
	::= { hpiSensorEnableChangeEventEntry 9 }

hpiHotSwapEventEntryCount 	OBJECT-TYPE
	SYNTAX Counter
	ACCESS read-only
	STATUS mandatory
	DESCRIPTION
		"This columnar node represents the subset of events that
		 are HotSwap Events."
	::= { events 18 }

hpiHotSwapEventTable 	OBJECT-TYPE
	SYNTAX SEQUENCE OF HpiHotSwapEventEntry
	ACCESS not-accessible
	STATUS mandatory
	DESCRIPTION
		"Event table. "
	::= { events 19 }

hpiHotSwapEventEntry 	OBJECT-TYPE
	SYNTAX HpiHotSwapEventEntry
	ACCESS not-accessible
	STATUS mandatory
	DESCRIPTION
		"Hot Swap events."
	INDEX {
		hpiDomainId,
		hpiResourceId,
		hpiEventSeverity,
		hpiEventTimeStamp
	}
	::= { hpiHotSwapEventTable 1 }

HpiHotSwapEventEntry ::= SEQUENCE {
	hpiHotSwapEventState          SaHpiHotSwapState,
	hpiHotSwapEventPreviousState  SaHpiHotSwapState
	}

hpiHotSwapEventState 	OBJECT-TYPE
	SYNTAX SaHpiHotSwapState
	ACCESS read-only
	STATUS mandatory
	DESCRIPTION
		"Refer to the textual convention for full details."
	::= { hpiHotSwapEventEntry 1 }

hpiHotSwapEventPreviousState 	OBJECT-TYPE
	SYNTAX SaHpiHotSwapState
	ACCESS read-only
	STATUS mandatory
	DESCRIPTION
		"Refer to the textual convention for full details."
	::= { hpiHotSwapEventEntry 2 }

hpiWatchdogEventEntryCount 	OBJECT-TYPE
	SYNTAX Counter
	ACCESS read-only
	STATUS mandatory
	DESCRIPTION
		"This columnar node represents the subset of events that
		 are Watchdog Events."
	::= { events 21 }

hpiWatchdogEventTable 	OBJECT-TYPE
	SYNTAX SEQUENCE OF HpiWatchdogEventEntry
	ACCESS not-accessible
	STATUS mandatory
	DESCRIPTION
		"Event table. "
	::= { events 22 }

hpiWatchdogEventEntry 	OBJECT-TYPE
	SYNTAX HpiWatchdogEventEntry
	ACCESS not-accessible
	STATUS mandatory
	DESCRIPTION
		"Watchdog events."
	INDEX {
		hpiDomainId,
		hpiResourceId,
		hpiEventSeverity,
		hpiEventTimeStamp
	}
	::= { hpiWatchdogEventTable 1 }

HpiWatchdogEventEntry ::= SEQUENCE {
	hpiWatchdogEventNum             Gauge,
	hpiWatchdogEventAction          INTEGER,
	hpiWatchdogEventPreTimerAction  SaHpiWatchdogPreTimerAction,
	hpiWatchdogEventUse             SaHpiWatchdogTimerUse
	}

hpiWatchdogEventNum 	OBJECT-TYPE
	SYNTAX Gauge
	ACCESS read-only
	STATUS mandatory
	DESCRIPTION
		""
	::= { hpiWatchdogEventEntry 1 }

hpiWatchdogEventAction 	OBJECT-TYPE
	SYNTAX INTEGER {
                               undefined (0),
                               noAction (1),
                               reset (2),
                               powerDown (3),
                               powerCycle (4),
                               timerInt (9)
                        }
	ACCESS read-only
	STATUS mandatory
	DESCRIPTION
		"These enumerations represent the possible actions to be taken
		 upon watchdog timer timeout and the events that are generated
		 for watchdog actions. "
	::= { hpiWatchdogEventEntry 2 }

hpiWatchdogEventPreTimerAction 	OBJECT-TYPE
	SYNTAX SaHpiWatchdogPreTimerAction
	ACCESS read-only
	STATUS mandatory
	DESCRIPTION
		"These enumerations represent the possible types of interrupts that may be
		 triggered by a watchdog pre-timer event. The actual meaning of these
		 operations may differ depending on the hardware architecture. "
	::= { hpiWatchdogEventEntry 3 }

hpiWatchdogEventUse 	OBJECT-TYPE
	SYNTAX SaHpiWatchdogTimerUse
	ACCESS read-only
	STATUS mandatory
	DESCRIPTION
		"Watchdog Timer Use
		 These enumerations represent the possible watchdog users that may have caused
		 the watchdog to expire. For instance, if watchdog is being used during power
		 on self test (POST), and it expires, the SAHPI_WTU_BIOS_POST expiration type
		 will be set. Most specific uses for Watchdog timer by users of HPI should
		 indicate SAHPI_WTU_SMS_OS  if the use is to provide an OS-healthy heartbeat,
		 or SAHPI_WTU_OEM if it is used for some other purpose."
	::= { hpiWatchdogEventEntry 4 }

hpiSoftwareEventEntryCount 	OBJECT-TYPE
	SYNTAX Counter
	ACCESS read-only
	STATUS mandatory
	DESCRIPTION
		"This columnar node represents the subset of events that
		 are Software Events."
	::= { events 24 }

hpiSoftwareEventTable 	OBJECT-TYPE
	SYNTAX SEQUENCE OF HpiSoftwareEventEntry
	ACCESS not-accessible
	STATUS mandatory
	DESCRIPTION
		"Event table. "
	::= { events 25 }

hpiSoftwareEventEntry 	OBJECT-TYPE
	SYNTAX HpiSoftwareEventEntry
	ACCESS not-accessible
	STATUS mandatory
	DESCRIPTION
		"Software events."
	INDEX {
		hpiDomainId,
		hpiResourceId,
		hpiEventSeverity,
		hpiEventTimeStamp
	}
	::= { hpiSoftwareEventTable 1 }

HpiSoftwareEventEntry ::= SEQUENCE {
	hpiSoftwareEventManufacturerId  SaHpiManufacturerId,
	hpiSoftwareEventType            INTEGER,
	hpiSoftwareEventTextType        SaHpiTextType,
	hpiSoftwareEventTextLanguage    SaHpiTextLanguage,
	hpiSoftwareEventText            SaHpiText
	}

hpiSoftwareEventManufacturerId 	OBJECT-TYPE
	SYNTAX SaHpiManufacturerId
	ACCESS read-only
	STATUS mandatory
	DESCRIPTION
		"Refer to the textual convention for more details."
	::= { hpiSoftwareEventEntry 1 }

hpiSoftwareEventType 	OBJECT-TYPE
	SYNTAX INTEGER {
                               undefined (0),
                               audit (1),
                               startup (2),
                               other (3)
                        }
	ACCESS read-only
	STATUS mandatory
	DESCRIPTION
		"The following type defines the types of events that can be
		 reported  by the HPI software implementation.
		 Audit events report a discrepancy in the audit process.
		 Audits are typically performed by HA software to detect problems.
		 Audits may look for such things as corrupted data stores,
		 inconsistent RPT information, or improperly managed queues.
		 Startup events report a failure to start-up properly, or
		 inconsistencies in persisted data.
		 Note: Enumerated values are increased by one value compared to
		 SAI-HPI-B spec."
	::= { hpiSoftwareEventEntry 2 }

hpiSoftwareEventTextType 	OBJECT-TYPE
	SYNTAX SaHpiTextType
	ACCESS read-only
	STATUS mandatory
	DESCRIPTION
		"Refer to the textual convention for more details."
	::= { hpiSoftwareEventEntry 3 }

hpiSoftwareEventTextLanguage 	OBJECT-TYPE
	SYNTAX SaHpiTextLanguage
	ACCESS read-only
	STATUS mandatory
	DESCRIPTION
		"Refer to the textual convention for more details."
	::= { hpiSoftwareEventEntry 4 }

hpiSoftwareEventText 	OBJECT-TYPE
	SYNTAX SaHpiText
	ACCESS read-only
	STATUS mandatory
	DESCRIPTION
		"Refer to the textual convention for more details."
	::= { hpiSoftwareEventEntry 5 }

hpiOEMEventEntryCount 	OBJECT-TYPE
	SYNTAX Counter
	ACCESS read-only
	STATUS mandatory
	DESCRIPTION
		"This columnar node represents the subset of events that
		 are OEM Events."
	::= { events 27 }

hpiOEMEventTable 	OBJECT-TYPE
	SYNTAX SEQUENCE OF HpiOEMEventEntry
	ACCESS not-accessible
	STATUS mandatory
	DESCRIPTION
		"Event table. "
	::= { events 28 }

hpiOEMEventEntry 	OBJECT-TYPE
	SYNTAX HpiOEMEventEntry
	ACCESS not-accessible
	STATUS mandatory
	DESCRIPTION
		"OEM events."
	INDEX {
		hpiDomainId,
		hpiResourceId,
		hpiEventSeverity,
		hpiEventTimeStamp
	}
	::= { hpiOEMEventTable 1 }

HpiOEMEventEntry ::= SEQUENCE {
	hpiOEMEventManufacturerId  SaHpiManufacturerId,
	hpiOEMEventTextType        SaHpiTextType,
	hpiOEMEventTextLanguage    SaHpiTextLanguage,
	hpiOEMEventText            SaHpiText
	}

hpiOEMEventManufacturerId 	OBJECT-TYPE
	SYNTAX SaHpiManufacturerId
	ACCESS read-only
	STATUS mandatory
	DESCRIPTION
		"Refer to the textual convention for more details."
	::= { hpiOEMEventEntry 1 }

hpiOEMEventTextType 	OBJECT-TYPE
	SYNTAX SaHpiTextType
	ACCESS read-only
	STATUS mandatory
	DESCRIPTION
		"Refer to the textual convention for more details."
	::= { hpiOEMEventEntry 2 }

hpiOEMEventTextLanguage 	OBJECT-TYPE
	SYNTAX SaHpiTextLanguage
	ACCESS read-only
	STATUS mandatory
	DESCRIPTION
		"Refer to the textual convention for more details."
	::= { hpiOEMEventEntry 3 }

hpiOEMEventText 	OBJECT-TYPE
	SYNTAX SaHpiText
	ACCESS read-only
	STATUS mandatory
	DESCRIPTION
		"Refer to the textual convention for more details."
	::= { hpiOEMEventEntry 4 }

hpiUserEventEntryCount 	OBJECT-TYPE
	SYNTAX Counter
	ACCESS read-only
	STATUS mandatory
	DESCRIPTION
		"This columnar node represents the subset of events that
		 are User Events."
	::= { events 30 }

hpiUserEventTable 	OBJECT-TYPE
	SYNTAX SEQUENCE OF HpiUserEventEntry
	ACCESS not-accessible
	STATUS mandatory
	DESCRIPTION
		"Event table. "
	::= { events 31 }

hpiUserEventEntry 	OBJECT-TYPE
	SYNTAX HpiUserEventEntry
	ACCESS not-accessible
	STATUS mandatory
	DESCRIPTION
		"User events."
	INDEX {
		hpiDomainId,
		hpiResourceId,
		hpiEventSeverity,
		hpiEventTimeStamp
	}
	::= { hpiUserEventTable 1 }

HpiUserEventEntry ::= SEQUENCE {
	hpiUserEventTextType      SaHpiTextType,
	hpiUserEventTextLanguage  SaHpiTextLanguage,
	hpiUserEventText          SaHpiText,
	hpiUserEventRowStatus     RowStatus
	}

hpiUserEventTextType 	OBJECT-TYPE
	SYNTAX SaHpiTextType
	ACCESS read-write
	STATUS mandatory
	DESCRIPTION
		"Refer to SaHpiTextType for more details."
	::= { hpiUserEventEntry 1 }

hpiUserEventTextLanguage 	OBJECT-TYPE
	SYNTAX SaHpiTextLanguage
	ACCESS read-write
	STATUS mandatory
	DESCRIPTION
		"Refer to hpiTextLanguage for more details."
	::= { hpiUserEventEntry 2 }

hpiUserEventText 	OBJECT-TYPE
	SYNTAX SaHpiText
	ACCESS read-write
	STATUS mandatory
	DESCRIPTION
		"Refer to hpiText for more details. "
	::= { hpiUserEventEntry 3 }

hpiUserEventRowStatus 	OBJECT-TYPE
	SYNTAX RowStatus
	ACCESS read-write
	STATUS mandatory
	DESCRIPTION
		"This columnar node contains the status of the row and also
		 perform add and delete operations.
		 
		 The status column uses four defined values:
		 
		 - `active(1)', which indicates that the conceptual row is
		 available for use by the managed device;
		 
		 - `createAndGo(4)', which is supplied by a management
		 station wishing to create a new instance of a
		 conceptual row (but not make it available for use by
		 the managed device). This function is used to add a
		 User Alarm  to this User Event Table and also to the
		 to the Domain Alarm Table; When creating this row,
		 the value of hpiEventSeverity indice must not be one of
		 these minor(3), major(2), and critical(3). The effect of
		 creating a new row will also be reflected in the DAT - with
		 a new row there.
		 
		 - `destroy(6)', which is supplied by a management station
		 wishing to delete all of the instances associated with
		 an existing conceptual row. This function allows the
		 HPI MIB User to delete a single User Alarm from the
		 User Event Table and Domain Alarm Table.
		 Only User Alarms added to the DAT and User Event Table can
		 be deleted. To delete a single, specific alarm, set the
		 hpiDomainAlarmId parameter to a value representing an
		 actual User Alarm in the User Event Table."
	::= { hpiUserEventEntry 4 }

hpiAnnouncementEntryCount 	OBJECT-TYPE
	SYNTAX Counter
	ACCESS read-only
	STATUS mandatory
	DESCRIPTION
		"The number of announcements present on this system."
	::= { events 33 }

hpiAnnouncementTable 	OBJECT-TYPE
	SYNTAX SEQUENCE OF HpiAnnouncementEntry
	ACCESS not-accessible
	STATUS mandatory
	DESCRIPTION
		"Table of Announcements."
	::= { events 34 }

hpiAnnouncementEntry 	OBJECT-TYPE
	SYNTAX HpiAnnouncementEntry
	ACCESS not-accessible
	STATUS mandatory
	DESCRIPTION
		"The table of announcements is used to provide
		 a common interface to varied mechanisms for announcing conditions.
		 Each announcement in an Annunciator's current set contains a severity level,
		 details describing the specific condition that is being reported, an
		 Acknowledged flag, a timestamp indicating when the announcement was added
		 to the set, and an EntryId that uniquely identifies the particular status
		 item within the set.
		 EntryIds are assigned to announcements as they are added to the set as well
		 as a Timestamp.  After an announcement is deleted from the current set, its
		 EntryId may be reused for a newly added announcement as long as the new
		 announcement will have a different timestamp than any previously deleted
		 announcement using the same EntryId.  Thus, the EntryId and Timestamp
		 together will uniquely identify any announcement, which was ever present
		 in the Annunciator's set.
		 
		 The actual meaning of the Acknowledged flag is arbitrary, and the actions
		 taken by the platform when announcements are flagged as 'acknowledged' or
		 'unacknowledged' are implementation-specific.  The intended use of the flag
		 is to indicate whether a particular announcement in the current set has been
		 recognized by whomever or whatever is inspecting the LEDs, displays, etc.,
		 that are being driven by the Annunciator management instrument.  Thus, when
		 announcements are added to the current set, generally the flag should be set
		 to indicate that the condition is 'unacknowledged'.  Later, either as the
		 result of an HPI User function call, or due to some implementation-dependent
		 action (such as pressing an 'acknowledge' button on a front-panel display),
		 the flag can be changed to indicate that the announcement is now 'acknowledged.'
		 
		 The ability to acknowledge announcements is not controlled by the Annunciator
		 'mode' setting (Auto, User, or Shared).  Any announcement may be acknowledged
		 by the HPI implementation, or via the hpiAnnunciatorAcknowledge() function
		 call, regardless of the current mode setting for the Annunciator.
		 
		 Over time, announcements are added to and deleted from an Annunciator`s
		 current set of announcements. This may be done automatically by the HPI
		 implementation to reflect platform fault conditions, or by the HPI User
		 via the HPI interface.  When announcements are added or deleted automatically
		 by the HPI implementation, it is implementation-specific which announcements
		 are added or removed.
		 "
	INDEX {
		hpiDomainId,
		hpiResourceId,
		hpiEventSeverity,
		hpiEventTimeStamp
	}
	::= { hpiAnnouncementTable 1 }

HpiAnnouncementEntry ::= SEQUENCE {
	hpiAnnouncementEntryId         SaHpiEntryId,
	hpiAnnouncementTimestamp       SaHpiTime,
	hpiAnnouncementAddedByUser     TruthValue,
	hpiAnnouncementSeverity        INTEGER,
	hpiAnnouncementAcknowledged    TruthValue,
	hpiAnnouncementStatusCondType  INTEGER,
	hpiAnnouncementEntityPath      OCTET STRING,
	hpiAnnouncementSensorNum       Gauge,
	hpiAnnouncementEventState      SaHpiEventState,
	hpiAnnouncementName            OCTET STRING,
	hpiAnnouncementMid             SaHpiManufacturerId,
	hpiAnnouncementTextType        SaHpiTextType,
	hpiAnnouncementTextLanguage    SaHpiTextLanguage,
	hpiAnnouncementText            SaHpiText,
	hpiAnnouncementDelete          RowStatus
	}

hpiAnnouncementEntryId 	OBJECT-TYPE
	SYNTAX SaHpiEntryId
	ACCESS not-accessible
	STATUS mandatory
	DESCRIPTION
		"Entry ID for record
		 Table Related Type Definitions
		 SAHPI_FIRST_ENTRY 0x00000000
		 SAHPI_LAST_ENTRY  0xFFFFFFFF"
	::= { hpiAnnouncementEntry 1 }

hpiAnnouncementTimestamp 	OBJECT-TYPE
	SYNTAX SaHpiTime
	ACCESS read-only
	STATUS mandatory
	DESCRIPTION
		"Time when announcement added to set."
	::= { hpiAnnouncementEntry 2 }

hpiAnnouncementAddedByUser 	OBJECT-TYPE
	SYNTAX TruthValue
	ACCESS read-only
	STATUS mandatory
	DESCRIPTION
		"True if added to set by HPI User, False if added
		 automatically by HPI implementation."
	::= { hpiAnnouncementEntry 3 }

hpiAnnouncementSeverity 	OBJECT-TYPE
	SYNTAX INTEGER {
                               undefined (0),
                               critical (1),
                               major (2),
                               minor (3),
                               informational (4),
                               ok (5),
                               debug (241),
                               allSeverities (256)
                        }
	ACCESS read-write
	STATUS mandatory
	DESCRIPTION
		"Only used with DAT and Annunciator functions.
		 This is not a valid severity for events or alarms."
	::= { hpiAnnouncementEntry 4 }

hpiAnnouncementAcknowledged 	OBJECT-TYPE
	SYNTAX TruthValue
	ACCESS read-write
	STATUS mandatory
	DESCRIPTION
		"Acknowledged flag."
	::= { hpiAnnouncementEntry 5 }

hpiAnnouncementStatusCondType 	OBJECT-TYPE
	SYNTAX INTEGER {
                               undefined (0),
                               sensor (1),
                               resource (2),
                               oem (3),
                               user (4)
                        }
	ACCESS read-write
	STATUS mandatory
	DESCRIPTION
		"Status Condition Type."
	::= { hpiAnnouncementEntry 6 }

hpiAnnouncementEntityPath 	OBJECT-TYPE
	SYNTAX OCTET STRING
	ACCESS read-write
	STATUS mandatory
	DESCRIPTION
		"Entity assoc. with status condition.
		 
		 This object converts HPI's hpiEntityPathT structure
		 and an OpenHPI canonical string. The canonical string is
		 formed by removing the SAHPI_ENT_ prefix from the
		 HPI types, and creating tuples for the entity types. 
		 
		 Order of significance is inverted to make entity paths
		 look more like Unix directory structure. It is also assumed
		 that {ROOT,0} exists implicitly before all of these entries. 
		 
		 For example:
		  {SYSTEM_CHASSIS,2}{PROCESSOR_BOARD,0} "
	::= { hpiAnnouncementEntry 7 }

hpiAnnouncementSensorNum 	OBJECT-TYPE
	SYNTAX Gauge
	ACCESS read-write
	STATUS mandatory
	DESCRIPTION
		"Sensor associated with status Only valid
		 if Type is SAHPI_STATUS_COND_TYPE_SENSOR."
	::= { hpiAnnouncementEntry 8 }

hpiAnnouncementEventState 	OBJECT-TYPE
	SYNTAX SaHpiEventState
	ACCESS read-write
	STATUS mandatory
	DESCRIPTION
		"Sensor event state. Only valid if Type is
		 SAHPI_STATUS_COND_TYPE_SENSOR.."
	::= { hpiAnnouncementEntry 9 }

hpiAnnouncementName 	OBJECT-TYPE
	SYNTAX OCTET STRING
	ACCESS read-write
	STATUS mandatory
	DESCRIPTION
		"AIS compatible identifier associated with Status condition."
	::= { hpiAnnouncementEntry 10 }

hpiAnnouncementMid 	OBJECT-TYPE
	SYNTAX SaHpiManufacturerId
	ACCESS read-write
	STATUS mandatory
	DESCRIPTION
		"Manufacturer Id associated with status condition,
		 required when type is SAHPI_STATUS_COND_TYPE_OEM."
	::= { hpiAnnouncementEntry 11 }

hpiAnnouncementTextType 	OBJECT-TYPE
	SYNTAX SaHpiTextType
	ACCESS read-write
	STATUS mandatory
	DESCRIPTION
		"Field Data.
		 See Definition for SaHpiTextType for more details."
	::= { hpiAnnouncementEntry 12 }

hpiAnnouncementTextLanguage 	OBJECT-TYPE
	SYNTAX SaHpiTextLanguage
	ACCESS read-write
	STATUS mandatory
	DESCRIPTION
		"Field Data.
		 See Definition for SaHpiTextLanguage for more details."
	::= { hpiAnnouncementEntry 13 }

hpiAnnouncementText 	OBJECT-TYPE
	SYNTAX SaHpiText
	ACCESS read-write
	STATUS mandatory
	DESCRIPTION
		"Field Data.
		 The type of date is specified
		 by hpiResourceTagTextType and hpiResourceTagLanguage."
	::= { hpiAnnouncementEntry 14 }

hpiAnnouncementDelete 	OBJECT-TYPE
	SYNTAX RowStatus
	ACCESS read-write
	STATUS mandatory
	DESCRIPTION
		"This function allows the HPI User to delete a single
		 announcement. Announcements may be deleted individually by specifying
		 a specific index and setting this columnar node to destroy(6).
		 "
	::= { hpiAnnouncementEntry 15 }

eventLog OBJECT IDENTIFIER ::= {hpiEvents 2}

hpiEventLogInfoTable 	OBJECT-TYPE
	SYNTAX SEQUENCE OF HpiEventLogInfoEntry
	ACCESS not-accessible
	STATUS mandatory
	DESCRIPTION
		"A table definining Event Log Information records."
	::= { eventLog 1 }

hpiEventLogInfoEntry 	OBJECT-TYPE
	SYNTAX HpiEventLogInfoEntry
	ACCESS not-accessible
	STATUS mandatory
	DESCRIPTION
		"Each resource has a Event Log Information record, which contains
		 per resource pertient logging information.
		 --FSC-DR
		 Use hpiResourceId = 0 (SAHPI_UNSPECIFIED_RESOURCE_ID)
		 to address the Domain Event Log."
	INDEX {
		hpiDomainId,
		hpiResourceId
	}
	::= { hpiEventLogInfoTable 1 }

HpiEventLogInfoEntry ::= SEQUENCE {
	hpiEventLogInfoEntries            Gauge,
	hpiEventLogInfoSize               Gauge,
	hpiEventLogInfoUserEventMaxSize   Gauge,
	hpiEventLogInfoUpdateTimestamp    SaHpiTime,
	hpiEventLogInfoTime               SaHpiTime,
	hpiEventLogInfoEnabled            TruthValue,
	hpiEventLogInfoOverflowFlag       TruthValue,
	hpiEventLogInfoOverflowResetable  TruthValue,
	hpiEventLogInfoOverflowAction     INTEGER,
	hpiEventLogInfoClearLog           INTEGER
	}

hpiEventLogInfoEntries 	OBJECT-TYPE
	SYNTAX Gauge
	ACCESS read-only
	STATUS mandatory
	DESCRIPTION
		"The number of active entries contained in the log."
	::= { hpiEventLogInfoEntry 1 }

hpiEventLogInfoSize 	OBJECT-TYPE
	SYNTAX Gauge
	ACCESS read-only
	STATUS mandatory
	DESCRIPTION
		"The total number of entries the log is able to hold."
	::= { hpiEventLogInfoEntry 2 }

hpiEventLogInfoUserEventMaxSize 	OBJECT-TYPE
	SYNTAX Gauge
	ACCESS read-only
	STATUS mandatory
	DESCRIPTION
		"The UserEventMaxSize entry indicates the maximum size of the
		 text buffer data field in an HPI User event that is supported
		 by the Event Log implementation.  If the implementation does
		 not enforce a more restrictive data length, it should be set
		 to SAHPI_MAX_TEXT_BUFFER_LENGTH (255)."
	::= { hpiEventLogInfoEntry 3 }

hpiEventLogInfoUpdateTimestamp 	OBJECT-TYPE
	SYNTAX SaHpiTime
	ACCESS read-only
	STATUS mandatory
	DESCRIPTION
		"The UpdateTimestamp entry denotes the time of the last
		 update to the Event Log.
		 Refer to SaHpiTime for full description."
	::= { hpiEventLogInfoEntry 4 }

hpiEventLogInfoTime 	OBJECT-TYPE
	SYNTAX SaHpiTime
	ACCESS read-write
	STATUS mandatory
	DESCRIPTION
		"The Time entry denotes the Event Log's idea of the
		 current time; i.e the timestamp that would be placed on an
		 entry if it was added now.
		 
		 Remarks:
		 
		 Entries placed in the Event Log after this function is called will 
		 have Event Log timestamps (i.e., the Timestamp field in the 
		 SaHpiEventLogEntryT structure) based on the new time.  Setting 
		 the clock does not affect existing Event Log entries.  If the time
		 is set to a relative time, subsequent entries placed in the Event Log 
		 will have an Event Log timestamp expressed as a relative time; if the 
		 time is set to an absolute time, subsequent entries will have an Event 
		 Log timestamp expressed as an absolute time.
		 
		 This function only sets the Event Log time clock and does not have any 
		 direct bearing on the timestamps placed on events (i.e., the Timestamp 
		 field in the SaHpiEventT structure), or the timestamps placed in the
		 domain RPT info record.  Setting the clocks used to generate timestamps 
		 other than Event Log timestamps is implementation-dependent, and should 
		 be documented by the HPI implementation provider.
		 
		 Some underlying implementations may not be able to handle the same 
		 relative and absolute time ranges, as those defined in HPI.  Such 
		 limitations will be documented in implementation-specific documentation.  
		 When a time value is set in a region that is not supported by the
		 implementation, an error code of SNMP_GENERROR  will be returned.
		 
		 Refer to SaHpiTime for full description."
	::= { hpiEventLogInfoEntry 5 }

hpiEventLogInfoEnabled 	OBJECT-TYPE
	SYNTAX TruthValue
	ACCESS read-write
	STATUS mandatory
	DESCRIPTION
		"The Enabled entry indicates whether the log is enabled.
		 If the event log is 'disabled' no events generated within the
		 HPI implementation will be added to the event log.
		 
		 User events may still be added to the event log.
		 
		 When the event log is 'enabled' events may be automatically
		 added to the event log as they are generated in a resource
		 or a domain, however, it is implementation-specific which
		 events are automatically added to any event log.  "
	::= { hpiEventLogInfoEntry 6 }

hpiEventLogInfoOverflowFlag 	OBJECT-TYPE
	SYNTAX TruthValue
	ACCESS read-write
	STATUS mandatory
	DESCRIPTION
		"The OverflowFlag entry indicates the log has overflowed.
		 Events have been dropped or overwritten due to a table overflow."
	::= { hpiEventLogInfoEntry 7 }

hpiEventLogInfoOverflowResetable 	OBJECT-TYPE
	SYNTAX TruthValue
	ACCESS read-only
	STATUS mandatory
	DESCRIPTION
		"Indicates if the the overflow falg can be cleared
		 by calling hpiEventLogInfoOverflowReset."
	::= { hpiEventLogInfoEntry 8 }

hpiEventLogInfoOverflowAction 	OBJECT-TYPE
	SYNTAX INTEGER {
                               undefined (0),
                               drop (1),
                               overwrite (2)
                        }
	ACCESS read-only
	STATUS mandatory
	DESCRIPTION
		"The OverflowAction entry indicates the behavior of the
		 event log when an overflow occurs.
		 drop(1) New entries are dropped when log is full
		 overwrite(2) Event Log overwrites existing entries when Event Log
		 is full"
	::= { hpiEventLogInfoEntry 9 }

hpiEventLogInfoClearLog 	OBJECT-TYPE
	SYNTAX INTEGER {
                               undefined (0),
                               clearLog (1)
                        }
	ACCESS read-write
	STATUS mandatory
	DESCRIPTION
		"This function erases the contents of the specified Event Log."
	::= { hpiEventLogInfoEntry 10 }

hpiEventLogEntryCount 	OBJECT-TYPE
	SYNTAX Counter
	ACCESS read-only
	STATUS mandatory
	DESCRIPTION
		"A table definining Event Log records."
	::= { eventLog 4 }

hpiEventLogTable 	OBJECT-TYPE
	SYNTAX SEQUENCE OF HpiEventLogEntry
	ACCESS not-accessible
	STATUS mandatory
	DESCRIPTION
		"A table definining Event Log records."
	::= { eventLog 5 }

hpiEventLogEntry 	OBJECT-TYPE
	SYNTAX HpiEventLogEntry
	ACCESS not-accessible
	STATUS mandatory
	DESCRIPTION
		"This section defines the types associated with the SEL."
	INDEX {
		hpiDomainId,
		hpiResourceId,
		hpiEventLogSeverity,
		hpiEventLogAddedTimestamp
	}
	::= { hpiEventLogTable 1 }

HpiEventLogEntry ::= SEQUENCE {
	hpiEventLogSeverity        INTEGER,
	hpiEventLogAddedTimestamp  SaHpiTime,
	hpiEventLogSource          INTEGER,
	hpiEventLogTime            OCTET STRING,
	hpiEventLogType            INTEGER
	}

hpiEventLogSeverity 	OBJECT-TYPE
	SYNTAX INTEGER {
                               undefined (0),
                               critical (1),
                               major (2),
                               minor (3),
                               informational (4),
                               ok (5),
                               debug (241)
                        }
	ACCESS read-only
	STATUS mandatory
	DESCRIPTION
		"Severity of event.
		 Note: Enumerated values are increased by one value compared to
		 SAI-HPI-B spec."
	::= { hpiEventLogEntry 1 }

hpiEventLogAddedTimestamp 	OBJECT-TYPE
	SYNTAX SaHpiTime
	ACCESS read-only
	STATUS mandatory
	DESCRIPTION
		"Refer to SaHpiTime for full description."
	::= { hpiEventLogEntry 2 }

hpiEventLogSource 	OBJECT-TYPE
	SYNTAX INTEGER {
                               unspecified (-1)
                        }
	ACCESS read-only
	STATUS mandatory
	DESCRIPTION
		""
	::= { hpiEventLogEntry 3 }

hpiEventLogTime 	OBJECT-TYPE
	SYNTAX OCTET STRING
	ACCESS read-only
	STATUS mandatory
	DESCRIPTION
		"Refer to SaHpiTime for full description."
	::= { hpiEventLogEntry 4 }

hpiEventLogType 	OBJECT-TYPE
	SYNTAX INTEGER {
                               undefined (0),
                               resource (1),
                               domain (2),
                               sensor (3),
                               sensorEnableChange (4),
                               hotswap (5),
                               watchdog (6),
                               hpiSoftware (7),
                               oem (8),
                               user (9)
                        }
	ACCESS read-only
	STATUS mandatory
	DESCRIPTION
		"The type of event.
		 Note: The enumerated named have +1 added as opposed to the
		 SA HPI  spec for the same constants."
	::= { hpiEventLogEntry 5 }

hpiResourceEventLogEntryCount 	OBJECT-TYPE
	SYNTAX Counter
	ACCESS read-only
	STATUS mandatory
	DESCRIPTION
		"This columnar node represents the subset of events that
		 are Resource Events."
	::= { eventLog 6 }

hpiResourceEventLogTable 	OBJECT-TYPE
	SYNTAX SEQUENCE OF HpiResourceEventLogEntry
	ACCESS not-accessible
	STATUS mandatory
	DESCRIPTION
		"Event table. "
	::= { eventLog 7 }

hpiResourceEventLogEntry 	OBJECT-TYPE
	SYNTAX HpiResourceEventLogEntry
	ACCESS not-accessible
	STATUS mandatory
	DESCRIPTION
		"Resource events."
	INDEX {
		hpiDomainId,
		hpiResourceId,
		hpiEventLogSeverity,
		hpiEventLogAddedTimestamp
	}
	::= { hpiResourceEventLogTable 1 }

HpiResourceEventLogEntry ::= SEQUENCE {
	hpiResourceEventLogType  INTEGER
	}

hpiResourceEventLogType 	OBJECT-TYPE
	SYNTAX INTEGER {
                               undefined (0),
                               resourceFailure (1),
                               resourceRestored (2),
                               resourceAdded (3)
                        }
	ACCESS read-only
	STATUS mandatory
	DESCRIPTION
		"Resource events are sent to indicate the failure or
		 subsequent restoration of a resource.  Resource events can also be
		 used to announce the addition of a non-FRU resource to the RPT table.
		 Note: Enumerated values are increased by one value compared to
		 SAI-HPI-B spec."
	::= { hpiResourceEventLogEntry 1 }

hpiDomainEventLogEntryCount 	OBJECT-TYPE
	SYNTAX Counter
	ACCESS read-only
	STATUS mandatory
	DESCRIPTION
		"hpiDomainEventEntryCount represents the subset of events
		 that are Domain events."
	::= { eventLog 8 }

hpiDomainEventLogTable 	OBJECT-TYPE
	SYNTAX SEQUENCE OF HpiDomainEventLogEntry
	ACCESS not-accessible
	STATUS mandatory
	DESCRIPTION
		"Event table. "
	::= { eventLog 9 }

hpiDomainEventLogEntry 	OBJECT-TYPE
	SYNTAX HpiDomainEventLogEntry
	ACCESS not-accessible
	STATUS mandatory
	DESCRIPTION
		"Domain events."
	INDEX {
		hpiDomainId,
		hpiResourceId,
		hpiEventLogSeverity,
		hpiEventLogAddedTimestamp
	}
	::= { hpiDomainEventLogTable 1 }

HpiDomainEventLogEntry ::= SEQUENCE {
	hpiDomainEventLogType    INTEGER,
	hpiDomainEventLogDomain  Gauge
	}

hpiDomainEventLogType 	OBJECT-TYPE
	SYNTAX INTEGER {
                               undefined (0),
                               domainRefAdded (1),
                               domainRefRemoved (2)
                        }
	ACCESS read-only
	STATUS mandatory
	DESCRIPTION
		"Domain events are used to announce the addition of domain
		 references and the removal of domain references to the DRT."
	::= { hpiDomainEventLogEntry 1 }

hpiDomainEventLogDomain 	OBJECT-TYPE
	SYNTAX Gauge
	ACCESS read-only
	STATUS mandatory
	DESCRIPTION
		"Domain Id of domain added to or removed from DRT."
	::= { hpiDomainEventLogEntry 2 }

hpiSensorEventLogEntryCount 	OBJECT-TYPE
	SYNTAX Counter
	ACCESS read-only
	STATUS mandatory
	DESCRIPTION
		"This columnar node represents the subset of events that
		 are Sensor Events."
	::= { eventLog 10 }

hpiSensorEventLogTable 	OBJECT-TYPE
	SYNTAX SEQUENCE OF HpiSensorEventLogEntry
	ACCESS not-accessible
	STATUS mandatory
	DESCRIPTION
		"Event table. "
	::= { eventLog 11 }

hpiSensorEventLogEntry 	OBJECT-TYPE
	SYNTAX HpiSensorEventLogEntry
	ACCESS not-accessible
	STATUS mandatory
	DESCRIPTION
		"Sensor events."
	INDEX {
		hpiDomainId,
		hpiResourceId,
		hpiEventLogSeverity,
		hpiEventLogAddedTimestamp
	}
	::= { hpiSensorEventLogTable 1 }

HpiSensorEventLogEntry ::= SEQUENCE {
	hpiSensorEventLogNum                   Gauge,
	hpiSensorEventLogType                  SaHpiSensorType,
	hpiSensorEventLogCategory              SaHpiEventCategory,
	hpiSensorEventLogAssertion             TruthValue,
	hpiSensorEventLogState                 SaHpiEventState,
	hpiSensorEventLogOptionalData          OCTET STRING,
	hpiSensorEventLogTriggerReadingType    SaHpiSensorReadingType,
	hpiSensorEventLogTriggerReading        SaHpiSensorReadingValue,
	hpiSensorEventLogTriggerThresholdType  SaHpiSensorReadingType,
	hpiSensorEventLogTriggerThreshold      SaHpiSensorReadingValue,
	hpiSensorEventLogPreviousState         SaHpiEventState,
	hpiSensorEventLogCurrentState          SaHpiEventState,
	hpiSensorEventLogOem                   Gauge,
	hpiSensorEventLogSpecific              Gauge
	}

hpiSensorEventLogNum 	OBJECT-TYPE
	SYNTAX Gauge
	ACCESS read-only
	STATUS mandatory
	DESCRIPTION
		""
	::= { hpiSensorEventLogEntry 1 }

hpiSensorEventLogType 	OBJECT-TYPE
	SYNTAX SaHpiSensorType
	ACCESS read-only
	STATUS mandatory
	DESCRIPTION
		"Refer to the textual convention for more
		 details."
	::= { hpiSensorEventLogEntry 2 }

hpiSensorEventLogCategory 	OBJECT-TYPE
	SYNTAX SaHpiEventCategory
	ACCESS read-only
	STATUS mandatory
	DESCRIPTION
		"Event category: See TEXTUAL-CONVENTION, SaHpiEventCategory."
	::= { hpiSensorEventLogEntry 3 }

hpiSensorEventLogAssertion 	OBJECT-TYPE
	SYNTAX TruthValue
	ACCESS read-only
	STATUS mandatory
	DESCRIPTION
		"Sensor Events and Sensor Event States:
		 Each Event State may be asserted or deasserted.  The set of Event
		 States a sensor may support is defined by the sensor's
		 'Event Category.'  A particular sensor, however, does not have to
		 support all the Event States defined for its event category.
		 The specific Event States that a particular sensor supports are
		 indicated in the 'Events' field in the sensor's RDR. A sensor is
		 not required to support any Event States. If no Event States are
		 supported by a sensor, the 'Events' field will be 0x0000.  A sensor
		 may not support any Event States that are not defined for its event
		 category. Each Event State is independent, although in some event
		 categories the meaning assigned to the Event States will imply that
		 certain Event States will be mutually exclusive.  For example, a
		 sensor that uses the SAHPI_EC_LIMIT event category should only have
		 one of the two Event States, SAHPI_ES_LIMIT_NOT_EXCEEDED or
		 SAHPI_ES_LIMIT_EXCEEDED asserted at any one time. Except where mutual
		 exclusion is implied, however, sensors may have multiple Event States
		 asserted simultaneously. For example, the event category
		 SAHPI_EC_THRESHOLD uses six different event states to report the
		 relationship between the value currently measured by the sensor and up
		 to six different 'threshold' values.  Each threshold is independently
		 examined, and each Event State that represents a threshold that has
		 been 'crossed' will be asserted.  Threshold values must be configured
		 so that 'Minor', 'Major' and 'Critical' thresholds are increasingly
		 extreme readings, such that when a 'Major' threshold has been crossed,
		 the corresponding 'Minor' threshold will also have been crossed, and
		 thus both Event States will be asserted. When a sensor Event State is
		 asserted or deasserted, an event may be generated by the resource.
		 The generated event identifies the sensor and the event state
		 being asserted or deasserted.  The HPI implementation may assign event
		 severity levels for each event state assertion or deassertion on an
		 individual sensor basis."
	::= { hpiSensorEventLogEntry 4 }

hpiSensorEventLogState 	OBJECT-TYPE
	SYNTAX SaHpiEventState
	ACCESS read-only
	STATUS mandatory
	DESCRIPTION
		"Refer to the textual convention for more details."
	::= { hpiSensorEventLogEntry 5 }

hpiSensorEventLogOptionalData 	OBJECT-TYPE
	SYNTAX OCTET STRING
	ACCESS read-only
	STATUS mandatory
	DESCRIPTION
		""
	::= { hpiSensorEventLogEntry 6 }

hpiSensorEventLogTriggerReadingType 	OBJECT-TYPE
	SYNTAX SaHpiSensorReadingType
	ACCESS read-only
	STATUS mandatory
	DESCRIPTION
		"Refer to the textual convention for more details."
	::= { hpiSensorEventLogEntry 7 }

hpiSensorEventLogTriggerReading 	OBJECT-TYPE
	SYNTAX SaHpiSensorReadingValue
	ACCESS read-only
	STATUS mandatory
	DESCRIPTION
		"Refer to the textual convention for more details."
	::= { hpiSensorEventLogEntry 8 }

hpiSensorEventLogTriggerThresholdType 	OBJECT-TYPE
	SYNTAX SaHpiSensorReadingType
	ACCESS read-only
	STATUS mandatory
	DESCRIPTION
		"Refer to the textual convention for more details."
	::= { hpiSensorEventLogEntry 9 }

hpiSensorEventLogTriggerThreshold 	OBJECT-TYPE
	SYNTAX SaHpiSensorReadingValue
	ACCESS read-only
	STATUS mandatory
	DESCRIPTION
		"Refer to the textual convention for more details."
	::= { hpiSensorEventLogEntry 10 }

hpiSensorEventLogPreviousState 	OBJECT-TYPE
	SYNTAX SaHpiEventState
	ACCESS read-only
	STATUS mandatory
	DESCRIPTION
		"Refer to the textual convention for more details."
	::= { hpiSensorEventLogEntry 11 }

hpiSensorEventLogCurrentState 	OBJECT-TYPE
	SYNTAX SaHpiEventState
	ACCESS read-only
	STATUS mandatory
	DESCRIPTION
		"Refer to SaHpiEventState textual convention for more details."
	::= { hpiSensorEventLogEntry 12 }

hpiSensorEventLogOem 	OBJECT-TYPE
	SYNTAX Gauge
	ACCESS read-only
	STATUS mandatory
	DESCRIPTION
		"Reserved for OEM use."
	::= { hpiSensorEventLogEntry 13 }

hpiSensorEventLogSpecific 	OBJECT-TYPE
	SYNTAX Gauge
	ACCESS read-only
	STATUS mandatory
	DESCRIPTION
		""
	::= { hpiSensorEventLogEntry 14 }

hpiSensorEnableChangeEventLogEntryCount 	OBJECT-TYPE
	SYNTAX Counter
	ACCESS read-only
	STATUS mandatory
	DESCRIPTION
		"This columnar node represents the subset of events that
		 are Sensor Enable ChangeEvents."
	::= { eventLog 12 }

hpiSensorEnableChangeEventLogTable 	OBJECT-TYPE
	SYNTAX SEQUENCE OF HpiSensorEnableChangeEventLogEntry
	ACCESS not-accessible
	STATUS mandatory
	DESCRIPTION
		"Event table. "
	::= { eventLog 13 }

hpiSensorEnableChangeEventLogEntry 	OBJECT-TYPE
	SYNTAX HpiSensorEnableChangeEventLogEntry
	ACCESS not-accessible
	STATUS mandatory
	DESCRIPTION
		"Sensor Enable Change events."
	INDEX {
		hpiDomainId,
		hpiResourceId,
		hpiEventLogSeverity,
		hpiEventLogAddedTimestamp
	}
	::= { hpiSensorEnableChangeEventLogTable 1 }

HpiSensorEnableChangeEventLogEntry ::= SEQUENCE {
	hpiSensorEnableChangeEventLogNum             Gauge,
	hpiSensorEnableChangeEventLogType            SaHpiSensorType,
	hpiSensorEnableChangeEventLogCategory        SaHpiEventCategory,
	hpiSensorEnableChangeEventLogEnabled         TruthValue,
	hpiSensorEnableChangeEventLogEventsEnabled   TruthValue,
	hpiSensorEnableChangeEventLogAssertEvents    SaHpiEventState,
	hpiSensorEnableChangeEventLogDeassertEvents  SaHpiEventState,
	hpiSensorEnableChangeEventLogOptionalData    OCTET STRING,
	hpiSensorEnableChangeEventLogCurrentState    SaHpiEventState
	}

hpiSensorEnableChangeEventLogNum 	OBJECT-TYPE
	SYNTAX Gauge
	ACCESS read-only
	STATUS mandatory
	DESCRIPTION
		""
	::= { hpiSensorEnableChangeEventLogEntry 1 }

hpiSensorEnableChangeEventLogType 	OBJECT-TYPE
	SYNTAX SaHpiSensorType
	ACCESS read-only
	STATUS mandatory
	DESCRIPTION
		"Refer to the textual convention for more
		 details."
	::= { hpiSensorEnableChangeEventLogEntry 2 }

hpiSensorEnableChangeEventLogCategory 	OBJECT-TYPE
	SYNTAX SaHpiEventCategory
	ACCESS read-only
	STATUS mandatory
	DESCRIPTION
		"Refer to the textual convention for more details."
	::= { hpiSensorEnableChangeEventLogEntry 3 }

hpiSensorEnableChangeEventLogEnabled 	OBJECT-TYPE
	SYNTAX TruthValue
	ACCESS read-only
	STATUS mandatory
	DESCRIPTION
		"Current sensor enable status."
	::= { hpiSensorEnableChangeEventLogEntry 4 }

hpiSensorEnableChangeEventLogEventsEnabled 	OBJECT-TYPE
	SYNTAX TruthValue
	ACCESS read-only
	STATUS mandatory
	DESCRIPTION
		"Current event enable status."
	::= { hpiSensorEnableChangeEventLogEntry 5 }

hpiSensorEnableChangeEventLogAssertEvents 	OBJECT-TYPE
	SYNTAX SaHpiEventState
	ACCESS read-only
	STATUS mandatory
	DESCRIPTION
		"Refer to the textual convention for more details."
	::= { hpiSensorEnableChangeEventLogEntry 6 }

hpiSensorEnableChangeEventLogDeassertEvents 	OBJECT-TYPE
	SYNTAX SaHpiEventState
	ACCESS read-only
	STATUS mandatory
	DESCRIPTION
		"Refer to the textual convention for more details."
	::= { hpiSensorEnableChangeEventLogEntry 7 }

hpiSensorEnableChangeEventLogOptionalData 	OBJECT-TYPE
	SYNTAX OCTET STRING
	ACCESS read-only
	STATUS mandatory
	DESCRIPTION
		""
	::= { hpiSensorEnableChangeEventLogEntry 8 }

hpiSensorEnableChangeEventLogCurrentState 	OBJECT-TYPE
	SYNTAX SaHpiEventState
	ACCESS read-only
	STATUS mandatory
	DESCRIPTION
		"Current set of asserted Event states."
	::= { hpiSensorEnableChangeEventLogEntry 9 }

hpiHotSwapEventLogEntryCount 	OBJECT-TYPE
	SYNTAX Counter
	ACCESS read-only
	STATUS mandatory
	DESCRIPTION
		"This columnar node represents the subset of events that
		 are HotSwap Events."
	::= { eventLog 14 }

hpiHotSwapEventLogTable 	OBJECT-TYPE
	SYNTAX SEQUENCE OF HpiHotSwapEventLogEntry
	ACCESS not-accessible
	STATUS mandatory
	DESCRIPTION
		"Event table. "
	::= { eventLog 15 }

hpiHotSwapEventLogEntry 	OBJECT-TYPE
	SYNTAX HpiHotSwapEventLogEntry
	ACCESS not-accessible
	STATUS mandatory
	DESCRIPTION
		"Hot Swap events."
	INDEX {
		hpiDomainId,
		hpiResourceId,
		hpiEventLogSeverity,
		hpiEventLogAddedTimestamp
	}
	::= { hpiHotSwapEventLogTable 1 }

HpiHotSwapEventLogEntry ::= SEQUENCE {
	hpiHotSwapEventLogState          SaHpiHotSwapState,
	hpiHotSwapEventLogPreviousState  SaHpiHotSwapState
	}

hpiHotSwapEventLogState 	OBJECT-TYPE
	SYNTAX SaHpiHotSwapState
	ACCESS read-only
	STATUS mandatory
	DESCRIPTION
		"Refer to the textual convention for full details."
	::= { hpiHotSwapEventLogEntry 1 }

hpiHotSwapEventLogPreviousState 	OBJECT-TYPE
	SYNTAX SaHpiHotSwapState
	ACCESS read-only
	STATUS mandatory
	DESCRIPTION
		"Refer to the textual convention for full details."
	::= { hpiHotSwapEventLogEntry 2 }

hpiWatchdogEventLogEntryCount 	OBJECT-TYPE
	SYNTAX Counter
	ACCESS read-only
	STATUS mandatory
	DESCRIPTION
		"This columnar node represents the subset of events that
		 are Watchdog Events."
	::= { eventLog 16 }

hpiWatchdogEventLogTable 	OBJECT-TYPE
	SYNTAX SEQUENCE OF HpiWatchdogEventLogEntry
	ACCESS not-accessible
	STATUS mandatory
	DESCRIPTION
		"Event table. "
	::= { eventLog 17 }

hpiWatchdogEventLogEntry 	OBJECT-TYPE
	SYNTAX HpiWatchdogEventLogEntry
	ACCESS not-accessible
	STATUS mandatory
	DESCRIPTION
		"Watchdog events."
	INDEX {
		hpiDomainId,
		hpiResourceId,
		hpiEventLogSeverity,
		hpiEventLogAddedTimestamp
	}
	::= { hpiWatchdogEventLogTable 1 }

HpiWatchdogEventLogEntry ::= SEQUENCE {
	hpiWatchdogEventLogNum             Gauge,
	hpiWatchdogEventLogAction          INTEGER,
	hpiWatchdogEventLogPreTimerAction  SaHpiWatchdogPreTimerAction,
	hpiWatchdogEventLogUse             SaHpiWatchdogTimerUse
	}

hpiWatchdogEventLogNum 	OBJECT-TYPE
	SYNTAX Gauge
	ACCESS read-only
	STATUS mandatory
	DESCRIPTION
		""
	::= { hpiWatchdogEventLogEntry 1 }

hpiWatchdogEventLogAction 	OBJECT-TYPE
	SYNTAX INTEGER {
                               undefined (0),
                               noAction (1),
                               reset (2),
                               powerDown (3),
                               powerCycle (4),
                               timerInt (9)
                        }
	ACCESS read-only
	STATUS mandatory
	DESCRIPTION
		"These enumerations represent the possible actions to be taken
		 upon watchdog timer timeout and the events that are generated
		 for watchdog actions. "
	::= { hpiWatchdogEventLogEntry 2 }

hpiWatchdogEventLogPreTimerAction 	OBJECT-TYPE
	SYNTAX SaHpiWatchdogPreTimerAction
	ACCESS read-only
	STATUS mandatory
	DESCRIPTION
		"These enumerations represent the possible types of interrupts that may be
		 triggered by a watchdog pre-timer event. The actual meaning of these
		 operations may differ depending on the hardware architecture. "
	::= { hpiWatchdogEventLogEntry 3 }

hpiWatchdogEventLogUse 	OBJECT-TYPE
	SYNTAX SaHpiWatchdogTimerUse
	ACCESS read-only
	STATUS mandatory
	DESCRIPTION
		"Watchdog Timer Use
		 These enumerations represent the possible watchdog users that may have caused
		 the watchdog to expire. For instance, if watchdog is being used during power
		 on self test (POST), and it expires, the SAHPI_WTU_BIOS_POST expiration type
		 will be set. Most specific uses for Watchdog timer by users of HPI should
		 indicate SAHPI_WTU_SMS_OS  if the use is to provide an OS-healthy heartbeat,
		 or SAHPI_WTU_OEM if it is used for some other purpose."
	::= { hpiWatchdogEventLogEntry 4 }

hpiSoftwareEventLogEntryCount 	OBJECT-TYPE
	SYNTAX Counter
	ACCESS read-only
	STATUS mandatory
	DESCRIPTION
		"This columnar node represents the subset of events that
		 are Software Events."
	::= { eventLog 18 }

hpiSoftwareEventLogTable 	OBJECT-TYPE
	SYNTAX SEQUENCE OF HpiSoftwareEventLogEntry
	ACCESS not-accessible
	STATUS mandatory
	DESCRIPTION
		"Event table. "
	::= { eventLog 19 }

hpiSoftwareEventLogEntry 	OBJECT-TYPE
	SYNTAX HpiSoftwareEventLogEntry
	ACCESS not-accessible
	STATUS mandatory
	DESCRIPTION
		"Software events."
	INDEX {
		hpiDomainId,
		hpiResourceId,
		hpiEventLogSeverity,
		hpiEventLogAddedTimestamp
	}
	::= { hpiSoftwareEventLogTable 1 }

HpiSoftwareEventLogEntry ::= SEQUENCE {
	hpiSoftwareEventLogManufacturerId  SaHpiManufacturerId,
	hpiSoftwareEventLogType            INTEGER,
	hpiSoftwareEventLogTextType        SaHpiTextType,
	hpiSoftwareEventLogTextLanguage    SaHpiTextLanguage,
	hpiSoftwareEventLogText            SaHpiText
	}

hpiSoftwareEventLogManufacturerId 	OBJECT-TYPE
	SYNTAX SaHpiManufacturerId
	ACCESS read-only
	STATUS mandatory
	DESCRIPTION
		"Refer to the textual convention for more details."
	::= { hpiSoftwareEventLogEntry 1 }

hpiSoftwareEventLogType 	OBJECT-TYPE
	SYNTAX INTEGER {
                               undefined (0),
                               audit (1),
                               startup (2),
                               other (3)
                        }
	ACCESS read-only
	STATUS mandatory
	DESCRIPTION
		"The following type defines the types of events that can be
		 reported  by the HPI software implementation.
		 Audit events report a discrepancy in the audit process.
		 Audits are typically performed by HA software to detect problems.
		 Audits may look for such things as corrupted data stores,
		 inconsistent RPT information, or improperly managed queues.
		 Startup events report a failure to start-up properly, or
		 inconsistencies in persisted data.
		 Note: Enumerated values are increased by one value compared to
		 SAI-HPI-B spec."
	::= { hpiSoftwareEventLogEntry 2 }

hpiSoftwareEventLogTextType 	OBJECT-TYPE
	SYNTAX SaHpiTextType
	ACCESS read-only
	STATUS mandatory
	DESCRIPTION
		"Refer to the textual convention for more details."
	::= { hpiSoftwareEventLogEntry 3 }

hpiSoftwareEventLogTextLanguage 	OBJECT-TYPE
	SYNTAX SaHpiTextLanguage
	ACCESS read-only
	STATUS mandatory
	DESCRIPTION
		"Refer to the textual convention for more details."
	::= { hpiSoftwareEventLogEntry 4 }

hpiSoftwareEventLogText 	OBJECT-TYPE
	SYNTAX SaHpiText
	ACCESS read-only
	STATUS mandatory
	DESCRIPTION
		"Refer to the textual convention for more details."
	::= { hpiSoftwareEventLogEntry 5 }

hpiOEMEventLogEntryCount 	OBJECT-TYPE
	SYNTAX Counter
	ACCESS read-only
	STATUS mandatory
	DESCRIPTION
		"This columnar node represents the subset of events that
		 are OEM Events."
	::= { eventLog 20 }

hpiOEMEventLogTable 	OBJECT-TYPE
	SYNTAX SEQUENCE OF HpiOEMEventLogEntry
	ACCESS not-accessible
	STATUS mandatory
	DESCRIPTION
		"Event table. "
	::= { eventLog 21 }

hpiOEMEventLogEntry 	OBJECT-TYPE
	SYNTAX HpiOEMEventLogEntry
	ACCESS not-accessible
	STATUS mandatory
	DESCRIPTION
		"OEM events."
	INDEX {
		hpiDomainId,
		hpiResourceId,
		hpiEventLogSeverity,
		hpiEventLogAddedTimestamp
	}
	::= { hpiOEMEventLogTable 1 }

HpiOEMEventLogEntry ::= SEQUENCE {
	hpiOEMEventLogManufacturerId  SaHpiManufacturerId,
	hpiOEMEventLogTextType        SaHpiTextType,
	hpiOEMEventLogTextLanguage    SaHpiTextLanguage,
	hpiOEMEventLogText            SaHpiText
	}

hpiOEMEventLogManufacturerId 	OBJECT-TYPE
	SYNTAX SaHpiManufacturerId
	ACCESS read-only
	STATUS mandatory
	DESCRIPTION
		"Refer to the textual convention for more details."
	::= { hpiOEMEventLogEntry 1 }

hpiOEMEventLogTextType 	OBJECT-TYPE
	SYNTAX SaHpiTextType
	ACCESS read-only
	STATUS mandatory
	DESCRIPTION
		"Refer to the textual convention for more details."
	::= { hpiOEMEventLogEntry 2 }

hpiOEMEventLogTextLanguage 	OBJECT-TYPE
	SYNTAX SaHpiTextLanguage
	ACCESS read-only
	STATUS mandatory
	DESCRIPTION
		"Refer to the textual convention for more details."
	::= { hpiOEMEventLogEntry 3 }

hpiOEMEventLogText 	OBJECT-TYPE
	SYNTAX SaHpiText
	ACCESS read-only
	STATUS mandatory
	DESCRIPTION
		"Refer to the textual convention for more details."
	::= { hpiOEMEventLogEntry 4 }

hpiUserEventLogEntryCount 	OBJECT-TYPE
	SYNTAX Counter
	ACCESS read-only
	STATUS mandatory
	DESCRIPTION
		"This columnar node represents the subset of events that
		 are User Events."
	::= { eventLog 22 }

hpiUserEventLogTable 	OBJECT-TYPE
	SYNTAX SEQUENCE OF HpiUserEventLogEntry
	ACCESS not-accessible
	STATUS mandatory
	DESCRIPTION
		"Event table. "
	::= { eventLog 23 }

hpiUserEventLogEntry 	OBJECT-TYPE
	SYNTAX HpiUserEventLogEntry
	ACCESS not-accessible
	STATUS mandatory
	DESCRIPTION
		"User events."
	INDEX {
		hpiDomainId,
		hpiResourceId,
		hpiEventLogSeverity,
		hpiEventLogAddedTimestamp
	}
	::= { hpiUserEventLogTable 1 }

HpiUserEventLogEntry ::= SEQUENCE {
	hpiUserEventLogTextType      SaHpiTextType,
	hpiUserEventLogTextLanguage  SaHpiTextLanguage,
	hpiUserEventLogText          SaHpiText,
	hpiUserEventLogRowStatus     RowStatus
	}

hpiUserEventLogTextType 	OBJECT-TYPE
	SYNTAX SaHpiTextType
	ACCESS read-write
	STATUS mandatory
	DESCRIPTION
		"Refer to SaHpiTextType for more details."
	::= { hpiUserEventLogEntry 1 }

hpiUserEventLogTextLanguage 	OBJECT-TYPE
	SYNTAX SaHpiTextLanguage
	ACCESS read-write
	STATUS mandatory
	DESCRIPTION
		"Refer to hpiTextLanguage for more details."
	::= { hpiUserEventLogEntry 2 }

hpiUserEventLogText 	OBJECT-TYPE
	SYNTAX SaHpiText
	ACCESS read-write
	STATUS mandatory
	DESCRIPTION
		"Refer to hpiText for more details. "
	::= { hpiUserEventLogEntry 3 }

hpiUserEventLogRowStatus 	OBJECT-TYPE
	SYNTAX RowStatus
	ACCESS read-write
	STATUS mandatory
	DESCRIPTION
		"This columnar node contains the status of the row and also
		 perform add and delete operations.
		 
		 The status column uses four defined values:
		 
		 - `active(1)', which indicates that the conceptual row is
		 available for use by the managed device;
		 
		 - `createAndGo(4)', which is supplied by a management
		 station wishing to create a new instance of a
		 conceptual row (but not make it available for use by
		 the managed device). This function is used to add a
		 User Alarm  to this User Event Table and also to the
		 to the Domain Alarm Table; When creating this row,
		 the value of hpiEventSeverity indice must not be one of
		 these minor(3), major(2), and critical(3). The effect of
		 creating a new row will also be reflected in the DAT - with
		 a new row there.
		 
		 - `destroy(6)', which is supplied by a management station
		 wishing to delete all of the instances associated with
		 an existing conceptual row. This function allows the
		 HPI MIB User to delete a single User Alarm from the
		 User EventLog Table and Domain Alarm Table.
		 Only User Alarms added to the DAT and User EventLog Table can
		 be deleted. To delete a single, specific alarm, set the
		 hpiDomainAlarmId parameter to a value representing an
		 actual User Alarm in the User EventLog Table."
	::= { hpiUserEventLogEntry 4 }

hpiResources OBJECT IDENTIFIER ::= {fscHpiBMIB 4}

hpiRdrEntryCount 	OBJECT-TYPE
	SYNTAX Counter
	ACCESS read-only
	STATUS mandatory
	DESCRIPTION
		"Number of resource data records in this system."
	::= { hpiResources 1 }

hpiRdrTable 	OBJECT-TYPE
	SYNTAX SEQUENCE OF HpiRdrEntry
	ACCESS not-accessible
	STATUS mandatory
	DESCRIPTION
		"A table definining RDR records."
	::= { hpiResources 2 }

hpiRdrEntry 	OBJECT-TYPE
	SYNTAX HpiRdrEntry
	ACCESS not-accessible
	STATUS mandatory
	DESCRIPTION
		"The following describes the different types of records that exist 
		 within a RDR repository and the RDR super-structure to all of the
		 specific RDR types (sensor, inventory data, watchdog, etc.)."
	INDEX {
		hpiDomainId,
		hpiResourceId,
		hpiRdrType,
		hpiRdrId
	}
	::= { hpiRdrTable 1 }

HpiRdrEntry ::= SEQUENCE {
	hpiRdrType              INTEGER,
	hpiRdrId                SaHpiInstrumentId,
	hpiRdrEntityPath        SaHpiEntityPath,
	hpiRdrIsFru             TruthValue,
	hpiRdrIdStringType      SaHpiTextType,
	hpiRdrIdStringLanguage  SaHpiTextLanguage,
	hpiRdrIdString          SaHpiText,
	hpiRdrIdText            DisplayString
	}

hpiRdrType 	OBJECT-TYPE
	SYNTAX INTEGER {
                               undefined (0),
                               noRecord (1),
                               ctrlRdr (2),
                               sensorRdr (3),
                               inventoryRdr (4),
                               watchdogRdr (5),
                               annunciatorRdr (6)
                        }
	ACCESS not-accessible
	STATUS mandatory
	DESCRIPTION
		"Type of RDR entry.
		 Note: Enumerated values are increased by one value compared to
		 SAI-HPI-B spec."
	::= { hpiRdrEntry 1 }

hpiRdrId 	OBJECT-TYPE
	SYNTAX SaHpiInstrumentId
	ACCESS not-accessible
	STATUS mandatory
	DESCRIPTION
		"Resource Data Record identifier - the instrumentID.
		 Together with the hpiRdrType this identifies the RDR within a
		 resource. Note: this is not the RDR record ID"
	::= { hpiRdrEntry 2 }

hpiRdrEntityPath 	OBJECT-TYPE
	SYNTAX SaHpiEntityPath
	ACCESS read-only
	STATUS mandatory
	DESCRIPTION
		"If resource manages a FRU, entity path of the FRU.
		 If resource manages a single entity, entity path of
		 that entity.
		 If resource manages multiple entities, the entity path
		 of the 'primary' entity managed by the resource.
		 Must be set to the same value in every domain which
		 contains this resource.
		 This object converts HPI's hpiEntityPathT structure
		 and an OpenHPI canonical string. The canonical string is
		 formed by removing the SAHPI_ENT_ prefix from the
		 HPI types, and creating tuples for the entity types.
		 Order of significance is inverted to make entity paths
		 look more like Unix directory structure. It is also assumed
		 that {ROOT,0} exists implicitly before all of these entries.
		 For example:
		 {SYSTEM_CHASSIS,2}{PROCESSOR_BOARD,0} "
	::= { hpiRdrEntry 3 }

hpiRdrIsFru 	OBJECT-TYPE
	SYNTAX TruthValue
	ACCESS read-only
	STATUS mandatory
	DESCRIPTION
		"Entity is a FRU.  This field is Only valid if the
		 Entity path given in the 'Entity' field is different from the Entity
		 path in the RPT entry for the resource."
	::= { hpiRdrEntry 4 }

hpiRdrIdStringType 	OBJECT-TYPE
	SYNTAX SaHpiTextType
	ACCESS read-only
	STATUS mandatory
	DESCRIPTION
		"See definition"
	::= { hpiRdrEntry 5 }

hpiRdrIdStringLanguage 	OBJECT-TYPE
	SYNTAX SaHpiTextLanguage
	ACCESS read-only
	STATUS mandatory
	DESCRIPTION
		"See definition"
	::= { hpiRdrEntry 6 }

hpiRdrIdString 	OBJECT-TYPE
	SYNTAX SaHpiText
	ACCESS read-only
	STATUS mandatory
	DESCRIPTION
		"ID String of the RDR entry."
	::= { hpiRdrEntry 7 }

hpiRdrIdText 	OBJECT-TYPE
	SYNTAX DisplayString
	ACCESS read-only
	STATUS mandatory
	DESCRIPTION
		"ID String of the RDR entry in readable form.
		 (valid only, if type == (text, , ) and language == ?)."
	::= { hpiRdrEntry 8 }

hpiRdrControlsCount 	OBJECT-TYPE
	SYNTAX Counter
	ACCESS read-only
	STATUS mandatory
	DESCRIPTION
		"Number of control data records in this system."
	::= { hpiResources 3 }

hpiControls OBJECT IDENTIFIER ::= {hpiResources 4}

hpiCtrlEntryCount 	OBJECT-TYPE
	SYNTAX Counter
	ACCESS read-only
	STATUS mandatory
	DESCRIPTION
		"The number of control resource data records in the system."
	::= { hpiControls 1 }

hpiCtrlTable 	OBJECT-TYPE
	SYNTAX SEQUENCE OF HpiCtrlEntry
	ACCESS not-accessible
	STATUS mandatory
	DESCRIPTION
		"A table definining Control Resource Data Records."
	::= { hpiControls 2 }

hpiCtrlEntry 	OBJECT-TYPE
	SYNTAX HpiCtrlEntry
	ACCESS not-accessible
	STATUS mandatory
	DESCRIPTION
		"Definition of the control resource data record."
	INDEX {
		hpiDomainId,
		hpiResourceId,
		hpiRdrType,
		hpiRdrId
	}
	::= { hpiCtrlTable 1 }

HpiCtrlEntry ::= SEQUENCE {
	hpiCtrlOutputType           INTEGER,
	hpiCtrlType                 INTEGER,
	hpiCtrlDefaultMode          INTEGER,
	hpiCtrlDefaultModeReadOnly  TruthValue,
	hpiCtrlWriteOnly            TruthValue,
	hpiCtrlOem                  Gauge
	}

hpiCtrlOutputType 	OBJECT-TYPE
	SYNTAX INTEGER {
                               undefined (0),
                               generic (1),
                               led (2),
                               fanSpeed (3),
                               dryContactClosure (4),
                               powerSupplyInhibit (5),
                               audible (6),
                               frontPanelLockout (7),
                               powerInterlock (8),
                               powerState (9),
                               lcdDisplay (10),
                               oem (11)
                        }
	ACCESS read-only
	STATUS mandatory
	DESCRIPTION
		"This enumeration defines the what the control's output will be.
		 Note: Enumerated values are increased by one value compared to
		 SAI-HPI-B spec."
	::= { hpiCtrlEntry 1 }

hpiCtrlType 	OBJECT-TYPE
	SYNTAX INTEGER {
                               undefined (0),
                               digital (1),
                               discrete (2),
                               analog (3),
                               stream (4),
                               text (5),
                               oem (193)
                        }
	ACCESS read-only
	STATUS mandatory
	DESCRIPTION
		"This enumerated type defines the different types of generic controls.
		 Note: Enumerated values are increased by one value compared to
		 SAI-HPI-B spec."
	::= { hpiCtrlEntry 2 }

hpiCtrlDefaultMode 	OBJECT-TYPE
	SYNTAX INTEGER {
                               undefined (0),
                               auto (1),
                               manual (2)
                        }
	ACCESS read-write
	STATUS mandatory
	DESCRIPTION
		"This object describes how the control is managed.
		 The control may be managed automatically by the implementation
		 (auto mode).  Or it may be managed by the HPI User (manual mode).
		 Some controls allow their modes to be changed, allowing the HPI User
		 to determine if they will manage the control, or relinquish the
		 management to the implementation.  But, other controls do not allow
		 the mode to be changed.  These static-mode controls are indicated
		 with the hpiCtrlReadOnly flag set as part of the default control
		 mode.
		 Note: Enumerated values are increased by one value compared to
		 SAI-HPI-B spec."
	::= { hpiCtrlEntry 3 }

hpiCtrlDefaultModeReadOnly 	OBJECT-TYPE
	SYNTAX TruthValue
	ACCESS read-only
	STATUS mandatory
	DESCRIPTION
		"Indicates if mode is read-only"
	::= { hpiCtrlEntry 4 }

hpiCtrlWriteOnly 	OBJECT-TYPE
	SYNTAX TruthValue
	ACCESS read-only
	STATUS mandatory
	DESCRIPTION
		"Indicates if mode is write-only"
	::= { hpiCtrlEntry 5 }

hpiCtrlOem 	OBJECT-TYPE
	SYNTAX Gauge
	ACCESS read-only
	STATUS mandatory
	DESCRIPTION
		"Reserved for OEM use"
	::= { hpiCtrlEntry 6 }

hpiCtrlDigitalEntryCount 	OBJECT-TYPE
	SYNTAX Counter
	ACCESS read-only
	STATUS mandatory
	DESCRIPTION
		"The number of control resource data records of
		 type DIGITAL in the system."
	::= { hpiControls 3 }

hpiCtrlDigitalTable 	OBJECT-TYPE
	SYNTAX SEQUENCE OF HpiCtrlDigitalEntry
	ACCESS not-accessible
	STATUS mandatory
	DESCRIPTION
		"A table definining Control Resource Data Records."
	::= { hpiControls 4 }

hpiCtrlDigitalEntry 	OBJECT-TYPE
	SYNTAX HpiCtrlDigitalEntry
	ACCESS not-accessible
	STATUS mandatory
	DESCRIPTION
		"Definition of the control resource data record."
	INDEX {
		hpiDomainId,
		hpiResourceId,
		hpiRdrType,
		hpiRdrId
	}
	::= { hpiCtrlDigitalTable 1 }

HpiCtrlDigitalEntry ::= SEQUENCE {
	hpiCtrlDigitalValue    INTEGER,
	hpiCtrlDigitalDefault  INTEGER
	}

hpiCtrlDigitalValue 	OBJECT-TYPE
	SYNTAX INTEGER {
                               undefined (0),
                               off (1),
                               on (2),
                               pulseOff (3),
                               pulseOn (4)
                        }
	ACCESS read-write
	STATUS mandatory
	DESCRIPTION
		""
	::= { hpiCtrlDigitalEntry 1 }

hpiCtrlDigitalDefault 	OBJECT-TYPE
	SYNTAX INTEGER {
                               undefined (0),
                               off (1),
                               on (2),
                               pulseOff (3),
                               pulseOn (4)
                        }
	ACCESS read-only
	STATUS mandatory
	DESCRIPTION
		""
	::= { hpiCtrlDigitalEntry 2 }

hpiCtrlDiscreteEntryCount 	OBJECT-TYPE
	SYNTAX Counter
	ACCESS read-only
	STATUS mandatory
	DESCRIPTION
		"The number of control resource data records of
		 type DISCRETE in the system."
	::= { hpiControls 5 }

hpiCtrlDiscreteTable 	OBJECT-TYPE
	SYNTAX SEQUENCE OF HpiCtrlDiscreteEntry
	ACCESS not-accessible
	STATUS mandatory
	DESCRIPTION
		"A table definining Control Resource Data Records."
	::= { hpiControls 6 }

hpiCtrlDiscreteEntry 	OBJECT-TYPE
	SYNTAX HpiCtrlDiscreteEntry
	ACCESS not-accessible
	STATUS mandatory
	DESCRIPTION
		"Definition of the control resource data record."
	INDEX {
		hpiDomainId,
		hpiResourceId,
		hpiRdrType,
		hpiRdrId
	}
	::= { hpiCtrlDiscreteTable 1 }

HpiCtrlDiscreteEntry ::= SEQUENCE {
	hpiCtrlDiscreteValue    Gauge,
	hpiCtrlDiscreteDefault  Gauge
	}

hpiCtrlDiscreteValue 	OBJECT-TYPE
	SYNTAX Gauge
	ACCESS read-write
	STATUS mandatory
	DESCRIPTION
		""
	::= { hpiCtrlDiscreteEntry 1 }

hpiCtrlDiscreteDefault 	OBJECT-TYPE
	SYNTAX Gauge
	ACCESS read-only
	STATUS mandatory
	DESCRIPTION
		""
	::= { hpiCtrlDiscreteEntry 2 }

hpiCtrlAnalogEntryCount 	OBJECT-TYPE
	SYNTAX Counter
	ACCESS read-only
	STATUS mandatory
	DESCRIPTION
		"The number of control resource data records of
		 type ANALOG in the system."
	::= { hpiControls 7 }

hpiCtrlAnalogTable 	OBJECT-TYPE
	SYNTAX SEQUENCE OF HpiCtrlAnalogEntry
	ACCESS not-accessible
	STATUS mandatory
	DESCRIPTION
		"A table definining Control Resource Data Records."
	::= { hpiControls 8 }

hpiCtrlAnalogEntry 	OBJECT-TYPE
	SYNTAX HpiCtrlAnalogEntry
	ACCESS not-accessible
	STATUS mandatory
	DESCRIPTION
		"Definition of the control resource data record."
	INDEX {
		hpiDomainId,
		hpiResourceId,
		hpiRdrType,
		hpiRdrId
	}
	::= { hpiCtrlAnalogTable 1 }

HpiCtrlAnalogEntry ::= SEQUENCE {
	hpiCtrlAnalogValue    INTEGER,
	hpiCtrlAnalogMin      INTEGER,
	hpiCtrlAnalogMax      INTEGER,
	hpiCtrlAnalogDefault  INTEGER
	}

hpiCtrlAnalogValue 	OBJECT-TYPE
	SYNTAX INTEGER
	ACCESS read-write
	STATUS mandatory
	DESCRIPTION
		""
	::= { hpiCtrlAnalogEntry 1 }

hpiCtrlAnalogMin 	OBJECT-TYPE
	SYNTAX INTEGER
	ACCESS read-only
	STATUS mandatory
	DESCRIPTION
		""
	::= { hpiCtrlAnalogEntry 2 }

hpiCtrlAnalogMax 	OBJECT-TYPE
	SYNTAX INTEGER
	ACCESS read-only
	STATUS mandatory
	DESCRIPTION
		""
	::= { hpiCtrlAnalogEntry 3 }

hpiCtrlAnalogDefault 	OBJECT-TYPE
	SYNTAX INTEGER
	ACCESS read-only
	STATUS mandatory
	DESCRIPTION
		""
	::= { hpiCtrlAnalogEntry 4 }

hpiCtrlStreamEntryCount 	OBJECT-TYPE
	SYNTAX Counter
	ACCESS read-only
	STATUS mandatory
	DESCRIPTION
		"The number of control resource data records of
		 type STREAM in the system."
	::= { hpiControls 9 }

hpiCtrlStreamTable 	OBJECT-TYPE
	SYNTAX SEQUENCE OF HpiCtrlStreamEntry
	ACCESS not-accessible
	STATUS mandatory
	DESCRIPTION
		"A table definining Control Resource Data Records."
	::= { hpiControls 10 }

hpiCtrlStreamEntry 	OBJECT-TYPE
	SYNTAX HpiCtrlStreamEntry
	ACCESS not-accessible
	STATUS mandatory
	DESCRIPTION
		"Definition of the control resource data record."
	INDEX {
		hpiDomainId,
		hpiResourceId,
		hpiRdrType,
		hpiRdrId
	}
	::= { hpiCtrlStreamTable 1 }

HpiCtrlStreamEntry ::= SEQUENCE {
	hpiCtrlStreamValueRepeat    TruthValue,
	hpiCtrlStreamValueStream    OCTET STRING,
	hpiCtrlStreamDefaultRepeat  TruthValue,
	hpiCtrlStreamDefaultStream  OCTET STRING
	}

hpiCtrlStreamValueRepeat 	OBJECT-TYPE
	SYNTAX TruthValue
	ACCESS read-write
	STATUS mandatory
	DESCRIPTION
		""
	::= { hpiCtrlStreamEntry 1 }

hpiCtrlStreamValueStream 	OBJECT-TYPE
	SYNTAX OCTET STRING
	ACCESS read-write
	STATUS mandatory
	DESCRIPTION
		""
	::= { hpiCtrlStreamEntry 2 }

hpiCtrlStreamDefaultRepeat 	OBJECT-TYPE
	SYNTAX TruthValue
	ACCESS read-only
	STATUS mandatory
	DESCRIPTION
		""
	::= { hpiCtrlStreamEntry 3 }

hpiCtrlStreamDefaultStream 	OBJECT-TYPE
	SYNTAX OCTET STRING
	ACCESS read-only
	STATUS mandatory
	DESCRIPTION
		""
	::= { hpiCtrlStreamEntry 4 }

hpiCtrlOemEntryCount 	OBJECT-TYPE
	SYNTAX Counter
	ACCESS read-only
	STATUS mandatory
	DESCRIPTION
		"The number of control resource data records of
		 type OEM in the system."
	::= { hpiControls 11 }

hpiCtrlOemTable 	OBJECT-TYPE
	SYNTAX SEQUENCE OF HpiCtrlOemEntry
	ACCESS not-accessible
	STATUS mandatory
	DESCRIPTION
		"A table definining Control Resource Data Records."
	::= { hpiControls 12 }

hpiCtrlOemEntry 	OBJECT-TYPE
	SYNTAX HpiCtrlOemEntry
	ACCESS not-accessible
	STATUS mandatory
	DESCRIPTION
		"Definition of the control resource data record."
	INDEX {
		hpiDomainId,
		hpiResourceId,
		hpiRdrType,
		hpiRdrId
	}
	::= { hpiCtrlOemTable 1 }

HpiCtrlOemEntry ::= SEQUENCE {
	hpiCtrlOemValueMId     Gauge,
	hpiCtrlOemValueBody    OCTET STRING,
	hpiCtrlOemConfigData   OCTET STRING,
	hpiCtrlOemDefaultMId   Gauge,
	hpiCtrlOemDefaultBody  OCTET STRING
	}

hpiCtrlOemValueMId 	OBJECT-TYPE
	SYNTAX Gauge
	ACCESS read-write
	STATUS mandatory
	DESCRIPTION
		""
	::= { hpiCtrlOemEntry 1 }

hpiCtrlOemValueBody 	OBJECT-TYPE
	SYNTAX OCTET STRING
	ACCESS read-write
	STATUS mandatory
	DESCRIPTION
		""
	::= { hpiCtrlOemEntry 2 }

hpiCtrlOemConfigData 	OBJECT-TYPE
	SYNTAX OCTET STRING
	ACCESS read-only
	STATUS mandatory
	DESCRIPTION
		""
	::= { hpiCtrlOemEntry 3 }

hpiCtrlOemDefaultMId 	OBJECT-TYPE
	SYNTAX Gauge
	ACCESS read-only
	STATUS mandatory
	DESCRIPTION
		""
	::= { hpiCtrlOemEntry 4 }

hpiCtrlOemDefaultBody 	OBJECT-TYPE
	SYNTAX OCTET STRING
	ACCESS read-only
	STATUS mandatory
	DESCRIPTION
		""
	::= { hpiCtrlOemEntry 5 }

hpiRdrSensorCount 	OBJECT-TYPE
	SYNTAX Counter
	ACCESS read-only
	STATUS mandatory
	DESCRIPTION
		"Number of sensor data records in this system."
	::= { hpiResources 5 }

hpiSensor OBJECT IDENTIFIER ::= {hpiResources 6}

hpiSensorEntryCount 	OBJECT-TYPE
	SYNTAX Counter
	ACCESS read-only
	STATUS mandatory
	DESCRIPTION
		"The number of sensor resource data records in the system."
	::= { hpiSensor 1 }

hpiSensorTable 	OBJECT-TYPE
	SYNTAX SEQUENCE OF HpiSensorEntry
	ACCESS not-accessible
	STATUS mandatory
	DESCRIPTION
		"A table definining Sensors records."
	::= { hpiSensor 2 }

hpiSensorEntry 	OBJECT-TYPE
	SYNTAX HpiSensorEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorTable 1 }

HpiSensorEntry ::= SEQUENCE {
	hpiSensorType                   SaHpiSensorType,
	hpiSensorCtrl                   TruthValue,
	hpiSensorEnable                 TruthValue,
	hpiSensorEventIsSupported       TruthValue,
	hpiSensorEventCurrState         SaHpiEventState,
	hpiSensorEventCat               SaHpiEventCategory,
	hpiSensorEventCtrl              INTEGER,
	hpiSensorEventEnable            TruthValue,
	hpiSensorReadingIsSupported     TruthValue,
	hpiSensorRangeSupported         SaHpiSensorRangeFlags,
	hpiSensorThresholdIsAccessible  TruthValue,
	hpiSensorOem                    Gauge
	}

hpiSensorType 	OBJECT-TYPE
	SYNTAX SaHpiSensorType
	ACCESS read-only
	STATUS mandatory
	DESCRIPTION
		"Refer to the textual convention for more details."
	::= { hpiSensorEntry 1 }

hpiSensorCtrl 	OBJECT-TYPE
	SYNTAX TruthValue
	ACCESS read-only
	STATUS mandatory
	DESCRIPTION
		"True if HPI User can enable or disable sensor via
		 hpiSensorEnableSet."
	::= { hpiSensorEntry 2 }

hpiSensorEnable 	OBJECT-TYPE
	SYNTAX TruthValue
	ACCESS read-write
	STATUS mandatory
	DESCRIPTION
		"When reading, this object returns the current sensor enable status
		 for an addressed sensor. When writing this object sets the sensor
		 enable status for an addressed sensor.  If a sensor is disabled,
		 the rows in hpiSensorReadingCurrent for that sensor will not be
		 present, and no events will be generated for the sensor."
	::= { hpiSensorEntry 3 }

hpiSensorEventIsSupported 	OBJECT-TYPE
	SYNTAX TruthValue
	ACCESS read-only
	STATUS mandatory
	DESCRIPTION
		"The Bit mask Events is not SAHPI_ES_UNSPECIFIED"
	::= { hpiSensorEntry 4 }

hpiSensorEventCurrState 	OBJECT-TYPE
	SYNTAX SaHpiEventState
	ACCESS read-only
	STATUS mandatory
	DESCRIPTION
		"The current event state of a sensor"
	::= { hpiSensorEntry 5 }

hpiSensorEventCat 	OBJECT-TYPE
	SYNTAX SaHpiEventCategory
	ACCESS read-only
	STATUS mandatory
	DESCRIPTION
		"Sensors category. Sensor events contain an event category and event
		 state. Depending on the event category, the event states take on
		 different meanings for events generated by specific sensors.
		 The generic(128) category can be used for discrete sensors which
		 have state meanings other than those identified with other event
		 categories."
	::= { hpiSensorEntry 6 }

hpiSensorEventCtrl 	OBJECT-TYPE
	SYNTAX INTEGER {
                               undefined (0),
                               perEvent (1),
                               readOnlyMasks (2),
                               readOnly (3)
                        }
	ACCESS read-write
	STATUS mandatory
	DESCRIPTION
		"perEvent(1) Event message control per event,
		 or by entire sensor; sensor event enable
		 Status can be changed, and assert/deassert
		 masks can be changed.
		 readOnlyMasks(2): Control for entire sensor only; sensor
		 event enable status can be changed, but
		 assert/deassert masks cannot be changed.
		 readOnly(3): Event control not supported; sensor event
		 enable status cannot be changed and
		 ssert/deassert masks cannot be changed.
		 Note: Enumerated values are increased by one value compared to
		 SAI-HPI-B spec."
	::= { hpiSensorEntry 7 }

hpiSensorEventEnable 	OBJECT-TYPE
	SYNTAX TruthValue
	ACCESS read-write
	STATUS mandatory
	DESCRIPTION
		"When reading, this object returns the current sensor event enable 
		 status for an addressed sensor. When writing this object sets the 
		 sensor event enable status for an addressed sensor.  If event
		 generation for a sensor is disabled, no events will be generated 
		 as a result of the assertion or deassertion of any event state, 
		 regardless of the setting of the assert or deassert event masks 
		 for the sensor.  If event generation for a sensor is enabled, events 
		 will be generated when event states are asserted or deasserted, 
		 according to the settings of the assert and deassert event masks 
		 for the sensor.  Event states may still be read for a sensor even 
		 if event generation is disabled, by reading the 
		 hpiSensorReadingCurrent table."
	::= { hpiSensorEntry 8 }

hpiSensorReadingIsSupported 	OBJECT-TYPE
	SYNTAX TruthValue
	ACCESS read-only
	STATUS mandatory
	DESCRIPTION
		"Indicates if sensor data readings are supported."
	::= { hpiSensorEntry 9 }

hpiSensorRangeSupported 	OBJECT-TYPE
	SYNTAX SaHpiSensorRangeFlags
	ACCESS read-only
	STATUS mandatory
	DESCRIPTION
		"Defines which range flags the sensor supports. They
		 can be MIN, MAX, NOMINAL, NORMAL_MAX, NORMAL_MIN, or
		 nothing if the sensor does not support any ranges."
	::= { hpiSensorEntry 10 }

hpiSensorThresholdIsAccessible 	OBJECT-TYPE
	SYNTAX TruthValue
	ACCESS read-only
	STATUS mandatory
	DESCRIPTION
		""
	::= { hpiSensorEntry 11 }

hpiSensorOem 	OBJECT-TYPE
	SYNTAX Gauge
	ACCESS read-only
	STATUS mandatory
	DESCRIPTION
		"Reserved for OEM use."
	::= { hpiSensorEntry 12 }

hpiSensorReadingCount 	OBJECT-TYPE
	SYNTAX Counter
	ACCESS read-only
	STATUS mandatory
	DESCRIPTION
		"The number of sensor resource data records in the system."
	::= { hpiSensor 3 }

hpiSensorReadingTable 	OBJECT-TYPE
	SYNTAX SEQUENCE OF HpiSensorReadingEntry
	ACCESS not-accessible
	STATUS mandatory
	DESCRIPTION
		"A table definining Sensors records."
	::= { hpiSensor 4 }

hpiSensorReadingEntry 	OBJECT-TYPE
	SYNTAX HpiSensorReadingEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorReadingTable 1 }

HpiSensorReadingEntry ::= SEQUENCE {
	hpiSensorReadingDataType        SaHpiSensorReadingType,
	hpiSensorReadingBaseUnits       SaHpiSensorUnits,
	hpiSensorReadingModifierUnits   SaHpiSensorUnits,
	hpiSensorReadingModifierUse     SaHpiSensorModUnitUse,
	hpiSensorReadingPercentage      TruthValue,
	hpiSensorReadingCurrentValue    SaHpiSensorReadingValue,
	hpiSensorReadingAccuracyFactor  Double
	}

hpiSensorReadingDataType 	OBJECT-TYPE
	SYNTAX SaHpiSensorReadingType
	ACCESS read-only
	STATUS mandatory
	DESCRIPTION
		""
	::= { hpiSensorReadingEntry 1 }

hpiSensorReadingBaseUnits 	OBJECT-TYPE
	SYNTAX SaHpiSensorUnits
	ACCESS read-only
	STATUS mandatory
	DESCRIPTION
		""
	::= { hpiSensorReadingEntry 2 }

hpiSensorReadingModifierUnits 	OBJECT-TYPE
	SYNTAX SaHpiSensorUnits
	ACCESS read-only
	STATUS mandatory
	DESCRIPTION
		""
	::= { hpiSensorReadingEntry 3 }

hpiSensorReadingModifierUse 	OBJECT-TYPE
	SYNTAX SaHpiSensorModUnitUse
	ACCESS read-only
	STATUS mandatory
	DESCRIPTION
		""
	::= { hpiSensorReadingEntry 4 }

hpiSensorReadingPercentage 	OBJECT-TYPE
	SYNTAX TruthValue
	ACCESS read-only
	STATUS mandatory
	DESCRIPTION
		""
	::= { hpiSensorReadingEntry 5 }

hpiSensorReadingCurrentValue 	OBJECT-TYPE
	SYNTAX SaHpiSensorReadingValue
	ACCESS read-only
	STATUS mandatory
	DESCRIPTION
		""
	::= { hpiSensorReadingEntry 6 }

hpiSensorReadingAccuracyFactor 	OBJECT-TYPE
	SYNTAX Double
	ACCESS read-only
	STATUS mandatory
	DESCRIPTION
		"The Accuracy Factor is expressed as a floating point percentage
		 (e.g. 0.05 = 5%) and represents statistically how close the measured
		 reading is to the actual value. It is an interpreted value that
		 figures in all sensor accuracies, resolutions, and tolerances."
	::= { hpiSensorReadingEntry 7 }

hpiSensorRangeCount 	OBJECT-TYPE
	SYNTAX Counter
	ACCESS read-only
	STATUS mandatory
	DESCRIPTION
		"The number of sensor resource data records in the system."
	::= { hpiSensor 5 }

hpiSensorRangeTable 	OBJECT-TYPE
	SYNTAX SEQUENCE OF HpiSensorRangeEntry
	ACCESS not-accessible
	STATUS mandatory
	DESCRIPTION
		"A table definining Sensors records."
	::= { hpiSensor 6 }

hpiSensorRangeEntry 	OBJECT-TYPE
	SYNTAX HpiSensorRangeEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorRangeTable 1 }

HpiSensorRangeEntry ::= SEQUENCE {
	hpiSensorRangeFlags      SaHpiSensorRangeFlags,
	hpiSensorRangeDataType   SaHpiSensorReadingType,
	hpiSensorRangeMin        SaHpiSensorReadingValue,
	hpiSensorRangeMax        SaHpiSensorReadingValue,
	hpiSensorRangeNormalMin  SaHpiSensorReadingValue,
	hpiSensorRangeNormalMax  SaHpiSensorReadingValue,
	hpiSensorRangeNominal    SaHpiSensorReadingValue
	}

hpiSensorRangeFlags 	OBJECT-TYPE
	SYNTAX SaHpiSensorRangeFlags
	ACCESS read-only
	STATUS mandatory
	DESCRIPTION
		""
	::= { hpiSensorRangeEntry 1 }

hpiSensorRangeDataType 	OBJECT-TYPE
	SYNTAX SaHpiSensorReadingType
	ACCESS read-only
	STATUS mandatory
	DESCRIPTION
		""
	::= { hpiSensorRangeEntry 2 }

hpiSensorRangeMin 	OBJECT-TYPE
	SYNTAX SaHpiSensorReadingValue
	ACCESS read-only
	STATUS mandatory
	DESCRIPTION
		""
	::= { hpiSensorRangeEntry 3 }

hpiSensorRangeMax 	OBJECT-TYPE
	SYNTAX SaHpiSensorReadingValue
	ACCESS read-only
	STATUS mandatory
	DESCRIPTION
		""
	::= { hpiSensorRangeEntry 4 }

hpiSensorRangeNormalMin 	OBJECT-TYPE
	SYNTAX SaHpiSensorReadingValue
	ACCESS read-only
	STATUS mandatory
	DESCRIPTION
		""
	::= { hpiSensorRangeEntry 5 }

hpiSensorRangeNormalMax 	OBJECT-TYPE
	SYNTAX SaHpiSensorReadingValue
	ACCESS read-only
	STATUS mandatory
	DESCRIPTION
		""
	::= { hpiSensorRangeEntry 6 }

hpiSensorRangeNominal 	OBJECT-TYPE
	SYNTAX SaHpiSensorReadingValue
	ACCESS read-only
	STATUS mandatory
	DESCRIPTION
		""
	::= { hpiSensorRangeEntry 7 }

hpiSensorThresholdCount 	OBJECT-TYPE
	SYNTAX Counter
	ACCESS read-only
	STATUS mandatory
	DESCRIPTION
		"The number of sensor resource data records in the system."
	::= { hpiSensor 7 }

hpiSensorThresholdTable 	OBJECT-TYPE
	SYNTAX SEQUENCE OF HpiSensorThresholdEntry
	ACCESS not-accessible
	STATUS mandatory
	DESCRIPTION
		"A table definining Sensors records."
	::= { hpiSensor 8 }

hpiSensorThresholdEntry 	OBJECT-TYPE
	SYNTAX HpiSensorThresholdEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorThresholdTable 1 }

HpiSensorThresholdEntry ::= SEQUENCE {
	hpiSensorThresholdReadMask          SaHpiSensorThdMask,
	hpiSensorThresholdWriteMask         SaHpiSensorThdMask,
	hpiSensorThresholdNonLinear         TruthValue,
	hpiSensorThresholdDataType          SaHpiSensorReadingType,
	hpiSensorThresholdLowMinor          SaHpiSensorReadingValue,
	hpiSensorThresholdLowMajor          SaHpiSensorReadingValue,
	hpiSensorThresholdLowCritical       SaHpiSensorReadingValue,
	hpiSensorThresholdUpMinor           SaHpiSensorReadingValue,
	hpiSensorThresholdUpMajor           SaHpiSensorReadingValue,
	hpiSensorThresholdUpCritical        SaHpiSensorReadingValue,
	hpiSensorThresholdPosThdHysteresis  SaHpiSensorReadingValue,
	hpiSensorThresholdNegThdHysteresis  SaHpiSensorReadingValue
	}

hpiSensorThresholdReadMask 	OBJECT-TYPE
	SYNTAX SaHpiSensorThdMask
	ACCESS read-only
	STATUS mandatory
	DESCRIPTION
		""
	::= { hpiSensorThresholdEntry 2 }

hpiSensorThresholdWriteMask 	OBJECT-TYPE
	SYNTAX SaHpiSensorThdMask
	ACCESS read-only
	STATUS mandatory
	DESCRIPTION
		""
	::= { hpiSensorThresholdEntry 3 }

hpiSensorThresholdNonLinear 	OBJECT-TYPE
	SYNTAX TruthValue
	ACCESS read-only
	STATUS mandatory
	DESCRIPTION
		""
	::= { hpiSensorThresholdEntry 4 }

hpiSensorThresholdDataType 	OBJECT-TYPE
	SYNTAX SaHpiSensorReadingType
	ACCESS read-only
	STATUS mandatory
	DESCRIPTION
		""
	::= { hpiSensorThresholdEntry 5 }

hpiSensorThresholdLowMinor 	OBJECT-TYPE
	SYNTAX SaHpiSensorReadingValue
	ACCESS read-only
	STATUS mandatory
	DESCRIPTION
		""
	::= { hpiSensorThresholdEntry 6 }

hpiSensorThresholdLowMajor 	OBJECT-TYPE
	SYNTAX SaHpiSensorReadingValue
	ACCESS read-only
	STATUS mandatory
	DESCRIPTION
		""
	::= { hpiSensorThresholdEntry 7 }

hpiSensorThresholdLowCritical 	OBJECT-TYPE
	SYNTAX SaHpiSensorReadingValue
	ACCESS read-only
	STATUS mandatory
	DESCRIPTION
		""
	::= { hpiSensorThresholdEntry 8 }

hpiSensorThresholdUpMinor 	OBJECT-TYPE
	SYNTAX SaHpiSensorReadingValue
	ACCESS read-only
	STATUS mandatory
	DESCRIPTION
		""
	::= { hpiSensorThresholdEntry 9 }

hpiSensorThresholdUpMajor 	OBJECT-TYPE
	SYNTAX SaHpiSensorReadingValue
	ACCESS read-only
	STATUS mandatory
	DESCRIPTION
		""
	::= { hpiSensorThresholdEntry 10 }

hpiSensorThresholdUpCritical 	OBJECT-TYPE
	SYNTAX SaHpiSensorReadingValue
	ACCESS read-only
	STATUS mandatory
	DESCRIPTION
		""
	::= { hpiSensorThresholdEntry 11 }

hpiSensorThresholdPosThdHysteresis 	OBJECT-TYPE
	SYNTAX SaHpiSensorReadingValue
	ACCESS read-only
	STATUS mandatory
	DESCRIPTION
		""
	::= { hpiSensorThresholdEntry 12 }

hpiSensorThresholdNegThdHysteresis 	OBJECT-TYPE
	SYNTAX SaHpiSensorReadingValue
	ACCESS read-only
	STATUS mandatory
	DESCRIPTION
		""
	::= { hpiSensorThresholdEntry 13 }

hpiSensorEvtCat OBJECT IDENTIFIER ::= {hpiSensor 10}

hpiSensorEvtCatThresholdEntryCount 	OBJECT-TYPE
	SYNTAX Counter
	ACCESS read-only
	STATUS mandatory
	DESCRIPTION
		""
	::= { hpiSensorEvtCat 1 }

hpiSensorEvtCatThresholdTable 	OBJECT-TYPE
	SYNTAX SEQUENCE OF HpiSensorEvtCatThresholdEntry
	ACCESS not-accessible
	STATUS mandatory
	DESCRIPTION
		""
	::= { hpiSensorEvtCat 2 }

hpiSensorEvtCatThresholdEntry 	OBJECT-TYPE
	SYNTAX HpiSensorEvtCatThresholdEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatThresholdTable 1 }

HpiSensorEvtCatThresholdEntry ::= SEQUENCE {
	hpiSensorEvtCatThresholdCurrentEvents    SaHpiThresholdEvents,
	hpiSensorEvtCatThresholdSupportedEvents  SaHpiThresholdEvents,
	hpiSensorEvtCatThresholdAssertEvents     SaHpiThresholdEvents,
	hpiSensorEvtCatThresholdDeassertEvents   SaHpiThresholdEvents
	}

hpiSensorEvtCatThresholdCurrentEvents 	OBJECT-TYPE
	SYNTAX SaHpiThresholdEvents
	ACCESS read-only
	STATUS mandatory
	DESCRIPTION
		"Refer to the textual convention for more details."
	::= { hpiSensorEvtCatThresholdEntry 1 }

hpiSensorEvtCatThresholdSupportedEvents 	OBJECT-TYPE
	SYNTAX SaHpiThresholdEvents
	ACCESS read-only
	STATUS mandatory
	DESCRIPTION
		"Refer to the textual convention for more details."
	::= { hpiSensorEvtCatThresholdEntry 2 }

hpiSensorEvtCatThresholdAssertEvents 	OBJECT-TYPE
	SYNTAX SaHpiThresholdEvents
	ACCESS read-only
	STATUS mandatory
	DESCRIPTION
		"Refer to the textual convention for more details."
	::= { hpiSensorEvtCatThresholdEntry 3 }

hpiSensorEvtCatThresholdDeassertEvents 	OBJECT-TYPE
	SYNTAX SaHpiThresholdEvents
	ACCESS read-only
	STATUS mandatory
	DESCRIPTION
		"Refer to the textual convention for more details."
	::= { hpiSensorEvtCatThresholdEntry 4 }

hpiSensorEvtCatUsageEntryCount 	OBJECT-TYPE
	SYNTAX Counter
	ACCESS read-only
	STATUS mandatory
	DESCRIPTION
		""
	::= { hpiSensorEvtCat 3 }

hpiSensorEvtCatUsageTable 	OBJECT-TYPE
	SYNTAX SEQUENCE OF HpiSensorEvtCatUsageEntry
	ACCESS not-accessible
	STATUS mandatory
	DESCRIPTION
		""
	::= { hpiSensorEvtCat 4 }

hpiSensorEvtCatUsageEntry 	OBJECT-TYPE
	SYNTAX HpiSensorEvtCatUsageEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatUsageTable 1 }

HpiSensorEvtCatUsageEntry ::= SEQUENCE {
	hpiSensorEvtCatUsageCurrentEvents    SaHpiUsageEvents,
	hpiSensorEvtCatUsageSupportedEvents  SaHpiUsageEvents,
	hpiSensorEvtCatUsageAssertEvents     SaHpiUsageEvents,
	hpiSensorEvtCatUsageDeassertEvents   SaHpiUsageEvents
	}

hpiSensorEvtCatUsageCurrentEvents 	OBJECT-TYPE
	SYNTAX SaHpiUsageEvents
	ACCESS read-only
	STATUS mandatory
	DESCRIPTION
		"Refer to the textual convention for more details."
	::= { hpiSensorEvtCatUsageEntry 1 }

hpiSensorEvtCatUsageSupportedEvents 	OBJECT-TYPE
	SYNTAX SaHpiUsageEvents
	ACCESS read-only
	STATUS mandatory
	DESCRIPTION
		"Refer to the textual convention for more details."
	::= { hpiSensorEvtCatUsageEntry 2 }

hpiSensorEvtCatUsageAssertEvents 	OBJECT-TYPE
	SYNTAX SaHpiUsageEvents
	ACCESS read-only
	STATUS mandatory
	DESCRIPTION
		"Refer to the textual convention for more details."
	::= { hpiSensorEvtCatUsageEntry 3 }

hpiSensorEvtCatUsageDeassertEvents 	OBJECT-TYPE
	SYNTAX SaHpiUsageEvents
	ACCESS read-only
	STATUS mandatory
	DESCRIPTION
		"Refer to the textual convention for more details."
	::= { hpiSensorEvtCatUsageEntry 4 }

hpiSensorEvtCatStateEntryCount 	OBJECT-TYPE
	SYNTAX Counter
	ACCESS read-only
	STATUS mandatory
	DESCRIPTION
		""
	::= { hpiSensorEvtCat 5 }

hpiSensorEvtCatStateTable 	OBJECT-TYPE
	SYNTAX SEQUENCE OF HpiSensorEvtCatStateEntry
	ACCESS not-accessible
	STATUS mandatory
	DESCRIPTION
		""
	::= { hpiSensorEvtCat 6 }

hpiSensorEvtCatStateEntry 	OBJECT-TYPE
	SYNTAX HpiSensorEvtCatStateEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatStateTable 1 }

HpiSensorEvtCatStateEntry ::= SEQUENCE {
	hpiSensorEvtCatStateCurrentEvents    SaHpiStateEvents,
	hpiSensorEvtCatStateSupportedEvents  SaHpiStateEvents,
	hpiSensorEvtCatStateAssertEvents     SaHpiStateEvents,
	hpiSensorEvtCatStateDeassertEvents   SaHpiStateEvents
	}

hpiSensorEvtCatStateCurrentEvents 	OBJECT-TYPE
	SYNTAX SaHpiStateEvents
	ACCESS read-only
	STATUS mandatory
	DESCRIPTION
		"Refer to the textual convention for more details."
	::= { hpiSensorEvtCatStateEntry 1 }

hpiSensorEvtCatStateSupportedEvents 	OBJECT-TYPE
	SYNTAX SaHpiStateEvents
	ACCESS read-only
	STATUS mandatory
	DESCRIPTION
		"Refer to the textual convention for more details."
	::= { hpiSensorEvtCatStateEntry 2 }

hpiSensorEvtCatStateAssertEvents 	OBJECT-TYPE
	SYNTAX SaHpiStateEvents
	ACCESS read-only
	STATUS mandatory
	DESCRIPTION
		"Refer to the textual convention for more details."
	::= { hpiSensorEvtCatStateEntry 3 }

hpiSensorEvtCatStateDeassertEvents 	OBJECT-TYPE
	SYNTAX SaHpiStateEvents
	ACCESS read-only
	STATUS mandatory
	DESCRIPTION
		"Refer to the textual convention for more details."
	::= { hpiSensorEvtCatStateEntry 4 }

hpiSensorEvtCatPredFailEntryCount 	OBJECT-TYPE
	SYNTAX Counter
	ACCESS read-only
	STATUS mandatory
	DESCRIPTION
		""
	::= { hpiSensorEvtCat 7 }

hpiSensorEvtCatPredFailTable 	OBJECT-TYPE
	SYNTAX SEQUENCE OF HpiSensorEvtCatPredFailEntry
	ACCESS not-accessible
	STATUS mandatory
	DESCRIPTION
		""
	::= { hpiSensorEvtCat 8 }

hpiSensorEvtCatPredFailEntry 	OBJECT-TYPE
	SYNTAX HpiSensorEvtCatPredFailEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatPredFailTable 1 }

HpiSensorEvtCatPredFailEntry ::= SEQUENCE {
	hpiSensorEvtCatPredFailCurrentEvents    SaHpiPredFailEvents,
	hpiSensorEvtCatPredFailSupportedEvents  SaHpiPredFailEvents,
	hpiSensorEvtCatPredFailAssertEvents     SaHpiPredFailEvents,
	hpiSensorEvtCatPredFailDeassertEvents   SaHpiPredFailEvents
	}

hpiSensorEvtCatPredFailCurrentEvents 	OBJECT-TYPE
	SYNTAX SaHpiPredFailEvents
	ACCESS read-only
	STATUS mandatory
	DESCRIPTION
		"Refer to the textual convention for more details."
	::= { hpiSensorEvtCatPredFailEntry 1 }

hpiSensorEvtCatPredFailSupportedEvents 	OBJECT-TYPE
	SYNTAX SaHpiPredFailEvents
	ACCESS read-only
	STATUS mandatory
	DESCRIPTION
		"Refer to the textual convention for more details."
	::= { hpiSensorEvtCatPredFailEntry 2 }

hpiSensorEvtCatPredFailAssertEvents 	OBJECT-TYPE
	SYNTAX SaHpiPredFailEvents
	ACCESS read-only
	STATUS mandatory
	DESCRIPTION
		"Refer to the textual convention for more details."
	::= { hpiSensorEvtCatPredFailEntry 3 }

hpiSensorEvtCatPredFailDeassertEvents 	OBJECT-TYPE
	SYNTAX SaHpiPredFailEvents
	ACCESS read-only
	STATUS mandatory
	DESCRIPTION
		"Refer to the textual convention for more details."
	::= { hpiSensorEvtCatPredFailEntry 4 }

hpiSensorEvtCatLimitEntryCount 	OBJECT-TYPE
	SYNTAX Counter
	ACCESS read-only
	STATUS mandatory
	DESCRIPTION
		""
	::= { hpiSensorEvtCat 9 }

hpiSensorEvtCatLimitTable 	OBJECT-TYPE
	SYNTAX SEQUENCE OF HpiSensorEvtCatLimitEntry
	ACCESS not-accessible
	STATUS mandatory
	DESCRIPTION
		""
	::= { hpiSensorEvtCat 10 }

hpiSensorEvtCatLimitEntry 	OBJECT-TYPE
	SYNTAX HpiSensorEvtCatLimitEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatLimitTable 1 }

HpiSensorEvtCatLimitEntry ::= SEQUENCE {
	hpiSensorEvtCatLimitCurrentEvents    SaHpiLimitEvents,
	hpiSensorEvtCatLimitSupportedEvents  SaHpiLimitEvents,
	hpiSensorEvtCatLimitAssertEvents     SaHpiLimitEvents,
	hpiSensorEvtCatLimitDeassertEvents   SaHpiLimitEvents
	}

hpiSensorEvtCatLimitCurrentEvents 	OBJECT-TYPE
	SYNTAX SaHpiLimitEvents
	ACCESS read-only
	STATUS mandatory
	DESCRIPTION
		"Refer to the textual convention for more details."
	::= { hpiSensorEvtCatLimitEntry 1 }

hpiSensorEvtCatLimitSupportedEvents 	OBJECT-TYPE
	SYNTAX SaHpiLimitEvents
	ACCESS read-only
	STATUS mandatory
	DESCRIPTION
		"Refer to the textual convention for more details."
	::= { hpiSensorEvtCatLimitEntry 2 }

hpiSensorEvtCatLimitAssertEvents 	OBJECT-TYPE
	SYNTAX SaHpiLimitEvents
	ACCESS read-only
	STATUS mandatory
	DESCRIPTION
		"Refer to the textual convention for more details."
	::= { hpiSensorEvtCatLimitEntry 3 }

hpiSensorEvtCatLimitDeassertEvents 	OBJECT-TYPE
	SYNTAX SaHpiLimitEvents
	ACCESS read-only
	STATUS mandatory
	DESCRIPTION
		"Refer to the textual convention for more details."
	::= { hpiSensorEvtCatLimitEntry 4 }

hpiSensorEvtCatPerformanceEntryCount 	OBJECT-TYPE
	SYNTAX Counter
	ACCESS read-only
	STATUS mandatory
	DESCRIPTION
		""
	::= { hpiSensorEvtCat 11 }

hpiSensorEvtCatPerformanceTable 	OBJECT-TYPE
	SYNTAX SEQUENCE OF HpiSensorEvtCatPerformanceEntry
	ACCESS not-accessible
	STATUS mandatory
	DESCRIPTION
		""
	::= { hpiSensorEvtCat 12 }

hpiSensorEvtCatPerformanceEntry 	OBJECT-TYPE
	SYNTAX HpiSensorEvtCatPerformanceEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatPerformanceTable 1 }

HpiSensorEvtCatPerformanceEntry ::= SEQUENCE {
	hpiSensorEvtCatPerformanceCurrentEvents    SaHpiPerformanceEvents,
	hpiSensorEvtCatPerformanceSupportedEvents  SaHpiPerformanceEvents,
	hpiSensorEvtCatPerformanceAssertEvents     SaHpiPerformanceEvents,
	hpiSensorEvtCatPerformanceDeassertEvents   SaHpiPerformanceEvents
	}

hpiSensorEvtCatPerformanceCurrentEvents 	OBJECT-TYPE
	SYNTAX SaHpiPerformanceEvents
	ACCESS read-only
	STATUS mandatory
	DESCRIPTION
		"Refer to the textual convention for more details."
	::= { hpiSensorEvtCatPerformanceEntry 1 }

hpiSensorEvtCatPerformanceSupportedEvents 	OBJECT-TYPE
	SYNTAX SaHpiPerformanceEvents
	ACCESS read-only
	STATUS mandatory
	DESCRIPTION
		"Refer to the textual convention for more details."
	::= { hpiSensorEvtCatPerformanceEntry 2 }

hpiSensorEvtCatPerformanceAssertEvents 	OBJECT-TYPE
	SYNTAX SaHpiPerformanceEvents
	ACCESS read-only
	STATUS mandatory
	DESCRIPTION
		"Refer to the textual convention for more details."
	::= { hpiSensorEvtCatPerformanceEntry 3 }

hpiSensorEvtCatPerformanceDeassertEvents 	OBJECT-TYPE
	SYNTAX SaHpiPerformanceEvents
	ACCESS read-only
	STATUS mandatory
	DESCRIPTION
		"Refer to the textual convention for more details."
	::= { hpiSensorEvtCatPerformanceEntry 4 }

hpiSensorEvtCatSeverityEntryCount 	OBJECT-TYPE
	SYNTAX Counter
	ACCESS read-only
	STATUS mandatory
	DESCRIPTION
		""
	::= { hpiSensorEvtCat 13 }

hpiSensorEvtCatSeverityTable 	OBJECT-TYPE
	SYNTAX SEQUENCE OF HpiSensorEvtCatSeverityEntry
	ACCESS not-accessible
	STATUS mandatory
	DESCRIPTION
		""
	::= { hpiSensorEvtCat 14 }

hpiSensorEvtCatSeverityEntry 	OBJECT-TYPE
	SYNTAX HpiSensorEvtCatSeverityEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatSeverityTable 1 }

HpiSensorEvtCatSeverityEntry ::= SEQUENCE {
	hpiSensorEvtCatSeverityCurrentEvents    SaHpiSeverityEvents,
	hpiSensorEvtCatSeveritySupportedEvents  SaHpiSeverityEvents,
	hpiSensorEvtCatSeverityAssertEvents     SaHpiSeverityEvents,
	hpiSensorEvtCatSeverityDeassertEvents   SaHpiSeverityEvents
	}

hpiSensorEvtCatSeverityCurrentEvents 	OBJECT-TYPE
	SYNTAX SaHpiSeverityEvents
	ACCESS read-only
	STATUS mandatory
	DESCRIPTION
		"Refer to the textual convention for more details."
	::= { hpiSensorEvtCatSeverityEntry 1 }

hpiSensorEvtCatSeveritySupportedEvents 	OBJECT-TYPE
	SYNTAX SaHpiSeverityEvents
	ACCESS read-only
	STATUS mandatory
	DESCRIPTION
		"Refer to the textual convention for more details."
	::= { hpiSensorEvtCatSeverityEntry 2 }

hpiSensorEvtCatSeverityAssertEvents 	OBJECT-TYPE
	SYNTAX SaHpiSeverityEvents
	ACCESS read-only
	STATUS mandatory
	DESCRIPTION
		"Refer to the textual convention for more details."
	::= { hpiSensorEvtCatSeverityEntry 3 }

hpiSensorEvtCatSeverityDeassertEvents 	OBJECT-TYPE
	SYNTAX SaHpiSeverityEvents
	ACCESS read-only
	STATUS mandatory
	DESCRIPTION
		"Refer to the textual convention for more details."
	::= { hpiSensorEvtCatSeverityEntry 4 }

hpiSensorEvtCatPresenceEntryCount 	OBJECT-TYPE
	SYNTAX Counter
	ACCESS read-only
	STATUS mandatory
	DESCRIPTION
		""
	::= { hpiSensorEvtCat 15 }

hpiSensorEvtCatPresenceTable 	OBJECT-TYPE
	SYNTAX SEQUENCE OF HpiSensorEvtCatPresenceEntry
	ACCESS not-accessible
	STATUS mandatory
	DESCRIPTION
		""
	::= { hpiSensorEvtCat 16 }

hpiSensorEvtCatPresenceEntry 	OBJECT-TYPE
	SYNTAX HpiSensorEvtCatPresenceEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatPresenceTable 1 }

HpiSensorEvtCatPresenceEntry ::= SEQUENCE {
	hpiSensorEvtCatPresenceCurrentEvents    SaHpiPresenceEvents,
	hpiSensorEvtCatPresenceSupportedEvents  SaHpiPresenceEvents,
	hpiSensorEvtCatPresenceAssertEvents     SaHpiPresenceEvents,
	hpiSensorEvtCatPresenceDeassertEvents   SaHpiPresenceEvents
	}

hpiSensorEvtCatPresenceCurrentEvents 	OBJECT-TYPE
	SYNTAX SaHpiPresenceEvents
	ACCESS read-only
	STATUS mandatory
	DESCRIPTION
		"Refer to the textual convention for more details."
	::= { hpiSensorEvtCatPresenceEntry 1 }

hpiSensorEvtCatPresenceSupportedEvents 	OBJECT-TYPE
	SYNTAX SaHpiPresenceEvents
	ACCESS read-only
	STATUS mandatory
	DESCRIPTION
		"Refer to the textual convention for more details."
	::= { hpiSensorEvtCatPresenceEntry 2 }

hpiSensorEvtCatPresenceAssertEvents 	OBJECT-TYPE
	SYNTAX SaHpiPresenceEvents
	ACCESS read-only
	STATUS mandatory
	DESCRIPTION
		"Refer to the textual convention for more details."
	::= { hpiSensorEvtCatPresenceEntry 3 }

hpiSensorEvtCatPresenceDeassertEvents 	OBJECT-TYPE
	SYNTAX SaHpiPresenceEvents
	ACCESS read-only
	STATUS mandatory
	DESCRIPTION
		"Refer to the textual convention for more details."
	::= { hpiSensorEvtCatPresenceEntry 4 }

hpiSensorEvtCatEnableEntryCount 	OBJECT-TYPE
	SYNTAX Counter
	ACCESS read-only
	STATUS mandatory
	DESCRIPTION
		""
	::= { hpiSensorEvtCat 17 }

hpiSensorEvtCatEnableTable 	OBJECT-TYPE
	SYNTAX SEQUENCE OF HpiSensorEvtCatEnableEntry
	ACCESS not-accessible
	STATUS mandatory
	DESCRIPTION
		""
	::= { hpiSensorEvtCat 18 }

hpiSensorEvtCatEnableEntry 	OBJECT-TYPE
	SYNTAX HpiSensorEvtCatEnableEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatEnableTable 1 }

HpiSensorEvtCatEnableEntry ::= SEQUENCE {
	hpiSensorEvtCatEnableCurrentEvents    SaHpiEnableEvents,
	hpiSensorEvtCatEnableSupportedEvents  SaHpiEnableEvents,
	hpiSensorEvtCatEnableAssertEvents     SaHpiEnableEvents,
	hpiSensorEvtCatEnableDeassertEvents   SaHpiEnableEvents
	}

hpiSensorEvtCatEnableCurrentEvents 	OBJECT-TYPE
	SYNTAX SaHpiEnableEvents
	ACCESS read-only
	STATUS mandatory
	DESCRIPTION
		"Refer to the textual convention for more details."
	::= { hpiSensorEvtCatEnableEntry 1 }

hpiSensorEvtCatEnableSupportedEvents 	OBJECT-TYPE
	SYNTAX SaHpiEnableEvents
	ACCESS read-only
	STATUS mandatory
	DESCRIPTION
		"Refer to the textual convention for more details."
	::= { hpiSensorEvtCatEnableEntry 2 }

hpiSensorEvtCatEnableAssertEvents 	OBJECT-TYPE
	SYNTAX SaHpiEnableEvents
	ACCESS read-only
	STATUS mandatory
	DESCRIPTION
		"Refer to the textual convention for more details."
	::= { hpiSensorEvtCatEnableEntry 3 }

hpiSensorEvtCatEnableDeassertEvents 	OBJECT-TYPE
	SYNTAX SaHpiEnableEvents
	ACCESS read-only
	STATUS mandatory
	DESCRIPTION
		"Refer to the textual convention for more details."
	::= { hpiSensorEvtCatEnableEntry 4 }

hpiSensorEvtCatAvailabilityEntryCount 	OBJECT-TYPE
	SYNTAX Counter
	ACCESS read-only
	STATUS mandatory
	DESCRIPTION
		""
	::= { hpiSensorEvtCat 19 }

hpiSensorEvtCatAvailabilityTable 	OBJECT-TYPE
	SYNTAX SEQUENCE OF HpiSensorEvtCatAvailabilityEntry
	ACCESS not-accessible
	STATUS mandatory
	DESCRIPTION
		""
	::= { hpiSensorEvtCat 20 }

hpiSensorEvtCatAvailabilityEntry 	OBJECT-TYPE
	SYNTAX HpiSensorEvtCatAvailabilityEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatAvailabilityTable 1 }

HpiSensorEvtCatAvailabilityEntry ::= SEQUENCE {
	hpiSensorEvtCatAvailabilityCurrentEvents    SaHpiAvailabilityEvents,
	hpiSensorEvtCatAvailabilitySupportedEvents  SaHpiAvailabilityEvents,
	hpiSensorEvtCatAvailabilityAssertEvents     SaHpiAvailabilityEvents,
	hpiSensorEvtCatAvailabilityDeassertEvents   SaHpiAvailabilityEvents
	}

hpiSensorEvtCatAvailabilityCurrentEvents 	OBJECT-TYPE
	SYNTAX SaHpiAvailabilityEvents
	ACCESS read-only
	STATUS mandatory
	DESCRIPTION
		"Refer to the textual convention for more details."
	::= { hpiSensorEvtCatAvailabilityEntry 1 }

hpiSensorEvtCatAvailabilitySupportedEvents 	OBJECT-TYPE
	SYNTAX SaHpiAvailabilityEvents
	ACCESS read-only
	STATUS mandatory
	DESCRIPTION
		"Refer to the textual convention for more details."
	::= { hpiSensorEvtCatAvailabilityEntry 2 }

hpiSensorEvtCatAvailabilityAssertEvents 	OBJECT-TYPE
	SYNTAX SaHpiAvailabilityEvents
	ACCESS read-only
	STATUS mandatory
	DESCRIPTION
		"Refer to the textual convention for more details."
	::= { hpiSensorEvtCatAvailabilityEntry 3 }

hpiSensorEvtCatAvailabilityDeassertEvents 	OBJECT-TYPE
	SYNTAX SaHpiAvailabilityEvents
	ACCESS read-only
	STATUS mandatory
	DESCRIPTION
		"Refer to the textual convention for more details."
	::= { hpiSensorEvtCatAvailabilityEntry 4 }

hpiSensorEvtCatRedundancyEntryCount 	OBJECT-TYPE
	SYNTAX Counter
	ACCESS read-only
	STATUS mandatory
	DESCRIPTION
		""
	::= { hpiSensorEvtCat 21 }

hpiSensorEvtCatRedundancyTable 	OBJECT-TYPE
	SYNTAX SEQUENCE OF HpiSensorEvtCatRedundancyEntry
	ACCESS not-accessible
	STATUS mandatory
	DESCRIPTION
		""
	::= { hpiSensorEvtCat 22 }

hpiSensorEvtCatRedundancyEntry 	OBJECT-TYPE
	SYNTAX HpiSensorEvtCatRedundancyEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatRedundancyTable 1 }

HpiSensorEvtCatRedundancyEntry ::= SEQUENCE {
	hpiSensorEvtCatRedundancyCurrentEvents    SaHpiRedundancyEvents,
	hpiSensorEvtCatRedundancySupportedEvents  SaHpiRedundancyEvents,
	hpiSensorEvtCatRedundancyAssertEvents     SaHpiRedundancyEvents,
	hpiSensorEvtCatRedundancyDeassertEvents   SaHpiRedundancyEvents
	}

hpiSensorEvtCatRedundancyCurrentEvents 	OBJECT-TYPE
	SYNTAX SaHpiRedundancyEvents
	ACCESS read-only
	STATUS mandatory
	DESCRIPTION
		"Refer to the textual convention for more details."
	::= { hpiSensorEvtCatRedundancyEntry 1 }

hpiSensorEvtCatRedundancySupportedEvents 	OBJECT-TYPE
	SYNTAX SaHpiRedundancyEvents
	ACCESS read-only
	STATUS mandatory
	DESCRIPTION
		"Refer to the textual convention for more details."
	::= { hpiSensorEvtCatRedundancyEntry 2 }

hpiSensorEvtCatRedundancyAssertEvents 	OBJECT-TYPE
	SYNTAX SaHpiRedundancyEvents
	ACCESS read-only
	STATUS mandatory
	DESCRIPTION
		"Refer to the textual convention for more details."
	::= { hpiSensorEvtCatRedundancyEntry 3 }

hpiSensorEvtCatRedundancyDeassertEvents 	OBJECT-TYPE
	SYNTAX SaHpiRedundancyEvents
	ACCESS read-only
	STATUS mandatory
	DESCRIPTION
		"Refer to the textual convention for more details."
	::= { hpiSensorEvtCatRedundancyEntry 4 }

hpiSensorEvtCatGenericEntryCount 	OBJECT-TYPE
	SYNTAX Counter
	ACCESS read-only
	STATUS mandatory
	DESCRIPTION
		""
	::= { hpiSensorEvtCat 23 }

hpiSensorEvtCatGenericTable 	OBJECT-TYPE
	SYNTAX SEQUENCE OF HpiSensorEvtCatGenericEntry
	ACCESS not-accessible
	STATUS mandatory
	DESCRIPTION
		""
	::= { hpiSensorEvtCat 24 }

hpiSensorEvtCatGenericEntry 	OBJECT-TYPE
	SYNTAX HpiSensorEvtCatGenericEntry
	ACCESS not-accessible
	STATUS mandatory
	DESCRIPTION
		"This is the sensor resource data record which
		 describes all of the static  data associated with a sensor."
	INDEX {
		hpiDomainId,
		hpiResourceId,
		hpiRdrType,
		hpiRdrId
	}
	::= { hpiSensorEvtCatGenericTable 1 }

HpiSensorEvtCatGenericEntry ::= SEQUENCE {
	hpiSensorEvtCatGenericCurrentEvents    SaHpiGenericEvents,
	hpiSensorEvtCatGenericSupportedEvents  SaHpiGenericEvents,
	hpiSensorEvtCatGenericAssertEvents     SaHpiGenericEvents,
	hpiSensorEvtCatGenericDeassertEvents   SaHpiGenericEvents
	}

hpiSensorEvtCatGenericCurrentEvents 	OBJECT-TYPE
	SYNTAX SaHpiGenericEvents
	ACCESS read-only
	STATUS mandatory
	DESCRIPTION
		"Refer to the textual convention for more details."
	::= { hpiSensorEvtCatGenericEntry 1 }

hpiSensorEvtCatGenericSupportedEvents 	OBJECT-TYPE
	SYNTAX SaHpiGenericEvents
	ACCESS read-only
	STATUS mandatory
	DESCRIPTION
		"Refer to the textual convention for more details."
	::= { hpiSensorEvtCatGenericEntry 2 }

hpiSensorEvtCatGenericAssertEvents 	OBJECT-TYPE
	SYNTAX SaHpiGenericEvents
	ACCESS read-only
	STATUS mandatory
	DESCRIPTION
		"Refer to the textual convention for more details."
	::= { hpiSensorEvtCatGenericEntry 3 }

hpiSensorEvtCatGenericDeassertEvents 	OBJECT-TYPE
	SYNTAX SaHpiGenericEvents
	ACCESS read-only
	STATUS mandatory
	DESCRIPTION
		"Refer to the textual convention for more details."
	::= { hpiSensorEvtCatGenericEntry 4 }

hpiRdrInventoryCount 	OBJECT-TYPE
	SYNTAX Counter
	ACCESS read-only
	STATUS mandatory
	DESCRIPTION
		"Number of inventory data records in this system."
	::= { hpiResources 7 }

hpiInventory OBJECT IDENTIFIER ::= {hpiResources 8}

hpiIdrEntryCount 	OBJECT-TYPE
	SYNTAX Counter
	ACCESS read-only
	STATUS mandatory
	DESCRIPTION
		"The number of inventory resource data records present on this system."
	::= { hpiInventory 1 }

hpiIdrTable 	OBJECT-TYPE
	SYNTAX SEQUENCE OF HpiIdrEntry
	ACCESS not-accessible
	STATUS mandatory
	DESCRIPTION
		"Table defining entity inventory resource data records."
	::= { hpiInventory 2 }

hpiIdrEntry 	OBJECT-TYPE
	SYNTAX HpiIdrEntry
	ACCESS not-accessible
	STATUS mandatory
	DESCRIPTION
		"These structures are used to read and write inventory data to entity 
		 inventory   repositories within a resource.
		 All inventory data contained in an inventory data repository (IDR)
		 must be represented in the RDR repository"
	INDEX {
		hpiDomainId,
		hpiResourceId,
		hpiRdrType,
		hpiRdrId
	}
	::= { hpiIdrTable 1 }

HpiIdrEntry ::= SEQUENCE {
	hpiIdrPersistent   TruthValue,
	hpiIdrOem          Gauge,
	hpiIdrUpdateCount  Gauge,
	hpiIdrIsReadOnly   TruthValue,
	hpiIdrNumAreas     Gauge
	}

hpiIdrPersistent 	OBJECT-TYPE
	SYNTAX TruthValue
	ACCESS read-only
	STATUS mandatory
	DESCRIPTION
		"True indicates that updates to IDR are automatically and immediately
		 persisted. False indicates that updates are notimmediately persisted;
		 but optionally may be persisted via hpiParmControl function, as
		 defined in implementation documentation."
	::= { hpiIdrEntry 1 }

hpiIdrOem 	OBJECT-TYPE
	SYNTAX Gauge
	ACCESS read-only
	STATUS mandatory
	DESCRIPTION
		"OEM value for the Idr record. This is manufacturere'
		 specific value."
	::= { hpiIdrEntry 2 }

hpiIdrUpdateCount 	OBJECT-TYPE
	SYNTAX Gauge
	ACCESS read-only
	STATUS mandatory
	DESCRIPTION
		"The count is incremented any time the IDR is changed."
	::= { hpiIdrEntry 3 }

hpiIdrIsReadOnly 	OBJECT-TYPE
	SYNTAX TruthValue
	ACCESS read-only
	STATUS mandatory
	DESCRIPTION
		"Describes if the IDR is read-only. If such, all area
		 headers and fields are flagged as well."
	::= { hpiIdrEntry 4 }

hpiIdrNumAreas 	OBJECT-TYPE
	SYNTAX Gauge
	ACCESS read-only
	STATUS mandatory
	DESCRIPTION
		"Number of area containted in IDR"
	::= { hpiIdrEntry 5 }

hpiIdrAreaEntryCount 	OBJECT-TYPE
	SYNTAX Counter
	ACCESS read-only
	STATUS mandatory
	DESCRIPTION
		"The number of inventory resource area data records present on this 
		 system."
	::= { hpiInventory 3 }

hpiIdrAreaTable 	OBJECT-TYPE
	SYNTAX SEQUENCE OF HpiIdrAreaEntry
	ACCESS not-accessible
	STATUS mandatory
	DESCRIPTION
		"Table defining inventory data respoitory data area records."
	::= { hpiInventory 4 }

hpiIdrAreaEntry 	OBJECT-TYPE
	SYNTAX HpiIdrAreaEntry
	ACCESS not-accessible
	STATUS mandatory
	DESCRIPTION
		"These structures are used to read and write inventory data respository
		 data area records.
		 The four-tuple index value consits of:
		 - hpiDomainId, which is the domain of the resource
		 - hpiResourceId, the id value for the resource
		 - hpiIdrId, the id value of entity inventory
		 - hpiAreaId, the id value of inventory data area.
		 New Area's are Created when 'hpiIdrAreaType' is written with
		 the appropriate index values's.  The 'AreadId' index is ignored.
		 SAI-HPI-B.01.01, pages 98...100, 104."
	INDEX {
		hpiDomainId,
		hpiResourceId,
		hpiRdrType,
		hpiRdrId,
		hpiIdrAreaId
	}
	::= { hpiIdrAreaTable 1 }

HpiIdrAreaEntry ::= SEQUENCE {
	hpiIdrAreaId          SaHpiInstrumentId,
	hpiIdrAreaType        INTEGER,
	hpiIdrAreaIsReadOnly  TruthValue,
	hpiIdrAreaNumFields   Gauge,
	hpiIdrAreaRowStatus   RowStatus
	}

hpiIdrAreaId 	OBJECT-TYPE
	SYNTAX SaHpiInstrumentId
	ACCESS not-accessible
	STATUS mandatory
	DESCRIPTION
		"See TEXTUAL-CONVENTION 'SaHpiInstrumentId'"
	::= { hpiIdrAreaEntry 1 }

hpiIdrAreaType 	OBJECT-TYPE
	SYNTAX INTEGER {
                               undefined (0),
                               internalUse (177),
                               chassisInfo (178),
                               boardInfo (179),
                               productInfo (180),
                               oem (193),
                               unspecified (256)
                        }
	ACCESS read-write
	STATUS mandatory
	DESCRIPTION
		"The type of Area.
		 Note: Enumerated values are increased by one value compared to
		 SAI-HPI-B spec."
	::= { hpiIdrAreaEntry 2 }

hpiIdrAreaIsReadOnly 	OBJECT-TYPE
	SYNTAX TruthValue
	ACCESS read-only
	STATUS mandatory
	DESCRIPTION
		"Describes if an area is read-only.  All area headers in a
		 read-only IDR are flagged as read-only as well."
	::= { hpiIdrAreaEntry 3 }

hpiIdrAreaNumFields 	OBJECT-TYPE
	SYNTAX Gauge
	ACCESS read-only
	STATUS mandatory
	DESCRIPTION
		"Number of Fields contained in Area"
	::= { hpiIdrAreaEntry 4 }

hpiIdrAreaRowStatus 	OBJECT-TYPE
	SYNTAX RowStatus
	ACCESS read-write
	STATUS mandatory
	DESCRIPTION
		"This columnar node contains the status of the row and also
		 perform add and delete operations.
		 
		 The status column uses three defined values:
		 
		 - `active(1)', which indicates that the conceptual row is
		 available for use by the managed device;
		 
		 - `notInService(2)', which indicates that the conceptual
		 row exists in the agent, but is unavailable for use by
		 the managed device (see NOTE below); 'notInService' has
		 no implication regarding the internal consistency of
		 the row, availability of resources, or consistency with
		 the current state of the managed device.
		 
		 - `createAndWait(5)', which is supplied by a management
		 station wishing to create a new instance of a
		 conceptual row (but not make it available for use by
		 the managed device). This function is used to add
		 an Area to the specified Inventory Data Repository.
		 The row is created (and changes state to 'active' when
		 the hpiAreaType has been correctly set) to a
		 new instance of the conceptual row. The dis-allowed
		 hpiAreaType value is undefined(0) and unspecified(256)
		 
		 - `destroy(6)', which is supplied by a management station
		 wishing to delete all of the instances associated with
		 an existing conceptual row. This function allows the
		 HPI MIB User to delete an Inventory Data Area, including
		 the Area header and all fields contained with the area,
		 from a particular Inventory Data Repository.
		 In some implementations, certain Areas are intrinsically
		 read-only.  The hpiAreaIsReadOnly flag, indicates if the
		 Area is read-only. If the Inventory Data Area is not
		 read-only, but contains a Field that is read-only, the Area
		 cannot be deleted.  An attempt to delete an Area that
		 contains a read-only Field will return an error."
	::= { hpiIdrAreaEntry 5 }

hpiIdrFieldEntryCount 	OBJECT-TYPE
	SYNTAX Counter
	ACCESS read-only
	STATUS mandatory
	DESCRIPTION
		"The number of inventory data repository IdrField records."
	::= { hpiInventory 5 }

hpiIdrFieldTable 	OBJECT-TYPE
	SYNTAX SEQUENCE OF HpiIdrFieldEntry
	ACCESS not-accessible
	STATUS mandatory
	DESCRIPTION
		"Table defining inventory data repository IdrField records."
	::= { hpiInventory 6 }

hpiIdrFieldEntry 	OBJECT-TYPE
	SYNTAX HpiIdrFieldEntry
	ACCESS not-accessible
	STATUS mandatory
	DESCRIPTION
		"These structures are used to read and write inventory data repository
		 IdrField records."
	INDEX {
		hpiDomainId,
		hpiResourceId,
		hpiRdrType,
		hpiRdrId,
		hpiIdrAreaId,
		hpiIdrFieldId
	}
	::= { hpiIdrFieldTable 1 }

HpiIdrFieldEntry ::= SEQUENCE {
	hpiIdrFieldId            SaHpiInstrumentId,
	hpiIdrFieldType          INTEGER,
	hpiIdrFieldIsReadOnly    TruthValue,
	hpiIdrFieldDataType      SaHpiTextType,
	hpiIdrFieldDataLanguage  SaHpiTextLanguage,
	hpiIdrFieldData          SaHpiText,
	hpiIdrFieldDataString    DisplayString,
	hpiIdrFieldStatus        RowStatus
	}

hpiIdrFieldId 	OBJECT-TYPE
	SYNTAX SaHpiInstrumentId
	ACCESS not-accessible
	STATUS mandatory
	DESCRIPTION
		"See TEXTUAL-CONVENTION 'SaHpiInstrumentId'"
	::= { hpiIdrFieldEntry 1 }

hpiIdrFieldType 	OBJECT-TYPE
	SYNTAX INTEGER {
                               undefined (0),
                               chassisType (1),
                               mfgDatetime (2),
                               manufacturer (3),
                               productName (4),
                               productVersion (5),
                               serialNumber (6),
                               partNumber (7),
                               fileId (8),
                               assetTag (9),
                               custom (10),
                               unspecified (256)
                        }
	ACCESS read-write
	STATUS mandatory
	DESCRIPTION
		"Inventory Data IdrField type definitions.
		 
		 Note: Enumerated values are increased by one value compared to
		 SAI-HPI-B spec."
	::= { hpiIdrFieldEntry 2 }

hpiIdrFieldIsReadOnly 	OBJECT-TYPE
	SYNTAX TruthValue
	ACCESS read-only
	STATUS mandatory
	DESCRIPTION
		"Describes if an IdrField is read-only.  All IdrField headers in a
		 read-only IDR are flagged as read-only as well."
	::= { hpiIdrFieldEntry 3 }

hpiIdrFieldDataType 	OBJECT-TYPE
	SYNTAX SaHpiTextType
	ACCESS read-write
	STATUS mandatory
	DESCRIPTION
		"IdrField Data.
		 See Definition for SaHpiTextType for more details."
	::= { hpiIdrFieldEntry 4 }

hpiIdrFieldDataLanguage 	OBJECT-TYPE
	SYNTAX SaHpiTextLanguage
	ACCESS read-write
	STATUS mandatory
	DESCRIPTION
		"IdrField Data.
		 See Definition for SaHpiTextLanguage for more details."
	::= { hpiIdrFieldEntry 6 }

hpiIdrFieldData 	OBJECT-TYPE
	SYNTAX SaHpiText
	ACCESS read-write
	STATUS mandatory
	DESCRIPTION
		"IdrField Data. The type of date is specified
		 by hpiResourceTagTextType and hpiResourceTagLanguage."
	::= { hpiIdrFieldEntry 7 }

hpiIdrFieldDataString 	OBJECT-TYPE
	SYNTAX DisplayString
	ACCESS read-write
	STATUS mandatory
	DESCRIPTION
		"IdrField Data. The type of date is specified
		 by hpiResourceTagTextType and hpiResourceTagLanguage."
	::= { hpiIdrFieldEntry 8 }

hpiIdrFieldStatus 	OBJECT-TYPE
	SYNTAX RowStatus
	ACCESS read-write
	STATUS mandatory
	DESCRIPTION
		"This object provides a method to create and delete a
		 Data Inventory IdrField.
		 
		 Supported states are:
		          active(1),
		          notInService(2),
		          createAndWait(5),
		          destroy(6)
		 The RowStatus textual convention is used to manage the
		 creation and deletion of conceptual rows, and is used as the
		 value of the SYNTAX clause for the status column of a
		 conceptual row (as described in Section 7.7.1 of [2].)
		 
		 The status column has four defined values:
		 
		 - `active(1)', which indicates that the conceptual row is
		 available for use by the managed device. For it to in such
		 state, the columnar objects: hpiIdrFieldType,
		 hpiIdrFieldTextType, hpiTextLanguage, and hpiIdrFieldText
		 must have valid values.
		 
		 - `notInService(2)', which indicates that the conceptual
		 row exists in the agent, but is unavailable for use by
		 the managed device (see NOTE below); 'notInService' has
		 no implication regarding the internal consistency of
		 the row, availability of resources, or consistency with
		 the current state of the managed device.
		 
		 - `createAndWait(5)', which is supplied by a management
		 station wishing to create a new instance of a
		 conceptual row. After setting this value, the management
		 station is responsible of providing valid values to the
		 columnar objects: hpiIdrFieldIsReadOnly, hpiIdrFieldType,
		 hpiIdrFieldTextType, hpiTextLanguage and hpiIdrFieldText.
		 
		 - `destroy(6)', which is supplied by a management station
		 wishing to delete all of the instances associated with
		 an existing conceptual row."
	::= { hpiIdrFieldEntry 9 }

hpiRdrWatchdogsCount 	OBJECT-TYPE
	SYNTAX Counter
	ACCESS read-only
	STATUS mandatory
	DESCRIPTION
		"Number of watchdogs data records in this system."
	::= { hpiResources 9 }

hpiWatchdogs OBJECT IDENTIFIER ::= {hpiResources 10}

hpiWatchdogEntryCount 	OBJECT-TYPE
	SYNTAX Counter
	ACCESS read-only
	STATUS mandatory
	DESCRIPTION
		"The number of watchdogs present on this system."
	::= { hpiWatchdogs 1 }

hpiWatchdogTable 	OBJECT-TYPE
	SYNTAX SEQUENCE OF HpiWatchdogEntry
	ACCESS not-accessible
	STATUS mandatory
	DESCRIPTION
		"Table of watchdog  resource data records."
	::= { hpiWatchdogs 2 }

hpiWatchdogEntry 	OBJECT-TYPE
	SYNTAX HpiWatchdogEntry
	ACCESS not-accessible
	STATUS mandatory
	DESCRIPTION
		"When the 'Watchdog' capability is set in a resource, a watchdog with
		 an identifier of SAHPI_DEFAULT_WATCHDOG_NUM is required. All
		 watchdogs must be represented in the RDR repository with an
		 hpiWatchdogRecT, including the watchdog with an identifier of
		 SAHPI_DEFAULT_WATCHDOG_NUM."
	INDEX {
		hpiDomainId,
		hpiResourceId,
		hpiRdrType,
		hpiRdrId
	}
	::= { hpiWatchdogTable 1 }

HpiWatchdogEntry ::= SEQUENCE {
	hpiWatchdogLog                 TruthValue,
	hpiWatchdogRunning             TruthValue,
	hpiWatchdogTimerUse            SaHpiWatchdogTimerUse,
	hpiWatchdogTimerAction         INTEGER,
	hpiWatchdogPretimerInterrupt   SaHpiWatchdogPreTimerAction,
	hpiWatchdogPreTimeoutInterval  Gauge,
	hpiWatchdogTimerUseExpFlags    OCTET STRING,
	hpiWatchdogTimerInitialCount   Gauge,
	hpiWatchdogTimerPresentCount   Gauge,
	hpiWatchdogTimerReset          TruthValue,
	hpiWatchdogOem                 Gauge
	}

hpiWatchdogLog 	OBJECT-TYPE
	SYNTAX TruthValue
	ACCESS read-write
	STATUS mandatory
	DESCRIPTION
		"
		 If you read this object, it means:
		 Log -  indicates whether or not the Watchdog is configured to
		 issue an event when it next times out. TRUE=event will
		    be issued on timeout.
		 If you set this object, it means:
		 Log -  indicates whether or not the Watchdog should  issue
		    an event when it next times out. TRUE=event will be
		    issued on timeout.
		 
		 Setting this object will NOT take effect on the Watchdog until the
		 object SaHpiWatchdogRunning is set to true(1)."
	::= { hpiWatchdogEntry 1 }

hpiWatchdogRunning 	OBJECT-TYPE
	SYNTAX TruthValue
	ACCESS read-write
	STATUS mandatory
	DESCRIPTION
		"
		 If you read this object, it means:
		 Running -       indicates whether or not the Watchdog is currently
		             running or stopped. TRUE=Watchdog is running.
		 If you set this object, it means:
		 Running -       indicates whether or not the Watchdog should be
		             stopped before updating.
		             TRUE =  Watchdog is not stopped. If it is already
		                     stopped, it will remain stopped, but if it is
		                     running, it will continue to run, with the
		                     countdown timer reset to the new InitialCount.
		                     Note that there is a race condition possible
		                     with this setting, so it should be used with
		                     care.
		             FALSE = Watchdog is stopped. After this object 
		                     is set, a subsequent read on this object
		                     is required to start the timer."
	::= { hpiWatchdogEntry 2 }

hpiWatchdogTimerUse 	OBJECT-TYPE
	SYNTAX SaHpiWatchdogTimerUse
	ACCESS read-write
	STATUS mandatory
	DESCRIPTION
		"
		 If you read this object, it means:
		 TimerUse - indicates the current use of the timer; one of five
		        preset uses which was included on the last
		        SET object request, or through some
		        other implementation-dependent means to start the
		        Watchdog timer.  
		 If you set this object, it means:
		 TimerUse - indicates the current use of the timer. Will control
		        which hpiWatchdogTimerUseExpFlags is set if the timer expires
		 
		 Setting this object will NOT take effect on the Watchdog until the
		 object SaHpiWatchdogRunning is set to true(1)."
	::= { hpiWatchdogEntry 3 }

hpiWatchdogTimerAction 	OBJECT-TYPE
	SYNTAX INTEGER {
                               undefined (0),
                               noAction (1),
                               reset (2),
                               powerDown (3),
                               powerCycle (4)
                        }
	ACCESS read-write
	STATUS mandatory
	DESCRIPTION
		"Indicates what action will be taken when the Watchdog times out.
		 
		 Setting this object will NOT take effect on the Watchdog until the
		 object SaHpiWatchdogRunning is set to true(1).
		 
		 Note: Enumerated values are increased by one value compared to
		 SAI-HPI-B spec."
	::= { hpiWatchdogEntry 4 }

hpiWatchdogPretimerInterrupt 	OBJECT-TYPE
	SYNTAX SaHpiWatchdogPreTimerAction
	ACCESS read-write
	STATUS mandatory
	DESCRIPTION
		"PretimerInterrupt -  indicates which action will be taken
		 'PreTimeoutInterval' seconds prior to Watchdog timer
		 expiration.
		 
		 Setting this object will NOT take effect on the Watchdog until the
		 object SaHpiWatchdogRunning is set to true(1)."
	::= { hpiWatchdogEntry 5 }

hpiWatchdogPreTimeoutInterval 	OBJECT-TYPE
	SYNTAX Gauge
	ACCESS read-write
	STATUS mandatory
	DESCRIPTION
		"PreTimeoutInterval indicates how many  milliseconds prior to timer
		 time out the PretimerInterrupt action will be taken. If
		 'PreTimeoutInterval' = 0, the PretimerInterrupt action
		 will occur concurrently with 'TimerAction.' HPI
		 implementations may not be able to support millisecond
		 resolution and may have a maximum value restriction.
		 These restrictions should be documented by the
		 provider of the HPI interface.
		 
		 Setting this object will NOT take effect on the Watchdog until the
		 object SaHpiWatchdogRunning is set to true(1)."
	::= { hpiWatchdogEntry 6 }

hpiWatchdogTimerUseExpFlags 	OBJECT-TYPE
	SYNTAX OCTET STRING
	ACCESS read-write
	STATUS mandatory
	DESCRIPTION
		"Set of values seperated by a delimiter.
		 For each value set, the corresponding Timer Use Expiration Flag will
		 be CLEARED. Generally, a program should only clear the Timer Use
		 Expiration Flag corresponding to its own TimerUse, so that other
		 software, which may have used the timer for another purpose in the
		 past can still read its TimerUseExpFlag to determine whether or not
		 the timer expired during that use.
		 
		 The values are:
		 
		 EXP_BIOS_FRB2
		 EXP_BIOS_POST
		 EXP_OS_LOAD
		 EXP_SMS_OS
		 EXP_OEM
		 
		 Setting this object will NOT take effect on the Watchdog until the
		 object SaHpiWatchdogRunning is set to true(1)."
	::= { hpiWatchdogEntry 7 }

hpiWatchdogTimerInitialCount 	OBJECT-TYPE
	SYNTAX Gauge
	ACCESS read-write
	STATUS mandatory
	DESCRIPTION
		"InitialCount -       The time, in milliseconds, 
		 before the timer will time
		 out after a SaHpiWatchdogTimerReset() function call is
		 made, or some other implementation-dependent strobe is
		 sent to the Watchdog. HPI implementations may not be
		 able to support millisecond resolution and may have a
		 maximum value restriction. These restrictions should
		 be documented by the provider of the HPI interface.
		 
		 Setting this object will NOT take effect on the Watchdog until the
		 object SaHpiWatchdogRunning is set to true(1)."
	::= { hpiWatchdogEntry 8 }

hpiWatchdogTimerPresentCount 	OBJECT-TYPE
	SYNTAX Gauge
	ACCESS read-write
	STATUS mandatory
	DESCRIPTION
		"PresentCount - The remaining time in milliseconds before
		 the timer will time out unless a SaHpiWatchdogTimerReset()
		 function call is made, or some other implementation-
		 dependent strobe is sent to the Watchdog.
		 HPI implementations may not be able to support
		 millisecond resolution on watchdog timers, but will
		 return the number of clock ticks remaining times the
		 number of milliseconds between each tick.
		 
		 Setting this object will NOT take effect on the Watchdog until the
		 object SaHpiWatchdogRunning is set to true(1)."
	::= { hpiWatchdogEntry 9 }

hpiWatchdogTimerReset 	OBJECT-TYPE
	SYNTAX TruthValue
	ACCESS read-write
	STATUS mandatory
	DESCRIPTION
		"This object provides a method to start or restart
		 the watchdog timer from the initial countdown value.
		 
		 Setting this to true(1) will 'strobe' the counter and reset to
		 the initial countdown value as specified in
		 hpiWatchdogTimerInitialCount.
		 
		 Setting this object will NOT take effect on the Watchdog until the
		 object SaHpiWatchdogRunning is set to true(1)."
	::= { hpiWatchdogEntry 10 }

hpiWatchdogOem 	OBJECT-TYPE
	SYNTAX Gauge
	ACCESS read-only
	STATUS mandatory
	DESCRIPTION
		"Reserved for OEM use"
	::= { hpiWatchdogEntry 11 }

hpiRdrAnnunciatorsCount 	OBJECT-TYPE
	SYNTAX Counter
	ACCESS read-only
	STATUS mandatory
	DESCRIPTION
		"Number of annunciators data records in this system."
	::= { hpiResources 11 }

hpiAnnunciators OBJECT IDENTIFIER ::= {hpiResources 12}

hpiAnnunciatorEntryCount 	OBJECT-TYPE
	SYNTAX Counter
	ACCESS read-only
	STATUS mandatory
	DESCRIPTION
		"The number of annunciators present on this system."
	::= { hpiAnnunciators 1 }

hpiAnnunciatorTable 	OBJECT-TYPE
	SYNTAX SEQUENCE OF HpiAnnunciatorEntry
	ACCESS not-accessible
	STATUS mandatory
	DESCRIPTION
		"Table of Annunciator resource data records."
	::= { hpiAnnunciators 2 }

hpiAnnunciatorEntry 	OBJECT-TYPE
	SYNTAX HpiAnnunciatorEntry
	ACCESS not-accessible
	STATUS mandatory
	DESCRIPTION
		"
		 The Annunciator table is used to control the set of annunciators 
		 associated with a resource.
		 An Annunciator management instrument holds a set of individual 
		 announcements.  The function of the Annunciator is to communicate   
		 the contents of its current set via whatever platform-specific 
		 mechanism is associated with that particular Annunciator management 
		 instrument.  For example, if announcements are to be communicated 
		 via lighting a set of LEDs on a front-panel display, the Annunciator 
		 management instrument may analyze its current set of announcements 
		 and turn on a single LED reflecting the most severe condition found, 
		 or turn on a 'System Ok' LED if there are currently no items in the 
		 set.  A different Annunciator may continuously scroll each 
		 announcement in its set on a text display, as well as turning 
		 on LEDs and setting dry-contact relays to reflect the severity of 
		 conditions present.  A third Annunciator may announce items in its 
		 set by sending messages to a proprietary management system, or by 
		 sending emails or pages to a system technician.
		 
		 The Annunciator provides a common interface to these varied 
		 mechanisms for announcing conditions, so the HPI User is not 
		 burdened by platform-to-platform differences.  However, the 
		 current content of any annunciator management instrument is not 
		 defined by the HPI standard in the same way that the contents of 
		 the DAT are defined.  Thus, the HPI implementation and HPI Users 
		 can exert more control over what conditions should be announced.  
		 Further, a platform can contain multiple Annunciator management 
		 instruments, each reflecting a different physical announcement 
		 device in the platform.  By exposing each separately, HPI Users 
		 and the HPI implementation can control which conditions are handled
		 by each announcement device.
		 An Annunciator management instrument may be implemented using other 
		 HPI controls that are in 'auto' mode; for example, digital controls 
		 to turn LEDs on and off, stream controls to sound audible alerts,
		 and/or text controls to display detailed information. However, A
		 nnunciators may also operate directly to report conditions using 
		 mechanisms that are not themselves visible directly in the HPI 
		 interface.
		 
		 Over time, announcements are added to and deleted from an 
		 Annunciator`s current set of announcements. This may be done 
		 automatically by the HPI implementation to reflect platform fault 
		 conditions, or by the HPI User via the HPI interface.  When 
		 announcements are added or deleted automatically by the HPI 
		 implementation, it is implementation-specific which announcements 
		 are added or removed."
	INDEX {
		hpiDomainId,
		hpiResourceId,
		hpiRdrType,
		hpiAnnunciatorNum
	}
	::= { hpiAnnunciatorTable 1 }

HpiAnnunciatorEntry ::= SEQUENCE {
	hpiAnnunciatorNum            SaHpiInstrumentId,
	hpiAnnunciatorType           INTEGER,
	hpiAnnunciatorModeReadOnly   TruthValue,
	hpiAnnunciatorMaxConditions  Gauge,
	hpiAnnunciatorMode           INTEGER,
	hpiAnnunciatorOem            Gauge,
	hpiAnnunciatorRDR            RowPointer
	}

hpiAnnunciatorNum 	OBJECT-TYPE
	SYNTAX SaHpiInstrumentId
	ACCESS read-only
	STATUS mandatory
	DESCRIPTION
		"Unique Number identifying each annunciator."
	::= { hpiAnnunciatorEntry 1 }

hpiAnnunciatorType 	OBJECT-TYPE
	SYNTAX INTEGER {
                               undefined (0),
                               led (1),
                               dryContactClosure (2),
                               audible (3),
                               lcdDisplay (4),
                               message (5),
                               composite (6),
                               oem (7)
                        }
	ACCESS read-only
	STATUS mandatory
	DESCRIPTION
		"The following enumerated type defines the possible output types 
		 which can be associated with an Annunciator Management Instrument.
		 Note: Enumerated values are increased by one value compared to
		 SAI-HPI-B spec."
	::= { hpiAnnunciatorEntry 2 }

hpiAnnunciatorModeReadOnly 	OBJECT-TYPE
	SYNTAX TruthValue
	ACCESS read-only
	STATUS mandatory
	DESCRIPTION
		"if True, Mode may not be changed by HPI User."
	::= { hpiAnnunciatorEntry 3 }

hpiAnnunciatorMaxConditions 	OBJECT-TYPE
	SYNTAX Gauge
	ACCESS read-only
	STATUS mandatory
	DESCRIPTION
		"maximum number of conditions that can be held in current 
		 set.  0 means no fixed limit.  "
	::= { hpiAnnunciatorEntry 4 }

hpiAnnunciatorMode 	OBJECT-TYPE
	SYNTAX INTEGER {
                               undefined (0),
                               auto (1),
                               user (2),
                               shared (3)
                        }
	ACCESS read-write
	STATUS mandatory
	DESCRIPTION
		"
		 The Annunciator management instrument has a current mode that 
		 indicates whether announcements are added and removed automatically 
		 by the HPI implementation, by the HPI User, or both.  The mode may 
		 be set to one of three values, with the following meanings:
		 
		 auto(1) - the HPI implementation automatically adds and deletes 
		 announcements; the HPI User is not permitted to add or delete 
		 announcements.
		 user(2) - the HPI User may add and delete announcements; the HPI 
		 implementation will not automatically add or delete announcements.
		 shared(3) -  the HPI implementation automatically adds and deletes
		 announcements and the HPI User may also add and delete announcements.
		 
		 The initial mode of each Annunciator is implementation-specific.  
		 The HPI User may change the mode of Annunciators with the 
		 hpiAnnunciatorMode object.  However, the mode may be configured
		 to be Read-only, in which case the HPI User will not be able to 
		 change the mode.
		 
		 When the mode is user(2) or shared(3), HPI Users may add or delete 
		 any types of announcements in the Annunciator's current set - not 
		 just HPI User announcements.  This is allowed so that the HPI User 
		 can exert complete control over what conditions are being announced, 
		 if that is required.  Note that this is less restrictive than the 
		 similar operations on the DAT.  To distinguish between announcements 
		 added to an Annunciator automatically and those added by an HPI User, 
		 an hpiAddedByUser IdrField in the announcement indicates the source
		 of the announcement in the set.
		 
		 Note: Enumerated values are increased by one value compared to
		 SAI-HPI-B spec."
	::= { hpiAnnunciatorEntry 5 }

hpiAnnunciatorOem 	OBJECT-TYPE
	SYNTAX Gauge
	ACCESS read-only
	STATUS mandatory
	DESCRIPTION
		"maximum number of conditions that can be held in current 
		 set.  0 means no fixed limit.  if True, Mode may not be
		 changed by HPI User."
	::= { hpiAnnunciatorEntry 6 }

hpiAnnunciatorRDR 	OBJECT-TYPE
	SYNTAX RowPointer
	ACCESS read-only
	STATUS mandatory
	DESCRIPTION
		"Forward pointer to the RDR OID."
	::= { hpiAnnunciatorEntry 7 }

hpiNotifications OBJECT IDENTIFIER ::= {fscHpiBMIB 5}

hpiSvTraps OBJECT IDENTIFIER ::= {hpiNotifications 10}

hpiSvResourceUndefined TRAP-TYPE
        ENTERPRISE hpiSvTraps
        VARIABLES {
                hpiEventSource,
                hpiEventTime,
                hpiResourceEventType
        }
        DESCRIPTION
                "Resource (RPT) change event notifications."
--#TYPE "HPI Resource state change event (Unknown severity)"
--#SUMMARY "The operational state of resource %d has changed to %s."
--#ARGUMENTS { 0,2 }
--#SEVERITY UNKNOWN
--#STATE OPERATIONAL
        ::= 1000

hpiSvResourceCritical TRAP-TYPE
        ENTERPRISE hpiSvTraps
        VARIABLES {
                hpiEventSource,
                hpiEventTime,
                hpiResourceEventType
        }
        DESCRIPTION
                "Resource (RPT) change event notifications."
--#TYPE "HPI Resource state change event (Severe)"
--#SUMMARY "The operational state of resource %d has changed to %s."
--#ARGUMENTS { 0,2 }
--#SEVERITY SEVERE
--#STATE OPERATIONAL
        ::= 1001

hpiSvResourceMajor TRAP-TYPE
        ENTERPRISE hpiSvTraps
        VARIABLES {
                hpiEventSource,
                hpiEventTime,
                hpiResourceEventType
        }
        DESCRIPTION
                "Resource (RPT) change event notifications."
--#TYPE "HPI Resource state change event (Major)"
--#SUMMARY "The operational state of resource %d has changed to %s."
--#ARGUMENTS { 0,2 }
--#SEVERITY MAJOR
--#STATE OPERATIONAL
        ::= 1002

hpiSvResourceMinor TRAP-TYPE
        ENTERPRISE hpiSvTraps
        VARIABLES {
                hpiEventSource,
                hpiEventTime,
                hpiResourceEventType
        }
        DESCRIPTION
                "Resource (RPT) change event notifications."
--#TYPE "HPI Resource state change event (Minor)"
--#SUMMARY "The operational state of resource %d has changed to %s."
--#ARGUMENTS { 0,2 }
--#SEVERITY MINOR
--#STATE OPERATIONAL
        ::= 1003

hpiSvResourceInformational TRAP-TYPE
        ENTERPRISE hpiSvTraps
        VARIABLES {
                hpiEventSource,
                hpiEventTime,
                hpiResourceEventType
        }
        DESCRIPTION
                "Resource (RPT) change event notifications."
--#TYPE "HPI Resource state change event (Informational)"
--#SUMMARY "The operational state of resource %d has changed to %s."
--#ARGUMENTS { 0,2 }
--#SEVERITY INFORMATIONAL
--#STATE OPERATIONAL
        ::= 1004

hpiSvResourceOk TRAP-TYPE
        ENTERPRISE hpiSvTraps
        VARIABLES {
                hpiEventSource,
                hpiEventTime,
                hpiResourceEventType
        }
        DESCRIPTION
                "Resource (RPT) change event notifications."
--#TYPE "HPI Resource state change event (OK)"
--#SUMMARY "The operational state of resource %d has changed to %s."
--#ARGUMENTS { 0,2 }
--#SEVERITY INFORMATIONAL
--#STATE OPERATIONAL
        ::= 1005

hpiSvResourceDebug TRAP-TYPE
        ENTERPRISE hpiSvTraps
        VARIABLES {
                hpiEventSource,
                hpiEventTime,
                hpiResourceEventType
        }
        DESCRIPTION
                "Resource (RPT) change event notifications."
--#TYPE "HPI Resource state change event (debug event)"
--#SUMMARY "The operational state of resource %d has changed to %s."
--#ARGUMENTS { 0,2 }
--#SEVERITY INFORMATIONAL
--#STATE OPERATIONAL
        ::= 1241

hpiSvDomainUndefined TRAP-TYPE
        ENTERPRISE hpiSvTraps
        VARIABLES {
                hpiEventSource,
                hpiEventTime,
                hpiDomainEventType
        }
        DESCRIPTION
                "Domain events are used to announce the addition of domain
		 references and the removal of domain references to the DRT."
--#TYPE "HPI Domain reference event (Unknown severity)"
--#SUMMARY "The domain reference table has been modified."
--#SUMMARY "(Domain: %d. Event type: %s.)"
--#ARGUMENTS { 0,2 }
--#SEVERITY UNKNOWN
--#STATE OPERATIONAL
        ::= 2000

hpiSvDomainCritical TRAP-TYPE
        ENTERPRISE hpiSvTraps
        VARIABLES {
                hpiEventSource,
                hpiEventTime,
                hpiDomainEventType
        }
        DESCRIPTION
                "Domain events are used to announce the addition of domain
		 references and the removal of domain references to the DRT."
--#TYPE "HPI Domain reference event (Severe)"
--#SUMMARY "The domain reference table has been modified."
--#SUMMARY "(Domain: %d. Event type: %s.)"
--#ARGUMENTS { 0,2 }
--#SEVERITY SEVERE
--#STATE OPERATIONAL
        ::= 2001

hpiSvDomainMajor TRAP-TYPE
        ENTERPRISE hpiSvTraps
        VARIABLES {
                hpiEventSource,
                hpiEventTime,
                hpiDomainEventType
        }
        DESCRIPTION
                "Domain events are used to announce the addition of domain
		 references and the removal of domain references to the DRT."
--#TYPE "HPI Domain reference event (Major)"
--#SUMMARY "The domain reference table has been modified."
--#SUMMARY "(Domain: %d. Event type: %s.)"
--#ARGUMENTS { 0,2 }
--#SEVERITY MAJOR
--#STATE OPERATIONAL
        ::= 2002

hpiSvDomainMinor TRAP-TYPE
        ENTERPRISE hpiSvTraps
        VARIABLES {
                hpiEventSource,
                hpiEventTime,
                hpiDomainEventType
        }
        DESCRIPTION
                "Domain events are used to announce the addition of domain
		 references and the removal of domain references to the DRT."
--#TYPE "HPI Domain reference event (Minor)"
--#SUMMARY "The domain reference table has been modified."
--#SUMMARY "(Domain: %d. Event type: %s.)"
--#ARGUMENTS { 0,2 }
--#SEVERITY MINOR
--#STATE OPERATIONAL
        ::= 2003

hpiSvDomainInformational TRAP-TYPE
        ENTERPRISE hpiSvTraps
        VARIABLES {
                hpiEventSource,
                hpiEventTime,
                hpiDomainEventType
        }
        DESCRIPTION
                "Domain events are used to announce the addition of domain
		 references and the removal of domain references to the DRT."
--#TYPE "HPI Domain reference event (Informational)"
--#SUMMARY "The domain reference table has been modified."
--#SUMMARY "(Domain: %d. Event type: %s.)"
--#ARGUMENTS { 0,2 }
--#SEVERITY INFORMATIONAL
--#STATE OPERATIONAL
        ::= 2004

hpiSvDomainOk TRAP-TYPE
        ENTERPRISE hpiSvTraps
        VARIABLES {
                hpiEventSource,
                hpiEventTime,
                hpiDomainEventType
        }
        DESCRIPTION
                "Domain events are used to announce the addition of domain
		 references and the removal of domain references to the DRT."
--#TYPE "HPI Domain reference event (OK)"
--#SUMMARY "The domain reference table has been modified."
--#SUMMARY "(Domain: %d. Event type: %s.)"
--#ARGUMENTS { 0,2 }
--#SEVERITY INFORMATIONAL
--#STATE OPERATIONAL
        ::= 2005

hpiSvDomainDebug TRAP-TYPE
        ENTERPRISE hpiSvTraps
        VARIABLES {
                hpiEventSource,
                hpiEventTime,
                hpiDomainEventType
        }
        DESCRIPTION
                "Domain events are used to announce the addition of domain
		 references and the removal of domain references to the DRT."
--#TYPE "HPI Domain reference event (debug event)"
--#SUMMARY "The domain reference table has been modified."
--#SUMMARY "(Domain: %d. Event type: %s.)"
--#ARGUMENTS { 0,2 }
--#SEVERITY INFORMATIONAL
--#STATE OPERATIONAL
        ::= 2241

hpiSvSensorUndefined TRAP-TYPE
        ENTERPRISE hpiSvTraps
        VARIABLES {
                hpiEventSource,
                hpiEventTime,
                hpiSensorEventNum,
                hpiSensorEventType,
                hpiSensorEventCategory,
                hpiSensorEventAssertion,
                hpiSensorEventState
        }
        DESCRIPTION
                "Sensor event notification."
--#TYPE "HPI Sensor state change event (Unknown severity)"
--#SUMMARY "Sensor event state asserted or de-asserted for sensor Id: %d."
--#SUMMARY "(Sensor number: %d, Sensor Type: %s, Event category: %s, Assertion: %s)"
--#ARGUMENTS { 0,2,3,4,5 }
--#SEVERITY UNKNOWN
--#STATE OPERATIONAL
        ::= 3000

hpiSvSensorCritical TRAP-TYPE
        ENTERPRISE hpiSvTraps
        VARIABLES {
                hpiEventSource,
                hpiEventTime,
                hpiSensorEventNum,
                hpiSensorEventType,
                hpiSensorEventCategory,
                hpiSensorEventAssertion,
                hpiSensorEventState
        }
        DESCRIPTION
                "Sensor event notification."
--#TYPE "HPI Sensor state change event (Severe)"
--#SUMMARY "Sensor event state asserted or de-asserted for sensor Id: %d."
--#SUMMARY "(Sensor number: %d, Sensor Type: %s, Event category: %s, Assertion: %s)"
--#ARGUMENTS { 0,2,3,4,5 }
--#SEVERITY SEVERE
--#STATE OPERATIONAL
        ::= 3001

hpiSvSensorMajor TRAP-TYPE
        ENTERPRISE hpiSvTraps
        VARIABLES {
                hpiEventSource,
                hpiEventTime,
                hpiSensorEventNum,
                hpiSensorEventType,
                hpiSensorEventCategory,
                hpiSensorEventAssertion,
                hpiSensorEventState
        }
        DESCRIPTION
                "Sensor event notification."
--#TYPE "HPI Sensor state change event (Major)"
--#SUMMARY "Sensor event state asserted or de-asserted for sensor Id: %d."
--#SUMMARY "(Sensor number: %d, Sensor Type: %s, Event category: %s, Assertion: %s)"
--#ARGUMENTS { 0,2,3,4,5 }
--#SEVERITY MAJOR
--#STATE OPERATIONAL
        ::= 3002

hpiSvSensorMinor TRAP-TYPE
        ENTERPRISE hpiSvTraps
        VARIABLES {
                hpiEventSource,
                hpiEventTime,
                hpiSensorEventNum,
                hpiSensorEventType,
                hpiSensorEventCategory,
                hpiSensorEventAssertion,
                hpiSensorEventState
        }
        DESCRIPTION
                "Sensor event notification."
--#TYPE "HPI Sensor state change event (Minor)"
--#SUMMARY "Sensor event state asserted or de-asserted for sensor Id: %d."
--#SUMMARY "(Sensor number: %d, Sensor Type: %s, Event category: %s, Assertion: %s)"
--#ARGUMENTS { 0,2,3,4,5 }
--#SEVERITY MINOR
--#STATE OPERATIONAL
        ::= 3003

hpiSvSensorInformational TRAP-TYPE
        ENTERPRISE hpiSvTraps
        VARIABLES {
                hpiEventSource,
                hpiEventTime,
                hpiSensorEventNum,
                hpiSensorEventType,
                hpiSensorEventCategory,
                hpiSensorEventAssertion,
                hpiSensorEventState
        }
        DESCRIPTION
                "Sensor event notification."
--#TYPE "HPI Sensor state change event (Informational)"
--#SUMMARY "Sensor event state asserted or de-asserted for sensor Id: %d."
--#SUMMARY "(Sensor number: %d, Sensor Type: %s, Event category: %s, Assertion: %s)"
--#ARGUMENTS { 0,2,3,4,5 }
--#SEVERITY INFORMATIONAL
--#STATE OPERATIONAL
        ::= 3004

hpiSvSensorOk TRAP-TYPE
        ENTERPRISE hpiSvTraps
        VARIABLES {
                hpiEventSource,
                hpiEventTime,
                hpiSensorEventNum,
                hpiSensorEventType,
                hpiSensorEventCategory,
                hpiSensorEventAssertion,
                hpiSensorEventState
        }
        DESCRIPTION
                "Sensor event notification."
--#TYPE "HPI Sensor state change event (OK)"
--#SUMMARY "Sensor event state asserted or de-asserted for sensor Id: %d."
--#SUMMARY "(Sensor number: %d, Sensor Type: %s, Event category: %s, Assertion: %s)"
--#ARGUMENTS { 0,2,3,4,5 }
--#SEVERITY INFORMATIONAL
--#STATE OPERATIONAL
        ::= 3005

hpiSvSensorDebug TRAP-TYPE
        ENTERPRISE hpiSvTraps
        VARIABLES {
                hpiEventSource,
                hpiEventTime,
                hpiSensorEventNum,
                hpiSensorEventType,
                hpiSensorEventCategory,
                hpiSensorEventAssertion,
                hpiSensorEventState
        }
        DESCRIPTION
                "Sensor event notification."
--#TYPE "HPI Sensor state change event (debug event)"
--#SUMMARY "Sensor event state asserted or de-asserted for sensor Id: %d."
--#SUMMARY "(Sensor number: %d, Sensor Type: %s, Event category: %s, Assertion: %s)"
--#ARGUMENTS { 0,2,3,4,5 }
--#SEVERITY INFORMATIONAL
--#STATE OPERATIONAL
        ::= 3241

hpiSvSensorEnableChangeUndefined TRAP-TYPE
        ENTERPRISE hpiSvTraps
        VARIABLES {
                hpiEventSource,
                hpiEventTime,
                hpiSensorEnableChangeEventNum,
                hpiSensorEnableChangeEventType,
                hpiSensorEnableChangeEventCategory
        }
        DESCRIPTION
                "Sensor event notification."
--#TYPE "HPI Sensor enable event (Unknown severity)"
--#SUMMARY "Sensor enable status has changed for sensor ID: %d."
--#SUMMARY "(Sensor number: %d, Sensor Type: %s, Event category: %s)"
--#ARGUMENTS { 0,2,3,4 }
--#SEVERITY UNKNOWN
--#STATE OPERATIONAL
        ::= 4000

hpiSvSensorEnableChangeCritical TRAP-TYPE
        ENTERPRISE hpiSvTraps
        VARIABLES {
                hpiEventSource,
                hpiEventTime,
                hpiSensorEnableChangeEventNum,
                hpiSensorEnableChangeEventType,
                hpiSensorEnableChangeEventCategory
        }
        DESCRIPTION
                "Sensor event notification."
--#TYPE "HPI Sensor enable event (Severe)"
--#SUMMARY "Sensor enable status has changed for sensor ID: %d."
--#SUMMARY "(Sensor number: %d, Sensor Type: %s, Event category: %s)"
--#ARGUMENTS { 0,2,3,4 }
--#SEVERITY SEVERE
--#STATE OPERATIONAL
        ::= 4001

hpiSvSensorEnableChangeMajor TRAP-TYPE
        ENTERPRISE hpiSvTraps
        VARIABLES {
                hpiEventSource,
                hpiEventTime,
                hpiSensorEnableChangeEventNum,
                hpiSensorEnableChangeEventType,
                hpiSensorEnableChangeEventCategory
        }
        DESCRIPTION
                "Sensor event notification."
--#TYPE "HPI Sensor enable event (Major)"
--#SUMMARY "Sensor enable status has changed for sensor ID: %d."
--#SUMMARY "(Sensor number: %d, Sensor Type: %s, Event category: %s)"
--#ARGUMENTS { 0,2,3,4 }
--#SEVERITY MAJOR
--#STATE OPERATIONAL
        ::= 4002

hpiSvSensorEnableChangeMinor TRAP-TYPE
        ENTERPRISE hpiSvTraps
        VARIABLES {
                hpiEventSource,
                hpiEventTime,
                hpiSensorEnableChangeEventNum,
                hpiSensorEnableChangeEventType,
                hpiSensorEnableChangeEventCategory
        }
        DESCRIPTION
                "Sensor event notification."
--#TYPE "HPI Sensor enable event (Minor)"
--#SUMMARY "Sensor enable status has changed for sensor ID: %d."
--#SUMMARY "(Sensor number: %d, Sensor Type: %s, Event category: %s)"
--#ARGUMENTS { 0,2,3,4 }
--#SEVERITY MINOR
--#STATE OPERATIONAL
        ::= 4003

hpiSvSensorEnableChangeInformational TRAP-TYPE
        ENTERPRISE hpiSvTraps
        VARIABLES {
                hpiEventSource,
                hpiEventTime,
                hpiSensorEnableChangeEventNum,
                hpiSensorEnableChangeEventType,
                hpiSensorEnableChangeEventCategory
        }
        DESCRIPTION
                "Sensor event notification."
--#TYPE "HPI Sensor enable event (Informational)"
--#SUMMARY "Sensor enable status has changed for sensor ID: %d."
--#SUMMARY "(Sensor number: %d, Sensor Type: %s, Event category: %s)"
--#ARGUMENTS { 0,2,3,4 }
--#SEVERITY INFORMATIONAL
--#STATE OPERATIONAL
        ::= 4004

hpiSvSensorEnableChangeOk TRAP-TYPE
        ENTERPRISE hpiSvTraps
        VARIABLES {
                hpiEventSource,
                hpiEventTime,
                hpiSensorEnableChangeEventNum,
                hpiSensorEnableChangeEventType,
                hpiSensorEnableChangeEventCategory
        }
        DESCRIPTION
                "Sensor event notification."
--#TYPE "HPI Sensor enable event (OK)"
--#SUMMARY "Sensor enable status has changed for sensor ID: %d."
--#SUMMARY "(Sensor number: %d, Sensor Type: %s, Event category: %s)"
--#ARGUMENTS { 0,2,3,4 }
--#SEVERITY INFORMATIONAL
--#STATE OPERATIONAL
        ::= 4005

hpiSvSensorEnableChangeDebug TRAP-TYPE
        ENTERPRISE hpiSvTraps
        VARIABLES {
                hpiEventSource,
                hpiEventTime,
                hpiSensorEnableChangeEventNum,
                hpiSensorEnableChangeEventType,
                hpiSensorEnableChangeEventCategory
        }
        DESCRIPTION
                "Sensor event notification."
--#TYPE "HPI Sensor enable event (debug event)"
--#SUMMARY "Sensor enable status has changed for sensor ID: %d."
--#SUMMARY "(Sensor number: %d, Sensor Type: %s, Event category: %s)"
--#ARGUMENTS { 0,2,3,4 }
--#SEVERITY INFORMATIONAL
--#STATE OPERATIONAL
        ::= 4241

hpiSvHotSwapUndefined TRAP-TYPE
        ENTERPRISE hpiSvTraps
        VARIABLES {
                hpiEventSource,
                hpiEventTime,
                hpiHotSwapEventState,
                hpiHotSwapEventPreviousState
        }
        DESCRIPTION
                "Hot swap notification."
--#TYPE "HPI Hot swap state change event (Unknown severity)"
--#SUMMARY "Resource ID: %d has changed hot swap state from %s to %s."
--#ARGUMENTS { 0,3,2 }
--#SEVERITY UNKNOWN
--#STATE OPERATIONAL
        ::= 5000

hpiSvHotSwapCritical TRAP-TYPE
        ENTERPRISE hpiSvTraps
        VARIABLES {
                hpiEventSource,
                hpiEventTime,
                hpiHotSwapEventState,
                hpiHotSwapEventPreviousState
        }
        DESCRIPTION
                "Hot swap notification."
--#TYPE "HPI Hot swap state change event (Severe)"
--#SUMMARY "Resource ID: %d has changed hot swap state from %s to %s."
--#ARGUMENTS { 0,3,2 }
--#SEVERITY SEVERE
--#STATE OPERATIONAL
        ::= 5001

hpiSvHotSwapMajor TRAP-TYPE
        ENTERPRISE hpiSvTraps
        VARIABLES {
                hpiEventSource,
                hpiEventTime,
                hpiHotSwapEventState,
                hpiHotSwapEventPreviousState
        }
        DESCRIPTION
                "Hot swap notification."
--#TYPE "HPI Hot swap state change event (Major)"
--#SUMMARY "Resource ID: %d has changed hot swap state from %s to %s."
--#ARGUMENTS { 0,3,2 }
--#SEVERITY MAJOR
--#STATE OPERATIONAL
        ::= 5002

hpiSvHotSwapMinor TRAP-TYPE
        ENTERPRISE hpiSvTraps
        VARIABLES {
                hpiEventSource,
                hpiEventTime,
                hpiHotSwapEventState,
                hpiHotSwapEventPreviousState
        }
        DESCRIPTION
                "Hot swap notification."
--#TYPE "HPI Hot swap state change event (Minor)"
--#SUMMARY "Resource ID: %d has changed hot swap state from %s to %s."
--#ARGUMENTS { 0,3,2 }
--#SEVERITY MINOR
--#STATE OPERATIONAL
        ::= 5003

hpiSvHotSwapInformational TRAP-TYPE
        ENTERPRISE hpiSvTraps
        VARIABLES {
                hpiEventSource,
                hpiEventTime,
                hpiHotSwapEventState,
                hpiHotSwapEventPreviousState
        }
        DESCRIPTION
                "Hot swap notification."
--#TYPE "HPI Hot swap state change event (Informational)"
--#SUMMARY "Resource ID: %d has changed hot swap state from %s to %s."
--#ARGUMENTS { 0,3,2 }
--#SEVERITY INFORMATIONAL
--#STATE OPERATIONAL
        ::= 5004

hpiSvHotSwapOk TRAP-TYPE
        ENTERPRISE hpiSvTraps
        VARIABLES {
                hpiEventSource,
                hpiEventTime,
                hpiHotSwapEventState,
                hpiHotSwapEventPreviousState
        }
        DESCRIPTION
                "Hot swap notification."
--#TYPE "HPI Hot swap state change event (OK)"
--#SUMMARY "Resource ID: %d has changed hot swap state from %s to %s."
--#ARGUMENTS { 0,3,2 }
--#SEVERITY INFORMATIONAL
--#STATE OPERATIONAL
        ::= 5005

hpiSvHotSwapDebug TRAP-TYPE
        ENTERPRISE hpiSvTraps
        VARIABLES {
                hpiEventSource,
                hpiEventTime,
                hpiHotSwapEventState,
                hpiHotSwapEventPreviousState
        }
        DESCRIPTION
                "Hot swap notification."
--#TYPE "HPI Hot swap state change event (debug event)"
--#SUMMARY "Resource ID: %d has changed hot swap state from %s to %s."
--#ARGUMENTS { 0,3,2 }
--#SEVERITY INFORMATIONAL
--#STATE OPERATIONAL
        ::= 5241

hpiSvWatchdogUndefined TRAP-TYPE
        ENTERPRISE hpiSvTraps
        VARIABLES {
                hpiEventSource,
                hpiEventTime,
                hpiWatchdogEventNum,
                hpiWatchdogEventAction,
                hpiWatchdogEventPreTimerAction,
                hpiWatchdogEventUse
        }
        DESCRIPTION
                "Watchdog notification."
--#TYPE "HPI Watchdog timer expiration event (Unknown severity)"
--#SUMMARY "Watchdog timer has expired."
--#SUMMARY "(Watchdog ID: %d, Event number: %d, Action: %s, PreTimerAction: %s, User: %s)"
--#ARGUMENTS { 0,2,3,4,5 }
--#SEVERITY UNKNOWN
--#STATE OPERATIONAL
        ::= 6000

hpiSvWatchdogCritical TRAP-TYPE
        ENTERPRISE hpiSvTraps
        VARIABLES {
                hpiEventSource,
                hpiEventTime,
                hpiWatchdogEventNum,
                hpiWatchdogEventAction,
                hpiWatchdogEventPreTimerAction,
                hpiWatchdogEventUse
        }
        DESCRIPTION
                "Watchdog notification."
--#TYPE "HPI Watchdog timer expiration event (Severe)"
--#SUMMARY "Watchdog timer has expired."
--#SUMMARY "(Watchdog ID: %d, Event number: %d, Action: %s, PreTimerAction: %s, User: %s)"
--#ARGUMENTS { 0,2,3,4,5 }
--#SEVERITY SEVERE
--#STATE OPERATIONAL
        ::= 6001

hpiSvWatchdogMajor TRAP-TYPE
        ENTERPRISE hpiSvTraps
        VARIABLES {
                hpiEventSource,
                hpiEventTime,
                hpiWatchdogEventNum,
                hpiWatchdogEventAction,
                hpiWatchdogEventPreTimerAction,
                hpiWatchdogEventUse
        }
        DESCRIPTION
                "Watchdog notification."
--#TYPE "HPI Watchdog timer expiration event (Major)"
--#SUMMARY "Watchdog timer has expired."
--#SUMMARY "(Watchdog ID: %d, Event number: %d, Action: %s, PreTimerAction: %s, User: %s)"
--#ARGUMENTS { 0,2,3,4,5 }
--#SEVERITY MAJOR
--#STATE OPERATIONAL
        ::= 6002

hpiSvWatchdogMinor TRAP-TYPE
        ENTERPRISE hpiSvTraps
        VARIABLES {
                hpiEventSource,
                hpiEventTime,
                hpiWatchdogEventNum,
                hpiWatchdogEventAction,
                hpiWatchdogEventPreTimerAction,
                hpiWatchdogEventUse
        }
        DESCRIPTION
                "Watchdog notification."
--#TYPE "HPI Watchdog timer expiration event (Minor)"
--#SUMMARY "Watchdog timer has expired."
--#SUMMARY "(Watchdog ID: %d, Event number: %d, Action: %s, PreTimerAction: %s, User: %s)"
--#ARGUMENTS { 0,2,3,4,5 }
--#SEVERITY MINOR
--#STATE OPERATIONAL
        ::= 6003

hpiSvWatchdogInformational TRAP-TYPE
        ENTERPRISE hpiSvTraps
        VARIABLES {
                hpiEventSource,
                hpiEventTime,
                hpiWatchdogEventNum,
                hpiWatchdogEventAction,
                hpiWatchdogEventPreTimerAction,
                hpiWatchdogEventUse
        }
        DESCRIPTION
                "Watchdog notification."
--#TYPE "HPI Watchdog timer expiration event (Informational)"
--#SUMMARY "Watchdog timer has expired."
--#SUMMARY "(Watchdog ID: %d, Event number: %d, Action: %s, PreTimerAction: %s, User: %s)"
--#ARGUMENTS { 0,2,3,4,5 }
--#SEVERITY INFORMATIONAL
--#STATE OPERATIONAL
        ::= 6004

hpiSvWatchdogOk TRAP-TYPE
        ENTERPRISE hpiSvTraps
        VARIABLES {
                hpiEventSource,
                hpiEventTime,
                hpiWatchdogEventNum,
                hpiWatchdogEventAction,
                hpiWatchdogEventPreTimerAction,
                hpiWatchdogEventUse
        }
        DESCRIPTION
                "Watchdog notification."
--#TYPE "HPI Watchdog timer expiration event (OK)"
--#SUMMARY "Watchdog timer has expired."
--#SUMMARY "(Watchdog ID: %d, Event number: %d, Action: %s, PreTimerAction: %s, User: %s)"
--#ARGUMENTS { 0,2,3,4,5 }
--#SEVERITY INFORMATIONAL
--#STATE OPERATIONAL
        ::= 6005

hpiSvWatchdogDebug TRAP-TYPE
        ENTERPRISE hpiSvTraps
        VARIABLES {
                hpiEventSource,
                hpiEventTime,
                hpiWatchdogEventNum,
                hpiWatchdogEventAction,
                hpiWatchdogEventPreTimerAction,
                hpiWatchdogEventUse
        }
        DESCRIPTION
                "Watchdog notification."
--#TYPE "HPI Watchdog timer expiration event (debug event)"
--#SUMMARY "Watchdog timer has expired."
--#SUMMARY "(Watchdog ID: %d, Event number: %d, Action: %s, PreTimerAction: %s, User: %s)"
--#ARGUMENTS { 0,2,3,4,5 }
--#SEVERITY INFORMATIONAL
--#STATE OPERATIONAL
        ::= 6241

hpiSvSoftwareUndefined TRAP-TYPE
        ENTERPRISE hpiSvTraps
        VARIABLES {
                hpiEventSource,
                hpiEventTime,
                hpiSoftwareEventManufacturerId,
                hpiSoftwareEventType,
                hpiSoftwareEventTextType,
                hpiSoftwareEventTextLanguage,
                hpiSoftwareEventText
        }
        DESCRIPTION
                "Audit events report a discrepancy in the audit process.  Audits are 
		 typically performed by HA software to detect problems.  Audits may 
		 look for such things as corrupted data stores, inconsistent RPT 
		 information, or improperly managed queues.  Startup events report a 
		 failure to start-up properly, or inconsistencies in persisted data."
--#TYPE "HPI Software event (Unknown severity)"
--#SUMMARY "HPI Software Event has been reported."
--#SUMMARY "(Manufacturer ID: %d, Event type: %s, Event text: %s)"
--#ARGUMENTS { 2,3,6 }
--#SEVERITY UNKNOWN
--#STATE OPERATIONAL
        ::= 7000

hpiSvSoftwareCritical TRAP-TYPE
        ENTERPRISE hpiSvTraps
        VARIABLES {
                hpiEventSource,
                hpiEventTime,
                hpiSoftwareEventManufacturerId,
                hpiSoftwareEventType,
                hpiSoftwareEventTextType,
                hpiSoftwareEventTextLanguage,
                hpiSoftwareEventText
        }
        DESCRIPTION
                "Audit events report a discrepancy in the audit process.  Audits are 
		 typically performed by HA software to detect problems.  Audits may 
		 look for such things as corrupted data stores, inconsistent RPT 
		 information, or improperly managed queues.  Startup events report a 
		 failure to start-up properly, or inconsistencies in persisted data."
--#TYPE "HPI Software event (Severe)"
--#SUMMARY "HPI Software Event has been reported."
--#SUMMARY "(Manufacturer ID: %d, Event type: %s, Event text: %s)"
--#ARGUMENTS { 2,3,6 }
--#SEVERITY SEVERE
--#STATE OPERATIONAL
        ::= 7001

hpiSvSoftwareMajor TRAP-TYPE
        ENTERPRISE hpiSvTraps
        VARIABLES {
                hpiEventSource,
                hpiEventTime,
                hpiSoftwareEventManufacturerId,
                hpiSoftwareEventType,
                hpiSoftwareEventTextType,
                hpiSoftwareEventTextLanguage,
                hpiSoftwareEventText
        }
        DESCRIPTION
                "Audit events report a discrepancy in the audit process.  Audits are 
		 typically performed by HA software to detect problems.  Audits may 
		 look for such things as corrupted data stores, inconsistent RPT 
		 information, or improperly managed queues.  Startup events report a 
		 failure to start-up properly, or inconsistencies in persisted data."
--#TYPE "HPI Software event (Major)"
--#SUMMARY "HPI Software Event has been reported."
--#SUMMARY "(Manufacturer ID: %d, Event type: %s, Event text: %s)"
--#ARGUMENTS { 2,3,6 }
--#SEVERITY MAJOR
--#STATE OPERATIONAL
        ::= 7002

hpiSvSoftwareMinor TRAP-TYPE
        ENTERPRISE hpiSvTraps
        VARIABLES {
                hpiEventSource,
                hpiEventTime,
                hpiSoftwareEventManufacturerId,
                hpiSoftwareEventType,
                hpiSoftwareEventTextType,
                hpiSoftwareEventTextLanguage,
                hpiSoftwareEventText
        }
        DESCRIPTION
                "Audit events report a discrepancy in the audit process.  Audits are 
		 typically performed by HA software to detect problems.  Audits may 
		 look for such things as corrupted data stores, inconsistent RPT 
		 information, or improperly managed queues.  Startup events report a 
		 failure to start-up properly, or inconsistencies in persisted data."
--#TYPE "HPI Software event (Minor)"
--#SUMMARY "HPI Software Event has been reported."
--#SUMMARY "(Manufacturer ID: %d, Event type: %s, Event text: %s)"
--#ARGUMENTS { 2,3,6 }
--#SEVERITY MINOR
--#STATE OPERATIONAL
        ::= 7003

hpiSvSoftwareInformational TRAP-TYPE
        ENTERPRISE hpiSvTraps
        VARIABLES {
                hpiEventSource,
                hpiEventTime,
                hpiSoftwareEventManufacturerId,
                hpiSoftwareEventType,
                hpiSoftwareEventTextType,
                hpiSoftwareEventTextLanguage,
                hpiSoftwareEventText
        }
        DESCRIPTION
                "Audit events report a discrepancy in the audit process.  Audits are 
		 typically performed by HA software to detect problems.  Audits may 
		 look for such things as corrupted data stores, inconsistent RPT 
		 information, or improperly managed queues.  Startup events report a 
		 failure to start-up properly, or inconsistencies in persisted data."
--#TYPE "HPI Software event (Informational)"
--#SUMMARY "HPI Software Event has been reported."
--#SUMMARY "(Manufacturer ID: %d, Event type: %s, Event text: %s)"
--#ARGUMENTS { 2,3,6 }
--#SEVERITY INFORMATIONAL
--#STATE OPERATIONAL
        ::= 7004

hpiSvSoftwareOk TRAP-TYPE
        ENTERPRISE hpiSvTraps
        VARIABLES {
                hpiEventSource,
                hpiEventTime,
                hpiSoftwareEventManufacturerId,
                hpiSoftwareEventType,
                hpiSoftwareEventTextType,
                hpiSoftwareEventTextLanguage,
                hpiSoftwareEventText
        }
        DESCRIPTION
                "Audit events report a discrepancy in the audit process.  Audits are 
		 typically performed by HA software to detect problems.  Audits may 
		 look for such things as corrupted data stores, inconsistent RPT 
		 information, or improperly managed queues.  Startup events report a 
		 failure to start-up properly, or inconsistencies in persisted data."
--#TYPE "HPI Software event (OK)"
--#SUMMARY "HPI Software Event has been reported."
--#SUMMARY "(Manufacturer ID: %d, Event type: %s, Event text: %s)"
--#ARGUMENTS { 2,3,6 }
--#SEVERITY INFORMATIONAL
--#STATE OPERATIONAL
        ::= 7005

hpiSvSoftwareDebug TRAP-TYPE
        ENTERPRISE hpiSvTraps
        VARIABLES {
                hpiEventSource,
                hpiEventTime,
                hpiSoftwareEventManufacturerId,
                hpiSoftwareEventType,
                hpiSoftwareEventTextType,
                hpiSoftwareEventTextLanguage,
                hpiSoftwareEventText
        }
        DESCRIPTION
                "Audit events report a discrepancy in the audit process.  Audits are 
		 typically performed by HA software to detect problems.  Audits may 
		 look for such things as corrupted data stores, inconsistent RPT 
		 information, or improperly managed queues.  Startup events report a 
		 failure to start-up properly, or inconsistencies in persisted data."
--#TYPE "HPI Software event (debug event)"
--#SUMMARY "HPI Software Event has been reported."
--#SUMMARY "(Manufacturer ID: %d, Event type: %s, Event text: %s)"
--#ARGUMENTS { 2,3,6 }
--#SEVERITY INFORMATIONAL
--#STATE OPERATIONAL
        ::= 7241

hpiSvOemUndefined TRAP-TYPE
        ENTERPRISE hpiSvTraps
        VARIABLES {
                hpiEventSource,
                hpiEventTime,
                hpiOEMEventManufacturerId,
                hpiOEMEventTextType,
                hpiOEMEventTextLanguage,
                hpiOEMEventText
        }
        DESCRIPTION
                "OEM event notifications."
--#TYPE "HPI OEM Custom event (Unknown severity)"
--#SUMMARY "HPI OEM Event has been reported."
--#SUMMARY "(Manufacturer ID: %d, Event text: %s)"
--#ARGUMENTS { 2,5 }
--#SEVERITY UNKNOWN
--#STATE OPERATIONAL
        ::= 8000

hpiSvOemCritical TRAP-TYPE
        ENTERPRISE hpiSvTraps
        VARIABLES {
                hpiEventSource,
                hpiEventTime,
                hpiOEMEventManufacturerId,
                hpiOEMEventTextType,
                hpiOEMEventTextLanguage,
                hpiOEMEventText
        }
        DESCRIPTION
                "OEM event notifications."
--#TYPE "HPI OEM Custom event (Severe)"
--#SUMMARY "HPI OEM Event has been reported."
--#SUMMARY "(Manufacturer ID: %d, Event text: %s)"
--#ARGUMENTS { 2,5 }
--#SEVERITY SEVERE
--#STATE OPERATIONAL
        ::= 8001

hpiSvOemMajor TRAP-TYPE
        ENTERPRISE hpiSvTraps
        VARIABLES {
                hpiEventSource,
                hpiEventTime,
                hpiOEMEventManufacturerId,
                hpiOEMEventTextType,
                hpiOEMEventTextLanguage,
                hpiOEMEventText
        }
        DESCRIPTION
                "OEM event notifications."
--#TYPE "HPI OEM Custom event (Major)"
--#SUMMARY "HPI OEM Event has been reported."
--#SUMMARY "(Manufacturer ID: %d, Event text: %s)"
--#ARGUMENTS { 2,5 }
--#SEVERITY MAJOR
--#STATE OPERATIONAL
        ::= 8002

hpiSvOemMinor TRAP-TYPE
        ENTERPRISE hpiSvTraps
        VARIABLES {
                hpiEventSource,
                hpiEventTime,
                hpiOEMEventManufacturerId,
                hpiOEMEventTextType,
                hpiOEMEventTextLanguage,
                hpiOEMEventText
        }
        DESCRIPTION
                "OEM event notifications."
--#TYPE "HPI OEM Custom event (Minor)"
--#SUMMARY "HPI OEM Event has been reported."
--#SUMMARY "(Manufacturer ID: %d, Event text: %s)"
--#ARGUMENTS { 2,5 }
--#SEVERITY MINOR
--#STATE OPERATIONAL
        ::= 8003

hpiSvOemInformational TRAP-TYPE
        ENTERPRISE hpiSvTraps
        VARIABLES {
                hpiEventSource,
                hpiEventTime,
                hpiOEMEventManufacturerId,
                hpiOEMEventTextType,
                hpiOEMEventTextLanguage,
                hpiOEMEventText
        }
        DESCRIPTION
                "OEM event notifications."
--#TYPE "HPI OEM Custom event (Informational)"
--#SUMMARY "HPI OEM Event has been reported."
--#SUMMARY "(Manufacturer ID: %d, Event text: %s)"
--#ARGUMENTS { 2,5 }
--#SEVERITY INFORMATIONAL
--#STATE OPERATIONAL
        ::= 8004

hpiSvOemOk TRAP-TYPE
        ENTERPRISE hpiSvTraps
        VARIABLES {
                hpiEventSource,
                hpiEventTime,
                hpiOEMEventManufacturerId,
                hpiOEMEventTextType,
                hpiOEMEventTextLanguage,
                hpiOEMEventText
        }
        DESCRIPTION
                "OEM event notifications."
--#TYPE "HPI OEM Custom event (OK)"
--#SUMMARY "HPI OEM Event has been reported."
--#SUMMARY "(Manufacturer ID: %d, Event text: %s)"
--#ARGUMENTS { 2,5 }
--#SEVERITY INFORMATIONAL
--#STATE OPERATIONAL
        ::= 8005

hpiSvOemDebug TRAP-TYPE
        ENTERPRISE hpiSvTraps
        VARIABLES {
                hpiEventSource,
                hpiEventTime,
                hpiOEMEventManufacturerId,
                hpiOEMEventTextType,
                hpiOEMEventTextLanguage,
                hpiOEMEventText
        }
        DESCRIPTION
                "OEM event notifications."
--#TYPE "HPI OEM Custom event (debug event)"
--#SUMMARY "HPI OEM Event has been reported."
--#SUMMARY "(Manufacturer ID: %d, Event text: %s)"
--#ARGUMENTS { 2,5 }
--#SEVERITY INFORMATIONAL
--#STATE OPERATIONAL
        ::= 8241

hpiSvUserUndefined TRAP-TYPE
        ENTERPRISE hpiSvTraps
        VARIABLES {
                hpiEventSource,
                hpiEventTime,
                hpiUserEventTextType,
                hpiUserEventTextLanguage,
                hpiUserEventText
        }
        DESCRIPTION
                "User events may be used for storing custom events created by an HPI 
		 User when injecting events into the Event Log using
		 hpiEventLogEntryAdd()."
--#TYPE "HPI Custom event, created by user program (Unknown severity)"
--#SUMMARY "HPI User Event has been reported."
--#SUMMARY "(Event text: %s)"
--#ARGUMENTS { 4 }
--#SEVERITY UNKNOWN
--#STATE OPERATIONAL
        ::= 9000

hpiSvUserCritical TRAP-TYPE
        ENTERPRISE hpiSvTraps
        VARIABLES {
                hpiEventSource,
                hpiEventTime,
                hpiUserEventTextType,
                hpiUserEventTextLanguage,
                hpiUserEventText
        }
        DESCRIPTION
                "User events may be used for storing custom events created by an HPI 
		 User when injecting events into the Event Log using
		 hpiEventLogEntryAdd()."
--#TYPE "HPI Custom event, created by user program (Severe)"
--#SUMMARY "HPI User Event has been reported."
--#SUMMARY "(Event text: %s)"
--#ARGUMENTS { 4 }
--#SEVERITY SEVERE
--#STATE OPERATIONAL
        ::= 9001

hpiSvUserMajor TRAP-TYPE
        ENTERPRISE hpiSvTraps
        VARIABLES {
                hpiEventSource,
                hpiEventTime,
                hpiUserEventTextType,
                hpiUserEventTextLanguage,
                hpiUserEventText
        }
        DESCRIPTION
                "User events may be used for storing custom events created by an HPI 
		 User when injecting events into the Event Log using
		 hpiEventLogEntryAdd()."
--#TYPE "HPI Custom event, created by user program (Major)"
--#SUMMARY "HPI User Event has been reported."
--#SUMMARY "(Event text: %s)"
--#ARGUMENTS { 4 }
--#SEVERITY MAJOR
--#STATE OPERATIONAL
        ::= 9002

hpiSvUserMinor TRAP-TYPE
        ENTERPRISE hpiSvTraps
        VARIABLES {
                hpiEventSource,
                hpiEventTime,
                hpiUserEventTextType,
                hpiUserEventTextLanguage,
                hpiUserEventText
        }
        DESCRIPTION
                "User events may be used for storing custom events created by an HPI 
		 User when injecting events into the Event Log using
		 hpiEventLogEntryAdd()."
--#TYPE "HPI Custom event, created by user program (Minor)"
--#SUMMARY "HPI User Event has been reported."
--#SUMMARY "(Event text: %s)"
--#ARGUMENTS { 4 }
--#SEVERITY MINOR
--#STATE OPERATIONAL
        ::= 9003

hpiSvUserInformational TRAP-TYPE
        ENTERPRISE hpiSvTraps
        VARIABLES {
                hpiEventSource,
                hpiEventTime,
                hpiUserEventTextType,
                hpiUserEventTextLanguage,
                hpiUserEventText
        }
        DESCRIPTION
                "User events may be used for storing custom events created by an HPI 
		 User when injecting events into the Event Log using
		 hpiEventLogEntryAdd()."
--#TYPE "HPI Custom event, created by user program (Informational)"
--#SUMMARY "HPI User Event has been reported."
--#SUMMARY "(Event text: %s)"
--#ARGUMENTS { 4 }
--#SEVERITY INFORMATIONAL
--#STATE OPERATIONAL
        ::= 9004

hpiSvUserOk TRAP-TYPE
        ENTERPRISE hpiSvTraps
        VARIABLES {
                hpiEventSource,
                hpiEventTime,
                hpiUserEventTextType,
                hpiUserEventTextLanguage,
                hpiUserEventText
        }
        DESCRIPTION
                "User events may be used for storing custom events created by an HPI 
		 User when injecting events into the Event Log using
		 hpiEventLogEntryAdd()."
--#TYPE "HPI Custom event, created by user program (OK)"
--#SUMMARY "HPI User Event has been reported."
--#SUMMARY "(Event text: %s)"
--#ARGUMENTS { 4 }
--#SEVERITY INFORMATIONAL
--#STATE OPERATIONAL
        ::= 9005

hpiSvUserDebug TRAP-TYPE
        ENTERPRISE hpiSvTraps
        VARIABLES {
                hpiEventSource,
                hpiEventTime,
                hpiUserEventTextType,
                hpiUserEventTextLanguage,
                hpiUserEventText
        }
        DESCRIPTION
                "User events may be used for storing custom events created by an HPI 
		 User when injecting events into the Event Log using
		 hpiEventLogEntryAdd()."
--#TYPE "HPI Custom event, created by user program (debug event)"
--#SUMMARY "HPI User Event has been reported."
--#SUMMARY "(Event text: %s)"
--#ARGUMENTS { 4 }
--#SEVERITY INFORMATIONAL
--#STATE OPERATIONAL
        ::= 9241

END
