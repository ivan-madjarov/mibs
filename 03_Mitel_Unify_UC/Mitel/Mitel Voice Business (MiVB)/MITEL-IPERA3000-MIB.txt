-- Copyright 2005, 2006, 2011, 2014 MITEL Networks Corporation
-- All rights reserved.
-- This MITEL SNMP Management Information Base Specification
-- (Specification) embodies MITEL's confidential and
-- proprietary intellectual property. MITEL retains all
-- title and ownership in the Specification, including any
-- revisions.

-- This Specification is supplied "AS IS", and MITEL makes
-- no warranty, either express or implied, as to the use,
-- operation, condition, or performance of the Specification.

MITEL-IperaVoiceLAN-MIB DEFINITIONS ::= BEGIN


    IMPORTS
	OBJECT-TYPE
		FROM RFC-1212
	TRAP-TYPE
		FROM RFC-1215
	DisplayString, sysName
		FROM RFC1213-MIB
        mitelAppCallServer, mitelConfCompliances,
        mitelConfAgents, 
        mitelGrpIpera3000, mitelIdCsIpera3000
            FROM MITEL-MIB;

    mitelAppCsIpera3000  OBJECT IDENTIFIER ::= {mitelAppCallServer 2}  -- "1" being used for sx2000 as mitelAppCs2000   
-- MODULE-IDENTITY
--        LAST-UPDATED      "20140227000000Z"
--        ORGANIZATION      "MITEL Networks Corporation"
--        CONTACT-INFO      "MITEL Networks Corporation
--                           4000 Innovation Drive 
--                           Kanata, Ontario
--                           Canada  K2K 3K1 
--                           Tel: +1 613 592 2122
--                           Fax: +1 613 592 4784
--                           URL: www.mitel.com"
--        DESCRIPTION       "The MITEL Ipera 3000 MIB module."
--        REVISION          "20140227000000Z"
--        DESCRIPTION   "Harmonized Reset Causes with resetCauseLib.h"
--        REVISION          "201402111200Z"
--        DESCRIPTION   "Replaced std@mitel.com with www.mitel.com."
--        REVISION          "20110120000000Z"
--        DESCRIPTION   "Add Voice Quality notification."
--        REVISION          "20060120000000Z"
--        DESCRIPTION   "Replaced Integer32 with INTEGER."
--        REVISION          "20051129000000Z"
--        DESCRIPTION   "Addition of shutdown and restart complete traps and
--                       new scalar objects.  Also updated the copyright notice
--                       and cleaned up some SMI lint warnings."
--        REVISION          "0011100000Z"
--        DESCRIPTION   "Mitel Ipera 3000 MIB Version 1.0"

-- For SNMPv1 compliance:
DateAndTime ::= OCTET STRING(SIZE(8 | 11))

    -- ************************************
    -- Ipera 3000-specific Textual Conventions
    -- ************************************

    MitelIpera3000AlarmLevelType ::= INTEGER   
                {               almClear(1),     -- all clear
                                almMinor(2),     -- minor alarm
                                almMajor(3),     -- major alarm
                                almCritical(4)   -- critical alarm
				}

    MitelIpera3000ShutdownCause ::= INTEGER
                {
                resourcesLowReboot (1), -- System reboot to reclaim resources. 
                softwareFailureReboot (2), --  System reboot due to a serious software fault.
		hardwareFailureReboot (3), --  System reboot due to a serious hardware fault.
                softwareUpgradedReboot (4), -- System reboot because software was upgraded. 
                databaseRestoreReboot (5), -- System reboot because a database was restored.
                intermediateReboot (6), -- System reboot during startup because of a configuration change.
                l2SwitchFailureReboot (7), -- Layer 2 switch shutdown system to restore internal communications.
                remoteAlarmButtonReboot (8), -- System reboot because user pressed remote alarm button.
                programmedReboot (9), -- A programmed reboot was scheduled and took place.
                maintenanceCommandReboot (10), -- System was reset by the user at the maintenance interface.
                maintenanceCommandShutdown (11), -- System was shutdown by the user at the maintenance interface.
                shutdownCauseNotReported (12) -- Shutdown cause not reported.
                }                

    MitelIpera3000ResetCause ::= INTEGER
                {
                pushButtonReset (1), -- The reset button on the chasis was pushed.
                softwareInitiatedReset (2), -- The software in the system requested a reset.
                powerOnReset (3), -- Reset because controller power was interrupted.
                systemFaultReset (4), -- A serious software or hardware error occurred.
                uknownReset (5) -- Reset cause unknown.
                }

--TEXTUAL-CONVENTION
--        STATUS            current
--        DESCRIPTION       "The MITEL-defined alarm level type."


--TEXTUAL-CONVENTION
--        STATUS            current
--        DESCRIPTION       "The MITEL-defined primary ICP operational state."


--TEXTUAL-CONVENTION
--        STATUS            current
--        DESCRIPTION       "The MITEL-defined primary ICP operational state."

    -- ************************************
    -- The mitelAppCsIpera3000 subtree... Ipera 3000.
    -- ************************************

    mitelIpera3000System  OBJECT IDENTIFIER ::= {mitelAppCsIpera3000 1 }    
--OBJECT-IDENTITY
--    STATUS                current
--    DESCRIPTION           "Subtree for any product-specific information."
--    ::= { mitelAppCsIpera3000 1 }

    mitelIpera3000Alarms  OBJECT IDENTIFIER ::= {mitelAppCsIpera3000 2}   
--OBJECT-IDENTITY
--    STATUS                current
--    DESCRIPTION           "Alarms information for the Ipera 3000."
--    ::= { mitelAppCsIpera3000 2 }

    mitelIpera3000Resilience  OBJECT IDENTIFIER ::= {mitelAppCsIpera3000 4}   
--OBJECT-IDENTITY
--    STATUS                current
--    DESCRIPTION           "Resiliency information for the Ipera 3000."
--    ::= { mitelAppCsIpera3000 4 }

    mitelIpera3000Applications  OBJECT IDENTIFIER ::= {mitelAppCsIpera3000 5}   
--OBJECT-IDENTITY
--    STATUS                current
--    DESCRIPTION           "Subtree for Ipera 3000 Applications."
--    ::= { mitelAppCsIpera3000 5 }

--  ::= { mitelIpera3000Applications 1 }         Located in MITEL-BWM-MIB

    -- ************************************
    -- The mitel subtree... table of Call Server-specific system information.
    -- ************************************

--    mitelIpera3000SysName    OBJECT-TYPE
--        SYNTAX            DisplayString (SIZE (0..255))
--        ACCESS        read-only
--        STATUS           obsolete 
--        DESCRIPTION       "The name of the call server."
--        ::= { mitelIpera3000System 1 }

    mitelIpera3000SysCapDisplay  OBJECT IDENTIFIER ::= {mitelIpera3000System 2 }    
--OBJECT-IDENTITY
--    STATUS                current
--    DESCRIPTION           "Subtree for any system capacity information."
--    ::= { mitelIpera3000System 2 }

    mitelIpera3000CEID  OBJECT-TYPE
        SYNTAX            DisplayString (SIZE (0..255))
        ACCESS        read-only
        STATUS           mandatory 
        DESCRIPTION       "The Cluster Element ID is a number to identify 
                           a node that is in a cluster.  This number is not
                           guaranteed to be unique."
    ::= { mitelIpera3000System 3 }

    mitelIpera3000PNI  OBJECT-TYPE
        SYNTAX            DisplayString (SIZE (0..255))
        ACCESS        read-only
        STATUS           mandatory 
        DESCRIPTION       "The Primary Node ID is a number assigned to a 
                           cluster of nodes for a dialing plan.  Though a 
                           good candidate to identify a cluster, it is not 
                           unique across a network."
    ::= { mitelIpera3000System 4 }

    mitelIpera3000ClusterName  OBJECT-TYPE
        SYNTAX            DisplayString (SIZE (0..255)) 
        ACCESS        read-only
        STATUS           mandatory 
        DESCRIPTION       "The Cluster Name is a unique name that clearly 
                           identifies a cluster.  Introduced in 3300 6.0 release."
    ::= { mitelIpera3000System 5 }

    mitelIpera3000VoiceQuality OBJECT IDENTIFIER ::= { mitelIpera3000Applications 2 }

    mitelIpera3000VQLatencyThreshold OBJECT-TYPE
        SYNTAX              INTEGER
        ACCESS              read-only
        STATUS              mandatory
        DESCRIPTION         "Defines the voice quality latency threshold to
                            generate trap"
        ::= { mitelIpera3000VoiceQuality 1 }

    mitelIpera3000VQLatency OBJECT-TYPE
        SYNTAX              INTEGER
        ACCESS              read-only
        STATUS              mandatory
        DESCRIPTION         "Defines the delay in the voice quality"
        ::= { mitelIpera3000VoiceQuality 2 }


    -- ************************************
    -- The mitel subtree... table of System Capacity Display-specific system information.
    -- ************************************

    mitelIpera3000IPUsrLicPurchased    OBJECT-TYPE
        SYNTAX            INTEGER
        ACCESS        read-only
        STATUS           mandatory 
        DESCRIPTION       "The number of the user license purchased."
        ::= { mitelIpera3000SysCapDisplay 1 }

    mitelIpera3000IPUsrLicUsed    OBJECT-TYPE
        SYNTAX            INTEGER
        ACCESS        read-only
        STATUS           mandatory 
        DESCRIPTION       "The number of the user license used."
        ::= { mitelIpera3000SysCapDisplay 2 }

    mitelIpera3000IPDevLicPurchased    OBJECT-TYPE
        SYNTAX            INTEGER
        ACCESS        read-only
        STATUS           mandatory 
        DESCRIPTION       "The number of the device license purchased."
        ::= { mitelIpera3000SysCapDisplay 3 }

    mitelIpera3000IPDevLicUsed    OBJECT-TYPE
        SYNTAX            INTEGER
        ACCESS        read-only
        STATUS           mandatory 
        DESCRIPTION       "The number of the device license used."
        ::= { mitelIpera3000SysCapDisplay 4 }

    -- ************************************
    -- The mitelIpera3000Alarms subtree... table of alarm states
    -- ************************************


    mitelIpera3000AlmLevel       OBJECT-TYPE
        SYNTAX            MitelIpera3000AlarmLevelType
        ACCESS        read-only
        STATUS           mandatory 
        DESCRIPTION       "The current overall alarm level for the call
                          server."
        ::= { mitelIpera3000Alarms 1 }

    mitelIpera3000AlmDetectDate  OBJECT-TYPE
        SYNTAX            DateAndTime
        ACCESS        read-only
        STATUS           mandatory 
        DESCRIPTION       "Defines when the alarm was detected."
        ::= { mitelIpera3000Alarms 2 }

    mitelIpera3000AlmNbrCategories OBJECT-TYPE
        SYNTAX            INTEGER
        ACCESS        read-only
        STATUS           mandatory 
        DESCRIPTION       "Defines the number of associated entries in
                          the categories table."
        ::= { mitelIpera3000Alarms 3 }

    -- ************************************
    -- The mitelIpera3000CategoryTable subtree... table of categorized alarms
    -- ************************************

    mitelIpera3000CategoryTable  OBJECT-TYPE
        SYNTAX            SEQUENCE OF MitelIpera3000CategoryTableEntry
        ACCESS        not-accessible
        STATUS           mandatory 
        DESCRIPTION       "Table defining the alarm state for individual
                          call server categories. There will be multiple
                          categories for each call server. The number of
                          rows in the table is determined by the total
                          of the mitelIpera3000AlmTblNbrCategories value."
        ::= { mitelIpera3000Alarms 4 }

    mitelIpera3000CategoryTableEntry OBJECT-TYPE
        SYNTAX            MitelIpera3000CategoryTableEntry
        ACCESS        not-accessible
        STATUS           mandatory 
        DESCRIPTION       "A row defining a single category."
        INDEX             { mitelIpera3000CatTblIndex }
        ::= { mitelIpera3000CategoryTable 1 }

    MitelIpera3000CategoryTableEntry ::=
        SEQUENCE {
          mitelIpera3000CatTblIndex            INTEGER,
          mitelIpera3000CatTblAvailable        INTEGER,
          mitelIpera3000CatTblUnavailable      INTEGER,
          mitelIpera3000CatTblLevel            MitelIpera3000AlarmLevelType,
          mitelIpera3000CatTblMinorThresh      INTEGER,
          mitelIpera3000CatTblMajorThresh      INTEGER,
          mitelIpera3000CatTblCriticalThresh   INTEGER,
          mitelIpera3000CatTblName             DisplayString
        }

    mitelIpera3000CatTblIndex    OBJECT-TYPE
        SYNTAX           INTEGER (1..65535)
        ACCESS        read-only
        STATUS           mandatory 
        DESCRIPTION       "Differentiates the different category reports
                          for the call server. The first category
                          will have an index value of 1, the second will
                          have 2, etc. up to the last category report. The
                          highest possible index value is 100."
        ::= { mitelIpera3000CategoryTableEntry 1 }

    mitelIpera3000CatTblAvailable OBJECT-TYPE
        SYNTAX            INTEGER
        ACCESS        read-only
        STATUS           mandatory 
        DESCRIPTION       "The number of available resources of this type
                          of category on this call server."
        ::= { mitelIpera3000CategoryTableEntry 2 }

    mitelIpera3000CatTblUnavailable OBJECT-TYPE
        SYNTAX            INTEGER
        ACCESS        read-only
        STATUS           mandatory 
        DESCRIPTION       "The number of unavailable resources of this type
                          of category on this call server."
        ::= { mitelIpera3000CategoryTableEntry 3 }

    mitelIpera3000CatTblLevel    OBJECT-TYPE
        SYNTAX            MitelIpera3000AlarmLevelType
        ACCESS        read-only
        STATUS           mandatory 
        DESCRIPTION       "Defines the alarm level for this category on this
                          call server."
        ::= { mitelIpera3000CategoryTableEntry 4 }

    mitelIpera3000CatTblMinorThresh OBJECT-TYPE
        SYNTAX            INTEGER
        ACCESS        read-only
        STATUS           mandatory 
        DESCRIPTION       "The percentage unavailable threshold indicating
                          a minor alarm on this call server category."
        ::= { mitelIpera3000CategoryTableEntry 5 }

    mitelIpera3000CatTblMajorThresh OBJECT-TYPE
        SYNTAX            INTEGER
        ACCESS        read-only
        STATUS           mandatory 
        DESCRIPTION       "The percentage unavailable threshold indicating
                          a major alarm on this call server category."
        ::= { mitelIpera3000CategoryTableEntry 6 }

    mitelIpera3000CatTblCriticalThresh OBJECT-TYPE
        SYNTAX            INTEGER
        ACCESS        read-only
        STATUS           mandatory 
        DESCRIPTION       "The percentage unavailable threshold indicating
                          a critical alarm on this call server category."
        ::= { mitelIpera3000CategoryTableEntry 7 }

    mitelIpera3000CatTblName     OBJECT-TYPE
        SYNTAX            DisplayString (SIZE (0..255))
        ACCESS        read-only
        STATUS           mandatory 
        DESCRIPTION       "The name of this resource category."
        ::= { mitelIpera3000CategoryTableEntry 8 }

    mitelIpera3000TrapAlmShutdownCause OBJECT-TYPE
        SYNTAX            MitelIpera3000ShutdownCause
        ACCESS        read-only
        STATUS           mandatory 
        DESCRIPTION       "This value is only useful for the shutdown
                          trap.  This scalar is not persistent.  A
                          GET on this scalar will always return:
                          shutdownCauseNotReported (11).
        
                          Defines the last known shutdown cause.
                          This shutdown is the last orderly shutdown
                          of the system.  Do not confuse this with the
                          ResetCause.  e.g. this value would have no
                          meaning if the shutdown cause was from a power
                          failure, but it does have meaning if the shutdown
                          was due to a scheduled reboot."
        ::= { mitelIpera3000Alarms 5 }

    mitelIpera3000TrapAlmShutdownDetailedCause  OBJECT-TYPE
        SYNTAX         INTEGER 
        ACCESS         read-only
        STATUS         mandatory
        DESCRIPTION    "The detailed reason for the last shutdown:
        
                       This value is only useful for the shutdown
                       trap.  This scalar is not persistent.  A
                       GET on this scalar will always return:
                       shutdownCauseNotReported.

                resourcesLowShutdown (1), -- System reboot to reclaim resources. 
                softwareComponentFailureShutdown (2), --  System reboot due to a serious software fault.
                softwareUpgradedShutdown (3), -- System reboot because software was upgraded. 
                databaseRestoreShutdown (4), -- System reboot because a database was restored.
                intermediateShutdown (5), -- System reboot during startup because of a configuration change.
                l2SwitchFailureShutdown (6), -- Layer 2 switch shutdown system to restore internal communications.
                remoteAlarmButtonShutdown (7), -- System reboot because user pressed remote alarm button.
                softRestart (8), -- System reboot because call control issues a soft restart.
                callControlProgrammedReboot (9), -- by programmed reboot in CC 
                                                  -- like a scheduled reboot.
                callControlHardwareTrap (10), -- by hardware trap in CC
                callControlSoftwareTrap (11), -- by software trap in CC
                callControlLOADCommand (12), -- by LOAD command in CC
                callControlDiskFailure (13), -- because of disk failure
                callControlHardwareReset (14), -- by hardware reset in CC
                callControlMemoryFragmentation (15), -- because of memory fragmentation in CC
                callControlVxWorksTaskDoesNotExist (16), -- because VxWorks task does not exist
                callControlVxWorksTaskSuspended (17), -- because VxWorks task is suspended
                callControlVxWorksTaskNotResponding (18), -- because VxWorks task is not responding
                callControlVxWorksRestart (19), -- because of unknown VxWorks restart
                callControlUnkownProcess (20), -- by unknown process
                shutdownCauseNotReported (21) -- Shutdown cause not reported."
                            
        ::= { mitelIpera3000Alarms 6 }

    mitelIpera3000AlmResetCause OBJECT-TYPE
        SYNTAX            MitelIpera3000ResetCause
        ACCESS        read-only
        STATUS           mandatory 
        DESCRIPTION       "Defines the last known reset cause.
                          As best can be determined by the platform."
        ::= { mitelIpera3000Alarms 7 }

    mitelIpera3000AlmResetCauseBITS  OBJECT-TYPE
        SYNTAX         INTEGER 
        ACCESS         read-only
        STATUS         mandatory
        DESCRIPTION    "The reset bits for this system.

                           hardReset(0),
                           softReset(1),
                           busMonitorReset(2),
                           cpuSwWatchdogReset(3),
                           checkStopReset(4),
                           JTAGReset(5),
                           CPLDWatchdogReset(6),
                           powerOnReset(7),
                           softwareReset(8),
                           pushButtonReset(9)
                           JTAGReset83xx(10)
                           powerVoltageRailReset(11)
                           hardReset83xx(12)
                           softReset83xx(13)
                           overlordWatchdogReset(14)
                           onLineSwUpgradeReset(15)
                            
                        If the bit is set, then that reason is responsible for
                        the system reset.  Note: combinations of bit sets are possible.
                        Most significant bit set is typically the reason for the reset.
                        Typical Combinations are listed below, in the order of increasing priority:
                        0x0003 - external hard and soft reset
                        0x8003 - online Software upgrade reset
                        0x0013 - check stop reset
                        0x0083 - power up reset
                        0x0103 - software initiated reset (e.g., appShutdown, ESM 'RESET SYSTEM', remote alarm button)
                        0x0803 - power voltage rail reset
                        0x0203 - push button reset
                        0x4003 - overlord Watchdog reset
                        0x0043 - CPLD watch dog reset"
        ::= { mitelIpera3000Alarms 8 }
        

    -- ***********************************************************************
    -- The mitelIpera3000Resilience subtree... table of resiliency states
    -- 
    -- The following table and corresponding notifications apply to the
    -- "Resiliency" application.  This application is summerized as follows:
    -- 
    -- Resiliency allows IP Phones to re-home to a secondary controller if
    -- a 3300 ICP fails or is taken out if service.  This ensures that there
    -- is no disruption in service for connected calls.  Calls that are in
    -- progress when an outage occures remain in progress and are not lost.
    -- 
    -- The mitelIpera3000ResTable will contain an entry for every primary 
    -- 3300 ICP that had a IP Phone re-home to this 3300 ICP at time of the 
    -- first instance.  This would correspond to a mitelIpera3000NotifResiltFirstSetFailover
    -- notification being generated by this agent.  The corresponding entry in 
    -- the table will have mitelIpera3000ResTblStatus set to firstSetFailover(1).  
    -- When a 3300 ICP has passed the system health check, the corresponding 
    -- entry in the table will have mitelIpera3000ResTblStatus set to healthCheckComplete(2).   
    -- Once the last phone of the primary controler has transfered 
    -- back to the primary, the corresponding entry in the table with have it's 
    -- mitelIpera3000ResTblStatus set to handOffComplete(3).  This occurance would 
    -- correspond to a mitelIpera3000NotifResiltRediversion notification 
    -- generated by this agent.
    --
    -- Entries in this table are not persistent over a reboot.
    --
    -- ************************************************************************

    mitelIpera3000ResTable  OBJECT-TYPE
        SYNTAX            SEQUENCE OF MitelIpera3000ResTableEntry
        ACCESS        not-accessible
        STATUS           mandatory 
        DESCRIPTION       "Table defining the resiliency state for the primary ICP that has
                          gone into resilient mode."
        ::= { mitelIpera3000Resilience 1 }

   mitelIpera3000ResTableEntry OBJECT-TYPE
        SYNTAX            MitelIpera3000ResTableEntry
        ACCESS        not-accessible
        STATUS           mandatory 
        DESCRIPTION       "A row defining a single resiliency table entry."
        INDEX             { mitelIpera3000ResTblPriSysName }
        ::= { mitelIpera3000ResTable 1 }

    MitelIpera3000ResTableEntry ::=
        SEQUENCE {
          mitelIpera3000ResTblPriSysName       DisplayString,
          mitelIpera3000ResTblPriCEID          DisplayString,
          mitelIpera3000ResTblClusterName      DisplayString,
          mitelIpera3000ResTblDetectDate       DateAndTime,
          mitelIpera3000ResTblStatus           INTEGER
        }

    mitelIpera3000ResTblPriSysName  OBJECT-TYPE
        SYNTAX            DisplayString (SIZE (0..255)) 
        ACCESS        read-only
        STATUS           mandatory 
        DESCRIPTION       "The System Name of the primary ICP.  Empty strigs are no allowed.  The 
                          index column for the Resilience Table."
        ::= { mitelIpera3000ResTableEntry 1 }

    mitelIpera3000ResTblPriCEID  OBJECT-TYPE
        SYNTAX            DisplayString (SIZE (0..255))
        ACCESS        read-only
        STATUS           mandatory 
        DESCRIPTION       "The Cluster Element ID of the primary ICP."
        ::= { mitelIpera3000ResTableEntry 2 }

    mitelIpera3000ResTblClusterName  OBJECT-TYPE
        SYNTAX            DisplayString (SIZE (0..255))
        ACCESS        read-only
        STATUS           mandatory 
        DESCRIPTION       "The Cluster Name of group that the primary and secondary are a member of."
        ::= { mitelIpera3000ResTableEntry 3 }

    mitelIpera3000ResTblDetectDate  OBJECT-TYPE
        SYNTAX            DateAndTime
        ACCESS        read-only
        STATUS           mandatory 
        DESCRIPTION       "Defines when the alarm was detected."
        ::= { mitelIpera3000ResTableEntry 4 }

    mitelIpera3000ResTblStatus    OBJECT-TYPE
        SYNTAX      INTEGER {
                    firstSetFailover(1),
                    healthCheckComplete(2),
                    handOffComplete(3)
                    }
        ACCESS      read-only
        STATUS      mandatory 
        DESCRIPTION "Status of the entry."
        ::= { mitelIpera3000ResTableEntry 5 }

    -- ************************************
    -- The Ipera 3000 Alarm Notifications
    -- ************************************

    mitelIpera3000Notifications  OBJECT IDENTIFIER ::= {mitelAppCsIpera3000 3}
--        STATUS           mandatory 
--        DESCRIPTION       "The common traps supported by MITEL agents."
--        ::= { mitelAppCsIpera3000 3 }

    mitelIpera3000NotifAlarm     TRAP-TYPE 
    ENTERPRISE mitelIdCsIpera3000
        VARIABLES {
--          mitelIpera3000SysName,      	     the name of the system 
          sysName,
          mitelIpera3000AlmLevel,           -- the call server alarm level
          mitelIpera3000AlmDetectDate,      -- the alarm detection time
          mitelIpera3000AlmNbrCategories    -- indicates the number of assoc'd categories
        }
--        STATUS           mandatory 
        DESCRIPTION       "This notification is generated whenever
                          an alarm condition is detected or cleared. The
                          manager is expected to retrieve the corresponding
                          alarm and category table information."
        ::= 301  -- "201" being used by sx-2000

    mitelIpera3000ShutdownAlarm     TRAP-TYPE 
    ENTERPRISE mitelIdCsIpera3000
        VARIABLES {
          sysName,
          mitelIpera3000TrapAlmShutdownCause,
          mitelIpera3000TrapAlmShutdownDetailedCause
        }
--        STATUS           mandatory 
        DESCRIPTION       "This notification is generated whenever
                          the system can detect a shutdown of the system."
        ::= 302

    mitelIpera3000RestartCompleteAlarm     TRAP-TYPE 
    ENTERPRISE mitelIdCsIpera3000
        VARIABLES {
          sysName,
          mitelIpera3000AlmResetCause,
          mitelIpera3000AlmResetCauseBITS
        }
--        STATUS           mandatory 
        DESCRIPTION       "This notification is generated whenever
                          the system has completed booting and is now 
                          opperational.  The Reset Cause can give a
                          post mortum reason for the startup."
        ::= 303

    -- ************************************
    -- The Ipera 3000 Resiliency Notifications
    -- ************************************

    mitelIpera3000NotifResiltFirstSetFailover     TRAP-TYPE 
    ENTERPRISE mitelIdCsIpera3000
        VARIABLES {
--          mitelIpera3000SysName,      	     the name of the system 
          sysName,
          mitelIpera3000ResTblPriCEID,
          mitelIpera3000ResTblPriSysName,
          mitelIpera3000ResTblClusterName,
          mitelIpera3000ResTblDetectDate   
        }
--        STATUS           mandatory 
        DESCRIPTION       "This notification is generated when the 
                          first set fails-over from a primary to
                          secondary node."
        ::= 501 -- "401" being used by ERN traps

    mitelIpera3000NotifResiltHealthCheckComplete     TRAP-TYPE 
    ENTERPRISE mitelIdCsIpera3000
        VARIABLES {
--          mitelIpera3000SysName,      	     the name of the system 
          sysName,
          mitelIpera3000ResTblPriCEID,
          mitelIpera3000ResTblPriSysName,
          mitelIpera3000ResTblClusterName,
          mitelIpera3000ResTblDetectDate   
        }
--        STATUS           mandatory 
        DESCRIPTION   "This notification is generated
                       when the primary ICP has now
                       recovered.  This means that the
                       primary ICP has passed a system
                       health check as determined by the
                       resiliency application on this 
                       node."
        ::= 502


    mitelIpera3000NotifResiltHandoffComplete     TRAP-TYPE 
    ENTERPRISE mitelIdCsIpera3000
        VARIABLES {
--          mitelIpera3000SysName,      	     the name of the system 
          sysName,
          mitelIpera3000ResTblPriCEID,
          mitelIpera3000ResTblPriSysName,
          mitelIpera3000ResTblClusterName,
          mitelIpera3000ResTblDetectDate   
        }
--        STATUS           mandatory 
        DESCRIPTION   "This notification is generated
                       when all phones, from a particular
                       primary ICP, that had failed
                       over to this node have completed
                       handoff back to the primary ICP."
        ::= 503 

    -- ************************************
    -- The Ipera 3000 Voice Quality Notifications
    -- ************************************

    mitelIpera3000NotifVoiceQuality TRAP-TYPE
        ENTERPRISE          mitelIdCsIpera3000
        VARIABLES           {
                                sysName,
                                mitelIpera3000VQLatencyThreshold,
                                mitelIpera3000VQLatency
                            }
        DESCRIPTION   "This notification is generated
                       when voice quality delay had exceeded
                       the threshold."
        ::= 601

    -- ************************************
    -- The mitelConformance subtree.
    -- ************************************

    mitelComplIpera3000 OBJECT IDENTIFIER ::= {mitelConfCompliances 4}    
-- MODULE-COMPLIANCE
--        STATUS           mandatory 
--        DESCRIPTION       "The compliance statement for SNMPv2 entities which
--                           implement the MITEL Ipera 3000 MIB."
--        MODULE 
--              compliance to the MITEL Ipera 3000 MIB module
--          MANDATORY-GROUPS { mitelGrpIpera3000System }
--        ::= { mitelConfCompliances 4 }

    mitelGrpIpera3000System  OBJECT IDENTIFIER ::= {mitelGrpIpera3000 1}    
--OBJECT-GROUP
--        OBJECTS           {
--                            mitelIpera3000SysName
--                          }
--        STATUS          mandatory 
--        DESCRIPTION       "The system information objects in the Ipera 3000 MIB."
--        ::= { mitelGrpIpera3000 1 }

    mitelGrpIpera3000Alarms  OBJECT IDENTIFIER ::= {mitelGrpIpera3000 2}    
--OBJECT-GROUP
--        OBJECTS           {
--                            mitelIpera3000AlmLevel, 
--                            mitelIpera3000AlmDetectDate,
--                            mitelIpera3000AlmNbrCategories,
--                            mitelIpera3000CatTblAvailable,
--                            mitelIpera3000CatTblUnavailable,
--                            mitelIpera3000CatTblLevel,
--                            mitelIpera3000CatTblMinorThresh, 
--                            mitelIpera3000CatTblMajorThresh,
--                            mitelIpera3000CatTblCriticalThresh, 
--                            mitelIpera3000CatTblName
--                          }
--        STATUS           mandatory 
--        DESCRIPTION       "The alarms-related objects in the Ipera 3000 MIB."
--        ::= { mitelGrpIpera3000 2 }

--  mitelGrpIpera3000AlarmsNotifs NOTIFICATION-GROUP
--      OBJECTS           {
--                          mitelIpera3000NotifAlarm
--                        }
--      STATUS           mandatory 
--      DESCRIPTION       "The current notifications in the Ipera 3000 MIB."
--      ::= { mitelGrpIpera3000 3 }

    -- ************************************
    -- The mitelConfAgents subtree.
    -- ************************************

    mitelAgentIpera3000    OBJECT IDENTIFIER ::= {mitelConfAgents 3}  --"2"being used by sx2000
--AGENT-CAPABILITIES
--        PRODUCT-RELEASE   "MITEL Agent Release 1.0 for Ipera 3000"
--        STATUS           mandatory 
--        DESCRIPTION       "MITEL Ipera 3000 Agent."
--
--        SUPPORTS          SNMPv2-MIB
--            INCLUDES      {
--                            snmpStatsGroup, snmpORGroup,
--                            snmpTrapGroup, snmpSetGroup,
--                            snmpV1Group
--                          systemGroup, snmpGroup, snmpSetGroup,
--                          snmpBasicNotificationsGroup
--                          }
--
--        SUPPORTS          MITEL-MIB
--            INCLUDES      {
--                            mitelGrpCmnNotifBasic
--                          }
--            VARIATION     mitelNotifEnblTblEnable
--                ACCESS      read-only
--                DESCRIPTION "Implemented as a configuration file item."
--            VARIATION     mitelNotifEnblTblAck
--                ACCESS      read-only
--                DESCRIPTION "Acknowledgement of notifications is not
--                             supported. Will always return False."
--
--        SUPPORTS          MITEL-SX2000-MIB
--            INCLUDES      {
--                            mitelGrpIpera3000Alarms,
--                          mitelGrpIpera3000AlarmsNotifs
--                         }
--    ::= { mitelConfAgents 2 }

END -- MITEL-IPERA3000-MIB
