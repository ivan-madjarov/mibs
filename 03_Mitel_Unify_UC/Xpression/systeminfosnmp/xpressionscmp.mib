--************************************************************************--
--  Name     : SNMP MIB for Siemens Xpressions and OpenScape CMP 	      --
--                                                                        --
--                                                                        --
--  Date     : 2010-04-29                                                 --
--                                                                        --
--  Version  : 1.0.0                                                      --
--                                                                        --
--  Author   : Cleber J. Gomes de Campos				                  --
--             Siemens Enterprise, Curitiba                               --
--                                                                        --
--  Purpose  : status report of Xpressions modules, logs and information  --
--                                                                        --
--                                                                        --
--************************************************************************-- 

--*HOC********************************************************************--
--*                                                                      *--
--*    HISTORY OF CHANGE:               VARIANTE: SharedServices V1.1.3  *--
--*                                                                      *--
--************************************************************************--
--*VERS| DATE | CHANGES                                      | KZ | VGNO *--
--*    |yymmdd|                                              |    |      *--
--************************************************************************--
--* 01 |100429| first version of XpressionsCmp               |cle |  N   *--
--************************************************************************--

   XpressionsCmp-MIB DEFINITIONS ::= BEGIN
   
   IMPORTS
        MODULE-IDENTITY, OBJECT-TYPE, NOTIFICATION-TYPE, Integer32, 
        Counter32 
       FROM SNMPv2-SMI
        TEXTUAL-CONVENTION 
       FROM SNMPv2-TC
        enterprises
       FROM RFC1155-SMI
        OBJECT-GROUP, NOTIFICATION-GROUP, MODULE-COMPLIANCE 
       FROM SNMPv2-CONF ;


-- Some MIB compilers require that the following lines
-- which define the path to this MIB are added.

-- tree              OBJECT IDENTIFIER ::= { iso(1) org(3) dod(6) internet(1) }
-- private           OBJECT IDENTIFIER ::= { tree 4 }
-- enterprises       OBJECT IDENTIFIER ::= { private 1 }
-- siemens           OBJECT IDENTIFIER ::= { enterprises 4329 }
-- com               OBJECT IDENTIFIER ::= { siemens 2 }

   xpressionsCmp        MODULE-IDENTITY
       LAST-UPDATED  "1005100000Z" -- Mai 05, 2010
       ORGANIZATION  "EN DB"
       CONTACT-INFO  "Cleber Campos, 
                      Email: cle@cycos.com"
       DESCRIPTION   "for Siemens Xpressions and OpenScape CMP"
       ::= { com 46 }

   siemens           OBJECT IDENTIFIER ::= { enterprises 4329 }
   com               OBJECT IDENTIFIER ::= { siemens 2 }


--   nodeGroup                 OBJECT IDENTIFIER ::= {sharedServices 1}
--   applicationGroup          OBJECT IDENTIFIER ::= {sharedServices 2}
--   containerGroup            OBJECT IDENTIFIER ::= {sharedServices 3}
--   serviceGroup              OBJECT IDENTIFIER ::= {sharedServices 4}
--   alarmGroup                OBJECT IDENTIFIER ::= {sharedServices 5}
--   trapGroup                 OBJECT IDENTIFIER ::= {sharedServices 90}
--   complianceGroup           OBJECT IDENTIFIER ::= {sharedServices 98}
--   complianceModules         OBJECT IDENTIFIER ::= {sharedServices 99}
     xpressionsInfo            OBJECT IDENTIFIER ::= {xpressionsCmp 1}
	 aplsInfo		           OBJECT IDENTIFIER ::= {xpressionsCmp 2}
	 physicalLinesInfo	       OBJECT IDENTIFIER ::= {xpressionsCmp 3}
	 hardDiskInfo		       OBJECT IDENTIFIER ::= {xpressionsCmp 4}
	 messagesInfo		       OBJECT IDENTIFIER ::= {xpressionsCmp 5}

   
--************************************************************************-- 
--******                     textual conventions                    ******--
--************************************************************************-- 

   DisplayString ::= OCTET STRING
       -- This data type is used to model textual information taken
       -- from the NVT ASCII character set.  By convention, objects
       -- with this syntax are declared as having SIZE (0..255)


   Boolean ::=  INTEGER { true(1), false(0) }
       -- encoding for alarm status:
       -- 1 = alarm on
       -- 0 = alarm off


   Severity ::= INTEGER {
                      normal(0),
                      information(1),
                      warning(2),
                      minor(3),
                      major(4),
                      critical(5),
                      unknown(6)
                    }

       -- States for node- /application- /container- and service- groups:
       --                           DisplayString: 
       -- started / executing    =  normal
       -- started / configuring  =  warning
       -- stopped                =  critical
   
--************************************************************************-- 
--******                     Accessible Elements                    ******--
--************************************************************************-- 
 
    --*******************************************--
    --************** Info Group *****************--
    --*******************************************--

    systemName  OBJECT-TYPE
        SYNTAX      DisplayString
        MAX-ACCESS  read-only
        STATUS      current
        DESCRIPTION
            "Xpressions system name"
        ::= { xpressionsInfo 1 }

	ipAddress OBJECT-TYPE
        SYNTAX                  DisplayString
        MAX-ACCESS              read-only
        STATUS                  current
        DESCRIPTION
            "IP address"
        ::= { xpressionsInfo 2 }

    hostName OBJECT-TYPE
        SYNTAX                  DisplayString
        MAX-ACCESS              read-only
        STATUS                  current
        DESCRIPTION
            "Host name"
        ::= { xpressionsInfo 3 }
		
	subnetMask OBJECT-TYPE
        SYNTAX                  DisplayString
        MAX-ACCESS              read-only
        STATUS                  current
        DESCRIPTION
            "Subnet mask"
        ::= { xpressionsInfo 4 }

	defaultGateway OBJECT-TYPE
        SYNTAX                  DisplayString
        MAX-ACCESS              read-only
        STATUS                  current
        DESCRIPTION
            "Default gateway"
        ::= { xpressionsInfo 5 }
		
	systemType OBJECT-TYPE
        SYNTAX                  DisplayString
        MAX-ACCESS              read-only
        STATUS                  current
        DESCRIPTION
            "System type"
        ::= { xpressionsInfo 6 }
		
	language OBJECT-TYPE
        SYNTAX                  DisplayString
        MAX-ACCESS              read-only
        STATUS                  current
        DESCRIPTION
            "Installed Language"
        ::= { xpressionsInfo 7 }
		
	voicemailProtocol OBJECT-TYPE
        SYNTAX                  DisplayString
        MAX-ACCESS              read-only
        STATUS                  current
        DESCRIPTION
            "Voice mail protocol"
        ::= { xpressionsInfo 8 }
 		
    osVersion OBJECT-TYPE
        SYNTAX                  DisplayString
        MAX-ACCESS              read-only
        STATUS                  current
        DESCRIPTION
            "OS Version"
        ::= { xpressionsInfo 9 }

    osServicePack OBJECT-TYPE
        SYNTAX                  DisplayString
        MAX-ACCESS              read-only
        STATUS                  current
        DESCRIPTION
            "OS Service Pack"
        ::= { xpressionsInfo 10 }
		
    computerName OBJECT-TYPE
        SYNTAX                  DisplayString
        MAX-ACCESS              read-only
        STATUS                  current
        DESCRIPTION
            "Computer Name"
        ::= { xpressionsInfo 11 }
		
    totalMemory OBJECT-TYPE
        SYNTAX                  DisplayString
        MAX-ACCESS              read-only
        STATUS                  current
        DESCRIPTION
            "Total Memory"
        ::= { xpressionsInfo 12 }
		
    availableMemory OBJECT-TYPE
        SYNTAX                  DisplayString
        MAX-ACCESS              read-only
        STATUS                  current
        DESCRIPTION
            "Available Memory"
        ::= { xpressionsInfo 13 }
	
    --*******************************************--
    --************** Apls Group *****************--
    --*******************************************--

	aplsTable OBJECT-TYPE
        SYNTAX      SEQUENCE OF NodeAplEntry
        MAX-ACCESS  accessible-for-notify
        STATUS      current
        DESCRIPTION
                    "This table shows the contents of Apls entries. 
                    A APL is a service running in the hosting 
                    machine."
        ::= { aplsInfo 1 }				
			
    nodeAplEntry  OBJECT-TYPE
        SYNTAX      NodeAplEntry
        MAX-ACCESS  not-accessible
        STATUS      current
        DESCRIPTION
                    "The Apl table entries."
        INDEX { nodeDisplayName }
        ::= { aplsTable 1 }
		
    NodeAplEntry ::= SEQUENCE {
           nodeDisplayName       DisplayString,
           nodeBuildNumber       DisplayString,
           nodeDescription       DisplayString,
           nodeStatus            DisplayString
        }
 
     nodeDisplayName OBJECT-TYPE
        SYNTAX                  DisplayString
        MAX-ACCESS              read-only
        STATUS                  current
        DESCRIPTION
            "The nodename." 
        ::= { nodeAplEntry 1 }
    
    nodeBuildNumber OBJECT-TYPE
        SYNTAX                  DisplayString
        MAX-ACCESS              read-only
        STATUS                  current
        DESCRIPTION
            "The build number of the node." 
        ::= { nodeAplEntry 2 }

    nodeDescription OBJECT-TYPE
        SYNTAX                  DisplayString
        MAX-ACCESS              read-only
        STATUS                  current
        DESCRIPTION
            "A description of the node."
        ::= { nodeAplEntry 3 }
    
    nodeStatus OBJECT-TYPE
        SYNTAX                  DisplayString
        MAX-ACCESS              read-only
        STATUS                  current
        DESCRIPTION
            "The status of the node."
        ::= { nodeAplEntry 4 }

 
    --*******************************************--
    --******** Physical Lines Group *************--
    --*******************************************--
	
	physicalLinesTable OBJECT-TYPE
        SYNTAX      SEQUENCE OF PhysicalLineEntry
        MAX-ACCESS  accessible-for-notify
        STATUS      current
        DESCRIPTION
                    "This table shows the contents of lines entries."
        ::= { physicalLinesInfo 1 }				
	
	physicalLineEntry  OBJECT-TYPE
        SYNTAX      PhysicalLineEntry
        MAX-ACCESS  not-accessible
        STATUS      current
        DESCRIPTION
                    "The Apl table entries."
        INDEX { nodePhysicalLineName }
        ::= { physicalLinesTable 1 }
				
    PhysicalLineEntry ::= SEQUENCE {
           nodePhysicalLineName       DisplayString,
           nodePhysicalLineStatus     DisplayString
        }
 
     nodePhysicalLineName OBJECT-TYPE
        SYNTAX                  DisplayString
        MAX-ACCESS              read-only
        STATUS                  current
        DESCRIPTION
            "The Physical Line Name." 
        ::= { physicalLineEntry 1 }
    		
	nodePhysicalLineStatus OBJECT-TYPE
        SYNTAX                  DisplayString
        MAX-ACCESS              read-only
        STATUS                  current
        DESCRIPTION
            "The Physical Line status." 
        ::= { physicalLineEntry 2 }
    		
 
    --*******************************************--
    --******** Hard disk Group ******************--
    --*******************************************--
		
	hardDiskTable OBJECT-TYPE
        SYNTAX      SEQUENCE OF HardDiskEntry
        MAX-ACCESS  accessible-for-notify
        STATUS      current
        DESCRIPTION
                    "This table shows the hard disks of the host machine."
        ::= { hardDiskInfo 1 }			

	hardDiskEntry  OBJECT-TYPE
        SYNTAX      HardDiskEntry
        MAX-ACCESS  not-accessible
        STATUS      current
        DESCRIPTION
                    "The hard disk entrie."
        INDEX { nodeHardDiskName }
        ::= { hardDiskTable 1 }
		
    HardDiskEntry ::= SEQUENCE {
           nodeHardDiskName     	 DisplayString,
           nodeHardDiskUsedSpace     DisplayString
        }
 
     nodeHardDiskName OBJECT-TYPE
        SYNTAX                  DisplayString
        MAX-ACCESS              read-only
        STATUS                  current
        DESCRIPTION
            "The hard disk name or description." 
        ::= { hardDiskEntry 1 }
    		
	nodeHardDiskUsedSpace OBJECT-TYPE
        SYNTAX                  DisplayString
        MAX-ACCESS              read-only
        STATUS                  current
        DESCRIPTION
            "The hard disk used space." 
        ::= { hardDiskEntry 2 }
		
		
	--*******************************************--
    --***** Messages/Log Group ******************--
    --*******************************************--
	
	logTable OBJECT-TYPE
        SYNTAX      SEQUENCE OF LogEntry
        MAX-ACCESS  accessible-for-notify
        STATUS      current
        DESCRIPTION
           "This table shows the latest lines of log availble in the server."
        ::= { messagesInfo 1 }			

	logEntry  OBJECT-TYPE
        SYNTAX      LogEntry
        MAX-ACCESS  not-accessible
        STATUS      current
        DESCRIPTION
                    "Log line."
        INDEX { nodeLogTimeStamp }
        ::= { logTable 1 }
		
    LogEntry ::= SEQUENCE {
           nodeLogLevel		     DisplayString,
           nodeLogTimeStamp    	 DisplayString,
           nodeLogModule	     DisplayString,
           nodeLogTopic		     DisplayString,
           nodeLogMessage	     DisplayString   
        }
 
 	nodeLogLevel OBJECT-TYPE
        SYNTAX                  DisplayString
        MAX-ACCESS              read-only
        STATUS                  current
        DESCRIPTION
            "The log level (error/warning/info or debug level." 
        ::= { logEntry 1 }

     nodeLogTimeStamp OBJECT-TYPE
        SYNTAX                  DisplayString
        MAX-ACCESS              read-only
        STATUS                  current
        DESCRIPTION
            "The log time stamp." 
        ::= { logEntry 2 }
    		
	nodeLogModule OBJECT-TYPE
        SYNTAX                  DisplayString
        MAX-ACCESS              read-only
        STATUS                  current
        DESCRIPTION
            "The module that wrote the log line." 
        ::= { logEntry 3 }
    		
	nodeLogTopic OBJECT-TYPE
        SYNTAX                  DisplayString
        MAX-ACCESS              read-only
        STATUS                  current
        DESCRIPTION
            "The topic of the log." 
        ::= { logEntry 4 }
		    			
	nodeLogMessage OBJECT-TYPE
        SYNTAX                  DisplayString
        MAX-ACCESS              read-only
        STATUS                  current
        DESCRIPTION
            "The log text." 
        ::= { logEntry 5 }
		
		
    --*******************************************--
    --******************* END *******************--
    --*******************************************--

END
