HIQ-FEAT-LIC-MIB    DEFINITIONS ::= BEGIN

-- ==================================================================
--  Copyright ? 1999 - 2008 Siemens Enterprise Communications
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
--
-- Copyright ? 1999 - 2008 Siemens Enterprise Communications 
-- ==================================================================

-- ==================================================================
-- Revision History
-- 02/16/2005     Pedro Henriques           End-user licenses
-- 03/19/2007     Chris Georgantonis        Sip Trunking Session Licenses
-- 03/20/2007     Haritos Chatzidimitriou   Dynamic Licenses
--  04/10/08      C. Chatzidimitriou        FRN3208. Cleanup of MIBS      
--  06/12/2008    C. Chatzidimitriou        Updated MIB to be fully compatible with SNMPv2N3208
-- 09/15/2008     G.Kouris                  FRN3211
-- ==================================================================

IMPORTS
   MODULE-IDENTITY, OBJECT-TYPE, OBJECT-IDENTITY, Integer32
        FROM SNMPv2-SMI
   surpassRtp
	FROM SURPASS-RTP-MIB
   hiq8000Admin
        FROM SURPASS-RTP-ADMIN-MIB;

-- ==================================================================

hiqFeatLic   MODULE-IDENTITY
        LAST-UPDATED "200806111500Z"
        ORGANIZATION "Siemens Network Convergence LLC"
        CONTACT-INFO " " 
        DESCRIPTION
           "This MIB describes the end-user licenses features for
            all devices (HIQ, HIPATH, PS)." 
            
        REVISION "200806111500Z"    
        DESCRIPTION
            "Updated the MIB to be fully compatible with SNMPv2"

        ::= { hiq8000Admin 5 }

        -- ******************************************
        -- MIB OBJECT Declarations:
        -- ******************************************
		
	hiqFeatLicTrunkSessionGroup OBJECT-IDENTITY
                STATUS current
                DESCRIPTION
                "The SIP Trunking Session License Group."
                ::= { hiqFeatLic 1 }

	hiqFeatDynamicLicenseGroup OBJECT-IDENTITY
                STATUS current
                DESCRIPTION
                "The Dynamic License Group has read-only objects to identify the
                 number of available Dynamic licenses, the number of licenses 
                 currently In Use, the maximum value of 'In Use' licenses during the 
		 previous 24 hours, the number of customer violations and the number 
		 of Licenses Rejections per DN per hour. 
		     Also it includes a read-write object that controls the barrier 
		 over which the system generates warnings to notify the administrator
		 that usage is close to the system's capacity."
                ::= { hiqFeatLic 2 } 
		
       hiqFeatOSMOLicenseGroup OBJECT-IDENTITY
                STATUS current
                DESCRIPTION
                "The Openscape mobile (OSMO) License Group."
                ::= { hiqFeatLic 3 }
		
			
        -- ************************************
        -- SIP Trunking Sesion License Objects: 
        -- ************************************


	hiqFeatLicTrunkSessionLicenses OBJECT-TYPE
                SYNTAX  Integer32
                MAX-ACCESS  read-only
                STATUS      obsolete
                DESCRIPTION
			"The licenses assigned to the system. This object change only when 
			 installing new licensing files. The parameter is valid in both ITU 
			 and ANSI variants."
                  ::= { hiqFeatLicTrunkSessionGroup 1 }

	hiqFeatLicTrunkAverageUsage OBJECT-TYPE
                SYNTAX  Integer32
                MAX-ACCESS  read-only
                STATUS      current
                DESCRIPTION
			"The average usage within one hour. License Manager will take snapshots 
			 of current usage counter every 5 minutes and get the average of the 
			 values during an hour. The parameter is valid in both ITU and ANSI variants."
                  ::= { hiqFeatLicTrunkSessionGroup 2 }

	hiqFeatLicTrunkMaxAverageUsage OBJECT-TYPE
                SYNTAX  Integer32
                MAX-ACCESS  read-only
                STATUS      current
                DESCRIPTION
			"The maximum average usage within one hour, during a 24h period. The parameter 
			 is valid in both ITU and ANSI variants."
                  ::= { hiqFeatLicTrunkSessionGroup 3 }

	hiqFeatLicTrunkCustomerViolations OBJECT-TYPE
                SYNTAX  Integer32
                MAX-ACCESS  read-only
                STATUS      obsolete
                DESCRIPTION
			"This object holds the number of Trunking Session usage violation detected. 
			 The License Manager detects violations based on the maximum 1h average usage.
			 The parameter is valid in both ITU and ANSI variants."
                  ::= { hiqFeatLicTrunkSessionGroup 4 }

	hiqFeatLicTrunkViolationLimit OBJECT-TYPE
                SYNTAX  Integer32
                MAX-ACCESS  read-only
                STATUS      obsolete
                DESCRIPTION
			"This object holds the number of usage violations the system allows, before 
			 activating the enforcement. The parameter is valid in both ITU and ANSI variants."
                  ::= { hiqFeatLicTrunkSessionGroup 5 }

	hiqFeatLicTrunkWarnThresLic  OBJECT-TYPE
                SYNTAX Integer32 (0..100)
                MAX-ACCESS read-only
                STATUS     obsolete
                DESCRIPTION "Warning Threshold for Trunking Session licensing.
                             It controls the barrier over which the system generates warnings
		     	     to notify administrator that usage is close to system's capacity.
                             The parameter is valid in both ITU and ANSI variants."
                DEFVAL { 95 }
                ::= { hiqFeatLicTrunkSessionGroup 6 } 
		
	-- *********************************
        -- Dynamic License Objects: 
        -- *********************************
    
        hiqFeatLicDynamicAvailable OBJECT-TYPE
                SYNTAX Integer32
                MAX-ACCESS read-only
                STATUS current
                DESCRIPTION                                      
                   "This object represents the number of Dynamic licenses that are
		    available in the system. It is calculated by the license manager
		    using the formula: Purchased - In Use."                     
                ::= { hiqFeatDynamicLicenseGroup 1 }
                          
        hiqFeatLicDynamicInUse OBJECT-TYPE
                SYNTAX Integer32
                MAX-ACCESS read-only
                STATUS     current
                DESCRIPTION
            	   "This object represents the number of Dynamic licenses currently in use
                    in the system. There is One Home DN per Dynamic license. This value must
		    be less or equal to the number of Dynamic licenses Purchased."
            	::= { hiqFeatDynamicLicenseGroup 2 } 
            	
        hiqFeatLicDynamicMaxInUse OBJECT-TYPE
                SYNTAX Integer32
                MAX-ACCESS read-only
                STATUS     current
                DESCRIPTION
                   "This number represents the maximum usage of Dynamic licenses over the
                    last 24 hour period."                    
            	::= { hiqFeatDynamicLicenseGroup 3 }   
            	
        hiqFeatLicDynamicViolations OBJECT-TYPE
                SYNTAX Integer32
                MAX-ACCESS read-only
                STATUS     current
                DESCRIPTION
            	   "This object is a counter holding the number of usage violations. 
                    License Manager detects Dynamic licensing violations based on the maximum
                    usage. Therefore, system counts one violation per day maximum, regardless
                    of how many times the actual usage exceeded the licensing limits during that
                    day. If this number exceeds the violation limit, the system activates the 
                    license enforcement. The default violation limit is 10 and this number cannot 
                    be modified by the system Administrator."                 
            	::= { hiqFeatDynamicLicenseGroup 4 }   
            	
        hiqFeatLicDynamicViolationsLimit OBJECT-TYPE
                SYNTAX Integer32
                MAX-ACCESS read-only
                STATUS     current
                DESCRIPTION
            	   "This is the number of usage violations the system allows,before activating the
            	    enforcement. This value cannot be modified by the system administrator"                 
            	::= { hiqFeatDynamicLicenseGroup 5 }             	
                                                    
        hiqFeatLicDynamicRejections OBJECT-TYPE
                SYNTAX Integer32
                MAX-ACCESS read-only
                STATUS     obsolete
                DESCRIPTION
                   "-- Dynamic licensing not currently supported --
		   
		    This object holds the number of License rejections per DN per hour due to 
                    Dynamic Session licensing. This counter is calculated using the formula: 
		    Rejections/number of DNs."                  
            	::= { hiqFeatDynamicLicenseGroup 6 }             	
            	 
        hiqFeatLicDynWarningThreshold OBJECT-TYPE
                SYNTAX  Integer32 (0..100)
                MAX-ACCESS read-only
                STATUS     obsolete
                DESCRIPTION
                   "-- Dynamic licensing not currently supported --
		   
		    This object holds a system-wide RTP parameter that controls the barrier over
                    which the system generates warnings to notify the administrator that usage
                    is close to the system's capacity. The default value is 95. This means that when
                    activated licenses are over the 95% of the assigned licenses, the system generates 
                    a warning. License Manager checks for changes of this parameter every 1h." 
                DEFVAL { 95 }
            	::= { hiqFeatDynamicLicenseGroup 7 }  
		
	-- *********************************
        -- OSMO License Objects: 
        -- *********************************

        hiqFeatLicOSMOLicensesAssigned OBJECT-TYPE
                SYNTAX Integer32
                MAX-ACCESS read-only
                STATUS     current
                DESCRIPTION
		"This is the number of OSMO licenses assigned to the system"                 
            	::= { hiqFeatOSMOLicenseGroup 1 } 

        hiqFeatLicOSMOLicensesInUse OBJECT-TYPE
                SYNTAX Integer32
                MAX-ACCESS read-only
                STATUS     current
                DESCRIPTION
		"This is the number of OSMO licenses currently in use"                 
            	::= { hiqFeatOSMOLicenseGroup 2 }  

        hiqFeatLicOSMOMaxInUsedOver24Hour OBJECT-TYPE
                SYNTAX Integer32
                MAX-ACCESS read-only
                STATUS     current
                DESCRIPTION
		"This is the maximum number of OSMO licenses used over the last 24 hour period"                 
            	::= { hiqFeatOSMOLicenseGroup 3 }             
           


END
