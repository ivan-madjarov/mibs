US-SRX-SERVICE-MIB DEFINITIONS ::= BEGIN

-- ==================================================================
-- Copyright © Siemens Network Convergence LLC  
--
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
--
-- Copyright © Siemens Network Convergence LLC 
-- ==================================================================

-- ****************************************************************************
-- Revision History
--  01/08/02      Mangping Chang         initial code
--  04/04/02      Mangping Chang         Added Speed Calling Counters
--  05/23/02      Mangping Chang         Updated description for C release
--  08/16/02      Emilio Negron          Added SLE, RCF, and  SCA Traffic 
--                                       Measurements.
--  09/17/02      Emilio Negron          Added MCT Traffic Measurements.
--  12/20/02      Emilio Negron          Added SCF, DRCW, and ICD Traffic 
--                                       Measurements.
--  02/07/03      Emilio Negron          Added VM, and CF Traffic Measurements.
--  02/20/03      Emilio Negron          Added ACAR Traffic Measurements.
--  05/08/03      Polly Yu               Updated copyright text
--  05/22/03      Emilio Negron          Added additional VM TCAP MWI Traffic 
--                                       Measurements, and additional AC Traffic
--                                       Measurements.
--  06/13/03      Emilio Negron          Added EACR Traffic Measurements.
--  06/20/03      Mangping Chang         Updated SCA counters
--  09/08/03      Emilio Negron          Added Call Park Traffic Measurements.
--  03/08/04      Ren Luo                Added Calling Name Delivery Method
--  08/23/04      Ren Luo                Obsoleted Calling Name Delivery Method
--                                       Added TCAP Calling Name Delivery
--  09/07/04      Evangelos Gentis       Added counters for ITU, 
--                                       TCAP, CCS, CCBS, CCNR, CW, MWI 
--  02/02/05      Aristeidis Nixarlidis  Added LONR and LINR counters for ITU
--  03/22/05      Evangelos Gentis       Merge Rel 9 to Rel 10.
--  04/22/05      Aristeidis Nixarlidis  Altered the description for CFDA,CFBL,CFV 
--                                                        counters to CFNR,CFB,CFU
--  05/20/05      Evangelos Gentis       Added counters for FRN1125, FRN1126,
--                                       FRN0424, FRN1131
--  11/07/05      Nikos Vittas	         Added 2 new counters for FRN1134
--  11/23/05      Evangelos Gentis       Merge of R09.03 to R10.01
--  06/06/05      Evangelos Gentis       Added three new tables and counters for FRN1121
--  01/09/06      Evangelos Gentis       Changed MCT counters description in order to
--                                       apply to World Market
--  02/08/06      Marco Silva            FRN1859: Carry-over of FRN1409 to R10.1
--  02/16/06	  Chris Georgantonis	 Added a new counter regarding the Override
--					 OCB feature.
--  01/23/07      Evangelos Gentis       Updated usSrxServiceTcapSvcLssnLssn range
--  04/20/07      Hong Nguyen            FRN 2636, PostDial Account Codes.
--  07/11/07      Hong Nguyen            Corrected description for account code.
--  04/10/08      C. Chatzidimitriou     FRN3208. Cleanup of MIBS      
--  06/12/2008    C. Chatzidimitriou     Updated MIB to be fully compatible with SNMPv2   
--
--  ******************************************************************************
IMPORTS
    MODULE-IDENTITY, OBJECT-TYPE, Counter32
        FROM SNMPv2-SMI
    DisplayString, RowStatus
        FROM SNMPv2-TC
    surpassRtp
	FROM SURPASS-RTP-MIB
    hiq8000Admin
        FROM SURPASS-RTP-ADMIN-MIB
    SrxRowCountType
        FROM HIQ-ADMIN-MIB;

--########################################################
-- SRX Services Measurements MIB MODULE                  #
--########################################################

usSrxService MODULE-IDENTITY
    LAST-UPDATED "200806111500Z"
    ORGANIZATION "Siemens Network Convergence LLC"
    CONTACT-INFO " "
    DESCRIPTION
        " SRX Service Measurements MIB module. " 
        
    REVISION "200806111500Z"    
    DESCRIPTION
            "Updated the MIB to be fully compatible with SNMPv2"
    ::= { hiq8000Admin 4 }

--####################
-- OBJECT IDENTIFIER #
--####################

usSrxServiceObjects                   OBJECT IDENTIFIER      ::= { usSrxService 1 }

usSrxServicePerformData               OBJECT IDENTIFIER      ::= { usSrxServiceObjects 1 }

usSrxServicePerfCallForwardingData    OBJECT IDENTIFIER      ::= { usSrxServicePerformData 1 }

usSrxServicePerfCallingIDData         OBJECT IDENTIFIER      ::= { usSrxServicePerformData 2 }

usSrxServicePerfACRData               OBJECT IDENTIFIER      ::= { usSrxServicePerformData 3 }

usSrxServicePerfSpeedCallingData      OBJECT IDENTIFIER      ::= { usSrxServicePerformData 4 }

usSrxServicePerfScrnListEditData      OBJECT IDENTIFIER      ::= { usSrxServicePerformData 5 }

usSrxServicePerfSelCallAcceptData     OBJECT IDENTIFIER      ::= { usSrxServicePerformData 6 }

usSrxServicePerfSelCallRejectData     OBJECT IDENTIFIER      ::= { usSrxServicePerformData 7 }

usSrxServicePerfMalCallTraceData      OBJECT IDENTIFIER      ::= { usSrxServicePerformData 8 }

usSrxServicePerfThreeWayCallData      OBJECT IDENTIFIER      ::= { usSrxServicePerformData 9 }

usSrxServicePerfIntercomCallData      OBJECT IDENTIFIER      ::= { usSrxServicePerformData 10 }

usSrxServicePerfVoiceMailData         OBJECT IDENTIFIER      ::= { usSrxServicePerformData 11 }

usSrxServiceDNDData     	      OBJECT IDENTIFIER      ::= { usSrxServicePerformData 12 }

usSrxServiceActCSTAMonitorData        OBJECT IDENTIFIER      ::= { usSrxServicePerformData 13 }

usSrxServiceActCSTARouteRegData       OBJECT IDENTIFIER      ::= { usSrxServicePerformData 14 }

usSrxServiceActCSTAMonDataAll         OBJECT IDENTIFIER      ::= { usSrxServicePerformData 15 }

usSrxServiceActCSTAMonDataSiemens     OBJECT IDENTIFIER      ::= { usSrxServicePerformData 16 }

usSrxServiceActCSTAMonDataOther       OBJECT IDENTIFIER      ::= { usSrxServicePerformData 17 }

usSrxServiceActCSTAMonDataTelefonica  OBJECT IDENTIFIER      ::= { usSrxServicePerformData 18 }

usSrxServiceActCSTARouteRegDataAll         OBJECT IDENTIFIER      ::= { usSrxServicePerformData 19 }

usSrxServiceActCSTARouteRegDataSiemens     OBJECT IDENTIFIER      ::= { usSrxServicePerformData 20 }

usSrxServiceActCSTARouteRegDataOther       OBJECT IDENTIFIER      ::= { usSrxServicePerformData 21 }

usSrxServiceActCSTARouteRegDataTelefonica  OBJECT IDENTIFIER      ::= { usSrxServicePerformData 22 }

-- *****************************************************
-- Textual Conventions used in the Service Translations MIB
-- *****************************************************

AccountCodeType ::= TEXTUAL-CONVENTION
    STATUS  current
    DESCRIPTION "
          Indicates the type of Account Code.
       'cdrAccountCode'        - CDRAccountCode
       'postDialAccountCode'   - PostDialAccountCode"
    SYNTAX INTEGER { cdrAccountCode(1),
                     postDialAccountCode(2) }

-- *****************************************************************
-- Services related Traffic and Maintenance Measurements/Statistics 
--
-- Every statistics counter will be shared by all instances of the
-- Services process.
-- *****************************************************************

-- *****************************************************************
-- Call Forwarding (CF) Traffic Measurements
-- *****************************************************************

usSrxServiceCFActToAllowedNumberCounter     OBJECT-TYPE
    SYNTAX      Counter32
    MAX-ACCESS  read-only
    STATUS      current
    DESCRIPTION
        " This object refers to the total number of times a 
          subscriber of the feature attempts to activate call
          forwarding. An activation attempt is defined as dialing
          the activation code plus a complete legitimate telephone
          number. 
          This counter is supported in ANSI and Japanese variants."
    ::= { usSrxServicePerfCallForwardingData 1  }

usSrxServiceCFActToNonAllowedNumberCounter   OBJECT-TYPE
    SYNTAX      Counter32
    MAX-ACCESS  read-only
    STATUS      current
    DESCRIPTION
        " This object refers to the total number of times a
          subscriber of the feature attempts to activate call
          forwarding but dials a non-allowed number. 
          This counter is supported in ANSI and Japanese variants."
    ::= { usSrxServicePerfCallForwardingData 2  }

usSrxServiceCFFirstAttemptSuccessCounter     OBJECT-TYPE
    SYNTAX      Counter32
    MAX-ACCESS  read-only
    STATUS      current
    DESCRIPTION
        " This object refers to the total number of activation 
          successfully completed by answer of remote station. 
          This counter is supported in ANSI and Japanese variants."
    ::= { usSrxServicePerfCallForwardingData 3  }

usSrxServiceCFSecondAttemptSuccessCounter     OBJECT-TYPE
    SYNTAX      Counter32
    MAX-ACCESS  read-only
    STATUS      current
    DESCRIPTION
        " This object refers to the total number of activation 
          successfully completed by a second activation procedure.
          This counter is supported in ANSI and Japanese variants."
    ::= { usSrxServicePerfCallForwardingData 4  }

usSrxServiceCFCFVOccuredCounter       OBJECT-TYPE
    SYNTAX      Counter32
    MAX-ACCESS  read-only
    STATUS      current
    DESCRIPTION
        " This object refers to the total number of times Call 
          Forwarding occurs for the Call Forwarding Unconditional (CFU)
          Feature. 
          This counter is supported in ANSI, ITU and Japanese variants."
    ::= { usSrxServicePerfCallForwardingData 5  }

usSrxServiceCFCFBLOccuredCounter      OBJECT-TYPE
    SYNTAX      Counter32
    MAX-ACCESS  read-only
    STATUS      current
    DESCRIPTION
        " This object refers to the total number of times Call
          Forwarding occurs for the Call Forwarding Busy
          (CFB) Feature. 
          This counter is supported in ANSI, ITU and Japanese variants."
    ::= { usSrxServicePerfCallForwardingData 6  }

usSrxServiceCFCFDAOccuredCounter       OBJECT-TYPE
    SYNTAX      Counter32
    MAX-ACCESS  read-only
    STATUS      current
    DESCRIPTION
        " This object refers to the total number of times Call
          Forwarding occurs for the Call Forwarding No Reply 
          (CFNR) Feature. 
          This counter is supported in ANSI, ITU and Japanese variants."
    ::= { usSrxServicePerfCallForwardingData 7  }

usSrxServiceSCFServAccCdDialedCounter  OBJECT-TYPE
    SYNTAX      Counter32
    MAX-ACCESS  read-only
    STATUS      current
    DESCRIPTION
        " This object refers to the total number of times the Call
          Forwarding Access Code is dialed.
          This counter is supported in ANSI, ITU and Japanese variants."
    ::= { usSrxServicePerfCallForwardingData 8  }

usSrxServiceSCFFeatActivatedCounter  OBJECT-TYPE
    SYNTAX      Counter32
    MAX-ACCESS  read-only
    STATUS      current
    DESCRIPTION
        " This object refers to the total number of times the Call
          Forwarding Feature is activated to a remote DN.
          This counter is supported in ANSI, ITU and Japanese variants."
    ::= { usSrxServicePerfCallForwardingData 9  }

usSrxServiceSCFOccurredCounter  OBJECT-TYPE
    SYNTAX      Counter32
    MAX-ACCESS  read-only
    STATUS      current
    DESCRIPTION
        " This object refers to the total number of forwardings that
          occur due to the Call Forwarding feature.
          This counter is supported in ANSI, ITU and Japanese variants."
    ::= { usSrxServicePerfCallForwardingData 10 }

usSrxServiceSCFFailedCounter  OBJECT-TYPE
    SYNTAX      Counter32
    MAX-ACCESS  read-only
    STATUS      current
    DESCRIPTION
        " This object refers to the total number of forwarding 
          attempts that fail.
          This counter is supported in ANSI, ITU and Japanese variants."
    ::= { usSrxServicePerfCallForwardingData 11 }

usSrxServiceRCFCallsOfferedCounter     OBJECT-TYPE
    SYNTAX      Counter32
    MAX-ACCESS  read-only
    STATUS      current
    DESCRIPTION
        " This object refers to the total number of times calls are
          'offered' to be forwarded to the RCF remote DN. Before
          forwarding a call to the RCF remote DN, a check is made
          to see if the customer-specified limit of simultaneous
          calls has been reached. If this limit has been reached,
          the calling party shall be given busy tone from the base
          switching office.
          This counter is supported in ANSI and Japanese variants."
    ::= { usSrxServicePerfCallForwardingData 12 }

usSrxServiceRCFCallsForwardedCounter     OBJECT-TYPE
    SYNTAX      Counter32
    MAX-ACCESS  read-only
    STATUS      current
    DESCRIPTION
        " This object refers to the total number of times calls are
          forwarded to the RCF remote DN.
          This counter is supported in ANSI and Japanese variants."
    ::= { usSrxServicePerfCallForwardingData 13 }

usSrxServiceRCFCallsOverflowCounter     OBJECT-TYPE
    SYNTAX      Counter32
    MAX-ACCESS  read-only
    STATUS      current
    DESCRIPTION
        " This object refers to the total number of times the calling
          parties are given busy tone from the base switching office
          in response to exceeding the customer-specified limit of
          simultaneous calls.
          This counter is supported in ANSI and Japanese variants."
    ::= { usSrxServicePerfCallForwardingData 14 }

usSrxServiceSCFScrnEditCounter  OBJECT-TYPE
    SYNTAX      Counter32
    MAX-ACCESS  read-only
    STATUS      current
    DESCRIPTION
        " This object refers to the total number of times the Selective
          Call Forwarding Screen Editing Service is accessed.
          This counter is supported in ANSI, ITU and Japanese variants."
    ::= { usSrxServicePerfCallForwardingData 15 }

usSrxServiceSCFCallsFwdedCounter  OBJECT-TYPE
    SYNTAX      Counter32
    MAX-ACCESS  read-only
    STATUS      current
    DESCRIPTION
        " This object refers to the total number of forwardings that
          occur due to the Selective Call Forwarding feature.
          This counter is supported in ANSI, ITU and Japanese variants."
    ::= { usSrxServicePerfCallForwardingData 16 }

usSrxServiceSCFActvRemoteDNCounter  OBJECT-TYPE
    SYNTAX      Counter32
    MAX-ACCESS  read-only
    STATUS      current
    DESCRIPTION
        " This object refers to the total number of times the
          Selective Call Forwarding feature activates the Remote DN.
          This counter is supported in ANSI, ITU and Japanese variants."
    ::= { usSrxServicePerfCallForwardingData 17 }

usSrxServiceSCFResUnavilCounter  OBJECT-TYPE
    SYNTAX      Counter32
    MAX-ACCESS  read-only
    STATUS      current
    DESCRIPTION
        " This object refers to the total number of times a
          customer could not activate SCF due to unavailable
          resources on the hiQ.
          This counter is supported in ANSI, ITU and Japanese variants."
    ::= { usSrxServicePerfCallForwardingData 18 }

usSrxServiceCFVoiceMailCounter  OBJECT-TYPE
    SYNTAX      Counter32
    MAX-ACCESS  read-only
    STATUS      current
    DESCRIPTION
        " This object refers to the total number of times a
          customer's  call is forwarded to Voice Mail.
          This counter is supported in ANSI and Japanese variants."
    ::= { usSrxServicePerfCallForwardingData 19 }

-- *****************************************************************
-- Calling Identity Delivery (CID) Traffic Measurements
-- *****************************************************************

usSrxServiceCIDDNToCalledCPECounter     OBJECT-TYPE
    SYNTAX      Counter32
    MAX-ACCESS  read-only
    STATUS      current
    DESCRIPTION
        " This object refers to the total number of times a
          calling party's directory number is delivered to a 
          subscriber with the Calling Number Delivery Service.
          This counter is supported in ANSI and Japanese variants. "
    ::= { usSrxServicePerfCallingIDData 1  }

usSrxServiceCIDAnonymousDNToCalledCPECounter   OBJECT-TYPE
    SYNTAX      Counter32
    MAX-ACCESS  read-only
    STATUS      current
    DESCRIPTION
        " This object refers to the total number of times a
          Private Number indication is delivered to a subscriber 
          with the Calling Number Delivery Service.
          This counter is supported in ANSI and Japanese variants. "
    ::= { usSrxServicePerfCallingIDData 2  }

usSrxServiceCIDUnavailDNToCalledCPECounter     OBJECT-TYPE
    SYNTAX      Counter32
    MAX-ACCESS  read-only
    STATUS      current
    DESCRIPTION
        " This object refers to the total number of times an
          out of area/unavailable indication is delivered to a 
          subscriber with the Calling Number Delivery Service.
          This counter is supported in ANSI and Japanese variants. "
    ::= { usSrxServicePerfCallingIDData 3  }

usSrxServiceCIDCNDActivateBySubscriberCounter   OBJECT-TYPE
    SYNTAX      Counter32
    MAX-ACCESS  read-only
    STATUS      current
    DESCRIPTION
        " This object refers to the total number of times the
          Calling Number Delivery (CND) feature is activated by    
          a subscriber with the Usage Sensitive version of the  
          feature. 
          This counter is supported in ANSI and Japanese variants. "
    ::= { usSrxServicePerfCallingIDData 4  }


usSrxServiceCIDCNDDeactivateBySubscriberCounter   OBJECT-TYPE
    SYNTAX      Counter32
    MAX-ACCESS  read-only
    STATUS      current
    DESCRIPTION
        " This object refers to the total number of times the
          Calling Number Delivery feature is deactivated by a
          subscriber with the Usage Sensitive version of the
          feature. 
          This counter is supported in ANSI and Japanese variants. "
    ::= { usSrxServicePerfCallingIDData 5  }

usSrxServiceCIDCallingNameToCalledCPECounter   OBJECT-TYPE
    SYNTAX      Counter32
    MAX-ACCESS  read-only
    STATUS      current
    DESCRIPTION
        " This object refers to the total number of times a
          calling party's name is delivered to a subscriber
          with the Calling Name Delivery Service. 
          This counter is supported in ANSI and Japanese variants. "
    ::= { usSrxServicePerfCallingIDData 6  }

usSrxServiceCIDAnonymousNameToCalledCPECounter     OBJECT-TYPE
    SYNTAX      Counter32
    MAX-ACCESS  read-only
    STATUS      current
    DESCRIPTION
        " This object refers to the total number of times an
          Anonymous Name indication is delivered to a subscriber
          with the Calling Name Delivery Service. 
          This counter is supported in ANSI and Japanese variants. "
    ::= { usSrxServicePerfCallingIDData 7  }

usSrxServiceCIDUnavailNameToCalledCPECounter OBJECT-TYPE
    SYNTAX      Counter32
    MAX-ACCESS  read-only
    STATUS      current
    DESCRIPTION
        " This object refers to the total number of times an
          out of area/unavailable name indication is delivered to 
          a subscriber with the Calling Name Delivery Service.
          This counter is supported in ANSI and Japanese variants. "
    ::= { usSrxServicePerfCallingIDData 8  }

usSrxServiceCIDTCAPNameQueryCounter     OBJECT-TYPE
    SYNTAX      Counter32
    MAX-ACCESS  read-only
    STATUS      current
    DESCRIPTION
        " This object refers to the total number of times a
          TCAP Name Query is sent to the SCP. 
          This counter is supported in ANSI and Japanese variants. "
    ::= { usSrxServicePerfCallingIDData 9  }

usSrxServiceCIDTCAPNameQueryTimeoutCounter OBJECT-TYPE
    SYNTAX      Counter32
    MAX-ACCESS  read-only
    STATUS      current
    DESCRIPTION
        " This object refers to the total number of timeouts that 
          occured while the SRX was waiting for the response from 
          the SCP for a Calling Name Query. 
          This counter is supported in ANSI and Japanese variants. "
    ::= { usSrxServicePerfCallingIDData 10  }

usSrxServiceCIDCNDBlockingActivateCounter OBJECT-TYPE
    SYNTAX      Counter32
    MAX-ACCESS  read-only
    STATUS      current
    DESCRIPTION
        " This object refers to the total number of times the 
          Calling Number Delivery Blocking feature was activated 
          due to subscriber dialing the Service Access Code for the 
          feature. 
          This counter is supported in ANSI and Japanese variants."
    ::= { usSrxServicePerfCallingIDData 11  }

usSrxServiceCIDCNDBlockingActMadeDNPublicCounter OBJECT-TYPE
    SYNTAX      Counter32
    MAX-ACCESS  read-only
    STATUS      current
    DESCRIPTION
        " This object refers to the total number of times the 
          Calling Number Delivery Blocking feature Activation 
          made the DN public. 
          This counter is supported in ANSI and Japanese variants."
    ::= { usSrxServicePerfCallingIDData 12  }

usSrxServiceCIDCNDBlockingActMadeDNPrivateCounter OBJECT-TYPE
    SYNTAX      Counter32
    MAX-ACCESS  read-only
    STATUS      current
    DESCRIPTION
        " This object refers to the total number of times the 
          Calling Number Delivery Blocking feature Activation 
          made the DN private. 
          This counter is supported in ANSI and Japanese variants."
    ::= { usSrxServicePerfCallingIDData 13  }

usSrxServiceCIDCallingNameDeliveryBlockingActCounter OBJECT-TYPE
    SYNTAX      Counter32
    MAX-ACCESS  read-only
    STATUS      current
    DESCRIPTION
        " This object refers to the total number of times the 
          Calling Name Delivery Blocking feature was activated 
          due to subscriber dialing the Service Access Code for  
          the feature. 
          This counter is supported in ANSI and Japanese variants. "
    ::= { usSrxServicePerfCallingIDData 14  }

usSrxServiceCIDCIDSDeliveryActCounter OBJECT-TYPE
    SYNTAX      Counter32
    MAX-ACCESS  read-only
    STATUS      current
    DESCRIPTION
        " This object refers to the total number of times the
          Calling Identity Delivery and Suppression's (CIDS)
          Delivery Feature was activated due to subscriber
          dialing the Service Access Code for the feature.
          This counter is supported in ANSI and Japanese variants. "
    ::= { usSrxServicePerfCallingIDData 15  }

usSrxServiceCIDCIDSSuppressionActCounter OBJECT-TYPE
    SYNTAX      Counter32
    MAX-ACCESS  read-only
    STATUS      current
    DESCRIPTION
        " This object refers to the total number of times the
          Calling Identity Delivery and Suppression's (CIDS)
          Suppression Feature was activated due to subscriber
          dialing the Service Access Code for the feature.
          This counter is supported in ANSI and Japanese variants. "
    ::= { usSrxServicePerfCallingIDData 16  }


-- *****************************************************************
-- Anonymous Call Rejection (ACR) Measurements
-- *****************************************************************

usSrxServiceACRActBySubscriberCounter     OBJECT-TYPE
    SYNTAX      Counter32
    MAX-ACCESS  read-only
    STATUS      current
    DESCRIPTION
        " This object refers to the total number of times the 
          ACR feature was activated due to subscriber dialing the
          Service Access Code for the feature. 
          This counter is supported in ANSI and Japanese variants. "
    ::= { usSrxServicePerfACRData 1  }


usSrxServiceACRDeactBySubscriberCounter     OBJECT-TYPE
    SYNTAX      Counter32
    MAX-ACCESS  read-only
    STATUS      current
    DESCRIPTION
        " This object refers to the total number of times the
          ACR feature was deactivated due to subscriber dialing
          the Service Access Code for the feature. 
          This counter is supported in ANSI and Japanese variants. "
    ::= { usSrxServicePerfACRData 2  }

usSrxServiceACRNotActDueToResourceUnavailCounter  OBJECT-TYPE
    SYNTAX      Counter32
    MAX-ACCESS  read-only
    STATUS      current
    DESCRIPTION
        " This object refers to the total number of times a
          customer could not activate ACR due to unavailable 
          resources on the SRX. 
          This counter is supported in ANSI and Japanese variants. "
    ::= { usSrxServicePerfACRData 3  }

usSrxServiceACRNotDeactDueToResourceUnavailCounter  OBJECT-TYPE
    SYNTAX      Counter32
    MAX-ACCESS  read-only
    STATUS      current
    DESCRIPTION
        " This object refers to the total number of times a
          customer could not deactivate ACR due to unavailable 
          resources on the SRX. 
          This counter is supported in ANSI and Japanese variants. "
    ::= { usSrxServicePerfACRData 4  }


usSrxServiceACRCallToDenialAnnounceCounter     OBJECT-TYPE
    SYNTAX      Counter32
    MAX-ACCESS  read-only
    STATUS      current
    DESCRIPTION
        " This object refers to the total number of times a
          call was routed to the ACR Denial Announcement.
          This counter is supported in ANSI and Japanese variants. "
    ::= { usSrxServicePerfACRData 5  }

usSrxServiceACRDenialAnnounceUnavailCounter  OBJECT-TYPE
    SYNTAX      Counter32
    MAX-ACCESS  read-only
    STATUS      current
    DESCRIPTION
        " This object refers to the total number of times the 
          ACR Denial Announcement facility is unavailable.
          This counter is supported in ANSI and Japanese variants. "
    ::= { usSrxServicePerfACRData 6  }

usSrxServiceACRActConfirmAnnounceUnavailCounter  OBJECT-TYPE
    SYNTAX      Counter32
    MAX-ACCESS  read-only
    STATUS      current
    DESCRIPTION
        " This object refers to the total number of times the 
          ACR Activation Confirmation Announcement facility is 
          unavailable. 
          This counter is supported in ANSI and Japanese variants. "
    ::= { usSrxServicePerfACRData 7  }

usSrxServiceACRDeactConfirmAnnounceUnavailCounter  OBJECT-TYPE
    SYNTAX      Counter32
    MAX-ACCESS  read-only
    STATUS      current
    DESCRIPTION
        " This object refers to the total number of times the 
          ACR Deactivation Confirmation Announcement facility is 
          unavailable. 
          This counter is supported in ANSI and Japanese variants. "
    ::= { usSrxServicePerfACRData 8  }

usSrxServiceEACRNotActDueToResUnavailCounter  OBJECT-TYPE
    SYNTAX      Counter32
    MAX-ACCESS  read-only
    STATUS      current
    DESCRIPTION
        " This object refers to the total number of times Enhanced
          Anonymous Call Rejection (EACR) is not activated due to 
          unavailability of resources.
          This counter is supported in ANSI and Japanese variants. "
    ::= { usSrxServicePerfACRData 9  }

usSrxServiceEACRNotDeactDueToResUnavailCounter  OBJECT-TYPE
    SYNTAX      Counter32
    MAX-ACCESS  read-only
    STATUS      current
    DESCRIPTION
        " This object refers to the total number of times Enhanced
          Anonymous Call Rejection (EACR) is not deactivated because 
          of unavailability of resources.
          This counter is supported in ANSI and Japanese variants. "
    ::= { usSrxServicePerfACRData 10  }

usSrxServiceEACRActConfirmAnnounceUnavailCounter  OBJECT-TYPE
    SYNTAX      Counter32
    MAX-ACCESS  read-only
    STATUS      current
    DESCRIPTION
        " This object refers to the total number of times the
          EACR Activation Confirmation Announcement facility is
          unavailable.
          This counter is supported in ANSI and Japanese variants. "
    ::= { usSrxServicePerfACRData 11  }

usSrxServiceEACRDeactConfirmAnnounceUnavailCounter  OBJECT-TYPE
    SYNTAX      Counter32
    MAX-ACCESS  read-only
    STATUS      current
    DESCRIPTION
        " This object refers to the total number of times the
          EACR Deactivation Confirmation Announcement facility is
          unavailable.
          This counter is supported in ANSI and Japanese variants. "
    ::= { usSrxServicePerfACRData 12  }

usSrxServiceEACRActBySubscriberCounter     OBJECT-TYPE
    SYNTAX      Counter32
    MAX-ACCESS  read-only
    STATUS      current
    DESCRIPTION
        " This object refers to the total number of times the
          EACR feature was activated due to subscriber dialing the
          Service Access Code for the feature.
          This counter is supported in ANSI and Japanese variants. "
    ::= { usSrxServicePerfACRData 13 }


usSrxServiceEACRDeactBySubscriberCounter     OBJECT-TYPE
    SYNTAX      Counter32
    MAX-ACCESS  read-only
    STATUS      current
    DESCRIPTION
        " This object refers to the total number of times the
          EACR feature was deactivated due to subscriber dialing
          the Service Access Code for the feature.
          This counter is supported in ANSI and Japanese variants. "
    ::= { usSrxServicePerfACRData 14  }


-- *****************************************************************
-- Speed Calling (SC) Measurements
-- *****************************************************************

usSrxServiceSCOneDigitCounter  OBJECT-TYPE
    SYNTAX      Counter32
    MAX-ACCESS  read-only
    STATUS      current
    DESCRIPTION
        " This object refers to the total number of times that 
          customers place calls to a repertory of frequently called 
          numbers by dialing a 1-digit speed calling code.
          Eight numbers(2 through 9) can be placed in the list for 
          POTS customers and six numbers (2 through 7) for Basic 
          Business Group (BBG) customers.
          This counter is supported in ANSI and Japanese variants. "
    ::= { usSrxServicePerfSpeedCallingData 1  }

usSrxServiceSCTwoDigitCounter   OBJECT-TYPE
    SYNTAX      Counter32
    MAX-ACCESS  read-only
    STATUS      current
    DESCRIPTION
        " This object refers to the total number of times that  
          customers place calls to a repertory of 30 frequently
          called numbers by dialing the 2-digit speed calling code 
          (20 through 49).
          This counter is supported in ANSI and Japanese variants. "
    ::= { usSrxServicePerfSpeedCallingData 2  }

usSrxServiceSCCCSCSuccessCounter  OBJECT-TYPE
    SYNTAX      Counter32
    MAX-ACCESS  read-only
    STATUS      current
    DESCRIPTION
        " This object refers to the total number of times that
          Customer-Changeable Speed Calling (CCSC) customers successfully 
          dial a change speed calling list access code and a new telephone
          number to assign their own speed calling codes directly and
          immediately from their own telephone. 
          The CCSC feature is available for 1-digit and/or 2-digit speed
          calling list owners.
          This counter is supported in ANSI and Japanese variants. "
    ::= { usSrxServicePerfSpeedCallingData 3  }

-- *****************************************************************
-- Screen List Editing (SLE) Traffic Measurements
-- *****************************************************************

usSrxServiceInvokingSLEAttemptsCounter  OBJECT-TYPE
    SYNTAX Counter32
    MAX-ACCESS  read-only
    STATUS      current
    DESCRIPTION
        " This object specifies the peg counts of attempts to invoke
          Screen List Editing as a result of dialing the access code. 
          The Service is responsible in incrementing this count.
          This counter is supported in ANSI and Japanese variants. "
    ::= { usSrxServicePerfScrnListEditData 1 }

usSrxServiceInvokingSLESuccessfulCounter  OBJECT-TYPE
    SYNTAX Counter32
    MAX-ACCESS  read-only
    STATUS      current
    DESCRIPTION
        " This object provides usage counts of successful innvocations
          of Screen List Editing as a result of dialing the access code. 
          The Service is responsible in incrementing this count.
          This counter is supported in ANSI and Japanese variants. "
    ::= { usSrxServicePerfScrnListEditData 2 }

usSrxServiceDeniedSLECounter  OBJECT-TYPE
    SYNTAX Counter32
    MAX-ACCESS  read-only
    STATUS      current
    DESCRIPTION
        " This object provides overflow counts of the number of
          customers denied access to Screen List Editing as a 
          result of unavailable resources. The Service is responsible 
          in incrementing this count.
          This counter is supported in ANSI and Japanese variants. "
    ::= { usSrxServicePerfScrnListEditData 3 }

-- *****************************************************************
-- Selective Call Acceptance (SCA) Traffic Measurements
-- *****************************************************************
usSrxServiceSCANotActDueToResUnavailCounter       OBJECT-TYPE
    SYNTAX      Counter32
    MAX-ACCESS  not-accessible
    STATUS      obsolete
    DESCRIPTION
        " This object is depricated from US 6.1 release.
          This object refers to the total number of times Selective
          Call Acceptance (SCA) is not activated due to unavailability
          of resources.
          This counter is supported in ANSI and Japanese variants."
    ::= { usSrxServicePerfSelCallAcceptData 1 }


usSrxServiceSCANotDeactDueToResUnavailCounter     OBJECT-TYPE
    SYNTAX      Counter32
    MAX-ACCESS  not-accessible 
    STATUS      obsolete 
    DESCRIPTION
        " This object is depricated from US 6.1 release.
          This object refers to the total number of times Selective
          Call Acceptance (SCA) is not deactivated because of
          unavailability of resources.
          This counter is supported in ANSI and Japanese variants."
    ::= { usSrxServicePerfSelCallAcceptData 2 }

usSrxServiceSCAAttemptedCounter     OBJECT-TYPE
    SYNTAX      Counter32
    MAX-ACCESS  not-accessible 
    STATUS      obsolete 
    DESCRIPTION
        " This object is depricated from US 6.1 release.
          This object refers to the total number of times the
          Stored Program Control Switch (SPCS) and/or any circuits
          are used to provide Selective Call Acceptance (SCA).
          This counter is supported in ANSI and Japanese variants."
    ::= { usSrxServicePerfSelCallAcceptData 3 }


usSrxServiceSCAAccessCodeAttemptedCounter     OBJECT-TYPE
    SYNTAX      Counter32
    MAX-ACCESS  read-only
    STATUS      current
    DESCRIPTION
        " This object refers to the total number of hourly peg counts
          and usage counts with a usage-scan rate of 1 per 10 seconds
          for SCA screening list editing and for attempts to invoke 
          control procedures as a result of dialing an SCA service 
          access code. These counts should be available 
          per hour on an individual SPCS basis. 
          This counter is supported in ANSI and Japanese variants."
    ::= { usSrxServicePerfSelCallAcceptData 4 }

usSrxServiceSCAUnacceptedCallsCounter     OBJECT-TYPE
    SYNTAX      Counter32
    MAX-ACCESS  read-only
    STATUS      current
    DESCRIPTION
        " This object refers to the total number of hourly 
          peg counts of unaccepted calls. 
          These counts should be available per hour on an
          individual SPCS basis.
          This counter is supported in ANSI and Japanese variants."
    ::= { usSrxServicePerfSelCallAcceptData 5 }

usSrxServiceSCAValidationCounter     OBJECT-TYPE
    SYNTAX      Counter32
    MAX-ACCESS  read-only
    STATUS      current
    DESCRIPTION
        " This object refers to the total number of hourly peg 
          counts of all calls checked against the screening list 
          of a customer with SCA active.
          These counts should be available per hour on an individual
          SPCS basis.
          This counter is supported in ANSI and Japanese variants."
    ::= { usSrxServicePerfSelCallAcceptData 6 }

usSrxServiceSCAPinValidatedCounter     OBJECT-TYPE
    SYNTAX      Counter32
    MAX-ACCESS  read-only
    STATUS      current
    DESCRIPTION
        " This object refers to the total number of calls on which
          a caller successfully entered a PIN.
          These counts should be available hourly on a per-SPCS and  
          a per-line basis.
          This counter is supported in ANSI and Japanese variants."
    ::= { usSrxServicePerfSelCallAcceptData 7 }

usSrxServiceSCAPinFailedCounter        OBJECT-TYPE
    SYNTAX      Counter32
    MAX-ACCESS  read-only
    STATUS      current
    DESCRIPTION
        " This object refers to the total number of calls on which
          a caller unsuccessfully attempted PIN entry.
          These counts should be available hourly on a per-SPCS and  
          a per-line basis.
          This counter is supported in ANSI and Japanese variants."
    ::= { usSrxServicePerfSelCallAcceptData 8 }


usSrxServiceSCACusDeniedResUnavailCounter       OBJECT-TYPE
    SYNTAX      Counter32
    MAX-ACCESS  read-only
    STATUS      current
    DESCRIPTION
        " This object refers to the total number of overflow counts
          for the number of customers denied access to SCA because of
          unavailable Stored Program Control Switch (SPCS) resources.
          These counts should be available on an individual SPCS basis.
          This counter is supported in ANSI and Japanese variants."
    ::= { usSrxServicePerfSelCallAcceptData 9 }


usSrxServiceSCATrtDeniedResUnavailCounter     OBJECT-TYPE
    SYNTAX      Counter32
    MAX-ACCESS  read-only
    STATUS      current
    DESCRIPTION
        " This object refers to the total number of overflow counts
          for the number of unaccepted calls.
          These counts should be available on an individual SPCS basis.
          This counter is supported in ANSI and Japanese variants."
    ::= { usSrxServicePerfSelCallAcceptData 10 }

usSrxServiceSCAAttpDeniedResUnavailCounter     OBJECT-TYPE
    SYNTAX      Counter32
    MAX-ACCESS  read-only
    STATUS      current
    DESCRIPTION
        " This object refers to the total number of overflow counts
          for the SPCS and/or any circuits used to provide SCA control
          procedures.
          These counts should be available on an individual SPCS basis.
          This counter is supported in ANSI and Japanese variants."
    ::= { usSrxServicePerfSelCallAcceptData 11 }


-- *****************************************************************
-- Selective Call Rejection (SCR) Traffic Measurements
-- *****************************************************************

usSrxServiceSCRAttemptCounter      OBJECT-TYPE
    SYNTAX      Counter32
    MAX-ACCESS  read-only
    STATUS      current
    DESCRIPTION
        " This object refers to the hourly peg counts and usage counts
          with a usage scan rate of 1 per 10 seconds for Selective Call
          Rejection (SCR) screen editing and for attempts to invoke
          control procedures as a result of dialing the SCR service 
          success code.
          This counter is supported in ANSI and Japanese variants."
    ::= { usSrxServicePerfSelCallRejectData 1 }

usSrxServiceSCRCallToDenialAnncCounter      OBJECT-TYPE
    SYNTAX      Counter32
    MAX-ACCESS  read-only
    STATUS      current
    DESCRIPTION
        " This object refers to the hourly peg counts of rejected
          calls.
          This counter is supported in ANSI and Japanese variants."
    ::= { usSrxServicePerfSelCallRejectData 2 }

usSrxServiceSCRAllCallsScreenedCounter      OBJECT-TYPE
    SYNTAX      Counter32
    MAX-ACCESS  read-only
    STATUS      current
    DESCRIPTION
        " This object refers to the hourly peg counts of all calls
          screened for a customer with Selective Call Rejection (SCR)
          active.
          This counter is supported in ANSI and Japanese variants."
    ::= { usSrxServicePerfSelCallRejectData 3 }

usSrxServiceSCRCusDeniedResUnaCounter      OBJECT-TYPE
    SYNTAX      Counter32
    MAX-ACCESS  read-only
    STATUS      current
    DESCRIPTION
        " This object refers to the overflow counts for the number
          of customers denied access to Selective Call Rejection (SCR)
          because of unavailable system resources.
          This counter is supported in ANSI and Japanese variants."
    ::= { usSrxServicePerfSelCallRejectData 4 }

usSrxServiceSCRDeniedAnncUnaCounter     OBJECT-TYPE
    SYNTAX      Counter32
    MAX-ACCESS  read-only
    STATUS      current
    DESCRIPTION
        " This object refers to the overflow counts for the number
          of rejected calls because of denied access to Selective 
          Call Rejection (SCR).
          This counter is supported in ANSI and Japanese variants."
    ::= { usSrxServicePerfSelCallRejectData 5 }

usSrxServiceSCRAccDeniedResUnaCounter   OBJECT-TYPE
    SYNTAX      Counter32
    MAX-ACCESS  read-only
    STATUS      current
    DESCRIPTION
        " This object refers to the overflow counts for the system
          and/or any circuits used to provide Selective Call
          Rejection (SCR) control procedures.
          This counter is supported in ANSI and Japanese variants."
    ::= { usSrxServicePerfSelCallRejectData 6 }

-- *****************************************************************
-- Malicious Call Trace (MCT) Traffic Measurements
-- *****************************************************************

usSrxServiceMCTStatAccessesCounter OBJECT-TYPE
    SYNTAX      Counter32
    MAX-ACCESS  read-only
    STATUS      current
    DESCRIPTION
        " This object refers to the number of times the subscriber 
          accesses the service by dialing the service access code.
          This counter is supported in ANSI, Japanese and ITU variants."
    ::= { usSrxServicePerfMalCallTraceData 1 }

usSrxServiceMCTStatActivCounter    OBJECT-TYPE
    SYNTAX      Counter32
    MAX-ACCESS  read-only
    STATUS      current
    DESCRIPTION
        " This object refers to the number of times a call trace is
          attempted after a subscriber accesses the service.
          This counter is supported in ANSI, Japanese and ITU variants."
    ::= { usSrxServicePerfMalCallTraceData 2 }

usSrxServiceMCTStatRecsSentCounter OBJECT-TYPE
    SYNTAX      Counter32
    MAX-ACCESS  read-only
    STATUS      current
    DESCRIPTION
        " This object refers to the number of call trace records 
          successfully written to file.
          This counter is supported in ANSI, Japanese and ITU variants."
    ::= { usSrxServicePerfMalCallTraceData 3 }

usSrxServiceMCTStatConfirmsCounter OBJECT-TYPE
    SYNTAX      Counter32
    MAX-ACCESS  read-only
    STATUS      current
    DESCRIPTION
        " This object refers to the number of successful activations
          completed.
          This counter is supported in ANSI, Japanese and ITU variants."
    ::= { usSrxServicePerfMalCallTraceData 4 }

usSrxServiceMCTStatOpFailCounter OBJECT-TYPE
    SYNTAX      Counter32
    MAX-ACCESS  read-only
    STATUS      current
    DESCRIPTION
        " This object refers to the number of times that the service
          cannot be successfully completed after subscriber access.
          This counter is supported in ANSI, Japanese and ITU variants."
    ::= { usSrxServicePerfMalCallTraceData 5 }

usSrxServiceMCTStatInvalDnCounter OBJECT-TYPE
    SYNTAX      Counter32
    MAX-ACCESS  read-only
    STATUS      current
    DESCRIPTION
        " This object refers to the number of times the subscriber
          accesses the service, but the service cannot proceed due
          to an invalid or missing calling DN in the subscriber's
          incoming memory slot (ie, the calling party number of the
          last received call is invalid or unavailable).
          This counter is supported in ANSI, Japanese and ITU variants."
    ::= { usSrxServicePerfMalCallTraceData 6 }

usSrxServiceMCTStatNoAuth OBJECT-TYPE
    SYNTAX      Counter32
    MAX-ACCESS  read-only
    STATUS      current
    DESCRIPTION
        " This object refers to the number of times the subscribers
          attempt to use Malicious Call Trace, but are denied access.
          This counter is supported in ANSI, Japanese and ITU variants."
    ::= { usSrxServicePerfMalCallTraceData 7 }

usSrxServiceMCTStatAbort OBJECT-TYPE
    SYNTAX      Counter32
    MAX-ACCESS  read-only
    STATUS      current
    DESCRIPTION
        " This object refers to the number of times that the subscriber
          dialed the MCT access code, but did not proceed with the 
          activation.
          This counter is supported in ANSI,Japanese and ITU variants."
    ::= { usSrxServicePerfMalCallTraceData 8 }

usSrxServiceMCTStatAfterCallCounter OBJECT-TYPE
    SYNTAX      Counter32
    MAX-ACCESS  read-only
    STATUS      current
    DESCRIPTION
        "This object refers to the number of call trace records 
         successfully written to file when malicious call trace 
         method 'after a call' is activated.
         This counter applies to both ANSI and ITU."
    ::= { usSrxServicePerfMalCallTraceData 9 }             

usSrxServiceMCTStatDuringCallCounter OBJECT-TYPE
    SYNTAX      Counter32
    MAX-ACCESS  read-only
    STATUS      current
    DESCRIPTION
        "This object refers to the number of call trace records 
         successfully written to file when malicious call trace 
         method 'during a call' is activated.
         This counter applies to both ANSI and ITU."
    ::= { usSrxServicePerfMalCallTraceData 10 }             


usSrxServiceMCTStatOnNoReplyCounter OBJECT-TYPE
    SYNTAX      Counter32
    MAX-ACCESS  read-only
    STATUS      current
    DESCRIPTION
        "This object refers to the number of call trace records 
         successfully written to file when malicious call trace 
         method 'Not-Answered calls' is activated.
         This counter applies to both ANSI and ITU."
    ::= { usSrxServicePerfMalCallTraceData 11 }             


usSrxServiceMCTStatOnAnswerCounter OBJECT-TYPE
    SYNTAX      Counter32
    MAX-ACCESS  read-only
    STATUS      current
    DESCRIPTION
        "This object refers to the number of call trace records 
         successfully written to file when malicious call trace 
         method 'Upon an answer' is activated.
         This counter applies to both ANSI and ITU."
    ::= { usSrxServicePerfMalCallTraceData 12 }             


usSrxServiceMCTStatOnAlertingCounter OBJECT-TYPE
    SYNTAX      Counter32
    MAX-ACCESS  read-only
    STATUS      current
    DESCRIPTION
        "This object refers to the number of call trace records 
         successfully written to file when malicious call trace 
         method 'Upon alerting' is activated.
         This counter applies to both ANSI and ITU."
    ::= { usSrxServicePerfMalCallTraceData 13 }   


-- *****************************************************************
-- Three Way Calling (TWC) Traffic Measurements
-- *****************************************************************

usSrxServiceTWCAttemptedCounter  OBJECT-TYPE
    SYNTAX      Counter32
    MAX-ACCESS  read-only
    STATUS      current
    DESCRIPTION
        " This object refers to the number of times TWC service
          customers attempt to add on a thid party. The count indicates
          the customer involved in a stable talking connection has
          flashed and dialed a complete set of digits that are valid
          for calling.
          This counter is supported in ANSI and Japanese variants."
    ::= { usSrxServicePerfThreeWayCallData 1 }

usSrxServiceTWCFormedCounter  OBJECT-TYPE
    SYNTAX      Counter32
    MAX-ACCESS  read-only
    STATUS      current
    DESCRIPTION
        " This object refers to the number of times successful Three 
          Way Calling is formed by a customer with TWC service.
          This counter is supported in ANSI and Japanese variants."
    ::= { usSrxServicePerfThreeWayCallData 2 }

-- *****************************************************************
-- Intercom Call (ICD) Traffic Measurements
-- *****************************************************************

usSrxServiceICDIncommingAttemptedCounter  OBJECT-TYPE
    SYNTAX      Counter32
    MAX-ACCESS  read-only
    STATUS      current
    DESCRIPTION
        " This object refers to the number of times ICD service 
          customers attempt to connect an incomming intercom call.
          This counter is supported in ANSI and Japanese variants."
    ::= { usSrxServicePerfIntercomCallData 1 }

usSrxServiceICDIncommingCompletedCounter  OBJECT-TYPE
    SYNTAX      Counter32
    MAX-ACCESS  read-only
    STATUS      current
    DESCRIPTION
        " This object refers to the number of successful times an 
          incomming Intercom Call is formed by a customer with ICD 
          service.
          This counter is supported in ANSI and Japanese variants."
    ::= { usSrxServicePerfIntercomCallData 2 }

usSrxServiceICDOutgoingAttemptedCounter  OBJECT-TYPE
    SYNTAX      Counter32
    MAX-ACCESS  read-only
    STATUS      current
    DESCRIPTION
        " This object refers to the number of times ICD service 
          customers attempt to connect an outgoing intercom call.
          This counter is supported in ANSI and Japanese variants."
    ::= { usSrxServicePerfIntercomCallData 3 }

usSrxServiceICDOutgoingCompletedCounter  OBJECT-TYPE
    SYNTAX      Counter32
    MAX-ACCESS  read-only
    STATUS      current
    DESCRIPTION
        " This object refers to the number of successful times an
          outgoing Intercom Call is formed by a customer with ICD 
          service.
          This counter is supported in ANSI and Japanese variants."
    ::= { usSrxServicePerfIntercomCallData 4 }

-- *****************************************************************
-- Voice Mail (VM) Traffic Measurements
-- *****************************************************************

usSrxServiceVMMWIOperCounter OBJECT-TYPE
    SYNTAX      Counter32
    MAX-ACCESS  read-only
    STATUS      current
    DESCRIPTION
        " This object refers to the number of times Voice Mail service
          customers trigger Message Waiting Indication.
          This counter is supported in ANSI and Japanese variants."
    ::= { usSrxServicePerfVoiceMailData 1 }

usSrxServiceVMMWIRemCounter OBJECT-TYPE
    SYNTAX      Counter32
    MAX-ACCESS  read-only
    STATUS      current
    DESCRIPTION
        " This object refers to the number of times Voice Mail service
          customers trigger the removal of Message Waiting Indication.
          This counter is supported in ANSI and Japanese variants."
    ::= { usSrxServicePerfVoiceMailData 2 }

usSrxServiceVMMWIQuerySentSuccessCounter OBJECT-TYPE
    SYNTAX      Counter32
    MAX-ACCESS  read-only
    STATUS      current
    DESCRIPTION
        " This object refers to the number of times TCAP Message
          Waiting Indicater queries are successfully sent.
          This counter is supported in ANSI and Japanese variants."
    ::= { usSrxServicePerfVoiceMailData 3 }

usSrxServiceVMMWIQuerySentUnsuccessCounter OBJECT-TYPE
    SYNTAX      Counter32
    MAX-ACCESS  read-only
    STATUS      current
    DESCRIPTION
        " This object refers to the number of times TCAP Message
          Waiting Indicater queries are unsuccessfully sent.
          This counter is supported in ANSI and Japanese variants."
    ::= { usSrxServicePerfVoiceMailData 4 }

usSrxServiceVMMWIQueryReceivedSuccessCounter OBJECT-TYPE
    SYNTAX      Counter32
    MAX-ACCESS  read-only
    STATUS      current
    DESCRIPTION
        " This object refers to the number of times TCAP Message
          Waiting Indicater queries are successfully received.
          This counter is supported in ANSI and Japanese variants."
    ::= { usSrxServicePerfVoiceMailData 5 }

usSrxServiceVMMWIQueryReceivedUnsuccessCounter OBJECT-TYPE
    SYNTAX      Counter32
    MAX-ACCESS  read-only
    STATUS      current
    DESCRIPTION
        " This object refers to the number of times TCAP Message
          Waiting Indicater queries are unsuccessfully received.
          This counter is supported in ANSI and Japanese variants."
    ::= { usSrxServicePerfVoiceMailData 6 }

usSrxServiceVMMWIQueryFailureCounter OBJECT-TYPE
    SYNTAX      Counter32
    MAX-ACCESS  read-only
    STATUS      current
    DESCRIPTION
        " This object refers to the number of times TCAP Message
          Waiting Indicater queries fail.
          This counter is supported in ANSI and Japanese variants."
    ::= { usSrxServicePerfVoiceMailData 7 }

usSrxServiceVMMWIInvRecNumOper OBJECT-TYPE
    SYNTAX      Counter32
    MAX-ACCESS  read-only
    STATUS      current
    DESCRIPTION
        " This object refers to the number of times 
        the E164 number provided to identify the receiving user 
        is not a valid number (Operate). This counter is supported in ITU."
    ::= { usSrxServicePerfVoiceMailData 8 }     

    
usSrxServiceVMMWIInvRecNumRem OBJECT-TYPE
    SYNTAX      Counter32
    MAX-ACCESS  read-only
    STATUS      current
    DESCRIPTION
        " This object refers to the number of times 
        the E164 number provided to identify the receiving user 
        is not a valid number (Remove). This counter is supported in ITU ."
    ::= { usSrxServicePerfVoiceMailData 9 }   


usSrxServiceVMMWIResUnavOper OBJECT-TYPE
    SYNTAX      Counter32
    MAX-ACCESS  read-only
    STATUS      current
    DESCRIPTION
        " This object refers to the number of times the resources required 
        to perform adequately the MWI supplementary service are not available 
        (Operate). This counter is supported in ITU ."
    ::= { usSrxServicePerfVoiceMailData 10 }     

usSrxServiceVMMWIResUnavRem OBJECT-TYPE
    SYNTAX      Counter32
    MAX-ACCESS  read-only
    STATUS      current
    DESCRIPTION
        " This object refers to the number of times the resources required 
        to perform adequately the MWI supplementary service are not available 
        (Remove). This counter is supported in ITU ."
    ::= { usSrxServicePerfVoiceMailData 11 }     

usSrxServiceVMMWIInvUsrNumOper OBJECT-TYPE
    SYNTAX      Counter32
    MAX-ACCESS  read-only
    STATUS      current
    DESCRIPTION
        " This object refers to the number of times the received E164 number 
          identifying the controlling user is a non authorized number 
          (in case of registration subscription option applies) or an invalid 
          number (Operate). This counter is supported in ITU ."
    ::= { usSrxServicePerfVoiceMailData 12 }     
    
usSrxServiceVMMWIInvUsrNumberRem OBJECT-TYPE
    SYNTAX      Counter32
    MAX-ACCESS  read-only
    STATUS      current
    DESCRIPTION
        " This object refers to the number of times the received E164 number 
          identifying the controlling user is a non authorized number (in case 
          of registration subscription option applies) or an invalid number 
          (Remove). This counter is supported in ITU ."
    ::= { usSrxServicePerfVoiceMailData 13 }
         
usSrxServiceVMMWIRecUsrNotSubOper OBJECT-TYPE
    SYNTAX      Counter32
    MAX-ACCESS  read-only
    STATUS      current
    DESCRIPTION
        " This object refers to the number of times the MWI supplementary 
          service has not been subscribed to by the receiving user (Operate). 
          This counter is supported in ITU ."
    ::= { usSrxServicePerfVoiceMailData 14 }     
    
usSrxServiceVMMWIRecUsrNotSubRem OBJECT-TYPE
    SYNTAX      Counter32
    MAX-ACCESS  read-only
    STATUS      current
    DESCRIPTION
        " This object refers to the number of times the MWI supplementary 
          service has not been subscribed to by the receiving user (Remove). 
          This counter is supported in ITU ."
    ::= { usSrxServicePerfVoiceMailData 15 }     

usSrxServiceVMMWIIndNotDelOper OBJECT-TYPE
    SYNTAX      Counter32
    MAX-ACCESS  read-only
    STATUS      current
    DESCRIPTION
        " This object refers to the number of times indication is not 
          delivered by the access signaling system (Operate). This counter 
          is supported in ITU ." 
    ::= { usSrxServicePerfVoiceMailData 16 }     

usSrxServiceVMMWIIndNotDelRem OBJECT-TYPE
    SYNTAX      Counter32
    MAX-ACCESS  read-only
    STATUS      current
    DESCRIPTION
        " This object refers to the number of times indication is not 
          delivered by the access signaling system (Remove). This counter 
          is supported in ITU ." 
    ::= { usSrxServicePerfVoiceMailData 17 }     

usSrxServiceVMMWIMaxNumUsrRch OBJECT-TYPE
    SYNTAX      Counter32
    MAX-ACCESS  read-only
    STATUS      current
    DESCRIPTION
        " This object refers to the number of times the receiving user's 
          network cannot handle any further controlling users. This counter 
          is supported in ITU ." 
    ::= { usSrxServicePerfVoiceMailData 18}     

usSrxServiceVMMWIMaxNumInstRch OBJECT-TYPE
    SYNTAX      Counter32
    MAX-ACCESS  read-only
    STATUS      current
    DESCRIPTION
        " this error value shall be used when the maximum number of activations 
          for the receiving user has been reached and a further activation has 
          been requested. This counter is supported in ITU ."
    ::= { usSrxServicePerfVoiceMailData 19}   
    
usSrxServiceVMMWISSIIntOper OBJECT-TYPE
    SYNTAX      Counter32
    MAX-ACCESS  read-only
    STATUS      current
    DESCRIPTION
        "This object refers to the number of times an error response indicating 
         'supplementary services interaction' is received by the far end switch, 
         in responce to a  MWI Set operation, send by the hiQ8000. This counter 
         is supported only in ITU."
    ::= { usSrxServicePerfVoiceMailData 20}    
     
usSrxServiceVMMWISSIIntRem OBJECT-TYPE
    SYNTAX      Counter32
    MAX-ACCESS  read-only
    STATUS      current
    DESCRIPTION
        "This object refers to the number of times an error response 
        indicating 'supplementary services interaction' is received by 
        the far end switch, in response to a  MWI Reset operation, send 
        by the hiQ8000. This counter is supported only in ITU."
    ::= { usSrxServicePerfVoiceMailData 21} 
        
usSrxServiceVMMWIRecUsrNoSubOperSnd OBJECT-TYPE
    SYNTAX      Counter32
    MAX-ACCESS  read-only
    STATUS      current
    DESCRIPTION
        "This object refers to the number of times an error response 
        indicating that the Receiving user is not subscribed, is send 
        by the switch in response to a received MWI Set operation. 
        This counter is supported only in ITU"
    ::= { usSrxServicePerfVoiceMailData 22}   
      
usSrxServiceVMMWIRecUsrNoSubRemSnd OBJECT-TYPE
    SYNTAX      Counter32
    MAX-ACCESS  read-only
    STATUS      current
    DESCRIPTION
        "This object refers to the number of times an error responce 
        indicating that the Receiving user is not subscribed, is send 
        by the switch in response to a received MWI Reset operation. 
        This counter is supported only in ITU."
    ::= { usSrxServicePerfVoiceMailData 23}    
     
usSrxServiceVMMWIIndNoDelOpeSnd OBJECT-TYPE
    SYNTAX      Counter32
    MAX-ACCESS  read-only
    STATUS      current
    DESCRIPTION
        "This object refers to the number of times an error response indicating 
        that  Indication is Not Delivered, is send by the switch in response to 
        a received MWI Set operation. This counter is supported only in ITU."
    ::= { usSrxServicePerfVoiceMailData 24}   
      
usSrxServiceVMMWIIndNoDelRemSnd OBJECT-TYPE
    SYNTAX      Counter32
    MAX-ACCESS  read-only
    STATUS      current
    DESCRIPTION
        "This object refers to the number of times an error response indicating 
        that  Indication is Not Delivered, is send by the switch in response to a 
        received MWI Reset operation. This counter is supported only in ITU."
    ::= { usSrxServicePerfVoiceMailData 25}         

    
-- *****************************************************************
-- ** Do Not Disturb Service Counters START
-- *****************************************************************

usSrxServiceDNDSucActivCntr     OBJECT-TYPE
    SYNTAX      Counter32
    MAX-ACCESS  read-only
    STATUS      current
    DESCRIPTION
        " This object refers to the total number of successful activations 
          of the DND service. This counter is supported both in ITU and ANSI."
    ::= { usSrxServiceDNDData 1  }

usSrxServiceDNDUnSucActivCntr     OBJECT-TYPE
    SYNTAX      Counter32
    MAX-ACCESS  read-only
    STATUS      current
    DESCRIPTION
        " This object refers to the total number of unsuccessful activations 
          of the DND service. This counter is supported both in ITU and ANSI."
    ::= { usSrxServiceDNDData 2  }

usSrxServiceDNDSucDeActivCntr     OBJECT-TYPE
    SYNTAX      Counter32
    MAX-ACCESS  read-only
    STATUS      current
    DESCRIPTION
        " This object refers to the total number of successful deactivations 
          of the DND service. This counter is supported both in ITU and ANSI."
    ::= { usSrxServiceDNDData 3  }

usSrxServiceDNDUnSucDeActivCntr     OBJECT-TYPE
    SYNTAX      Counter32
    MAX-ACCESS  read-only
    STATUS      current
    DESCRIPTION
        " This object refers to the total number of unsuccessful deactivations 
          of the DND service. This counter is supported both in ITU and ANSI."
    ::= { usSrxServiceDNDData 4  }


-- *****************************************************************
-- ** Number of Active CSTA Monitors
-- *****************************************************************

usSrxServiceActCSTAMonitoredAll     OBJECT-TYPE
    SYNTAX      Counter32
    MAX-ACCESS  read-only
    STATUS      current
    DESCRIPTION
        " This object refers to the total number active CSTA monitor for 
	  All CSTA applications.."
    ::= { usSrxServiceActCSTAMonitorData 1  }


usSrxServiceActCSTAMonitoredSiemens     OBJECT-TYPE
    SYNTAX      Counter32
    MAX-ACCESS  read-only
    STATUS      current
    DESCRIPTION
        " This object refers to the total number active CSTA monitors 
	  for application type = OpenScape "
    ::= { usSrxServiceActCSTAMonitorData 2  }


usSrxServiceActCSTAMonitoredOther     OBJECT-TYPE
    SYNTAX      Counter32
    MAX-ACCESS  read-only
    STATUS      current
    DESCRIPTION
        " This object refers to the total number active CSTA monitors 
	  for application type = 3rd Party"
    ::= { usSrxServiceActCSTAMonitorData 3  }


usSrxServiceActCSTAMonitoredTelefonica     OBJECT-TYPE
    SYNTAX      Counter32
    MAX-ACCESS  read-only
    STATUS      current
    DESCRIPTION
        " This object refers to the total number active CSTA monitors 
	  for application type = Telefonica."
    ::= { usSrxServiceActCSTAMonitorData 4  }

-- *****************************************************************
-- ** Number of Active CSTA Route Registrations
-- *****************************************************************


usSrxServiceActCSTARoutingAll     OBJECT-TYPE
    SYNTAX      Counter32
    MAX-ACCESS  read-only
    STATUS      current
    DESCRIPTION
        " This object refers to the total number active CSTA Route Registration for
	  All CSTA applications."
    ::= { usSrxServiceActCSTARouteRegData 1  }


usSrxServiceActCSTARoutingSiemens     OBJECT-TYPE
    SYNTAX      Counter32
    MAX-ACCESS  read-only
    STATUS      current
    DESCRIPTION
        " This object refers to the total number active CSTA monitors 
	  for application type = OpenScape "
    ::= { usSrxServiceActCSTARouteRegData 2  }


usSrxServiceActCSTARoutingOther     OBJECT-TYPE
    SYNTAX      Counter32
    MAX-ACCESS  read-only
    STATUS      current
    DESCRIPTION
        " This object refers to the total number active CSTA monitors 
	  for application type = 3rd Party "
    ::= { usSrxServiceActCSTARouteRegData 3  }


usSrxServiceActCSTARoutingTelefonica     OBJECT-TYPE
    SYNTAX      Counter32
    MAX-ACCESS  read-only
    STATUS      current
    DESCRIPTION
        " This object refers to the total number active CSTA monitors 
	  for application type = Telefonica "
    ::= { usSrxServiceActCSTARouteRegData 4  }

-- **************************************************************************
-- ** Number of Active CSTA Monitored Devices with Application type All Table
-- **************************************************************************

usSrxServiceActCSTAMonDataTableAll     OBJECT-TYPE
    SYNTAX SEQUENCE OF UsSrxServiceActCSTAMonDataTableAllEntry
    MAX-ACCESS  not-accessible
    STATUS      current
    DESCRIPTION
        "The Active CSTA Monitored Devices Table.
         A table containing an array of devices that currently have an 
	 active CSTA Monitor by CSTA Application type All"
    ::= { usSrxServiceActCSTAMonDataAll 1 }


usSrxServiceActCSTAMonDataTableAllEntry  OBJECT-TYPE
        SYNTAX UsSrxServiceActCSTAMonDataTableAllEntry  
        MAX-ACCESS not-accessible
        STATUS  current
        DESCRIPTION "
          An entry in the usSrxServiceActCSTAMonDataTableAll."
        INDEX  { usSrxServiceActCSTAMonDevAll}
        ::= { usSrxServiceActCSTAMonDataTableAll 1 }


UsSrxServiceActCSTAMonDataTableAllEntry  ::=
        SEQUENCE {
	      usSrxServiceActCSTAMonDevAll	  DisplayString 
             }
	
usSrxServiceActCSTAMonDevAll     OBJECT-TYPE
    SYNTAX      DisplayString
    MAX-ACCESS  read-only
    STATUS      current
    DESCRIPTION
        " This object refers to the list of active CSTA monitored devices
	  for All application "
    ::= { usSrxServiceActCSTAMonDataTableAllEntry 1 }

-- ******************************************************************************
-- ** Number of Active CSTA Monitored Devices with Application type Siemens Table
-- ******************************************************************************

usSrxServiceActCSTAMonDataTableSiemens     OBJECT-TYPE
    SYNTAX SEQUENCE OF UsSrxServiceActCSTAMonDataTableSiemensEntry
    MAX-ACCESS  not-accessible
    STATUS      current
    DESCRIPTION
        "The Active CSTA Monitored Devices Table.
         A table containing an array of devices that currently have an 
	 active CSTA Monitor by CSTA Application type Siemens"
    ::= { usSrxServiceActCSTAMonDataSiemens 1 }


usSrxServiceActCSTAMonDataTableSiemensEntry  OBJECT-TYPE
        SYNTAX UsSrxServiceActCSTAMonDataTableSiemensEntry  
        MAX-ACCESS not-accessible
        STATUS  current
        DESCRIPTION "
          An entry in the usSrxServiceActCSTAMonDataTableSiemens."
        INDEX  { usSrxServiceActCSTAMonDevSiemens }
        ::= { usSrxServiceActCSTAMonDataTableSiemens 1 }


UsSrxServiceActCSTAMonDataTableSiemensEntry  ::=
        SEQUENCE {
	      usSrxServiceActCSTAMonDevSiemens	  DisplayString 
             }
	
usSrxServiceActCSTAMonDevSiemens     OBJECT-TYPE
    SYNTAX      DisplayString
    MAX-ACCESS  read-only
    STATUS      current
    DESCRIPTION
        " This object refers to the list of active CSTA monitored devices
	  for Siemens application "
    ::= { usSrxServiceActCSTAMonDataTableSiemensEntry 1 }
    
-- *********************************************************************************
-- ** Number of Active CSTA Monitored Devices with Application type Other Table
-- *********************************************************************************

usSrxServiceActCSTAMonDataTableOther     OBJECT-TYPE
    SYNTAX SEQUENCE OF UsSrxServiceActCSTAMonDataTableOtherEntry
    MAX-ACCESS  not-accessible
    STATUS      current
    DESCRIPTION
        "The Active CSTA Monitored Devices Table.
         A table containing an array of devices that currently have an 
	 active CSTA Monitor by CSTA Application type Other"
    ::= { usSrxServiceActCSTAMonDataOther 1 }


usSrxServiceActCSTAMonDataTableOtherEntry  OBJECT-TYPE
        SYNTAX UsSrxServiceActCSTAMonDataTableOtherEntry  
        MAX-ACCESS not-accessible
        STATUS  current
        DESCRIPTION "
          An entry in the usSrxServiceActCSTAMonDataTableOther."
        INDEX  { usSrxServiceActCSTAMonDevOther }
        ::= { usSrxServiceActCSTAMonDataTableOther 1 }


UsSrxServiceActCSTAMonDataTableOtherEntry  ::=
        SEQUENCE {
	      usSrxServiceActCSTAMonDevOther	  DisplayString 
             }
	
usSrxServiceActCSTAMonDevOther     OBJECT-TYPE
    SYNTAX      DisplayString
    MAX-ACCESS  read-only
    STATUS      current
    DESCRIPTION
        " This object refers to the list of active CSTA monitored devices
	  for Other application "
    ::= { usSrxServiceActCSTAMonDataTableOtherEntry 1 }    

-- *********************************************************************************
-- ** Number of Active CSTA Monitored Devices with Application type Telefonica Table
-- *********************************************************************************

usSrxServiceActCSTAMonDataTableTelefonica     OBJECT-TYPE
    SYNTAX SEQUENCE OF UsSrxServiceActCSTAMonDataTableTelefonicaEntry
    MAX-ACCESS  not-accessible
    STATUS      current
    DESCRIPTION
        "The Active CSTA Monitored Devices Table.
         A table containing an array of devices that currently have an 
	 active CSTA Monitor by CSTA Application type Telefonica"
    ::= { usSrxServiceActCSTAMonDataTelefonica 1 }


usSrxServiceActCSTAMonDataTableTelefonicaEntry  OBJECT-TYPE
        SYNTAX UsSrxServiceActCSTAMonDataTableTelefonicaEntry  
        MAX-ACCESS not-accessible
        STATUS  current
        DESCRIPTION "
          An entry in the usSrxServiceActCSTAMonDataTableTelefonica."
        INDEX  { usSrxServiceActCSTAMonDevTelefonica }
        ::= { usSrxServiceActCSTAMonDataTableTelefonica 1 }


UsSrxServiceActCSTAMonDataTableTelefonicaEntry  ::=
        SEQUENCE {
	      usSrxServiceActCSTAMonDevTelefonica	  DisplayString 
             }
	
usSrxServiceActCSTAMonDevTelefonica     OBJECT-TYPE
    SYNTAX      DisplayString
    MAX-ACCESS  read-only
    STATUS      current
    DESCRIPTION
        " This object refers to the list of active CSTA monitored devices
	  for Telefonica application "
    ::= { usSrxServiceActCSTAMonDataTableTelefonicaEntry 1 }
    
-- **************************************************************************
-- ** Number of Active CSTA Route Registration Devices with Application type All Table
-- **************************************************************************

usSrxServiceActCSTARouteRegDataTableAll     OBJECT-TYPE
    SYNTAX SEQUENCE OF UsSrxServiceActCSTARouteRegDataTableAllEntry
    MAX-ACCESS  not-accessible
    STATUS      current
    DESCRIPTION
        "The Active CSTA Monitored Devices Table.
         A table containing an array of devices that currently have an 
	 active CSTA Route Registration by CSTA Application type All"
    ::= { usSrxServiceActCSTARouteRegDataAll 1 }


usSrxServiceActCSTARouteRegDataTableAllEntry  OBJECT-TYPE
        SYNTAX UsSrxServiceActCSTARouteRegDataTableAllEntry  
        MAX-ACCESS not-accessible
        STATUS  current
        DESCRIPTION "
          An entry in the usSrxServiceActCSTARouteRegDataTableAll."
        INDEX  { usSrxServiceActCSTARouteRegDevAll }
        ::= { usSrxServiceActCSTARouteRegDataTableAll 1 }


UsSrxServiceActCSTARouteRegDataTableAllEntry  ::=
        SEQUENCE {
	      usSrxServiceActCSTARouteRegDevAll	  DisplayString 
             }
	
usSrxServiceActCSTARouteRegDevAll     OBJECT-TYPE
    SYNTAX      DisplayString
    MAX-ACCESS  read-only
    STATUS      current
    DESCRIPTION
        " This object refers to the list of active CSTA Route Registration devices
	  for All application "
    ::= { usSrxServiceActCSTARouteRegDataTableAllEntry 1 }

-- ******************************************************************************
-- ** Number of Active CSTA Route Registration Devices with Application type Siemens Table
-- ******************************************************************************

usSrxServiceActCSTARouteRegDataTableSiemens     OBJECT-TYPE
    SYNTAX SEQUENCE OF UsSrxServiceActCSTARouteRegDataTableSiemensEntry
    MAX-ACCESS  not-accessible
    STATUS      current
    DESCRIPTION
        "The Active CSTA Route Registration Devices Table.
         A table containing an array of devices that currently have an 
	 active CSTA Route Registration by CSTA Application type Siemens"
    ::= { usSrxServiceActCSTARouteRegDataSiemens 1 }


usSrxServiceActCSTARouteRegDataTableSiemensEntry  OBJECT-TYPE
        SYNTAX UsSrxServiceActCSTARouteRegDataTableSiemensEntry  
        MAX-ACCESS not-accessible
        STATUS  current
        DESCRIPTION "
          An entry in the usSrxServiceActCSTARouteRegDataTableSiemens."
        INDEX  { usSrxServiceActCSTARouteRegDevSiemens }
        ::= { usSrxServiceActCSTARouteRegDataTableSiemens 1 }


UsSrxServiceActCSTARouteRegDataTableSiemensEntry  ::=
        SEQUENCE {
	      usSrxServiceActCSTARouteRegDevSiemens	  DisplayString 
             }
	
usSrxServiceActCSTARouteRegDevSiemens     OBJECT-TYPE
    SYNTAX      DisplayString
    MAX-ACCESS  read-only
    STATUS      current
    DESCRIPTION
        " This object refers to the list of active CSTA Route Registration devices
	  for Siemens application "
    ::= { usSrxServiceActCSTARouteRegDataTableSiemensEntry 1 }
    
-- *********************************************************************************
-- ** Number of Active CSTA Route Registration Devices with Application type Other Table
-- *********************************************************************************

usSrxServiceActCSTARouteRegDataTableOther     OBJECT-TYPE
    SYNTAX SEQUENCE OF UsSrxServiceActCSTARouteRegDataTableOtherEntry
    MAX-ACCESS  not-accessible
    STATUS      current
    DESCRIPTION
        "The Active CSTA Route Registration Devices Table.
         A table containing an array of devices that currently have an 
	 active CSTA Route Registration by CSTA Application type Other"
    ::= { usSrxServiceActCSTARouteRegDataOther 1 }


usSrxServiceActCSTARouteRegDataTableOtherEntry  OBJECT-TYPE
        SYNTAX UsSrxServiceActCSTARouteRegDataTableOtherEntry  
        MAX-ACCESS not-accessible
        STATUS  current
        DESCRIPTION "
          An entry in the usSrxServiceActCSTARouteRegDataTableOther."
        INDEX  { usSrxServiceActCSTARouteRegDevOther }
        ::= { usSrxServiceActCSTARouteRegDataTableOther 1 }


UsSrxServiceActCSTARouteRegDataTableOtherEntry  ::=
        SEQUENCE {
	      usSrxServiceActCSTARouteRegDevOther	  DisplayString 
             }
	
usSrxServiceActCSTARouteRegDevOther     OBJECT-TYPE
    SYNTAX      DisplayString
    MAX-ACCESS  read-only
    STATUS      current
    DESCRIPTION
        " This object refers to the list of active CSTA Route Registration devices
	  for Other application "
    ::= { usSrxServiceActCSTARouteRegDataTableOtherEntry 1 }    

-- *********************************************************************************
-- ** Number of Active CSTA Route Registration Devices with Application type Telefonica Table
-- *********************************************************************************

usSrxServiceActCSTARouteRegDataTableTelefonica     OBJECT-TYPE
    SYNTAX SEQUENCE OF UsSrxServiceActCSTARouteRegDataTableTelefonicaEntry
    MAX-ACCESS  not-accessible
    STATUS      current
    DESCRIPTION
        "The Active CSTA Route Registration Devices Table.
         A table containing an array of devices that currently have an 
	 active CSTA Route Registration by CSTA Application type Telefonica"
    ::= { usSrxServiceActCSTARouteRegDataTelefonica 1 }


usSrxServiceActCSTARouteRegDataTableTelefonicaEntry  OBJECT-TYPE
        SYNTAX UsSrxServiceActCSTARouteRegDataTableTelefonicaEntry  
        MAX-ACCESS not-accessible
        STATUS  current
        DESCRIPTION "
          An entry in the usSrxServiceActCSTARouteRegDataTableTelefonica."
        INDEX  { usSrxServiceActCSTARouteRegDevTelefonica }
        ::= { usSrxServiceActCSTARouteRegDataTableTelefonica 1 }


UsSrxServiceActCSTARouteRegDataTableTelefonicaEntry  ::=
        SEQUENCE {
	      usSrxServiceActCSTARouteRegDevTelefonica	  DisplayString 
             }
	
usSrxServiceActCSTARouteRegDevTelefonica     OBJECT-TYPE
    SYNTAX      DisplayString
    MAX-ACCESS  read-only
    STATUS      current
    DESCRIPTION
        " This object refers to the list of active CSTA Route Registration devices
	  for Telefonica application "
    ::= { usSrxServiceActCSTARouteRegDataTableTelefonicaEntry 1 }    

END
