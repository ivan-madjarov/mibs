HIQ-ADMIN-MIB         DEFINITIONS ::= BEGIN

-- ==================================================================
--  Copyright © Siemens Network Convergence LLC
--
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
--
--  Copyright © Siemens Network Convergence LLC
-- ==================================================================

-- **************************************************************************
-- Revision History
-- 08/01/02   K. Teelucksingh   Creation/Migration to SurpassRtpAdmin OID 
-- 05/08/03   Polly Yu          Updated copyright text
-- 09/12/03   Emilio Negron     Added new hiqCSTA entry
-- 10/8/03    Polly Yu, Dan Z.  Added new hiqIN, hiqSmdi.
-- 07/15/04   Ren Luo           Added new hiqDfAdmin
-- 02/10/04   Badri Narayan     Added new items for Jim B & E Hansen
-- 04/10/05   Ren Luo           Added subscriber admin
-- 04/10/08   C. Chatzidimitriou  FRN3208. Cleanup of MIBS      
-- 06/12/08   C. Chatzidimitriou  Updated MIB to be fully compatible with SNMPv2  
--
-- **************************************************************************

IMPORTS
   MODULE-IDENTITY, Integer32
        FROM SNMPv2-SMI
   surpassRtp
	FROM SURPASS-RTP-MIB
   surpassRtpAdmin
        FROM SURPASS-RTP-ADMIN-MIB
   TEXTUAL-CONVENTION
        FROM SNMPv2-TC;

-- **************************************************************************

hiq8000Admin MODULE-IDENTITY
        LAST-UPDATED "200806111500Z"
        ORGANIZATION "Siemens Network Convergence LLC"
        CONTACT-INFO " "

        DESCRIPTION "This is the MIB module that describes 
                     the hiQ8000 managed objects. The
                     hiQ8000 was formerly called Unisphere SRX3000)."
        
        REVISION     "200806111500Z"
        DESCRIPTION
                     "Updated the MIB to be fully compatible with SNMPv2"

        ::= { surpassRtpAdmin 1 }

SrxRowCountType ::= TEXTUAL-CONVENTION
           STATUS   current
           DESCRIPTION "Max size for table row count"
           SYNTAX Integer32 (0..2147483647)

SrxOnOffType ::= TEXTUAL-CONVENTION
           STATUS   current
           DESCRIPTION "Indicates the values of on and off variables."
           SYNTAX INTEGER {on(1),off(2)}

IkeKeyGenMethod ::= TEXTUAL-CONVENTION
           STATUS   current
           DESCRIPTION "The key Generation method for IKE"
           SYNTAX INTEGER {automatic(1),userinput(2)}

IkeKeyType ::= TEXTUAL-CONVENTION
           STATUS   current
           DESCRIPTION "The type of key to be used "
           SYNTAX INTEGER {ascii(1),hex(2)}

IkeKeyLength ::= TEXTUAL-CONVENTION
           STATUS   current
           DESCRIPTION "The length of the IKE key being used"
           SYNTAX Integer32 (16..200)

IkeKey ::= TEXTUAL-CONVENTION
           STATUS   current
           DESCRIPTION "The  IKE key being used"
           SYNTAX OCTET STRING(SIZE(16..200))

NameType ::= TEXTUAL-CONVENTION
           STATUS current
           DESCRIPTION "Defines the size of the Name field."
           SYNTAX OCTET STRING(SIZE(0..63))

-- **************************************************************************
-- hiPath8000 Managed Objects Object Identifiers
-- **************************************************************************

usSrxUce                  OBJECT IDENTIFIER ::= { hiq8000Admin 1 }

usSrxSip                  OBJECT IDENTIFIER ::= { hiq8000Admin 2 }

usSrxMgcp                 OBJECT IDENTIFIER ::= { hiq8000Admin 3 }

usSrxService              OBJECT IDENTIFIER ::= { hiq8000Admin 4 }

hiqFeatLic                OBJECT IDENTIFIER ::= { hiq8000Admin 5 }

hiqTraps                  OBJECT IDENTIFIER ::= { hiq8000Admin 47 } -- 47 is used for legacy reasons

END
