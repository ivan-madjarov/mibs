US-HIQ-TRAP-MIB    DEFINITIONS ::= BEGIN

IMPORTS
   MODULE-IDENTITY, OBJECT-TYPE, Integer32, IpAddress 
      FROM SNMPv2-SMI
   DisplayString, RowStatus
        FROM SNMPv2-TC
   hiq8000Admin
        FROM HIQ-ADMIN-MIB
   rtpEvtSequenceNumberIndex,
   rtpEvtCurrId, rtpEvtSet, rtpEvtNum,
   rtpEvtSeverity, rtpEvtEventTime,
   rtpEvtReportingObject, rtpEvtFaultyObject,
   rtpEvtEndkey, rtpEvtFormatText,
   rtpEvtParameters,  rtpEvtAlarmType, rtpEvtShortText,
   rtpEvtFilterLastTransId , rtpClusterName 
   
   FROM FTS-RTP-MIB-EVENT-MGMT;

-- =================================================================
--      rtpEvtSeverity:  level 1-7, 1 is critical, 
--                                  2 major
--                                  3 minor
--                                  4 warning
--                                  5 informational (NOT reported by OSV)
--                                  6 cleared
--                                  7 unknown (NOT reported by OSV)
--      rtpEvtAlarmType: types 0-99, 0 is undeterminate,
--                                   1 is communication alarm
--                                   2 is service alarm
--                                   3 is processing alarm
--                                   4 is equipement alarm
--                                   5 is environment alarm (NOT reported by OSV)
--                                   6 is db alarm
--                                   7 is mib alarm
--                                   8 is the first user defineable alarm
--                                   32 is security alarm
--                                   34 is indication event
--
--
-- OSV Version:                      V6
-- OSV Patch Set:                    17
-- ==================================================================

hiqTraps   MODULE-IDENTITY
           LAST-UPDATED "201110180000Z"
           ORGANIZATION "Siemens Enterprise Network"
           CONTACT-INFO "James Bridge" 
           DESCRIPTION
           "This MIB describes the Siemens Enterprise Network traps of the OSV cluster.
           The definition of the event is taken from
           RtpAdmEventMgmt.mib. For the description
           of these objects:  rtpEvtSequenceNumberIndex,
                              rtpEvtCurrId,
                              rtpEvtSet,
                              rtpEvtNum,
                              rtpEvtSeverity,
                              rtpEvtEventTime,
                              rtpEvtReportingObject,
                              rtpEvtFaultyObject,
                              rtpEvtEndkey,
                              rtpEvtFormatText,
                              rtpEvtParameters,
                              rtpEvtAlarmType,
                              rtpEvtShortText,
                              rtpEvtFilterLastTransId,
		                      rtpClusterName"
        ::= { hiq8000Admin 47 }

hiQEvtFaultMgt OBJECT-IDENTITY
                STATUS current
                DESCRIPTION
                "Events from Rtp event set RTP_NLS_EVT (100)."
                ::= { hiqTraps 100 }		

hiQAudFaultMgt OBJECT-IDENTITY
                STATUS current
                DESCRIPTION
                "Events from Rtp event set RTP_NLS_AUD (102)."
                ::= { hiqTraps 102 }

hiQNmFaultMgt OBJECT-IDENTITY
                STATUS current
                DESCRIPTION
                "Events from Rtp event set RTP_NLS_NM (107)."
                ::= { hiqTraps 107 }

hiQTicFaultMgt OBJECT-IDENTITY
                STATUS current
                DESCRIPTION
                "Events from Rtp event set 111."
                ::= { hiqTraps 111 }

hiQSnmFaultMgt OBJECT-IDENTITY
                STATUS current
                DESCRIPTION
                "Events from Rtp event set RTP_NLS_SNM (119)."
                ::= { hiqTraps 119 }

hiQLogSolidFaultMgt OBJECT-IDENTITY
                STATUS current
                DESCRIPTION
                "Events from Rtp event set RTP_NLS_SOLID (141)."
                ::= { hiqTraps 141 }

hiQAucAuthFaultMgmt OBJECT-IDENTITY
        	STATUS current
        	DESCRIPTION
            	"The AUC, Authentication (AUTH) Fault Management MOs."
        	::= { hiqTraps 181 }

hiQAucUscFaultMgmt OBJECT-IDENTITY
        	STATUS current
        	DESCRIPTION
            	"The AUC, User Collection(USC) Fault Management MOs."
        	::= { hiqTraps 182 }

hiQUceFaultMgmt OBJECT-IDENTITY
        	STATUS current
        	DESCRIPTION
            	"The UCE Fault Management MOs."
        	::= { hiqTraps 176 }

hiQOvlFaultMgmt OBJECT-IDENTITY
        	STATUS current
        	DESCRIPTION
            	"The Overload Fault Management MOs."
        	::= { hiqTraps 190 }

hiQUCEServicesFaultMgmt OBJECT-IDENTITY
        	STATUS current
        	DESCRIPTION
            	"The LNP Fault Management MOs."
        	::= { hiqTraps 193 }

hiQTcapFaultMgmt OBJECT-IDENTITY
        	STATUS current
        	DESCRIPTION
            	"The TCAP Fault Management MOs."
        	::= { hiqTraps 192 }

hiQXdmFaultMgmt OBJECT-IDENTITY
        	STATUS current
        	DESCRIPTION
            	"The XDM Fault Management MOs."
        	::= { hiqTraps 183 }

hiQDbFaultMgmt OBJECT-IDENTITY
        	STATUS current
        	DESCRIPTION
            	"The DB Fault Management MOs."
        	::= { hiqTraps 191 }

hiQSoapServerFaultMgmt OBJECT-IDENTITY
                STATUS current
                DESCRIPTION
                "The SOAP Server Fault Management Messages."
                ::= { hiqTraps 207 }

hiQCstaFaultMgmt OBJECT-IDENTITY
                STATUS current
                DESCRIPTION
                "The CSTA Fault Management Messages."
                ::= { hiqTraps 210 }

				
hiQSmdiFaultMgmt OBJECT-IDENTITY
                STATUS current
                DESCRIPTION
                "The SMDI Fault Management Messages."
                ::= { hiqTraps 208 }
		
hiQDatabaseSizeMgmt OBJECT-IDENTITY
                STATUS current
                DESCRIPTION
                "The SMDI Fault Management Messages."
                ::= { hiqTraps 215 }		

hiQHardwareFaultMgt OBJECT-IDENTITY
                STATUS current
                DESCRIPTION
                "Events from hardware event set HARDWARE_EVT_SET_ID (219)."
                ::= { hiqTraps 219 }

hiQSecurityFaultMgt OBJECT-IDENTITY
                STATUS current
                DESCRIPTION
                "Events from security event set SECURITY_EVT_SET_ID (218)."
                ::= { hiqTraps 218 }

hiQLicensingFaultMgt OBJECT-IDENTITY
                STATUS current
                DESCRIPTION
                "Events from software licensing event set LICENSING_EVT_SET_ID (220)."
                ::= { hiqTraps 220 }

hiQGlobalFaultMgt OBJECT-IDENTITY
                STATUS current
                DESCRIPTION
                "Events from global event set GLOBAL_EVT_SET_ID (217)."
                ::= { hiqTraps 217 }

hiQAccountMgmtFaultMgt OBJECT-IDENTITY
                STATUS current
                DESCRIPTION
                "Events from account management event set ACCOUNT_EVT_SET_ID (221)."
                ::= { hiqTraps 221 }

hiQSipFaultMgmt OBJECT-IDENTITY
                STATUS current
                DESCRIPTION
                "Events from operational maintenance measurement event set OMM_EVT_SET_ID (230)."
                ::= { hiqTraps 230 }

hiQCacFaultMgt OBJECT-IDENTITY
                STATUS current
                DESCRIPTION
                "Events from CAC specific event set CAC_EVT_SET_ID (231)."
                ::= { hiqTraps 231 }

hiQTcaFaultMgt OBJECT-IDENTITY
                STATUS current
                DESCRIPTION
                "Events from TCA event set TCA_EVT_SET_ID (216)."
                ::= { hiqTraps 216 }

hiQPlatformFaultMgmt OBJECT-IDENTITY
                STATUS current
                DESCRIPTION
                "Events from Platform event set PLATFORM_EVT_SET_ID (234)."
                ::= { hiqTraps 234 }

hiQTcgFaultMgt OBJECT-IDENTITY
                STATUS current
                DESCRIPTION
                "Events from TCG event set TCG_EVT_SET_ID (233)."
                ::= { hiqTraps 233 }

hiQRapidStatFaultMgt  OBJECT-IDENTITY
                STATUS current
                DESCRIPTION
                "Events from RapidStat event set RAPIDSTAT_EVT_SET_ID (235)."
                ::= { hiqTraps 235 }

hiQInterfaceSecurityFaultMgmt OBJECT-IDENTITY
                STATUS current
                DESCRIPTION
                "Events from Security Fault Management event set IFSEC_EVT_SET_ID (236)."
                ::= { hiqTraps 236 }

hiQNotificationMgt OBJECT-IDENTITY
                STATUS current
                DESCRIPTION
                "Events from Rtp event set EMERGENCY_CALL_EVT_ID (250)."
                ::= { hiqTraps 250 }

        
-- ************************************************************************
-- The two Survival Authority traps below are not
-- alarms and not alarm clearance traps.
-- They are informational traps exclusively sent from the OSV cluster nodes
-- to the Survival Authority to test the communication link or
-- to report a broken or repaired partner node communication link
-- ***************************************************************************

hiQSurvivalAuthorityObjects OBJECT IDENTIFIER ::= { hiqTraps 222 }

-- Trap type
hiQSurvivalTrapType OBJECT-TYPE
    SYNTAX INTEGER { takeover(1), requestcommtest(2) }
    MAX-ACCESS read-only
    STATUS current
    DESCRIPTION "An enumerated value indicating the trap type."
    ::= { hiQSurvivalAuthorityObjects 1 }
 
-- Node name
hiQSurvivalNodeName OBJECT-TYPE
    SYNTAX OCTET STRING (SIZE (0..63))
    MAX-ACCESS read-only
    STATUS current
    DESCRIPTION "Name of node reporting to survival authority."
    ::= { hiQSurvivalAuthorityObjects 2 }
 
-- Cluster name
hiQSurvivalClusterName OBJECT-TYPE
    SYNTAX OCTET STRING (SIZE (0..63))
    MAX-ACCESS read-only
    STATUS current
    DESCRIPTION "Name of cluster reporting to survival authority."
    ::= { hiQSurvivalAuthorityObjects 3 }
 
-- IP Address
hiQSurvivalNodeIPAddress OBJECT-TYPE
    SYNTAX IpAddress
    MAX-ACCESS read-only
    STATUS current
    DESCRIPTION "IP address of node reporting to survival authority."
    ::= { hiQSurvivalAuthorityObjects 4 }

--  Community String 
hiQSurvivalCommunityString OBJECT-TYPE
    SYNTAX OCTET STRING (SIZE (0..15))
    MAX-ACCESS read-only
    STATUS current
    DESCRIPTION "Temporary community string to be used by the SET command 
    		 acknowledging the hiQPartnerNodeLeftCLusterTrap."
    ::= { hiQSurvivalAuthorityObjects 5 }


hiQSurvivalAuthorityTraps OBJECT-IDENTITY
                STATUS current
                DESCRIPTION
                "Events for Survival Authority processing"
                ::= { hiqTraps 223 }
 
hiQPartnerNodeLeftClusterTrap NOTIFICATION-TYPE
            OBJECTS {
                hiQSurvivalTrapType,
                hiQSurvivalNodeName,
                hiQSurvivalClusterName,
                hiQSurvivalNodeIPAddress,
		hiQSurvivalCommunityString
            }
            STATUS current
            DESCRIPTION  "Sent to the 'Survival Authority' to request
                          a communication test or when a node cannot
                          communicate with its partner, the 'Survival
                          Authority' is requested to respond with an
                          SNMP set command."
            ::= { hiQSurvivalAuthorityTraps 1 }

hiQResetSurvivalModeTrap NOTIFICATION-TYPE
            OBJECTS {
                hiQSurvivalTrapType,
                hiQSurvivalNodeName,
                hiQSurvivalClusterName,
                hiQSurvivalNodeIPAddress
            }
            STATUS current
            DESCRIPTION  
                          "Sent to the 'Survival Authority' to reset
                           the current Survival Authority status to
                           'no longer in survival mode'."
            ::= { hiQSurvivalAuthorityTraps 2 }


-- ***************************************************************************************************
-- Start of OSV alarm and alarm clearance traps
-- ***************************************************************************************************


hiQProcessExitedTrap NOTIFICATION-TYPE
            OBJECTS { rtpEvtSequenceNumberIndex,
                      rtpEvtCurrId,
                      rtpEvtSet ,                     --100
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The process terminated normally because of either a request by RTP to shut down
                        a configured process or the normal termination of a dynamic, non-configured process." 
            ::= { hiQEvtFaultMgt 2 }

hiQAuditStartingTrap NOTIFICATION-TYPE
            OBJECTS { rtpEvtSequenceNumberIndex,
                      rtpEvtCurrId,
                      rtpEvtSet ,                     --102
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Audit Manager process is starting." 
            ::= { hiQAudFaultMgt 1 }

hiQAudAvailDiskSpBelowCritThld NOTIFICATION-TYPE
            OBJECTS { rtpEvtSequenceNumberIndex,
                      rtpEvtCurrId,
                      rtpEvtSet ,                     --102
                      rtpEvtNum ,                     --201
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The available space in a file system / disk partition is the space usable by
                        non-superuser. The rest of the space is either used or reserved for superuser. Refer
                        to man page df(1). The available space in a database depends on the type of database.
                        The partitions can be: /, /dev,
                        /cdr,/enterprise,/global,/home,/log,/opt,/software,/tmp,/tpa,/unisphere,/var." 
            ::= { hiQAudFaultMgt 201 }

hiQAudAvailDiskSpBelowMajorThld NOTIFICATION-TYPE
            OBJECTS { rtpEvtSequenceNumberIndex,
                      rtpEvtCurrId,
                      rtpEvtSet ,                     --102
                      rtpEvtNum ,                     --202
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The available space in a file system / disk partition is the space usable by
                        non-superuser. The rest of the space is either used or reserved for superuser. Refer
                        to man page df(1). The available space in a database depends on the type of database.
                        The partitions can be: /, /dev,
                        /cdr,/enterprise,/global,/home,/log,/opt,/software,/tmp,/tpa,/unisphere,/var." 
            ::= { hiQAudFaultMgt 202 }

hiQAudAvailDiskSpBelowMinorThld NOTIFICATION-TYPE
            OBJECTS { rtpEvtSequenceNumberIndex,
                      rtpEvtCurrId,
                      rtpEvtSet ,                     --102
                      rtpEvtNum ,                     --203
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The available space in a file system / disk partition is the space usable by
                        non-superuser. The rest of the space is either used or reserved for superuser. Refer
                        to man page df(1). The available space in a database depends on the type of database.
                        The partitions can be: /, /dev,
                        /cdr,/enterprise,/global,/home,/log,/opt,/software,/tmp,/tpa,/unisphere,/var." 
            ::= { hiQAudFaultMgt 203 }

hiQAudFileSystemBelowMin1Trap NOTIFICATION-TYPE
            OBJECTS { rtpEvtSequenceNumberIndex,
                      rtpEvtCurrId,
                      rtpEvtSet ,                     --102
                      rtpEvtNum ,                     --211
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "File system (disk partition) or database space has changed but it is still below
                        the configured minimum level. The partitions can be: /, /dev,
                        /cdr,/enterprise,/global,/home,/log,/opt,/software,/tmp,/tpa,/unisphere,/var." 
            ::= { hiQAudFaultMgt 211 }

hiQAudFileSystemBelowMin2Trap NOTIFICATION-TYPE
            OBJECTS { rtpEvtSequenceNumberIndex,
                      rtpEvtCurrId,
                      rtpEvtSet ,                     --102
                      rtpEvtNum ,                     --212
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "File system (disk partition) or database space has changed but it is still below
                        the configured minimum level. File system or database space error messages with a
                        lower severity level than critical concerning the given data space will be
                        automatically cleared with this abatement so that only the new critical alarm is left
                        open. The partitions can be: /, /dev, cdr, /enterprise, /global, /home, /log, /opt,
                        /software, /tmp, /tpa, /unisphere, /var." 
            ::= { hiQAudFaultMgt 212 }

hiQAudFileSystemBelowMin3Trap NOTIFICATION-TYPE
            OBJECTS { rtpEvtSequenceNumberIndex,
                      rtpEvtCurrId,
                      rtpEvtSet ,                     --102
                      rtpEvtNum ,                     --213
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "File system (disk partition) or database space has changed but it is still below
                        the configured minimum level. File system or database space error messages with a
                        lower severity level than critical concerning the given data space will be
                        automatically cleared with this abatement so that only the new critical alarm is left
                        open. The partitions can be: /, /dev, cdr, /enterprise, /global, /home, /log, /opt,
                        /software, /tmp, /tpa, /unisphere, /var." 
            ::= { hiQAudFaultMgt 213 }

hiQAudFileSystemBelowMin4Trap NOTIFICATION-TYPE
            OBJECTS { rtpEvtSequenceNumberIndex,
                      rtpEvtCurrId,
                      rtpEvtSet ,                     --102
                      rtpEvtNum ,                     --214
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "File system (disk partition) or database space has changed but it is still below
                        the configured minimum level. File system or database space error messages with a
                        lower severity level than critical concerning the given data space will be
                        automatically cleared with this abatement so that only the new critical alarm is left
                        open. The partitions can be: /, /dev, cdr, /enterprise, /global, /home, /log, /opt,
                        /software, /tmp, /tpa, /unisphere, /var." 
            ::= { hiQAudFaultMgt 214 }

hiQAudFileSystemAboveMinTrap NOTIFICATION-TYPE
            OBJECTS { rtpEvtSequenceNumberIndex,
                      rtpEvtCurrId,
                      rtpEvtSet ,                     --102
                      rtpEvtNum ,                     --215
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "File system or database space has increased above the configured minimum level." 
            ::= { hiQAudFaultMgt 215 }

hiQAudFileGrpAboveCritThld NOTIFICATION-TYPE
            OBJECTS { rtpEvtSequenceNumberIndex,
                      rtpEvtCurrId,
                      rtpEvtSet ,                     --102
                      rtpEvtNum ,                     --301
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The size of the given file group is monitored by the audit process and has
                        exceeded the maximum configured size." 
            ::= { hiQAudFaultMgt 301 }

hiQAudFileGrpAboveMajorThld NOTIFICATION-TYPE
            OBJECTS { rtpEvtSequenceNumberIndex,
                      rtpEvtCurrId,
                      rtpEvtSet ,                     --102
                      rtpEvtNum ,                     --302
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The size of the given file group is monitored by the audit process and has
                        exceeded the configured limit for a major alarm." 
            ::= { hiQAudFaultMgt 302 }

hiQAudFileGrpAboveMinorThld NOTIFICATION-TYPE
            OBJECTS { rtpEvtSequenceNumberIndex,
                      rtpEvtCurrId,
                      rtpEvtSet ,                     --102
                      rtpEvtNum ,                     --303
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The size of the given file group is monitored by the audit process and has
                        exceeded the configured limit for a minor alarm." 
            ::= { hiQAudFaultMgt 303 }

hiQAudFileGroupSizeChanged1Trap NOTIFICATION-TYPE
            OBJECTS { rtpEvtSequenceNumberIndex,
                      rtpEvtCurrId,
                      rtpEvtSet ,                     --102
                      rtpEvtNum ,                     --311
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The size of the given file group has changed but is still too high." 
            ::= { hiQAudFaultMgt 311 }

hiQAudFileGroupSizeChanged2Trap NOTIFICATION-TYPE
            OBJECTS { rtpEvtSequenceNumberIndex,
                      rtpEvtCurrId,
                      rtpEvtSet ,                     --102
                      rtpEvtNum ,                     --312
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The size of the given file group has changed but is still too high." 
            ::= { hiQAudFaultMgt 312 }

hiQAudFileGroupSizeChanged3Trap NOTIFICATION-TYPE
            OBJECTS { rtpEvtSequenceNumberIndex,
                      rtpEvtCurrId,
                      rtpEvtSet ,                     --102
                      rtpEvtNum ,                     --313
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The size of the given file group has changed but is still too high." 
            ::= { hiQAudFaultMgt 313 }

hiQAudFileGroupSizeChanged4Trap NOTIFICATION-TYPE
            OBJECTS { rtpEvtSequenceNumberIndex,
                      rtpEvtCurrId,
                      rtpEvtSet ,                     --102
                      rtpEvtNum ,                     --314
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The size of the given file group has changed but is still too high." 
            ::= { hiQAudFaultMgt 314 }

hiQAudFileGrpBelowThreshTrap NOTIFICATION-TYPE
            OBJECTS { rtpEvtSequenceNumberIndex,
                      rtpEvtCurrId,
                      rtpEvtSet ,                     --102
                      rtpEvtNum ,                     --315
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The size of the given file group has previously been reported to have grown
                        beyond alarming threshold. The size of this file group has shrunk again below this
                        limitation." 
            ::= { hiQAudFaultMgt 315 }

hiQAudProcHeapAboveCritThld NOTIFICATION-TYPE
            OBJECTS { rtpEvtSequenceNumberIndex,
                      rtpEvtCurrId,
                      rtpEvtSet ,                     --102
                      rtpEvtNum ,                     --401
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The heap size of the named process is extremely high, i.e. the program has been
                        dynamically allocating more and more memory but freeing only part of it again or none
                        at all. This may be caused by a program error (memory leakage) or large input data
                        from outside the process or a configuration error where the heap size limit for the
                        named process is set too low in the audit configuration." 
            ::= { hiQAudFaultMgt 401 }

hiQAudProcHeapAboveMajorThld NOTIFICATION-TYPE
            OBJECTS { rtpEvtSequenceNumberIndex,
                      rtpEvtCurrId,
                      rtpEvtSet ,                     --102
                      rtpEvtNum ,                     --402
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The heap size of the named process is high, i.e. the program has been
                        dynamically allocating more and more memory but freeing only part of it again or none
                        at all. This may be caused by a program error (memory leakage) or large input data
                        from outside the process or a configuration error where the break size limit for the
                        named process is set too low in the audit configuration." 
            ::= { hiQAudFaultMgt 402 }

hiQAudProcHeapAboveMinorThld NOTIFICATION-TYPE
            OBJECTS { rtpEvtSequenceNumberIndex,
                      rtpEvtCurrId,
                      rtpEvtSet ,                     --102
                      rtpEvtNum ,                     --403
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The heap size of the named process is high, i.e. the program has been
                        dynamically allocating more and more memory but freeing only part of it again or none
                        at all. This may be caused by a program error (memory leakage) or large input data
                        from outside the process or a configuration error where the break size limit for the
                        named process is set too low in the audit configuration." 
            ::= { hiQAudFaultMgt 403 }

hiQAudProcHeapSizeChanged1Trap NOTIFICATION-TYPE
            OBJECTS { rtpEvtSequenceNumberIndex,
                      rtpEvtCurrId,
                      rtpEvtSet ,                     --102
                      rtpEvtNum ,                     --411
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This is an information that the heap size of the named process has changed but
                        is still too high." 
            ::= { hiQAudFaultMgt 411 }

hiQAudProcHeapSizeChanged2Trap NOTIFICATION-TYPE
            OBJECTS { rtpEvtSequenceNumberIndex,
                      rtpEvtCurrId,
                      rtpEvtSet ,                     --102
                      rtpEvtNum ,                     --412
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This is an information that the heap size of the named process has changed but
                        is still too high." 
            ::= { hiQAudFaultMgt 412 }

hiQAudProcHeapSizeChanged3Trap NOTIFICATION-TYPE
            OBJECTS { rtpEvtSequenceNumberIndex,
                      rtpEvtCurrId,
                      rtpEvtSet ,                     --102
                      rtpEvtNum ,                     --413
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This is an information that the heap size of the named process has changed but
                        is still too high." 
            ::= { hiQAudFaultMgt 413 }

hiQAudProcHeapSizeChanged4Trap NOTIFICATION-TYPE
            OBJECTS { rtpEvtSequenceNumberIndex,
                      rtpEvtCurrId,
                      rtpEvtSet ,                     --102
                      rtpEvtNum ,                     --414
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This is an information that the heap size of the named process has changed but
                        is still too high." 
            ::= { hiQAudFaultMgt 414 }

hiQAudProcHeapSizeOkTrap NOTIFICATION-TYPE
            OBJECTS { rtpEvtSequenceNumberIndex,
                      rtpEvtCurrId,
                      rtpEvtSet ,                     --102
                      rtpEvtNum ,                     --415
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The heap size of the process is now below the configured threshold." 
            ::= { hiQAudFaultMgt 415 }

hiQAudProcStackAboveCritThld NOTIFICATION-TYPE
            OBJECTS { rtpEvtSequenceNumberIndex,
                      rtpEvtCurrId,
                      rtpEvtSet ,                     --102
                      rtpEvtNum ,                     --421
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The program stack of the named process is extremely high. This might be caused
                        by a programming error within recursive function calls, recursively defined input data
                        or a configuration error where the stack size limit for the named process is set too
                        low in audit configuration." 
            ::= { hiQAudFaultMgt 421 }

hiQAudProcStackAboveMajorThld NOTIFICATION-TYPE
            OBJECTS { rtpEvtSequenceNumberIndex,
                      rtpEvtCurrId,
                      rtpEvtSet ,                     --102
                      rtpEvtNum ,                     --422
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The program stack of the named process is high. This might be caused by a
                        programming error within recursive function calls, recursively defined input data or a
                        configuration error where the stack size limit for the named process is set too low in
                        audit configuration." 
            ::= { hiQAudFaultMgt 422 }

hiQAudProcStackAboveMinorThld NOTIFICATION-TYPE
            OBJECTS { rtpEvtSequenceNumberIndex,
                      rtpEvtCurrId,
                      rtpEvtSet ,                     --102
                      rtpEvtNum ,                     --423
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The program stack of the named process is high. This might be caused by a
                        programming error within recursive function calls, recursively defined input data or a
                        configuration error where the stack size limit for the named process is set too low in
                        audit configuration." 
            ::= { hiQAudFaultMgt 423 }

hiQAudProcStackSizeChanged1Trap NOTIFICATION-TYPE
            OBJECTS { rtpEvtSequenceNumberIndex,
                      rtpEvtCurrId,
                      rtpEvtSet ,                     --102
                      rtpEvtNum ,                     --431
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This is an information that the stack size of the named process has changed but
                        is still too high." 
            ::= { hiQAudFaultMgt 431 }

hiQAudProcStackSizeChanged2Trap NOTIFICATION-TYPE
            OBJECTS { rtpEvtSequenceNumberIndex,
                      rtpEvtCurrId,
                      rtpEvtSet ,                     --102
                      rtpEvtNum ,                     --432
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This is an information that the stack size of the named process has changed but
                        is still too high." 
            ::= { hiQAudFaultMgt 432 }

hiQAudProcStackSizeChanged3Trap NOTIFICATION-TYPE
            OBJECTS { rtpEvtSequenceNumberIndex,
                      rtpEvtCurrId,
                      rtpEvtSet ,                     --102
                      rtpEvtNum ,                     --433
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This is an information that the stack size of the named process has changed but
                        is still too high." 
            ::= { hiQAudFaultMgt 433 }

hiQAudProcStackSizeChanged4Trap NOTIFICATION-TYPE
            OBJECTS { rtpEvtSequenceNumberIndex,
                      rtpEvtCurrId,
                      rtpEvtSet ,                     --102
                      rtpEvtNum ,                     --434
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This is an information that the stack size of the named process has changed but
                        is still too high." 
            ::= { hiQAudFaultMgt 434 }

hiQAudProcStackSizeOkTrap NOTIFICATION-TYPE
            OBJECTS { rtpEvtSequenceNumberIndex,
                      rtpEvtCurrId,
                      rtpEvtSet ,                     --102
                      rtpEvtNum ,                     --435
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The stack size of the process is now below the configured threshold." 
            ::= { hiQAudFaultMgt 435 }

hiQAudOSProcNotRunningTrap NOTIFICATION-TYPE
            OBJECTS { rtpEvtSequenceNumberIndex,
                      rtpEvtCurrId,
                      rtpEvtSet ,                     --102
                      rtpEvtNum ,                     --481
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The named process is no longer running." 
            ::= { hiQAudFaultMgt 481 }

hiQAudOSProcInstanceNotRunningTrap NOTIFICATION-TYPE
            OBJECTS { rtpEvtSequenceNumberIndex,
                      rtpEvtCurrId,
                      rtpEvtSet ,                     --102
                      rtpEvtNum ,                     --482
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "No instance of the named process type is currently running." 
            ::= { hiQAudFaultMgt 482 }

hiQAudProcNotRunningCriticalTrap NOTIFICATION-TYPE
            OBJECTS { rtpEvtSequenceNumberIndex,
                      rtpEvtCurrId,
                      rtpEvtSet ,                     --102
                      rtpEvtNum ,                     --491
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The named process is currently not running." 
            ::= { hiQAudFaultMgt 491 }

hiQAudProcessNotRunningMajorTrap NOTIFICATION-TYPE
            OBJECTS { rtpEvtSequenceNumberIndex,
                      rtpEvtCurrId,
                      rtpEvtSet ,                     --102
                      rtpEvtNum ,                     --492
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The named process is currently not running." 
            ::= { hiQAudFaultMgt 492 }

hiQAudProcessNotRunningMinorTrap NOTIFICATION-TYPE
            OBJECTS { rtpEvtSequenceNumberIndex,
                      rtpEvtCurrId,
                      rtpEvtSet ,                     --102
                      rtpEvtNum ,                     --493
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The named process is currently not running." 
            ::= { hiQAudFaultMgt 493 }

hiQAudProcessRunningTrap NOTIFICATION-TYPE
            OBJECTS { rtpEvtSequenceNumberIndex,
                      rtpEvtCurrId,
                      rtpEvtSet ,                     --102
                      rtpEvtNum ,                     --496
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The named process is running (again)." 
            ::= { hiQAudFaultMgt 496 }

hiQAudCpuUtilAboveCritThld NOTIFICATION-TYPE
            OBJECTS { rtpEvtSequenceNumberIndex,
                      rtpEvtCurrId,
                      rtpEvtSet ,                     --102
                      rtpEvtNum ,                     --620
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The current cpu utilization is too high. Cpu utilization checks are done
                        periodically by audit and if this is a temporary situation which no longer exists
                        during the next check cycle, a clearing event will then be issued." 
            ::= { hiQAudFaultMgt 620 }

hiQAudCpuUtilAboveMajorThld NOTIFICATION-TYPE
            OBJECTS { rtpEvtSequenceNumberIndex,
                      rtpEvtCurrId,
                      rtpEvtSet ,                     --102
                      rtpEvtNum ,                     --621
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The current cpu utilization is high. Cpu utilization checks are done
                        periodically by audit and if this is a temporary situation which no longer exists
                        during the next check cycle, a clearing event will then be issued." 
            ::= { hiQAudFaultMgt 621 }

hiQAudCpuUtilAboveMinorThld NOTIFICATION-TYPE
            OBJECTS { rtpEvtSequenceNumberIndex,
                      rtpEvtCurrId,
                      rtpEvtSet ,                     --102
                      rtpEvtNum ,                     --622
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The current cpu utilization is high. Cpu utilization checks are done
                        periodically by audit and if this is a temporary situation which no longer exists
                        during the next check cycle, a clearing event will then be issued." 
            ::= { hiQAudFaultMgt 622 }

hiQAudCpuUtilTrap NOTIFICATION-TYPE
            OBJECTS { rtpEvtSequenceNumberIndex,
                      rtpEvtCurrId,
                      rtpEvtSet ,                     --102
                      rtpEvtNum ,                     --628
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Information about the current CPU utilization." 
            ::= { hiQAudFaultMgt 628 }

hiQAudCpuUtilBelowThreshTrap NOTIFICATION-TYPE
            OBJECTS { rtpEvtSequenceNumberIndex,
                      rtpEvtCurrId,
                      rtpEvtSet ,                     --102
                      rtpEvtNum ,                     --629
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The current cpu utilization is now below the configured threshold." 
            ::= { hiQAudFaultMgt 629 }

hiQAudCpuUtilChangedTrap NOTIFICATION-TYPE
            OBJECTS { rtpEvtSequenceNumberIndex,
                      rtpEvtCurrId,
                      rtpEvtSet ,                     --102
                      rtpEvtNum ,                     --630
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The current cpu utilization has changed but is still high." 
            ::= { hiQAudFaultMgt 630 }

hiQAudSwapSpaceAboveCritThld NOTIFICATION-TYPE
            OBJECTS { rtpEvtSequenceNumberIndex,
                      rtpEvtCurrId,
                      rtpEvtSet ,                     --102
                      rtpEvtNum ,                     --640
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The system is running out of swap space. Swap space checks are done periodically
                        by audit and if this is a temporary situation which no longer exists during the next
                        check cycle, a clearing event will be issued.If the system runs out of swap space, the
                        system may experience unpredictable failures, including a system crash." 
            ::= { hiQAudFaultMgt 640 }

hiQAudSwapSpaceAboveMajorThld NOTIFICATION-TYPE
            OBJECTS { rtpEvtSequenceNumberIndex,
                      rtpEvtCurrId,
                      rtpEvtSet ,                     --102
                      rtpEvtNum ,                     --641
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The system is running out of swap space. Swap space checks are done periodically
                        by audit and if this is a temporary situation which no longer exists during the next
                        check cycle, a clearing event will be issued.If the system runs out of swap space, the
                        system may experience unpredictable failures, including a system crash." 
            ::= { hiQAudFaultMgt 641 }

hiQAudSwapSpaceAboveMinorThld NOTIFICATION-TYPE
            OBJECTS { rtpEvtSequenceNumberIndex,
                      rtpEvtCurrId,
                      rtpEvtSet ,                     --102
                      rtpEvtNum ,                     --642
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The system is running out of swap space. Swap space checks are done periodically
                        by audit and if this is a temporary situation which no longer exists during the next
                        check cycle, a clearing event will be issued.If the system runs out of swap space, the
                        system may experience unpredictable failures, including a system crash." 
            ::= { hiQAudFaultMgt 642 }

hiQAudSwapUtilTrap NOTIFICATION-TYPE
            OBJECTS { rtpEvtSequenceNumberIndex,
                      rtpEvtCurrId,
                      rtpEvtSet ,                     --102
                      rtpEvtNum ,                     --648
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Information about the current swap space utilization." 
            ::= { hiQAudFaultMgt 648 }

hiQAudSwapUtilBelowThreshTrap NOTIFICATION-TYPE
            OBJECTS { rtpEvtSequenceNumberIndex,
                      rtpEvtCurrId,
                      rtpEvtSet ,                     --102
                      rtpEvtNum ,                     --649
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Current swap space utilization below the configured threshold." 
            ::= { hiQAudFaultMgt 649 }

hiQAudSwapUtilChangedTrap NOTIFICATION-TYPE
            OBJECTS { rtpEvtSequenceNumberIndex,
                      rtpEvtCurrId,
                      rtpEvtSet ,                     --102
                      rtpEvtNum ,                     --650
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The swap space utilization has changed but is still too high." 
            ::= { hiQAudFaultMgt 650 }

hiQAudShMemUtilTooAboveCritThld NOTIFICATION-TYPE
            OBJECTS { rtpEvtSequenceNumberIndex,
                      rtpEvtCurrId,
                      rtpEvtSet ,                     --102
                      rtpEvtNum ,                     --680
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used shared memory segments is high. Shared memory
                        segment checks are done periodically by audit and if this is a temporary situation
                        which no longer exists during the next check cycle, a clearing event will be issued.
                        If the system runs out of shared memory, some functions of the system may fail in an
                        unpredictable manner." 
            ::= { hiQAudFaultMgt 680 }

hiQAudShMemUtilTooAboveMajorThld NOTIFICATION-TYPE
            OBJECTS { rtpEvtSequenceNumberIndex,
                      rtpEvtCurrId,
                      rtpEvtSet ,                     --102
                      rtpEvtNum ,                     --681
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used shared memory segments is high. Shared memory
                        segment checks are done periodically by audit and if this is a temporary situation
                        which no longer exists during the next check cycle, a clearing event will be issued.
                        If the system runs out of shared memory, some functions of the system may fail in an
                        unpredictable manner." 
            ::= { hiQAudFaultMgt 681 }

hiQAudShMemUtilTooAboveMinorThld NOTIFICATION-TYPE
            OBJECTS { rtpEvtSequenceNumberIndex,
                      rtpEvtCurrId,
                      rtpEvtSet ,                     --102
                      rtpEvtNum ,                     --682
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used shared memory segments is high. Shared memory
                        segment checks are done periodically by audit and if this is a temporary situation
                        which no longer exists during the next check cycle, a clearing event will be issued.
                        If the system runs out of shared memory, some functions of the system may fail in an
                        unpredictable manner." 
            ::= { hiQAudFaultMgt 682 }

hiQAudShMemUtilTrap NOTIFICATION-TYPE
            OBJECTS { rtpEvtSequenceNumberIndex,
                      rtpEvtCurrId,
                      rtpEvtSet ,                     --102
                      rtpEvtNum ,                     --688
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Information about the current shared memory id utilization." 
            ::= { hiQAudFaultMgt 688 }

hiQAudShMemUtilBelowThreshTrap NOTIFICATION-TYPE
            OBJECTS { rtpEvtSequenceNumberIndex,
                      rtpEvtCurrId,
                      rtpEvtSet ,                     --102
                      rtpEvtNum ,                     --689
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used shared memory ids is now below the configured
                        threshold." 
            ::= { hiQAudFaultMgt 689 }

hiQAudShMemUtilChangedTrap NOTIFICATION-TYPE
            OBJECTS { rtpEvtSequenceNumberIndex,
                      rtpEvtCurrId,
                      rtpEvtSet ,                     --102
                      rtpEvtNum ,                     --690
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used shared memory ids has changed but is still above
                        the configured thresholds." 
            ::= { hiQAudFaultMgt 690 }

hiQAudSemUtilAboveCritThld NOTIFICATION-TYPE
            OBJECTS { rtpEvtSequenceNumberIndex,
                      rtpEvtCurrId,
                      rtpEvtSet ,                     --102
                      rtpEvtNum ,                     --700
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used semaphores is high. Semaphore utilization checks
                        are done periodically by audit and if this is a temporary situation which no longer
                        exists during the next check cycle, a clearing event will be issued. If the system
                        runs out of semaphores, some functions of the system may fail in an unpredictable
                        manner." 
            ::= { hiQAudFaultMgt 700 }

hiQAudSemUtilAboveMajorThld NOTIFICATION-TYPE
            OBJECTS { rtpEvtSequenceNumberIndex,
                      rtpEvtCurrId,
                      rtpEvtSet ,                     --102
                      rtpEvtNum ,                     --701
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used semaphores is high. Semaphore utilization checks
                        are done periodically by audit and if this is a temporary situation which no longer
                        exists during the next check cycle, a clearing event will be issued. If the system
                        runs out of semaphores, some functions of the system may fail in an unpredictable
                        manner." 
            ::= { hiQAudFaultMgt 701 }

hiQAudSemUtilAboveMinorThld NOTIFICATION-TYPE
            OBJECTS { rtpEvtSequenceNumberIndex,
                      rtpEvtCurrId,
                      rtpEvtSet ,                     --102
                      rtpEvtNum ,                     --702
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used semaphores is high. Semaphore utilization checks
                        are done periodically by audit and if this is a temporary situation which no longer
                        exists during the next check cycle, a clearing event will be issued. If the system
                        runs out of semaphores, some functions of the system may fail in an unpredictable
                        manner." 
            ::= { hiQAudFaultMgt 702 }

hiQAudSemUtilTrap NOTIFICATION-TYPE
            OBJECTS { rtpEvtSequenceNumberIndex,
                      rtpEvtCurrId,
                      rtpEvtSet ,                     --102
                      rtpEvtNum ,                     --708
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Information about the current semaphore utilization." 
            ::= { hiQAudFaultMgt 708 }

hiQAudSemUtilBelowThreshTrap NOTIFICATION-TYPE
            OBJECTS { rtpEvtSequenceNumberIndex,
                      rtpEvtCurrId,
                      rtpEvtSet ,                     --102
                      rtpEvtNum ,                     --709
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used semaphores is now below the configured threshold." 
            ::= { hiQAudFaultMgt 709 }

hiQAudSemUtilChangedTrap NOTIFICATION-TYPE
            OBJECTS { rtpEvtSequenceNumberIndex,
                      rtpEvtCurrId,
                      rtpEvtSet ,                     --102
                      rtpEvtNum ,                     --710
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of currently used semaphores has changed but is still above the
                        configured thresholds." 
            ::= { hiQAudFaultMgt 710 }

hiQAudSwapFrequencyAboveCritThld NOTIFICATION-TYPE
            OBJECTS { rtpEvtSequenceNumberIndex,
                      rtpEvtCurrId,
                      rtpEvtSet ,                     --102
                      rtpEvtNum ,                     --720
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP Audit swap frequency detector has detected high swap out activities.
                        This may affect the system's performance and compromise your running RTP if these
                        activities continue. If the situation abates, an abatement will be issued during the
                        next check cycle." 
            ::= { hiQAudFaultMgt 720 }

hiQAudSwapFrequencyAboveMajorThld NOTIFICATION-TYPE
            OBJECTS { rtpEvtSequenceNumberIndex,
                      rtpEvtCurrId,
                      rtpEvtSet ,                     --102
                      rtpEvtNum ,                     --721
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP Audit swap frequency detector has detected high swap out activities.
                        This may affect the system's performance and compromise your running RTP if these
                        activities continue. If the situation abates, an abatement will be issued during the
                        next check cycle." 
            ::= { hiQAudFaultMgt 721 }

hiQAudSwapFrequencyAboveMinorThld NOTIFICATION-TYPE
            OBJECTS { rtpEvtSequenceNumberIndex,
                      rtpEvtCurrId,
                      rtpEvtSet ,                     --102
                      rtpEvtNum ,                     --722
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP Audit swap frequency detector has detected high swap out activities.
                        This may affect the system's performance and compromise your running RTP if these
                        activities continue. If the situation abates, an abatement will be issued during the
                        next check cycle." 
            ::= { hiQAudFaultMgt 722 }

hiQAudSwapFrequenyAboveWarningThld NOTIFICATION-TYPE
            OBJECTS { rtpEvtSequenceNumberIndex,
                      rtpEvtCurrId,
                      rtpEvtSet ,                     --102
                      rtpEvtNum ,                     --723
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP Audit swap frequency detector has detected high swap out activities.
                        This may affect the system's performance and compromise your running RTP if these
                        activities continue. If the situation abates, an abatement will be issued during the
                        next check cycle." 
            ::= { hiQAudFaultMgt 723 }

hiQAudSwapFrequencyUtilTrap NOTIFICATION-TYPE
            OBJECTS { rtpEvtSequenceNumberIndex,
                      rtpEvtCurrId,
                      rtpEvtSet ,                     --102
                      rtpEvtNum ,                     --728
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Information about the current swap frequency." 
            ::= { hiQAudFaultMgt 728 }

hiQAudSwapFrequencyBelowThreshTrap NOTIFICATION-TYPE
            OBJECTS { rtpEvtSequenceNumberIndex,
                      rtpEvtCurrId,
                      rtpEvtSet ,                     --102
                      rtpEvtNum ,                     --729
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Current swap frequency below the configured threshold." 
            ::= { hiQAudFaultMgt 729 }

hiQAudSwapFrequencyUtilChangedTrap NOTIFICATION-TYPE
            OBJECTS { rtpEvtSequenceNumberIndex,
                      rtpEvtCurrId,
                      rtpEvtSet ,                     --102
                      rtpEvtNum ,                     --730
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The swap frequency has abated but is still too high." 
            ::= { hiQAudFaultMgt 730 }

hiQAudCouldNotGetSwapFrequencyTrap NOTIFICATION-TYPE
            OBJECTS { rtpEvtSequenceNumberIndex,
                      rtpEvtCurrId,
                      rtpEvtSet ,                     --102
                      rtpEvtNum ,                     --738
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Audit could not determine the current swap frequency." 
            ::= { hiQAudFaultMgt 738 }

hiQNmProcessInitCompleteTrap NOTIFICATION-TYPE
            OBJECTS { rtpEvtSequenceNumberIndex,
                      rtpEvtCurrId,
                      rtpEvtSet ,                     --107
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Process <LogicalName> called RtpNmReady() to indicate, that it finished its
                        initialization phase successfully." 
            ::= { hiQNmFaultMgt 1 }

hiQNmDbUnreachable1Trap NOTIFICATION-TYPE
            OBJECTS { rtpEvtSequenceNumberIndex,
                      rtpEvtCurrId,
                      rtpEvtSet ,                     --107
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The database could not be reached from the node manager." 
            ::= { hiQNmFaultMgt 5 }

hiQNmDbMaxProcGrpExceededTrap NOTIFICATION-TYPE
            OBJECTS { rtpEvtSequenceNumberIndex,
                      rtpEvtCurrId,
                      rtpEvtSet ,                     --107
                      rtpEvtNum ,                     --8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The database contains more <processes/groups> than can be handled by the node
                        manager. These entries are ignored by the node manager." 
            ::= { hiQNmFaultMgt 8 }

hiQNmDbUnreachable2Trap NOTIFICATION-TYPE
            OBJECTS { rtpEvtSequenceNumberIndex,
                      rtpEvtCurrId,
                      rtpEvtSet ,                     --107
                      rtpEvtNum ,                     --9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The database could not be reached from the node manager." 
            ::= { hiQNmFaultMgt 9 }

hiQNmDbTableNotOpenedTrap NOTIFICATION-TYPE
            OBJECTS { rtpEvtSequenceNumberIndex,
                      rtpEvtCurrId,
                      rtpEvtSet ,                     --107
                      rtpEvtNum ,                     --10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The database table could not be opened by the node manager." 
            ::= { hiQNmFaultMgt 10 }

hiQNmDbTableNotClosedTrap NOTIFICATION-TYPE
            OBJECTS { rtpEvtSequenceNumberIndex,
                      rtpEvtCurrId,
                      rtpEvtSet ,                     --107
                      rtpEvtNum ,                     --11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The database table could not be closed by the node manager." 
            ::= { hiQNmFaultMgt 11 }

hiQNmProcessReadyTimeoutTrap NOTIFICATION-TYPE
            OBJECTS { rtpEvtSequenceNumberIndex,
                      rtpEvtCurrId,
                      rtpEvtSet ,                     --107
                      rtpEvtNum ,                     --12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The given process did not inform RTP that it had completed initialization before
                        the configured timeout expired.RTP will attempt to restart the process." 
            ::= { hiQNmFaultMgt 12 }

hiQNmProcessHealthChkTimeoutTrap NOTIFICATION-TYPE
            OBJECTS { rtpEvtSequenceNumberIndex,
                      rtpEvtCurrId,
                      rtpEvtSet ,                     --107
                      rtpEvtNum ,                     --13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The given process did not answer the healthcheck in time.The RTP healthcheck
                        kills non-reponding processes (e.g. deadlock or endess loops) so that they can be
                        restarted by RTP." 
            ::= { hiQNmFaultMgt 13 }

hiQNmNodeShutdownTrap NOTIFICATION-TYPE
            OBJECTS { rtpEvtSequenceNumberIndex,
                      rtpEvtCurrId,
                      rtpEvtSet ,                     --107
                      rtpEvtNum ,                     --19
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Node <node> will be stopped on behalf of process <LogicalName>." 
            ::= { hiQNmFaultMgt 19 }

hiQNmQueueCorruptedTrap NOTIFICATION-TYPE
            OBJECTS { rtpEvtSequenceNumberIndex,
                      rtpEvtCurrId,
                      rtpEvtSet ,                     --107
                      rtpEvtNum ,                     --22
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The queue of process %s is not in a consistent state. To avoid further problems
                        the process is killed and should come up with a new clean queue." 
            ::= { hiQNmFaultMgt 22 }

hiQNmNodeMgrStartingTrap NOTIFICATION-TYPE
            OBJECTS { rtpEvtSequenceNumberIndex,
                      rtpEvtCurrId,
                      rtpEvtSet ,                     --107
                      rtpEvtNum ,                     --31
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "RTP local node manager starting on <NodeName>" 
            ::= { hiQNmFaultMgt 31 }

hiQNmProcessRestartShortTimeTrap NOTIFICATION-TYPE
            OBJECTS { rtpEvtSequenceNumberIndex,
                      rtpEvtCurrId,
                      rtpEvtSet ,                     --107
                      rtpEvtNum ,                     --36
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Process <LogicalName> restarts too soon. To avoid frequent restarts, the node
                        manager will now wait <number> seconds, before it tries again to bring the process up." 
            ::= { hiQNmFaultMgt 36 }

hiQNmQueueAllocErrorTrap NOTIFICATION-TYPE
            OBJECTS { rtpEvtSequenceNumberIndex,
                      rtpEvtCurrId,
                      rtpEvtSet ,                     --107
                      rtpEvtNum ,                     --39
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The process queue of %s could not be allocated, due to problems with shared
                        memory." 
            ::= { hiQNmFaultMgt 39 }

hiQNmResizeGlobalProcTblTrap NOTIFICATION-TYPE
            OBJECTS { rtpEvtSequenceNumberIndex,
                      rtpEvtCurrId,
                      rtpEvtSet ,                     --107
                      rtpEvtNum ,                     --42
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of processes on another node has changed due to a node restart. As a
                        consequence the process table for that node must be resized." 
            ::= { hiQNmFaultMgt 42 }

hiQNmAliasTableLenExceededTrap NOTIFICATION-TYPE
            OBJECTS { rtpEvtSequenceNumberIndex,
                      rtpEvtCurrId,
                      rtpEvtSet ,                     --107
                      rtpEvtNum ,                     --43
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP parameter Rtp/Nm/MaxAliases must be greater or equal to the number of
                        aliases configured by tcn files or by the GUI/CLI." 
            ::= { hiQNmFaultMgt 43 }

hiQNmAliasMembersExceededTrap NOTIFICATION-TYPE
            OBJECTS { rtpEvtSequenceNumberIndex,
                      rtpEvtCurrId,
                      rtpEvtSet ,                     --107
                      rtpEvtNum ,                     --44
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP parameter Rtp/Nm/ProcsPerAlias specified the maximal number of members
                        for all aliases. This parameter must suffice for all alias members configured by tcn
                        files or CLI/GUI." 
            ::= { hiQNmFaultMgt 44 }

hiQNmProcessExecvErrorTrap NOTIFICATION-TYPE
            OBJECTS { rtpEvtSequenceNumberIndex,
                      rtpEvtCurrId,
                      rtpEvtSet ,                     --107
                      rtpEvtNum ,                     --46
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The binary could not be started since execv returned the errno. If restart is
                        set for the RTP process, RTP will try to start it again" 
            ::= { hiQNmFaultMgt 46 }

hiQNmProcessExitedwithCodeTrap NOTIFICATION-TYPE
            OBJECTS { rtpEvtSequenceNumberIndex,
                      rtpEvtCurrId,
                      rtpEvtSet ,                     --107
                      rtpEvtNum ,                     --47
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "An RTP process terminated unexpectedly. The string in parentheses contains an
                        exit status or signal number. If the exit status is unknown, the process was not a
                        child of the RTP node manager. The event also tells whether the node manager will
                        attempt to restart the process or not." 
            ::= { hiQNmFaultMgt 47 }

hiQNmProcessCoreCreatedTrap NOTIFICATION-TYPE
            OBJECTS { rtpEvtSequenceNumberIndex,
                      rtpEvtCurrId,
                      rtpEvtSet ,                     --107
                      rtpEvtNum ,                     --49
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The core is found in the directory $HOME/$PLID/core if the core was written by
                        RTP.  The process aborted and is normally automatically restarted" 
            ::= { hiQNmFaultMgt 49 }

hiQNmDiagnosticErrorTrap NOTIFICATION-TYPE
            OBJECTS { rtpEvtSequenceNumberIndex,
                      rtpEvtCurrId,
                      rtpEvtSet ,                     --107
                      rtpEvtNum ,                     --53
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The occurrence of this event means that a process has terminated while acquiring
                        or releasing an RTP queue lock. The RTP fixes any resulting inconsistencies
                        automatically, but the behaviour of the platform should be carefully monitored." 
            ::= { hiQNmFaultMgt 53 }

hiQNmNodeDownMsgErrorTrap NOTIFICATION-TYPE
            OBJECTS { rtpEvtSequenceNumberIndex,
                      rtpEvtCurrId,
                      rtpEvtSet ,                     --107
                      rtpEvtNum ,                     --102
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "When trying to send the NODEDOWN message to the specified node an error occured.
                        The NODEDOWN message is very important for an orderly termination of the shutdown." 
            ::= { hiQNmFaultMgt 102 }

hiQNmNodeMgrSignalRestartTrap NOTIFICATION-TYPE
            OBJECTS { rtpEvtSequenceNumberIndex,
                      rtpEvtCurrId,
                      rtpEvtSet ,                     --107
                      rtpEvtNum ,                     --104
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A signal of type SIGTERM, SIGINT or SIGQUIT was sent to the node manager. The
                        pid and possibly the logical name of the sending process can be found in []." 
            ::= { hiQNmFaultMgt 104 }

hiQTicDiskFullTicketPoolFailed NOTIFICATION-TYPE
            OBJECTS { rtpEvtSequenceNumberIndex,
                      rtpEvtCurrId,
                      rtpEvtSet ,                     --111
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A new ticket file has to be created by the ticket manager. However, a check of
                        the available free disc space failed: there is not enough disc space to create the new
                        ticket file." 
            ::= { hiQTicFaultMgt 7 }

hiQTicCopyToTicketPoolFailed NOTIFICATION-TYPE
            OBJECTS { rtpEvtSequenceNumberIndex,
                      rtpEvtCurrId,
                      rtpEvtSet ,                     --111
                      rtpEvtNum ,                     --23
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "In order to move a ticket file from or to the central ticket pool, the copy
                        command failed." 
            ::= { hiQTicFaultMgt 23 }

hiQTicPoolDiskDevNotAccessible NOTIFICATION-TYPE
            OBJECTS { rtpEvtSequenceNumberIndex,
                      rtpEvtCurrId,
                      rtpEvtSet ,                     --111
                      rtpEvtNum ,                     --47
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "During ticket manager initialization, an error occurred: the configured disk
                        device for the central ticket pool was not accessible." 
            ::= { hiQTicFaultMgt 47 }

hiQSnmSubsysAlreadyRunningTrap NOTIFICATION-TYPE
            OBJECTS { rtpEvtSequenceNumberIndex,
                      rtpEvtCurrId,
                      rtpEvtSet ,                     --119
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The super node manager tried to start an already running subsystem." 
            ::= { hiQSnmFaultMgt 1 }

hiQSnmSubsystemStartErrorTrap NOTIFICATION-TYPE
            OBJECTS { rtpEvtSequenceNumberIndex,
                      rtpEvtCurrId,
                      rtpEvtSet ,                     --119
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The super node manager can't start the mentioned subsystem. The associated start
                        script returns an error." 
            ::= { hiQSnmFaultMgt 2 }

hiQSnmSubsysAdmInterventionTrap NOTIFICATION-TYPE
            OBJECTS { rtpEvtSequenceNumberIndex,
                      rtpEvtCurrId,
                      rtpEvtSet ,                     --119
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The health detector script of the mentioned subsystem requires an administrator
                        intervention." 
            ::= { hiQSnmFaultMgt 7 }

hiQSnmRtpRestartForSubsystemTrap NOTIFICATION-TYPE
            OBJECTS { rtpEvtSequenceNumberIndex,
                      rtpEvtCurrId,
                      rtpEvtSet ,                     --119
                      rtpEvtNum ,                     --10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The health detector script of the mentioned subsystem requires to restart the
                        whole RTP. Refer to the logfile of the health detector script in $HOME/$PLID/log for
                        the reason." 
            ::= { hiQSnmFaultMgt 10 }

hiQSnmRebootForSubsystemTrap NOTIFICATION-TYPE
            OBJECTS { rtpEvtSequenceNumberIndex,
                      rtpEvtCurrId,
                      rtpEvtSet ,                     --119
                      rtpEvtNum ,                     --11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The health detector script requires a reboot of the system. Refer to the logfile
                        of the health detector script in $HOME/$PLID/log for more information." 
            ::= { hiQSnmFaultMgt 11 }

hiQSnmSystemSwitchOffTrap NOTIFICATION-TYPE
            OBJECTS { rtpEvtSequenceNumberIndex,
                      rtpEvtCurrId,
                      rtpEvtSet ,                     --119
                      rtpEvtNum ,                     --13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The health detector script requires a shutdown of the system. Refer to the
                        logfile of the health detector script in $HOME/$PLID/log for more information." 
            ::= { hiQSnmFaultMgt 13 }

hiQSnmSpecialActScrExecTrap NOTIFICATION-TYPE
            OBJECTS { rtpEvtSequenceNumberIndex,
                      rtpEvtCurrId,
                      rtpEvtSet ,                     --119
                      rtpEvtNum ,                     --14
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The health detector script of the mentioned subsystem requires to execute the
                        special action script. Refer to the logfile of the health detector script in
                        $HOME/$PLID/log for more information." 
            ::= { hiQSnmFaultMgt 14 }

hiQSnmSpecialActScrSuccessTrap NOTIFICATION-TYPE
            OBJECTS { rtpEvtSequenceNumberIndex,
                      rtpEvtCurrId,
                      rtpEvtSet ,                     --119
                      rtpEvtNum ,                     --18
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The special action script of the mentioned subsystem returned successfully." 
            ::= { hiQSnmFaultMgt 18 }

hiQSnmStartupSuccessTrap NOTIFICATION-TYPE
            OBJECTS { rtpEvtSequenceNumberIndex,
                      rtpEvtCurrId,
                      rtpEvtSet ,                     --119
                      rtpEvtNum ,                     --22
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The super node manager process started successfully. After successful start of
                        the subsystems, it continues to observe the RTP." 
            ::= { hiQSnmFaultMgt 22 }

hiQSnmStartupFailedTrap NOTIFICATION-TYPE
            OBJECTS { rtpEvtSequenceNumberIndex,
                      rtpEvtCurrId,
                      rtpEvtSet ,                     --119
                      rtpEvtNum ,                     --39
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The super node manager failed to start a single subsystem during the start of
                        the whole RTP. For this reason, the start of the RTP cannot be continued and all
                        subsystems that have been started so far are stopped." 
            ::= { hiQSnmFaultMgt 39 }

hiQSnmSubsysRestartSuccessTrap NOTIFICATION-TYPE
            OBJECTS { rtpEvtSequenceNumberIndex,
                      rtpEvtCurrId,
                      rtpEvtSet ,                     --119
                      rtpEvtNum ,                     --45
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The super node manager has tried to restart the subsystem without success in the
                        past, but now the subsystem is detected as running again." 
            ::= { hiQSnmFaultMgt 45 }

hiQSnmRtpNodeUpTrap NOTIFICATION-TYPE
            OBJECTS { rtpEvtSequenceNumberIndex,
                      rtpEvtCurrId,
                      rtpEvtSet ,                     --119
                      rtpEvtNum ,                     --100
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP node with the given ID is detected as UP when the super node manager is
                        starting." 
            ::= { hiQSnmFaultMgt 100 }

hiQSnmRtpNodeUpWasDownTrap NOTIFICATION-TYPE
            OBJECTS { rtpEvtSequenceNumberIndex,
                      rtpEvtCurrId,
                      rtpEvtSet ,                     --119
                      rtpEvtNum ,                     --101
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP node with the given ID changed its state from DOWN to UP." 
            ::= { hiQSnmFaultMgt 101 }

hiQSnmRtpNodeDownTrap NOTIFICATION-TYPE
            OBJECTS { rtpEvtSequenceNumberIndex,
                      rtpEvtCurrId,
                      rtpEvtSet ,                     --119
                      rtpEvtNum ,                     --102
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP node with the given ID is detected as DOWN when the super node manager
                        is starting." 
            ::= { hiQSnmFaultMgt 102 }

hiQSnmRtpNodeDownWasUpTrap NOTIFICATION-TYPE
            OBJECTS { rtpEvtSequenceNumberIndex,
                      rtpEvtCurrId,
                      rtpEvtSet ,                     --119
                      rtpEvtNum ,                     --103
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The RTP node with the given ID changed its state from UP to DOWN. This may be
                        the result of an administrative shutdown, but also of a node or communication failure." 
            ::= { hiQSnmFaultMgt 103 }

hiQSnmNodeInfoMismatchTrap NOTIFICATION-TYPE
            OBJECTS { rtpEvtSequenceNumberIndex,
                      rtpEvtCurrId,
                      rtpEvtSet ,                     --119
                      rtpEvtNum ,                     --109
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The super node manager detects a mismatch between the own node information (name
                        and ID)  listed in the RtpClustertab and the node information supplied by the cluster
                        software." 
            ::= { hiQSnmFaultMgt 109 }

hiQSolidUserConnected NOTIFICATION-TYPE
            OBJECTS { rtpEvtSequenceNumberIndex,
                      rtpEvtCurrId,
                      rtpEvtSet ,                     --141
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A user has connected from a remote control."
            ::= { hiQLogSolidFaultMgt 6 }

hiQSolidTooManyClientsTrap NOTIFICATION-TYPE
            OBJECTS { rtpEvtSequenceNumberIndex,
                      rtpEvtCurrId,
                      rtpEvtSet ,                     --141
                      rtpEvtNum ,                     --12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified user failed to connect due to too many connected clients" 
            ::= { hiQLogSolidFaultMgt 12 }

hiQSolidNewConnsAllowedTrap NOTIFICATION-TYPE
            OBJECTS { rtpEvtSequenceNumberIndex,
                      rtpEvtCurrId,
                      rtpEvtSet ,                     --141
                      rtpEvtNum ,                     --13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "New database connections are allowed." 
            ::= { hiQLogSolidFaultMgt 13 }

hiQSolidNoNewConnsAllowedTrap NOTIFICATION-TYPE
            OBJECTS { rtpEvtSequenceNumberIndex,
                      rtpEvtCurrId,
                      rtpEvtSet ,                     --141
                      rtpEvtNum ,                     --20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database server is in a fatal state - no new connections are allowed" 
            ::= { hiQLogSolidFaultMgt 20 }

hiQSolidShutdownTrap NOTIFICATION-TYPE
            OBJECTS { rtpEvtSequenceNumberIndex,
                      rtpEvtCurrId,
                      rtpEvtSet ,                     --141
                      rtpEvtNum ,                     --105
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database was shut down." 
            ::= { hiQLogSolidFaultMgt 105 }

hiQSolidServerStartFailedTrap NOTIFICATION-TYPE
            OBJECTS { rtpEvtSequenceNumberIndex,
                      rtpEvtCurrId,
                      rtpEvtSet ,                     --141
                      rtpEvtNum ,                     --120
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database failed to start." 
            ::= { hiQLogSolidFaultMgt 120 }

hiQSolidFlowEngineIntErrorTrap NOTIFICATION-TYPE
            OBJECTS { rtpEvtSequenceNumberIndex,
                      rtpEvtCurrId,
                      rtpEvtSet ,                     --141
                      rtpEvtNum ,                     --130
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid FlowEngine process has encountered an internal error and is unable to
                        continue normally." 
            ::= { hiQLogSolidFaultMgt 130 }

hiQSolidFatalErrSrvShutdownTrap NOTIFICATION-TYPE
            OBJECTS { rtpEvtSequenceNumberIndex,
                      rtpEvtCurrId,
                      rtpEvtSet ,                     --141
                      rtpEvtNum ,                     --149
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "An emergency shutdown of the Solid database server has occurred due to a fatal
                        error." 
            ::= { hiQLogSolidFaultMgt 149 }

hiQSolidFatalErrSrvNotStartTrap NOTIFICATION-TYPE
            OBJECTS { rtpEvtSequenceNumberIndex,
                      rtpEvtCurrId,
                      rtpEvtSet ,                     --141
                      rtpEvtNum ,                     --150
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database server was not started due to a fatal error." 
            ::= { hiQLogSolidFaultMgt 150 }

hiQSolidDatabaseStartedTrap NOTIFICATION-TYPE
            OBJECTS { rtpEvtSequenceNumberIndex,
                      rtpEvtCurrId,
                      rtpEvtSet ,                     --141
                      rtpEvtNum ,                     --151
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database was started." 
            ::= { hiQLogSolidFaultMgt 151 }

hiQSolidDbConvertedTrap NOTIFICATION-TYPE
            OBJECTS { rtpEvtSequenceNumberIndex,
                      rtpEvtCurrId,
                      rtpEvtSet ,                     --141
                      rtpEvtNum ,                     --201
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database was successfully converted." 
            ::= { hiQLogSolidFaultMgt 201 }

hiQSolidOldDbVersionTrap NOTIFICATION-TYPE
            OBJECTS { rtpEvtSequenceNumberIndex,
                      rtpEvtCurrId,
                      rtpEvtSet ,                     --141
                      rtpEvtNum ,                     --204
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database is from an older version of Solid." 
            ::= { hiQLogSolidFaultMgt 204 }

hiQSolidNewDbNotCreatedTrap NOTIFICATION-TYPE
            OBJECTS { rtpEvtSequenceNumberIndex,
                      rtpEvtCurrId,
                      rtpEvtSet ,                     --141
                      rtpEvtNum ,                     --205
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The new Solid database was not created." 
            ::= { hiQLogSolidFaultMgt 205 }

hiQSolidDbDoesNotExistsTrap NOTIFICATION-TYPE
            OBJECTS { rtpEvtSequenceNumberIndex,
                      rtpEvtCurrId,
                      rtpEvtSet ,                     --141
                      rtpEvtNum ,                     --206
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Can not create a new database,  because the server is not running as a
                        foreground process." 
            ::= { hiQLogSolidFaultMgt 206 }

hiQSolidDbOpenFailureTrap NOTIFICATION-TYPE
            OBJECTS { rtpEvtSequenceNumberIndex,
                      rtpEvtCurrId,
                      rtpEvtSet ,                     --141
                      rtpEvtNum ,                     --207
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database failed to open." 
            ::= { hiQLogSolidFaultMgt 207 }

hiQSolidDbIndexTestSuccessTrap NOTIFICATION-TYPE
            OBJECTS { rtpEvtSequenceNumberIndex,
                      rtpEvtCurrId,
                      rtpEvtSet ,                     --141
                      rtpEvtNum ,                     --224
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database index has been tested and is OK." 
            ::= { hiQLogSolidFaultMgt 224 }

hiQSolidDbIndexErrorTrap NOTIFICATION-TYPE
            OBJECTS { rtpEvtSequenceNumberIndex,
                      rtpEvtCurrId,
                      rtpEvtSet ,                     --141
                      rtpEvtNum ,                     --225
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The index for the specified Solid database is not OK." 
            ::= { hiQLogSolidFaultMgt 225 }

hiQSolidDbTstOpenFailureTrap NOTIFICATION-TYPE
            OBJECTS { rtpEvtSequenceNumberIndex,
                      rtpEvtCurrId,
                      rtpEvtSet ,                     --141
                      rtpEvtNum ,                     --226
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database failed to open for testing with a fatal error." 
            ::= { hiQLogSolidFaultMgt 226 }

hiQSolidDbTstConnectFailureTrap NOTIFICATION-TYPE
            OBJECTS { rtpEvtSequenceNumberIndex,
                      rtpEvtCurrId,
                      rtpEvtSet ,                     --141
                      rtpEvtNum ,                     --227
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database failed to connect for testing with a fatal error." 
            ::= { hiQLogSolidFaultMgt 227 }

hiQSolidCreateNewDbFailedTrap NOTIFICATION-TYPE
            OBJECTS { rtpEvtSequenceNumberIndex,
                      rtpEvtCurrId,
                      rtpEvtSet ,                     --141
                      rtpEvtNum ,                     --240
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A failure occurred when creating a new Solid database." 
            ::= { hiQLogSolidFaultMgt 240 }

hiQSolidTableConvertedTrap NOTIFICATION-TYPE
            OBJECTS { rtpEvtSequenceNumberIndex,
                      rtpEvtCurrId,
                      rtpEvtSet ,                     --141
                      rtpEvtNum ,                     --247
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified Solid database table was converted." 
            ::= { hiQLogSolidFaultMgt 247 }

hiQSolidDbOpeningProblemTrap NOTIFICATION-TYPE
            OBJECTS { rtpEvtSequenceNumberIndex,
                      rtpEvtCurrId,
                      rtpEvtSet ,                     --141
                      rtpEvtNum ,                     --249
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A problem was encountered when opening a Solid database." 
            ::= { hiQLogSolidFaultMgt 249 }

hiQSolidDbBrokenCopyTrap NOTIFICATION-TYPE
            OBJECTS { rtpEvtSequenceNumberIndex,
                      rtpEvtCurrId,
                      rtpEvtSet ,                     --141
                      rtpEvtNum ,                     --254
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database is a broken hot standby or netcopy database." 
            ::= { hiQLogSolidFaultMgt 254 }

hiQSolidBackupSuccessTrap NOTIFICATION-TYPE
            OBJECTS { rtpEvtSequenceNumberIndex,
                      rtpEvtCurrId,
                      rtpEvtSet ,                     --141
                      rtpEvtNum ,                     --300
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid backup competed successfully." 
            ::= { hiQLogSolidFaultMgt 300 }

hiQSolidBackupFailedTrap NOTIFICATION-TYPE
            OBJECTS { rtpEvtSequenceNumberIndex,
                      rtpEvtCurrId,
                      rtpEvtSet ,                     --141
                      rtpEvtNum ,                     --304
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid backup failed." 
            ::= { hiQLogSolidFaultMgt 304 }

hiQSolidStartedHSBPrimaryTrap NOTIFICATION-TYPE
            OBJECTS { rtpEvtSequenceNumberIndex,
                      rtpEvtCurrId,
                      rtpEvtSet ,                     --141
                      rtpEvtNum ,                     --500
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Started as a hot standby primary." 
            ::= { hiQLogSolidFaultMgt 500 }

hiQSolidStartedHSBSecondaryTrap NOTIFICATION-TYPE
            OBJECTS { rtpEvtSequenceNumberIndex,
                      rtpEvtCurrId,
                      rtpEvtSet ,                     --141
                      rtpEvtNum ,                     --501
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Started as a hot standby secondary." 
            ::= { hiQLogSolidFaultMgt 501 }

hiQSolidHSBSwitchPrimErrTrap NOTIFICATION-TYPE
            OBJECTS { rtpEvtSequenceNumberIndex,
                      rtpEvtCurrId,
                      rtpEvtSet ,                     --141
                      rtpEvtNum ,                     --512
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Failed to switch hot standby role to primary with the specified error." 
            ::= { hiQLogSolidFaultMgt 512 }

hiQSolidHSBSwitchSecErrTrap NOTIFICATION-TYPE
            OBJECTS { rtpEvtSequenceNumberIndex,
                      rtpEvtCurrId,
                      rtpEvtSet ,                     --141
                      rtpEvtNum ,                     --513
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Failed to switch hot standby roe to secondary with the specified error." 
            ::= { hiQLogSolidFaultMgt 513 }

hiQSolidBothHSBDbPrimaryTrap NOTIFICATION-TYPE
            OBJECTS { rtpEvtSequenceNumberIndex,
                      rtpEvtCurrId,
                      rtpEvtSet ,                     --141
                      rtpEvtNum ,                     --515
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Both Solid hot standby databases are marked as primary." 
            ::= { hiQLogSolidFaultMgt 515 }

hiQSolidDatabaseStarted2Trap NOTIFICATION-TYPE
            OBJECTS { rtpEvtSequenceNumberIndex,
                      rtpEvtCurrId,
                      rtpEvtSet ,                     --141
                      rtpEvtNum ,                     --572
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Solid database was started." 
            ::= { hiQLogSolidFaultMgt 572 }

hiQSolidDbServerCorruptTrap NOTIFICATION-TYPE
            OBJECTS { rtpEvtSequenceNumberIndex,
                      rtpEvtCurrId,
                      rtpEvtSet ,                     --141
                      rtpEvtNum ,                     --1101
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The single database server is corrupted." 
            ::= { hiQLogSolidFaultMgt 1101 }

hiQSolidLocalDbServerCorruptTrap NOTIFICATION-TYPE
            OBJECTS { rtpEvtSequenceNumberIndex,
                      rtpEvtCurrId,
                      rtpEvtSet ,                     --141
                      rtpEvtNum ,                     --1103
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The local database server failed, it is not possible to restart it, because the
                        database content is inconsistent." 
            ::= { hiQLogSolidFaultMgt 1103 }

hiQAucUscServerTxCdrTrap NOTIFICATION-TYPE
            OBJECTS { rtpEvtSequenceNumberIndex,
                      rtpEvtCurrId,
                      rtpEvtSet ,                     --182
                      rtpEvtNum ,                     --15
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Usage Collection server failed to send CDR file to FTP site" 
            ::= { hiQAucUscFaultMgmt 15 }

hiQAucUscPriStorNotPossibleTrap NOTIFICATION-TYPE
            OBJECTS { rtpEvtSequenceNumberIndex,
                      rtpEvtCurrId,
                      rtpEvtSet ,                     --182
                      rtpEvtNum ,                     --35
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Primary storage of CDR billing data is no longer possible on this node. This may
                        be caused by lack of disk space or the cdr disk partition is not writable." 
            ::= { hiQAucUscFaultMgmt 35 }

hiQAucUscPriStorOKTrap NOTIFICATION-TYPE
            OBJECTS { rtpEvtSequenceNumberIndex,
                      rtpEvtCurrId,
                      rtpEvtSet ,                     --182
                      rtpEvtNum ,                     --36
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Primary storage of CDR billing data is possible on this node." 
            ::= { hiQAucUscFaultMgmt 36 }

hiQAucUscSecStorNotPossibleTrap NOTIFICATION-TYPE
            OBJECTS { rtpEvtSequenceNumberIndex,
                      rtpEvtCurrId,
                      rtpEvtSet ,                     --182
                      rtpEvtNum ,                     --37
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Secondary storage of CDR billing data is no longer possible on this node. This
                        may be caused by lack of disk space or the cdr disk partition is not writable." 
            ::= { hiQAucUscFaultMgmt 37 }

hiQAucUscFileSeqNumberErrorTrap NOTIFICATION-TYPE
            OBJECTS { rtpEvtSequenceNumberIndex,
                      rtpEvtCurrId,
                      rtpEvtSet ,                     --182
                      rtpEvtNum ,                     --38
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The CDR file sequence number may be incorrect. This is caused by a database read
                        or write error." 
            ::= { hiQAucUscFaultMgmt 38 }

hiQAucUscLocalSecStorageOk NOTIFICATION-TYPE
            OBJECTS { rtpEvtSequenceNumberIndex,
                      rtpEvtCurrId,
                      rtpEvtSet ,                     --182
                      rtpEvtNum ,                     --39
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Secondary storage of CDR billing data is OK on this node." 
            ::= { hiQAucUscFaultMgmt 39 }

hiQOvlCongLevelToCL3Trap NOTIFICATION-TYPE
            OBJECTS { rtpEvtSequenceNumberIndex,
                      rtpEvtCurrId,
                      rtpEvtSet ,                     --190
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The congestion level has changed to congestion level 3.  This indicates a severe
                        CPU overload situation in the node and may severely degrade performance of the OSV.
                        The previous congestion level is indicated in the text." 
            ::= { hiQOvlFaultMgmt 2 }

hiQOvlCongLevelToCL2Trap NOTIFICATION-TYPE
            OBJECTS { rtpEvtSequenceNumberIndex,
                      rtpEvtCurrId,
                      rtpEvtSet ,                     --190
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The congestion level has changed to congestion level 2.  This indicates a major
                        CPU overload situation in the node and may severely degrade performance of the OSV.
                        The previous congestion level is indicated in the text." 
            ::= { hiQOvlFaultMgmt 3 }

hiQOvlCongLevelToCL1Trap NOTIFICATION-TYPE
            OBJECTS { rtpEvtSequenceNumberIndex,
                      rtpEvtCurrId,
                      rtpEvtSet ,                     --190
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The congestion level has changed to congestion level 1.  This indicates a minor
                        CPU overload situation in the node and may severely degrade performance of the OSV.
                        The previous congestion level is indicated in the text." 
            ::= { hiQOvlFaultMgmt 4 }

hiQOvlCongLevelToCL0Trap NOTIFICATION-TYPE
            OBJECTS { rtpEvtSequenceNumberIndex,
                      rtpEvtCurrId,
                      rtpEvtSet ,                     --190
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The CPU overload condition no longer exists. The previous congestion level is
                        indicated in the text." 
            ::= { hiQOvlFaultMgmt 5 }

hiQOvlCongLevelChangeTrap NOTIFICATION-TYPE
            OBJECTS { rtpEvtSequenceNumberIndex,
                      rtpEvtCurrId,
                      rtpEvtSet ,                     --190
                      rtpEvtNum ,                     --10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The CPU congestion level has changed.  This event will clear the previous CPU
                        congestion level alarm prior to reporting the new level." 
            ::= { hiQOvlFaultMgmt 10 }

hiQUCEServicesRegistrationFailedTrap NOTIFICATION-TYPE
            OBJECTS { rtpEvtSequenceNumberIndex,
                      rtpEvtCurrId,
                      rtpEvtSet ,                     --193
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report that UCE services failed registration" 
            ::= { hiQUCEServicesFaultMgmt 2 }

hiQUCEServicesRegisteringTrap NOTIFICATION-TYPE
            OBJECTS { rtpEvtSequenceNumberIndex,
                      rtpEvtCurrId,
                      rtpEvtSet ,                     --193
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Start of UCE services registering." 
            ::= { hiQUCEServicesFaultMgmt 5 }

hiQSubMgmtRemoveResourceError NOTIFICATION-TYPE
            OBJECTS { rtpEvtSequenceNumberIndex,
                      rtpEvtCurrId,
                      rtpEvtSet ,                     --207
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The job to remove resources failed" 
            ::= { hiQSoapServerFaultMgmt 5 }

hiQSubMgmtRemoveResourceSuccess NOTIFICATION-TYPE
            OBJECTS { rtpEvtSequenceNumberIndex,
                      rtpEvtCurrId,
                      rtpEvtSet ,                     --207
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The job to remove resources completed successfully" 
            ::= { hiQSoapServerFaultMgmt 6 }

hiQSmdiREcvIPAddrPortError NOTIFICATION-TYPE
            OBJECTS { rtpEvtSequenceNumberIndex,
                      rtpEvtCurrId,
                      rtpEvtSet ,                     --208
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Cannot listen on SMDI virtual IP address/port needed to receive SMDI messages
                        from a Voice Message System over a TCP link." 
            ::= { hiQSmdiFaultMgmt 7 }

hiQSmdiRecvIPAddrPortOk NOTIFICATION-TYPE
            OBJECTS { rtpEvtSequenceNumberIndex,
                      rtpEvtCurrId,
                      rtpEvtSet ,                     --208
                      rtpEvtNum ,                     --8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Can listen on SMDI virtual IP address/port needed to receive SMDI messages from
                        a Voice Message System over a TCP link." 
            ::= { hiQSmdiFaultMgmt 8 }

-- ***************************************************************************************************
-- Start of hiQDatabaseSizeMgmt
-- ***************************************************************************************************

hiQDatabaseSizeOK NOTIFICATION-TYPE
            OBJECTS { rtpEvtSequenceNumberIndex,
                      rtpEvtCurrId,
                      rtpEvtSet ,                     --215
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION "The reported database size is within the limits."
            ::= { hiQDatabaseSizeMgmt 1 }

hiQDatabaseSizeHigh NOTIFICATION-TYPE
            OBJECTS { rtpEvtSequenceNumberIndex,
                      rtpEvtCurrId,
                      rtpEvtSet ,                     --215
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION "The database is more than half full. A database re-organization is recommended"
            ::= { hiQDatabaseSizeMgmt 2 }

hiQDatabaseSizeTooHigh NOTIFICATION-TYPE
            OBJECTS { rtpEvtSequenceNumberIndex,
                      rtpEvtCurrId,
                      rtpEvtSet ,                     --215
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION "The database is too full.A database re-organization is necessary 
	                 to avoid future service impacts.
	                 If this is not possible contact the next level of customer service"
            ::= { hiQDatabaseSizeMgmt 4 }
	    
hiQDatabaseFull NOTIFICATION-TYPE
            OBJECTS { rtpEvtSequenceNumberIndex,
                      rtpEvtCurrId,
                      rtpEvtSet ,                     --215
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION "The database is full. Callprocessing and provisioning may be impacted. 
	                 Contact next level of customer support."
            ::= { hiQDatabaseSizeMgmt 5 }

hiQTcaL3CommunicationTrap NOTIFICATION-TYPE
            OBJECTS { rtpEvtSequenceNumberIndex,
                      rtpEvtCurrId,
                      rtpEvtSet ,                     --216
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): END_POINT_OOS . endpoint is out of service or not
                        responding,COM_EXT_PROTOCOL_ERR . internal communications and other
                        errors,COM_EXT_TIME_OUT . external communications . response
                        timeout,COM_EXT_BAD_SYNTAX . external  communications . bad message
                        syntax,COM_EXT_RESP_ERR_RX . external communications . bad message
                        syntax,COM_INT_BAD_SYNTAX . internal communications . bad syntax,COM_INT_PROTOCOL_ERR
                        - internal communications . other errors,COM_INT_TIME_OUT - internal communications .
                        response timeout,END_POINT_INVALID . endpoint is not known to the OSV,DNS_UNAVAILABLE
                        . DNS is unavailable,RSIP_RX . MGCP RSIP received,LOG_FAILURE . failure to log
                        security event,RES_MGMT_COMM_ERR . Resource Manager communication error,LINK_ERR .
                        CSTA link connection status" 
            ::= { hiQTcaFaultMgt 1 }

hiQTcaL2CommunicationTrap NOTIFICATION-TYPE
            OBJECTS { rtpEvtSequenceNumberIndex,
                      rtpEvtCurrId,
                      rtpEvtSet ,                     --216
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): END_POINT_OOS . endpoint is out of service or not
                        responding,COM_EXT_PROTOCOL_ERR . internal communications and other
                        errors,COM_EXT_TIME_OUT . external communications . response
                        timeout,COM_EXT_BAD_SYNTAX . external  communications . bad message
                        syntax,COM_EXT_RESP_ERR_RX . external communications . bad message
                        syntax,COM_INT_BAD_SYNTAX . internal communications . bad syntax,COM_INT_PROTOCOL_ERR
                        - internal communications . other errors,COM_INT_TIME_OUT - internal communications .
                        response timeout,END_POINT_INVALID . endpoint is not known to the OSV,DNS_UNAVAILABLE
                        . DNS is unavailable,RSIP_RX . MGCP RSIP received,LOG_FAILURE . failure to log
                        security event,RES_MGMT_COMM_ERR . Resource Manager communication error,LINK_ERR .
                        CSTA link connection status" 
            ::= { hiQTcaFaultMgt 2 }

hiQTcaL1CommunicationTrap NOTIFICATION-TYPE
            OBJECTS { rtpEvtSequenceNumberIndex,
                      rtpEvtCurrId,
                      rtpEvtSet ,                     --216
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): END_POINT_OOS . endpoint is out of service or not
                        responding,COM_EXT_PROTOCOL_ERR . internal communications and other
                        errors,COM_EXT_TIME_OUT . external communications . response
                        timeout,COM_EXT_BAD_SYNTAX . external  communications . bad message
                        syntax,COM_EXT_RESP_ERR_RX . external communications . bad message
                        syntax,COM_INT_BAD_SYNTAX . internal communications . bad syntax,COM_INT_PROTOCOL_ERR
                        - internal communications . other errors,COM_INT_TIME_OUT - internal communications .
                        response timeout,END_POINT_INVALID . endpoint is not known to the OSV,DNS_UNAVAILABLE
                        . DNS is unavailable,RSIP_RX . MGCP RSIP received,LOG_FAILURE . failure to log
                        security event,RES_MGMT_COMM_ERR . Resource Manager communication error,LINK_ERR .
                        CSTA link connection status" 
            ::= { hiQTcaFaultMgt 3 }

hiQTcaL3ServiceTrap NOTIFICATION-TYPE
            OBJECTS { rtpEvtSequenceNumberIndex,
                      rtpEvtCurrId,
                      rtpEvtSet ,                     --216
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 4 }

hiQTcaL2ServiceTrap NOTIFICATION-TYPE
            OBJECTS { rtpEvtSequenceNumberIndex,
                      rtpEvtCurrId,
                      rtpEvtSet ,                     --216
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 5 }

hiQTcaL1ServiceTrap NOTIFICATION-TYPE
            OBJECTS { rtpEvtSequenceNumberIndex,
                      rtpEvtCurrId,
                      rtpEvtSet ,                     --216
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 6 }

hiQTcaL3ProcessingTrap NOTIFICATION-TYPE
            OBJECTS { rtpEvtSequenceNumberIndex,
                      rtpEvtCurrId,
                      rtpEvtSet ,                     --216
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): API_ERR . errors returned from a non-RTP API call,RTP_API_ERR . errors
                        returned from RTP API calls,CALL_PROC_ERR . general processing
                        errors,CLUSTER_COM_PROBLEM . inter-cluster communication problems,END_POINT_EXPIRED .
                        endpoint expired,OVERLOAD . transactions rejected due to overload,RESOURCE_LIMIT .
                        resource limit reached,SRVR_OR_GW_OVERLOAD . server or gateway overload,MAINTENANCE .
                        maintenance related,SW_ERR . software errors,PROC_INIT_FAILURE . process
                        initialization failure,PROC_EXIT . process exit due to failure,VIP_SUBSCRIBER_PROBLEM
                        . VIP subscriber problems" 
            ::= { hiQTcaFaultMgt 7 }

hiQTcaL2ProcessingTrap NOTIFICATION-TYPE
            OBJECTS { rtpEvtSequenceNumberIndex,
                      rtpEvtCurrId,
                      rtpEvtSet ,                     --216
                      rtpEvtNum ,                     --8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): API_ERR . errors returned from a non-RTP API call,RTP_API_ERR . errors
                        returned from RTP API calls,CALL_PROC_ERR . general processing
                        errors,CLUSTER_COM_PROBLEM . inter-cluster communication problems,END_POINT_EXPIRED .
                        endpoint expired,OVERLOAD . transactions rejected due to overload,RESOURCE_LIMIT .
                        resource limit reached,SRVR_OR_GW_OVERLOAD . server or gateway overload,MAINTENANCE .
                        maintenance related,SW_ERR . software errors,PROC_INIT_FAILURE . process
                        initialization failure,PROC_EXIT . process exit due to failure,VIP_SUBSCRIBER_PROBLEM
                        . VIP subscriber problems" 
            ::= { hiQTcaFaultMgt 8 }

hiQTcaL1ProcessingTrap NOTIFICATION-TYPE
            OBJECTS { rtpEvtSequenceNumberIndex,
                      rtpEvtCurrId,
                      rtpEvtSet ,                     --216
                      rtpEvtNum ,                     --9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): API_ERR . errors returned from a non-RTP API call,RTP_API_ERR . errors
                        returned from RTP API calls,CALL_PROC_ERR . general processing
                        errors,CLUSTER_COM_PROBLEM . inter-cluster communication problems,END_POINT_EXPIRED .
                        endpoint expired,OVERLOAD . transactions rejected due to overload,RESOURCE_LIMIT .
                        resource limit reached,SRVR_OR_GW_OVERLOAD . server or gateway overload,MAINTENANCE .
                        maintenance related,SW_ERR . software errors,PROC_INIT_FAILURE . process
                        initialization failure,PROC_EXIT . process exit due to failure,VIP_SUBSCRIBER_PROBLEM
                        . VIP subscriber problems" 
            ::= { hiQTcaFaultMgt 9 }

hiQTcaL3EquipmentTrap NOTIFICATION-TYPE
            OBJECTS { rtpEvtSequenceNumberIndex,
                      rtpEvtCurrId,
                      rtpEvtSet ,                     --216
                      rtpEvtNum ,                     --10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 10 }

hiQTcaL2EquipmentTrap NOTIFICATION-TYPE
            OBJECTS { rtpEvtSequenceNumberIndex,
                      rtpEvtCurrId,
                      rtpEvtSet ,                     --216
                      rtpEvtNum ,                     --11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 11 }

hiQTcaL1EquipmentTrap NOTIFICATION-TYPE
            OBJECTS { rtpEvtSequenceNumberIndex,
                      rtpEvtCurrId,
                      rtpEvtSet ,                     --216
                      rtpEvtNum ,                     --12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 12 }

hiQTcaL3EnvironmentTrap NOTIFICATION-TYPE
            OBJECTS { rtpEvtSequenceNumberIndex,
                      rtpEvtCurrId,
                      rtpEvtSet ,                     --216
                      rtpEvtNum ,                     --13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 13 }

hiQTcaL2EnvironmentTrap NOTIFICATION-TYPE
            OBJECTS { rtpEvtSequenceNumberIndex,
                      rtpEvtCurrId,
                      rtpEvtSet ,                     --216
                      rtpEvtNum ,                     --14
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 14 }

hiQTcaL1EnvironmentTrap NOTIFICATION-TYPE
            OBJECTS { rtpEvtSequenceNumberIndex,
                      rtpEvtCurrId,
                      rtpEvtSet ,                     --216
                      rtpEvtNum ,                     --15
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 15 }

hiQTcaL3DatabaseTrap NOTIFICATION-TYPE
            OBJECTS { rtpEvtSequenceNumberIndex,
                      rtpEvtCurrId,
                      rtpEvtSet ,                     --216
                      rtpEvtNum ,                     --16
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): AUDIT_ERR . audit errors,DATABASE_CON_ERR . database connection
                        errors,DATABASE_SQL_ERR . database SQL errors,DATABASE_ERR . general database
                        errors,DATA_ERR . data problems, e.g.: consistency checks,PROVISIONING_ERR .
                        provisioning errors,SUB_PROVISIONING_ERR . subscriber provisioning errors" 
            ::= { hiQTcaFaultMgt 16 }

hiQTcaL2DatabaseTrap NOTIFICATION-TYPE
            OBJECTS { rtpEvtSequenceNumberIndex,
                      rtpEvtCurrId,
                      rtpEvtSet ,                     --216
                      rtpEvtNum ,                     --17
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): AUDIT_ERR . audit errors,DATABASE_CON_ERR . database connection
                        errors,DATABASE_SQL_ERR . database SQL errors,DATABASE_ERR . general database
                        errors,DATA_ERR . data problems, e.g.: consistency checks,PROVISIONING_ERR .
                        provisioning errors,SUB_PROVISIONING_ERR . subscriber provisioning errors" 
            ::= { hiQTcaFaultMgt 17 }

hiQTcaL1DatabaseTrap NOTIFICATION-TYPE
            OBJECTS { rtpEvtSequenceNumberIndex,
                      rtpEvtCurrId,
                      rtpEvtSet ,                     --216
                      rtpEvtNum ,                     --18
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): AUDIT_ERR . audit errors,DATABASE_CON_ERR . database connection
                        errors,DATABASE_SQL_ERR . database SQL errors,DATABASE_ERR . general database
                        errors,DATA_ERR . data problems, e.g.: consistency checks,PROVISIONING_ERR .
                        provisioning errors,SUB_PROVISIONING_ERR . subscriber provisioning errors" 
            ::= { hiQTcaFaultMgt 18 }

hiQTcaL3MibTrap NOTIFICATION-TYPE
            OBJECTS { rtpEvtSequenceNumberIndex,
                      rtpEvtCurrId,
                      rtpEvtSet ,                     --216
                      rtpEvtNum ,                     --19
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 19 }

hiQTcaL2MibTrap NOTIFICATION-TYPE
            OBJECTS { rtpEvtSequenceNumberIndex,
                      rtpEvtCurrId,
                      rtpEvtSet ,                     --216
                      rtpEvtNum ,                     --20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 20 }

hiQTcaL1MibTrap NOTIFICATION-TYPE
            OBJECTS { rtpEvtSequenceNumberIndex,
                      rtpEvtCurrId,
                      rtpEvtSet ,                     --216
                      rtpEvtNum ,                     --21
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 21 }

hiQTcaL3SecurityTrap NOTIFICATION-TYPE
            OBJECTS { rtpEvtSequenceNumberIndex,
                      rtpEvtCurrId,
                      rtpEvtSet ,                     --216
                      rtpEvtNum ,                     --25
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        is reported for log category: OP_LOG_CAT_IPSEC_ERR . IP security" 
            ::= { hiQTcaFaultMgt 25 }

hiQTcaL2SecurityTrap NOTIFICATION-TYPE
            OBJECTS { rtpEvtSequenceNumberIndex,
                      rtpEvtCurrId,
                      rtpEvtSet ,                     --216
                      rtpEvtNum ,                     --26
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        is reported for log category: OP_LOG_CAT_IPSEC_ERR . IP security" 
            ::= { hiQTcaFaultMgt 26 }

hiQTcaL1SecurityTrap NOTIFICATION-TYPE
            OBJECTS { rtpEvtSequenceNumberIndex,
                      rtpEvtCurrId,
                      rtpEvtSet ,                     --216
                      rtpEvtNum ,                     --27
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        is reported for log category: OP_LOG_CAT_IPSEC_ERR . IP security" 
            ::= { hiQTcaFaultMgt 27 }

hiQTcaL3IndicationTrap NOTIFICATION-TYPE
            OBJECTS { rtpEvtSequenceNumberIndex,
                      rtpEvtCurrId,
                      rtpEvtSet ,                     --216
                      rtpEvtNum ,                     --31
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 31 }

hiQTcaL2IndicationTrap NOTIFICATION-TYPE
            OBJECTS { rtpEvtSequenceNumberIndex,
                      rtpEvtCurrId,
                      rtpEvtSet ,                     --216
                      rtpEvtNum ,                     --32
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 32 }

hiQTcaL1IndicationTrap NOTIFICATION-TYPE
            OBJECTS { rtpEvtSequenceNumberIndex,
                      rtpEvtCurrId,
                      rtpEvtSet ,                     --216
                      rtpEvtNum ,                     --33
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 33 }

hiQTcaL4CommunicationTrap NOTIFICATION-TYPE
            OBJECTS { rtpEvtSequenceNumberIndex,
                      rtpEvtCurrId,
                      rtpEvtSet ,                     --216
                      rtpEvtNum ,                     --34
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): END_POINT_OOS . endpoint is out of service or not
                        responding,COM_EXT_PROTOCOL_ERR . internal communications and other
                        errors,COM_EXT_TIME_OUT . external communications . response
                        timeout,COM_EXT_BAD_SYNTAX . external  communications . bad message
                        syntax,COM_EXT_RESP_ERR_RX . external communications . bad message
                        syntax,COM_INT_BAD_SYNTAX . internal communications . bad syntax,COM_INT_PROTOCOL_ERR
                        - internal communications . other errors,COM_INT_TIME_OUT - internal communications .
                        response timeout,END_POINT_INVALID . endpoint is not known to the OSV,DNS_UNAVAILABLE
                        . DNS is unavailable,RSIP_RX . MGCP RSIP received,LOG_FAILURE . failure to log
                        security event,RES_MGMT_COMM_ERR . Resource Manager communication error,LINK_ERR .
                        CSTA link connection status" 
            ::= { hiQTcaFaultMgt 34 }

hiQTcaL4ServiceTrap NOTIFICATION-TYPE
            OBJECTS { rtpEvtSequenceNumberIndex,
                      rtpEvtCurrId,
                      rtpEvtSet ,                     --216
                      rtpEvtNum ,                     --35
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the hiQ logging feature. The alarm
                        can be cleared manually or, if configured accordingly, it will clear automatically
                        after a certain time period without threshold crossing event." 
            ::= { hiQTcaFaultMgt 35 }

hiQTcaL4ProcessingTrap NOTIFICATION-TYPE
            OBJECTS { rtpEvtSequenceNumberIndex,
                      rtpEvtCurrId,
                      rtpEvtSet ,                     --216
                      rtpEvtNum ,                     --36
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): API_ERR . errors returned from a non-RTP API call,RTP_API_ERR . errors
                        returned from RTP API calls,CALL_PROC_ERR . general processing
                        errors,CLUSTER_COM_PROBLEM . inter-cluster communication problems,END_POINT_EXPIRED .
                        endpoint expired,OVERLOAD . transactions rejected due to overload,RESOURCE_LIMIT .
                        resource limit reached,SRVR_OR_GW_OVERLOAD . server or gateway overload,MAINTENANCE .
                        maintenance related,SW_ERR . software errors,PROC_INIT_FAILURE . process
                        initialization failure,PROC_EXIT . process exit due to failure,VIP_SUBSCRIBER_PROBLEM
                        . VIP subscriber problems" 
            ::= { hiQTcaFaultMgt 36 }

hiQTcaL4EquipmentTrap NOTIFICATION-TYPE
            OBJECTS { rtpEvtSequenceNumberIndex,
                      rtpEvtCurrId,
                      rtpEvtSet ,                     --216
                      rtpEvtNum ,                     --37
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 37 }

hiQTcaL4EnvironmentTrap NOTIFICATION-TYPE
            OBJECTS { rtpEvtSequenceNumberIndex,
                      rtpEvtCurrId,
                      rtpEvtSet ,                     --216
                      rtpEvtNum ,                     --38
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 38 }

hiQTcaL4DatabaseTrap NOTIFICATION-TYPE
            OBJECTS { rtpEvtSequenceNumberIndex,
                      rtpEvtCurrId,
                      rtpEvtSet ,                     --216
                      rtpEvtNum ,                     --39
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        can be reported for any of the following log categories (categories are prefixed with
                        OP_LOG_CAT_): AUDIT_ERR . audit errors,DATABASE_CON_ERR . database connection
                        errors,DATABASE_SQL_ERR . database SQL errors,DATABASE_ERR . general database
                        errors,DATA_ERR . data problems, e.g.: consistency checks,PROVISIONING_ERR .
                        provisioning errors,SUB_PROVISIONING_ERR . subscriber provisioning errors" 
            ::= { hiQTcaFaultMgt 39 }

hiQTcaL4MibTrap NOTIFICATION-TYPE
            OBJECTS { rtpEvtSequenceNumberIndex,
                      rtpEvtCurrId,
                      rtpEvtSet ,                     --216
                      rtpEvtNum ,                     --40
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 40 }

hiQTcaL4SecurityTrap NOTIFICATION-TYPE
            OBJECTS { rtpEvtSequenceNumberIndex,
                      rtpEvtCurrId,
                      rtpEvtSet ,                     --216
                      rtpEvtNum ,                     --41
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. This alarm
                        is reported for log category: OP_LOG_CAT_IPSEC_ERR . IP security" 
            ::= { hiQTcaFaultMgt 41 }

hiQTcaL4IndicationTrap NOTIFICATION-TYPE
            OBJECTS { rtpEvtSequenceNumberIndex,
                      rtpEvtCurrId,
                      rtpEvtSet ,                     --216
                      rtpEvtNum ,                     --42
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has crossed the high
                        threshold of logs per time interval as defined by the OSV logging feature. Currently
                        no alarm category is configured to generate this event/alarm." 
            ::= { hiQTcaFaultMgt 42 }

hiQTcaClearedTrap NOTIFICATION-TYPE
            OBJECTS { rtpEvtSequenceNumberIndex,
                      rtpEvtCurrId,
                      rtpEvtSet ,                     --216
                      rtpEvtNum ,                     --100
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of logged entries for the specified log category has not crossed the
                        threshold that caused a previous alarm for a certain period of time." 
            ::= { hiQTcaFaultMgt 100 }

hiQGlobalCriticalLossOfCommsTrap NOTIFICATION-TYPE
            OBJECTS { rtpEvtSequenceNumberIndex,
                      rtpEvtCurrId,
                      rtpEvtSet ,                     --217
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report a critical loss of communication
                        alarm.Communication alarms are reported for example for:Survival Authority . A failure
                        to communicate with the Survival Authority.Maintenance Controllers (RSA, IMM, iRMC) .
                        This communication failure can cause a failure to remove the partner node from service
                        in the event of a partner node failure, creating the potential for a split-brain
                        scenario where both nodes are independently active and writing to the database.RSH . A
                        background test of SSH connectivity between two nodes of a cluster has failed, causing
                        reduced maintenance functionality.ENUM . A failure to communicate with the ENUM server
                        has occurred and could cause reduced call processing functionality.GUT_MEDIA_SERVER .
                        The media server is operationally blocked.XDM:SIP Endpoint . A proxy failed to respond
                        to a SIP Invite and subsequent audit, resulting in call processing failures to and
                        from that proxy.Billing Server . A communication failure has occurred between the OSV
                        and one or more billing servers.  This can cause a loss of billing (call detail
                        recording) records.Router - A linkDown SNMP trap was received for a tunnel.  The IP
                        address of the router is specified in the faultyObject." 
            ::= { hiQGlobalFaultMgt 1 }

hiQGlobalMajorLossOfCommsTrap NOTIFICATION-TYPE
            OBJECTS { rtpEvtSequenceNumberIndex,
                      rtpEvtCurrId,
                      rtpEvtSet ,                     --217
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report a major loss of communication alarm. Communication
                        alarms are reported for example for:Survival Authority . A failure to communicate with
                        the Survival Authority.Maintenance Controllers (RSA, IMM, iRMC) . This communication
                        failure can cause a failure to remove the partner node from service in the event of a
                        partner node failure, creating the potential for a split-brain scenario where both
                        nodes are independently active and writing to the database.RSH . A background test of
                        SSH connectivity between two nodes of a cluster has failed, causing reduced
                        maintenance functionality.ENUM . A failure to communicate with the ENUM server has
                        occurred and could cause reduced call processing functionality.GUT_MEDIA_SERVER . The
                        media server is operationally blocked.XDM:SIP Endpoint . A proxy failed to respond to
                        a SIP Invite and subsequent audit, resulting in call processing failures to and from
                        that proxy.Billing Server . A communication failure has occurred between the OSV and
                        one or more billing servers.  This can cause a loss of billing (call detail recording)
                        records.Router - A linkDown SNMP trap was received for a tunnel.  The IP address of
                        the router is specified in the faultyObject." 
            ::= { hiQGlobalFaultMgt 2 }

hiQGlobalMinorLossOfCommsTrap NOTIFICATION-TYPE
            OBJECTS { rtpEvtSequenceNumberIndex,
                      rtpEvtCurrId,
                      rtpEvtSet ,                     --217
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report a minor loss of communication alarm. Communication
                        alarms are reported for example for:Survival Authority . A failure to communicate with
                        the Survival Authority.Maintenance Controllers (RSA, IMM, iRMC) . This communication
                        failure can cause a failure to remove the partner node from service in the event of a
                        partner node failure, creating the potential for a split-brain scenario where both
                        nodes are independently active and writing to the database.RSH . A background test of
                        SSH connectivity between two nodes of a cluster has failed, causing reduced
                        maintenance functionality.ENUM . A failure to communicate with the ENUM server has
                        occurred and could cause reduced call processing functionality.GUT_MEDIA_SERVER . The
                        media server is operationally blocked.XDM:SIP Endpoint . A proxy failed to respond to
                        a SIP Invite and subsequent audit, resulting in call processing failures to and from
                        that proxy.Billing Server . A communication failure has occurred between the OSV and
                        one or more billing servers.  This can cause a loss of billing (call detail recording)
                        records.Router - A linkDown SNMP trap was received for a tunnel.  The IP address of
                        the router is specified in the faultyObject." 
            ::= { hiQGlobalFaultMgt 3 }

hiQGlobalCommsEstablishedTrap NOTIFICATION-TYPE
            OBJECTS { rtpEvtSequenceNumberIndex,
                      rtpEvtCurrId,
                      rtpEvtSet ,                     --217
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report that communication with the element specified in
                        the faultyObject has been established." 
            ::= { hiQGlobalFaultMgt 4 }

hiQGlobalProcessInitActiveTrap NOTIFICATION-TYPE
            OBJECTS { rtpEvtSequenceNumberIndex,
                      rtpEvtCurrId,
                      rtpEvtSet ,                     --217
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The process has started successfully." 
            ::= { hiQGlobalFaultMgt 5 }

hiQGlobalProcSevereInitFailTrap NOTIFICATION-TYPE
            OBJECTS { rtpEvtSequenceNumberIndex,
                      rtpEvtCurrId,
                      rtpEvtSet ,                     --217
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The process encountered an error during initialization failure and cannot
                        continue." 
            ::= { hiQGlobalFaultMgt 6 }

hiQGlobalProcPartialInitFailTrap NOTIFICATION-TYPE
            OBJECTS { rtpEvtSequenceNumberIndex,
                      rtpEvtCurrId,
                      rtpEvtSet ,                     --217
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The process encountered an error during initialization but not severe enough to
                        keep the process from running." 
            ::= { hiQGlobalFaultMgt 7 }

hiQGlobalProcAbnormalTermTrap NOTIFICATION-TYPE
            OBJECTS { rtpEvtSequenceNumberIndex,
                      rtpEvtCurrId,
                      rtpEvtSet ,                     --217
                      rtpEvtNum ,                     --8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The process exited due to an error condition." 
            ::= { hiQGlobalFaultMgt 8 }

hiQGlobalProcessAliasGrpAvail NOTIFICATION-TYPE
            OBJECTS { rtpEvtSequenceNumberIndex,
                      rtpEvtCurrId,
                      rtpEvtSet ,                     --217
                      rtpEvtNum ,                     --9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "At least one process servicing the RTP message queue for the given alias group
                        is now running." 
            ::= { hiQGlobalFaultMgt 9 }

hiQGlobalProcessAliasGrpUnavail NOTIFICATION-TYPE
            OBJECTS { rtpEvtSequenceNumberIndex,
                      rtpEvtCurrId,
                      rtpEvtSet ,                     --217
                      rtpEvtNum ,                     --10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "All members that service the RTP message queue for the given alias group are
                        unavailable." 
            ::= { hiQGlobalFaultMgt 10 }

hiQGlobalResourceExceedLimitTrap NOTIFICATION-TYPE
            OBJECTS { rtpEvtSequenceNumberIndex,
                      rtpEvtCurrId,
                      rtpEvtSet ,                     --217
                      rtpEvtNum ,                     --11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The resource specified in the faultyObject parameter of the alarm has exceeded a
                        defined limit.Possible faultyObject values include:RapidStat . RapidStat has run a
                        test and determined that an unexpected condition exists that should be investigated
                        and corrected." 
            ::= { hiQGlobalFaultMgt 11 }

hiQGlobalResourceWithinLimitTrap NOTIFICATION-TYPE
            OBJECTS { rtpEvtSequenceNumberIndex,
                      rtpEvtCurrId,
                      rtpEvtSet ,                     --217
                      rtpEvtNum ,                     --12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified resource usage is within the defined limit." 
            ::= { hiQGlobalFaultMgt 12 }

hiQVeryImportantFuncUnavailTrap NOTIFICATION-TYPE
            OBJECTS { rtpEvtSequenceNumberIndex,
                      rtpEvtCurrId,
                      rtpEvtSet ,                     --217
                      rtpEvtNum ,                     --13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The system function identified by the faulty object is not available.An alarm
                        with faultyObject = Function: Registration Audit/Timer is reported when the
                        registration audit cannot set a timer to periodically check for expired registrations." 
            ::= { hiQGlobalFaultMgt 13 }

hiQImportantFuncUnavailTrap NOTIFICATION-TYPE
            OBJECTS { rtpEvtSequenceNumberIndex,
                      rtpEvtCurrId,
                      rtpEvtSet ,                     --217
                      rtpEvtNum ,                     --14
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The system function identified by the faulty object is not available." 
            ::= { hiQGlobalFaultMgt 14 }

hiQGlobalFuncUnavailTrap NOTIFICATION-TYPE
            OBJECTS { rtpEvtSequenceNumberIndex,
                      rtpEvtCurrId,
                      rtpEvtSet ,                     --217
                      rtpEvtNum ,                     --15
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The system function identified by the faulty object is not available." 
            ::= { hiQGlobalFaultMgt 15 }

hiQGlobalFuncAvailTrap NOTIFICATION-TYPE
            OBJECTS { rtpEvtSequenceNumberIndex,
                      rtpEvtCurrId,
                      rtpEvtSet ,                     --217
                      rtpEvtNum ,                     --16
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The system function identified in the faulty object is available." 
            ::= { hiQGlobalFaultMgt 16 }

hiQGlobalMsgQueueAboveHighThld NOTIFICATION-TYPE
            OBJECTS { rtpEvtSequenceNumberIndex,
                      rtpEvtCurrId,
                      rtpEvtSet ,                     --217
                      rtpEvtNum ,                     --17
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of elements in the specified queue has exceeded a defined threshold
                        limit.The Internal Resource Manager will report this alarm if the internal message
                        queue exceeds a predefined limit." 
            ::= { hiQGlobalFaultMgt 17 }

hiQGlobalMsgQueueAboveMedThld NOTIFICATION-TYPE
            OBJECTS { rtpEvtSequenceNumberIndex,
                      rtpEvtCurrId,
                      rtpEvtSet ,                     --217
                      rtpEvtNum ,                     --18
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of elements in the specified queue has exceeded a defined threshold
                        limit.The Internal Resource Manager will report this alarm if the internal message
                        queue exceeds a predefined limit." 
            ::= { hiQGlobalFaultMgt 18 }

hiQGlobalMsgQueueAboveLowThld NOTIFICATION-TYPE
            OBJECTS { rtpEvtSequenceNumberIndex,
                      rtpEvtCurrId,
                      rtpEvtSet ,                     --217
                      rtpEvtNum ,                     --19
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of elements in the specified queue has exceeded a defined threshold
                        limit.The Internal Resource Manager will report this alarm if the internal message
                        queue exceeds a predefined limit." 
            ::= { hiQGlobalFaultMgt 19 }

hiQGlobalMsgQueueBelowThld NOTIFICATION-TYPE
            OBJECTS { rtpEvtSequenceNumberIndex,
                      rtpEvtCurrId,
                      rtpEvtSet ,                     --217
                      rtpEvtNum ,                     --20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of elements in the specified queue is below the defined threshold
                        limit." 
            ::= { hiQGlobalFaultMgt 20 }

hiQGlobalVerySevereDegradedCommsTrap NOTIFICATION-TYPE
            OBJECTS { rtpEvtSequenceNumberIndex,
                      rtpEvtCurrId,
                      rtpEvtSet ,                     --217
                      rtpEvtNum ,                     --21
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified communication link is either congested or operating in a degraded
                        state.If this alarm is reported with a faultyObject containing CAC Group, backup
                        routing policy has been activated for the specified CAC group." 
            ::= { hiQGlobalFaultMgt 21 }

hiQGlobalSevereDegradedCommsTrap NOTIFICATION-TYPE
            OBJECTS { rtpEvtSequenceNumberIndex,
                      rtpEvtCurrId,
                      rtpEvtSet ,                     --217
                      rtpEvtNum ,                     --22
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified communication link is either congested or operating in a degraded
                        state.If this alarm is reported with a faultyObject containing CAC Group, backup
                        routing policy has been activated for the specified CAC group." 
            ::= { hiQGlobalFaultMgt 22 }

hiQGlobalDegradedCommsTrap NOTIFICATION-TYPE
            OBJECTS { rtpEvtSequenceNumberIndex,
                      rtpEvtCurrId,
                      rtpEvtSet ,                     --217
                      rtpEvtNum ,                     --23
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified communication link is either congested or operating in a degraded
                        state.If this alarm is reported with a faultyObject containing CAC Group, backup
                        routing policy has been activated for the specified CAC group." 
            ::= { hiQGlobalFaultMgt 23 }

hiQGlobalCommsOperationalTrap NOTIFICATION-TYPE
            OBJECTS { rtpEvtSequenceNumberIndex,
                      rtpEvtCurrId,
                      rtpEvtSet ,                     --217
                      rtpEvtNum ,                     --24
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified communication link is fully operational." 
            ::= { hiQGlobalFaultMgt 24 }

hiQOperationModeStateChange NOTIFICATION-TYPE
            OBJECTS { rtpEvtSequenceNumberIndex,
                      rtpEvtCurrId,
                      rtpEvtSet ,                     --217
                      rtpEvtNum ,                     --25
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Operation Mode has transitioned to a new state.Shown below are the possible
                        state values.  SMU indicates operation modes for Split Mode
                        Upgrade.OM_STATE_INITIAL,OM_STATE_INITIAL_PROMPT,OM_STATE_NORMAL . normal operating
                        state with all nodes active,OM_STATE_NORMAL_C . node is booting with the partner
                        already active and accessible,OM_STATE_STANDALONE_PRIMARY - no active virtual partner
                        IP address, partner status is unknown,OM_STATE_STANDALONE_SYNC . same as
                        OM_STATE_STANDALONE_PRIMARY but synchronizing from partner, partner node is shutting
                        down,OM_STATE_STANDALONE . no new provisioning, no active partner virtual IP address,
                        the x-channel is down and the Survival Authority has not yet selected the primary
                        node,OM_STATE_STANDALONE_SECONDARY . no new provisioning, no active virtual partner IP
                        address, partner status is unknown,OM_STATE_SHUTTING_DOWN . synchronization of call
                        processing data to the partner node,OM_STATE_SPLIT . SMU: start of upgrade state, no
                        x-channel,OM_STATE_STOP_DB . SMU: No changes to the OSV database, including subscriber
                        controlled input.  The database is backed up and installed at the new software
                        load,OM_STATE_SYNC . SMU: call data synchronization to the new
                        side,OM_STATE_NO_TRAFFIC . SMU: IP addresses are blocked, no call
                        processing,OM_STATE_INIT . SMU: Re-initialization of transient data in preparation for
                        fallback,OM_STATE_BEFORE_TRAFFIC . SMU: no active OSV applications,OM_STATE_TRAFFIC .
                        SMU: IP addresses active,OM_STATE_UNKNOWN . state of the partner node if the x-channel
                        is down." 
            ::= { hiQGlobalFaultMgt 25 }

hiQMinorOperationModeStateChange NOTIFICATION-TYPE
            OBJECTS { rtpEvtSequenceNumberIndex,
                      rtpEvtCurrId,
                      rtpEvtSet ,                     --217
                      rtpEvtNum ,                     --26
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Operation Mode has transitioned to a new state.Shown below are the possible
                        state values.  SMU indicates operation modes for Split Mode
                        Upgrade.OM_STATE_INITIAL,OM_STATE_INITIAL_PROMPT,OM_STATE_NORMAL . normal operating
                        state with all nodes active,OM_STATE_NORMAL_C . node is booting with the partner
                        already active and accessible,OM_STATE_STANDALONE_PRIMARY - no active virtual partner
                        IP address, partner status is unknown,OM_STATE_STANDALONE_SYNC . same as
                        OM_STATE_STANDALONE_PRIMARY but synchronizing from partner, partner node is shutting
                        down,OM_STATE_STANDALONE . no new provisioning, no active partner virtual IP address,
                        the x-channel is down and the Survival Authority has not yet selected the primary
                        node,OM_STATE_STANDALONE_SECONDARY . no new provisioning, no active virtual partner IP
                        address, partner status is unknown,OM_STATE_SHUTTING_DOWN . synchronization of call
                        processing data to the partner node,OM_STATE_SPLIT . SMU: start of upgrade state, no
                        x-channel,OM_STATE_STOP_DB . SMU: No changes to the OSV database, including subscriber
                        controlled input.  The database is backed up and installed at the new software
                        load,OM_STATE_SYNC . SMU: call data synchronization to the new
                        side,OM_STATE_NO_TRAFFIC . SMU: IP addresses are blocked, no call
                        processing,OM_STATE_INIT . SMU: Re-initialization of transient data in preparation for
                        fallback,OM_STATE_BEFORE_TRAFFIC . SMU: no active OSV applications,OM_STATE_TRAFFIC .
                        SMU: IP addresses active,OM_STATE_UNKNOWN . state of the partner node if the x-channel
                        is down." 
            ::= { hiQGlobalFaultMgt 26 }

hiQMajorOperationModeStateChange NOTIFICATION-TYPE
            OBJECTS { rtpEvtSequenceNumberIndex,
                      rtpEvtCurrId,
                      rtpEvtSet ,                     --217
                      rtpEvtNum ,                     --27
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Operation Mode has transitioned to a new state.Shown below are the possible
                        state values.  SMU indicates operation modes for Split Mode
                        Upgrade.OM_STATE_INITIAL,OM_STATE_INITIAL_PROMPT,OM_STATE_NORMAL . normal operating
                        state with all nodes active,OM_STATE_NORMAL_C . node is booting with the partner
                        already active and accessible,OM_STATE_STANDALONE_PRIMARY - no active virtual partner
                        IP address, partner status is unknown,OM_STATE_STANDALONE_SYNC . same as
                        OM_STATE_STANDALONE_PRIMARY but synchronizing from partner, partner node is shutting
                        down,OM_STATE_STANDALONE . no new provisioning, no active partner virtual IP address,
                        the x-channel is down and the Survival Authority has not yet selected the primary
                        node,OM_STATE_STANDALONE_SECONDARY . no new provisioning, no active virtual partner IP
                        address, partner status is unknown,OM_STATE_SHUTTING_DOWN . synchronization of call
                        processing data to the partner node,OM_STATE_SPLIT . SMU: start of upgrade state, no
                        x-channel,OM_STATE_STOP_DB . SMU: No changes to the OSV database, including subscriber
                        controlled input.  The database is backed up and installed at the new software
                        load,OM_STATE_SYNC . SMU: call data synchronization to the new
                        side,OM_STATE_NO_TRAFFIC . SMU: IP addresses are blocked, no call
                        processing,OM_STATE_INIT . SMU: Re-initialization of transient data in preparation for
                        fallback,OM_STATE_BEFORE_TRAFFIC . SMU: no active OSV applications,OM_STATE_TRAFFIC .
                        SMU: IP addresses active,OM_STATE_UNKNOWN . state of the partner node if the x-channel
                        is down." 
            ::= { hiQGlobalFaultMgt 27 }

hiQCritOperationModeStateChange NOTIFICATION-TYPE
            OBJECTS { rtpEvtSequenceNumberIndex,
                      rtpEvtCurrId,
                      rtpEvtSet ,                     --217
                      rtpEvtNum ,                     --28
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Operation Mode has transitioned to a new state.Shown below are the possible
                        state values.  SMU indicates operation modes for Split Mode
                        Upgrade.OM_STATE_INITIAL,OM_STATE_INITIAL_PROMPT,OM_STATE_NORMAL . normal operating
                        state with all nodes active,OM_STATE_NORMAL_C . node is booting with the partner
                        already active and accessible,OM_STATE_STANDALONE_PRIMARY - no active virtual partner
                        IP address, partner status is unknown,OM_STATE_STANDALONE_SYNC . same as
                        OM_STATE_STANDALONE_PRIMARY but synchronizing from partner, partner node is shutting
                        down,OM_STATE_STANDALONE . no new provisioning, no active partner virtual IP address,
                        the x-channel is down and the Survival Authority has not yet selected the primary
                        node,OM_STATE_STANDALONE_SECONDARY . no new provisioning, no active virtual partner IP
                        address, partner status is unknown,OM_STATE_SHUTTING_DOWN . synchronization of call
                        processing data to the partner node,OM_STATE_SPLIT . SMU: start of upgrade state, no
                        x-channel,OM_STATE_STOP_DB . SMU: No changes to the OSV database, including subscriber
                        controlled input.  The database is backed up and installed at the new software
                        load,OM_STATE_SYNC . SMU: call data synchronization to the new
                        side,OM_STATE_NO_TRAFFIC . SMU: IP addresses are blocked, no call
                        processing,OM_STATE_INIT . SMU: Re-initialization of transient data in preparation for
                        fallback,OM_STATE_BEFORE_TRAFFIC . SMU: no active OSV applications,OM_STATE_TRAFFIC .
                        SMU: IP addresses active,OM_STATE_UNKNOWN . state of the partner node if the x-channel
                        is down." 
            ::= { hiQGlobalFaultMgt 28 }

hiQNormalOperationMode NOTIFICATION-TYPE
            OBJECTS { rtpEvtSequenceNumberIndex,
                      rtpEvtCurrId,
                      rtpEvtSet ,                     --217
                      rtpEvtNum ,                     --29
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Operation Mode has transitioned to Normal state.Shown below are the possible
                        state values.  SMU indicates operation modes for Split Mode
                        Upgrade.OM_STATE_INITIAL,OM_STATE_INITIAL_PROMPT,OM_STATE_NORMAL . normal operating
                        state with all nodes active,OM_STATE_NORMAL_C . node is booting with the partner
                        already active and accessible,OM_STATE_STANDALONE_PRIMARY - no active virtual partner
                        IP address, partner status is unknown,OM_STATE_STANDALONE_SYNC . same as
                        OM_STATE_STANDALONE_PRIMARY but synchronizing from partner, partner node is shutting
                        down,OM_STATE_STANDALONE . no new provisioning, no active partner virtual IP address,
                        the x-channel is down and the Survival Authority has not yet selected the primary
                        node,OM_STATE_STANDALONE_SECONDARY . no new provisioning, no active virtual partner IP
                        address, partner status is unknown,OM_STATE_SHUTTING_DOWN . synchronization of call
                        processing data to the partner node,OM_STATE_SPLIT . SMU: start of upgrade state, no
                        x-channel,OM_STATE_STOP_DB . SMU: No changes to the OSV database, including subscriber
                        controlled input.  The database is backed up and installed at the new software
                        load,OM_STATE_SYNC . SMU: call data synchronization to the new
                        side,OM_STATE_NO_TRAFFIC . SMU: IP addresses are blocked, no call
                        processing,OM_STATE_INIT . SMU: Re-initialization of transient data in preparation for
                        fallback,OM_STATE_BEFORE_TRAFFIC . SMU: no active OSV applications,OM_STATE_TRAFFIC .
                        SMU: IP addresses active,OM_STATE_UNKNOWN . state of the partner node if the x-channel
                        is down." 
            ::= { hiQGlobalFaultMgt 29 }

hiQResourceMediumLimitExceeded NOTIFICATION-TYPE
            OBJECTS { rtpEvtSequenceNumberIndex,
                      rtpEvtCurrId,
                      rtpEvtSet ,                     --217
                      rtpEvtNum ,                     --30
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified resource has exceeded the defined medium limit." 
            ::= { hiQGlobalFaultMgt 30 }

hiQResourceHIghLimitExceeded NOTIFICATION-TYPE
            OBJECTS { rtpEvtSequenceNumberIndex,
                      rtpEvtCurrId,
                      rtpEvtSet ,                     --217
                      rtpEvtNum ,                     --31
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified resource has exceeded the defined high limit." 
            ::= { hiQGlobalFaultMgt 31 }
	    
hiqCSTAAppConnectionStateUp NOTIFICATION-TYPE
            OBJECTS { rtpEvtSequenceNumberIndex,
                      rtpEvtCurrId,
                      rtpEvtSet ,                     --217
                      rtpEvtNum ,                     --32
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The application named specified in the fault object (Application Identification)
	                  is connected to OpenScape Voice server" 
            ::= { hiQGlobalFaultMgt 32 }
	    
hiqCSTAAppConnectionStateDown NOTIFICATION-TYPE
            OBJECTS { rtpEvtSequenceNumberIndex,
                      rtpEvtCurrId,
                      rtpEvtSet ,                     --217
                      rtpEvtNum ,                     --33
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The heartbeat for the application named specified in the fault object (Application Identification)
	                  has failed or was intentionally stopped. Previously established call monitors and route registrations
			  are available." 
            ::= { hiQGlobalFaultMgt 33 }

hiqCSTAAppConnectionStateFailed NOTIFICATION-TYPE
            OBJECTS { rtpEvtSequenceNumberIndex,
                      rtpEvtCurrId,
                      rtpEvtSet ,                     --217
                      rtpEvtNum ,                     --34
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The application named specified in the fault object (Application Identification) has missed an heartbeat.
	                  This is possibly due to a temporary network issue. Previously established call monitors and
			  route registrations are currently available should if this a temporary network issue." 
            ::= { hiQGlobalFaultMgt 34 }

hiqCSTAAppConnectionStateRetrieved NOTIFICATION-TYPE
            OBJECTS { rtpEvtSequenceNumberIndex,
                      rtpEvtCurrId,
                      rtpEvtSet ,                     --217
                      rtpEvtNum ,                     --35
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The heartbeat for the application named specified in the fault object (Application Identification)
	                  has been recovered. This clears a prior missed heartbeat alarm." 
            ::= { hiQGlobalFaultMgt 35 }

hiqCSTASystemStatusChanged NOTIFICATION-TYPE
            OBJECTS { rtpEvtSequenceNumberIndex,
                      rtpEvtCurrId,
                      rtpEvtSet ,                     --217
                      rtpEvtNum ,                     --36
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The fault object identifies the current CSTA system status, such as; normal, enabled, disabled,
	                  partially disabled, overload reached or overload relieved." 
            ::= { hiQGlobalFaultMgt 36 }

hiQSecurityFirewallTrigTrap NOTIFICATION-TYPE
            OBJECTS { rtpEvtSequenceNumberIndex,
                      rtpEvtCurrId,
                      rtpEvtSet ,                     --218
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of packets per second that were received from an endpoint exceeded
                        the rate limit.   Network packets from that IP address are blocked by the firewall for
                        60 seconds." 
            ::= { hiQSecurityFaultMgt 1 }

hiQSecurityFirewallTrigClearTrap NOTIFICATION-TYPE
            OBJECTS { rtpEvtSequenceNumberIndex,
                      rtpEvtCurrId,
                      rtpEvtSet ,                     --218
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The condition causing the triggering of the firewall has been cleared." 
            ::= { hiQSecurityFaultMgt 2 }

hiQSIPRegistrationCountingStarted NOTIFICATION-TYPE
            OBJECTS { rtpEvtSequenceNumberIndex,
                      rtpEvtCurrId,
                      rtpEvtSet ,                     --218
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event clears all SIPDeviceRegistrationQuarantined alarms that may have been reported previously."
            ::= { hiQSecurityFaultMgt 5 }

hiQSIPDeviceRegistrationQuarantined NOTIFICATION-TYPE
            OBJECTS { rtpEvtSequenceNumberIndex,
                      rtpEvtCurrId,
                      rtpEvtSet ,                     --218
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The device identified in the FaultyObject has exceeded the acceptable registration rate. All registration messages from this device are discarded for a limited time to preserve system resources."
            ::= { hiQSecurityFaultMgt 6 }

hiQSIPDeviceRegistrationAccepted NOTIFICATION-TYPE
            OBJECTS { rtpEvtSequenceNumberIndex,
                      rtpEvtCurrId,
                      rtpEvtSet ,                     --218
                      rtpEvtNum ,                     --8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Registration messages from this SIP device are now processed again after being ignored due to high registration rate. If there is still registration flooding the user agent will be ignored again."
            ::= { hiQSecurityFaultMgt 8 }

hiQVerySevereHardwareFailureTrap NOTIFICATION-TYPE
            OBJECTS { rtpEvtSequenceNumberIndex,
                      rtpEvtCurrId,
                      rtpEvtSet ,                     --219
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report a hardware-related critical alarm. Listed below are
                        the typically reported hardware alarms along with the frequency that the status of
                        each is checked: Ethernet link or Bonding Group is inactive (checked every minute),
                        RAID storage failures (checked every 5 minutes), Disk errors (checked in real-time),
                        Platform Hardware errors (Temperature, Voltage, etc) detected via IPMI sensors
                        (checked every 30 seconds)" 
            ::= { hiQHardwareFaultMgt 1 }

hiQSevereHardwareTrap NOTIFICATION-TYPE
            OBJECTS { rtpEvtSequenceNumberIndex,
                      rtpEvtCurrId,
                      rtpEvtSet ,                     --219
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report a hardware-related major alarm. Listed below are
                        the typically reported hardware alarms along with the frequency that the status of
                        each is checked: Ethernet link or Bonding Group is inactive (checked every minute),
                        RAID storage failures (checked every 5 minutes), Disk errors (checked in real-time),
                        Platform Hardware errors (Temperature, Voltage, etc) detected via IPMI sensors
                        (checked every 30 seconds)" 
            ::= { hiQHardwareFaultMgt 2 }

hiQHardwareFailureTrap NOTIFICATION-TYPE
            OBJECTS { rtpEvtSequenceNumberIndex,
                      rtpEvtCurrId,
                      rtpEvtSet ,                     --219
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report a hardware-related minor alarm. Listed below are
                        the typically reported hardware alarms along with the frequency that the status of
                        each is checked: Ethernet link or Bonding Group is inactive (checked every minute),
                        RAID storage failures (checked every 5 minutes), Disk errors (checked in real-time),
                        Platform Hardware errors (Temperature, Voltage, etc) detected via IPMI sensors
                        (checked every 30 seconds)" 
            ::= { hiQHardwareFaultMgt 3 }

hiQHardwareInServiceTrap NOTIFICATION-TYPE
            OBJECTS { rtpEvtSequenceNumberIndex,
                      rtpEvtCurrId,
                      rtpEvtSet ,                     --219
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to clear a hardware-related alarm.Listed below are the
                        typically reported hardware alarms along with the frequency that the status of each is
                        checked: Ethernet link or Bonding Group is inactive (checked every minute), RAID
                        storage failures (checked every 5 minutes), Disk errors (checked in real-time),
                        Platform Hardware errors (Temperature, Voltage, etc) detected via IPMI sensors
                        (checked every 30 seconds)" 
            ::= { hiQHardwareFaultMgt 4 }

hiQLicensesExceededTrap NOTIFICATION-TYPE
            OBJECTS { rtpEvtSequenceNumberIndex,
                      rtpEvtCurrId,
                      rtpEvtSet ,                     --220
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of assigned licenses has exceeded the number of activated licenses
                        for the type identified by FaultyObject.This indicates that a license violation has
                        been detected and will be recorded for the current 24-hour period. After 10 such
                        violations have been detected then licensing enforcement is activated and will
                        activate related licensing restrictions, for example, disabling the creation of new
                        elements associated with the specified license type." 
            ::= { hiQLicensingFaultMgt 1 }

hiQLicenseCountOkTrap NOTIFICATION-TYPE
            OBJECTS { rtpEvtSequenceNumberIndex,
                      rtpEvtCurrId,
                      rtpEvtSet ,                     --220
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of assigned licenses is now within the limit allowed by the number of
                        licenses." 
            ::= { hiQLicensingFaultMgt 2 }

hiQLicenseCountMismatchTrap NOTIFICATION-TYPE
            OBJECTS { rtpEvtSequenceNumberIndex,
                      rtpEvtCurrId,
                      rtpEvtSet ,                     --220
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The license count is different between the two nodes of the hiQ cluster for the
                        type identified by FaultyObject. The system's behavior will change if the node that is
                        currently hosting the primary license manager process fails or if the process itself
                        is shut down and the secondary becomes the primary. This happens during rolling
                        upgrade, for example. All license functionality uses the values in the primary license
                        manager, the secondary is only used to take over if the primary is shut down. If there
                        is a license count mismatch then license violations may be detected in error during
                        upgrades or if a node failure occurs.  This in turn may cause licensing restrictions
                        to be activated in error." 
            ::= { hiQLicensingFaultMgt 3 }

hiQLicenseCountSyncTrap NOTIFICATION-TYPE
            OBJECTS { rtpEvtSequenceNumberIndex,
                      rtpEvtCurrId,
                      rtpEvtSet ,                     --220
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The license count is now the same between the two nodes of the hiQ cluster for
                        the type identified by faultyObject." 
            ::= { hiQLicensingFaultMgt 4 }

hiQLicenseSessionsTrap NOTIFICATION-TYPE
            OBJECTS { rtpEvtSequenceNumberIndex,
                      rtpEvtCurrId,
                      rtpEvtSet ,                     --220
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of license sessions exceeds the warning threshold for the type
                        identified by FaultyObject. A licensed category is close to a violation using a
                        configured threshold.  No functionality is lost." 
            ::= { hiQLicensingFaultMgt 5 }

hiQLicenseSessionCountOkTrap NOTIFICATION-TYPE
            OBJECTS { rtpEvtSequenceNumberIndex,
                      rtpEvtCurrId,
                      rtpEvtSet ,                     --220
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The number of license sessions is now below the warning threshold for the type
                        identified by faultyObject." 
            ::= { hiQLicensingFaultMgt 6 }

hiQLicenseRestoreTrap NOTIFICATION-TYPE
            OBJECTS { rtpEvtSequenceNumberIndex,
                      rtpEvtCurrId,
                      rtpEvtSet ,                     --220
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The LicenseManager started and determined that 72 or more hours had passed since
                        the last license database use." 
            ::= { hiQLicensingFaultMgt 7 }

hiQAccountInactiveTrap NOTIFICATION-TYPE
            OBJECTS { rtpEvtSequenceNumberIndex,
                      rtpEvtCurrId,
                      rtpEvtSet ,                     --221
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified login account has not been used recently and may be disabled in
                        the future." 
            ::= { hiQAccountMgmtFaultMgt 1 }

hiQAccountDisabledTrap NOTIFICATION-TYPE
            OBJECTS { rtpEvtSequenceNumberIndex,
                      rtpEvtCurrId,
                      rtpEvtSet ,                     --221
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified login account has not been used recently and may be deleted in the
                        future." 
            ::= { hiQAccountMgmtFaultMgt 2 }

hiQAccountDeletedTrap NOTIFICATION-TYPE
            OBJECTS { rtpEvtSequenceNumberIndex,
                      rtpEvtCurrId,
                      rtpEvtSet ,                     --221
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Alarms were previously reported, indicating that the specified account has been
                        inactive and subsequently disabled. The account was still not used and has now been
                        deleted." 
            ::= { hiQAccountMgmtFaultMgt 3 }

hiQSSHDisabled NOTIFICATION-TYPE
            OBJECTS { rtpEvtSequenceNumberIndex,
                      rtpEvtCurrId,
                      rtpEvtSet ,                     --221
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "SSH has been disabled due to successive failed login attempts." 
            ::= { hiQAccountMgmtFaultMgt 4 }

hiQAccountDisabled2 NOTIFICATION-TYPE
            OBJECTS { rtpEvtSequenceNumberIndex,
                      rtpEvtCurrId,
                      rtpEvtSet ,                     --221
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified  account is disabled." 
            ::= { hiQAccountMgmtFaultMgt 5 }

hiQLogonAttempts NOTIFICATION-TYPE
            OBJECTS { rtpEvtSequenceNumberIndex,
                      rtpEvtCurrId,
                      rtpEvtSet ,                     --221
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified user attempted to logon for a configurable number of times." 
            ::= { hiQAccountMgmtFaultMgt 6 }
	   
hiQCertificateNearExpiration NOTIFICATION-TYPE
            OBJECTS { rtpEvtSequenceNumberIndex,
                      rtpEvtCurrId,
                      rtpEvtSet ,                     --221
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified certificate is near to expiration." 
            ::= { hiQAccountMgmtFaultMgt 7 }

hiQSessionDenied NOTIFICATION-TYPE
            OBJECTS { rtpEvtSequenceNumberIndex,
                      rtpEvtCurrId,
                      rtpEvtSet ,                     --221
                      rtpEvtNum ,                     --8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified session has been denied because of certificate revocation." 
            ::= { hiQAccountMgmtFaultMgt 8 }

hiQSessionTerminated NOTIFICATION-TYPE
            OBJECTS { rtpEvtSequenceNumberIndex,
                      rtpEvtCurrId,
                      rtpEvtSet ,                     --221
                      rtpEvtNum ,                     --9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The specified session has been terminated because of certificate revocation." 
            ::= { hiQAccountMgmtFaultMgt 9 }	 

hiQOCSPNotResponding NOTIFICATION-TYPE
            OBJECTS { rtpEvtSequenceNumberIndex,
                      rtpEvtCurrId,
                      rtpEvtSet ,                     --221
                      rtpEvtNum ,                     --10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The OCSP responder failed to respond to an OCSP request." 
            ::= { hiQAccountMgmtFaultMgt 10 }

hiQCRLDownloadFailure NOTIFICATION-TYPE
            OBJECTS { rtpEvtSequenceNumberIndex,
                      rtpEvtCurrId,
                      rtpEvtSet ,                     --221
                      rtpEvtNum ,                     --11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The most recent CRL list could not be downloaded." 
            ::= { hiQAccountMgmtFaultMgt 11 }

hiQClientAuthenticationFailure NOTIFICATION-TYPE
            OBJECTS { rtpEvtSequenceNumberIndex,
                      rtpEvtCurrId,
                      rtpEvtSet ,                     --221
                      rtpEvtNum ,                     --12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The authentication credentials configured on the client do not match with the 
                          authentication credentials recorded in OpenScape Voice."
            ::= { hiQAccountMgmtFaultMgt 12 }

hiQClearClientAuthenticationFailure NOTIFICATION-TYPE
            OBJECTS { rtpEvtSequenceNumberIndex,
                      rtpEvtCurrId,
                      rtpEvtSet ,                     --221
                      rtpEvtNum ,                     --13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The authentication credentials configured on the client match with the 
                          authentication credentials recorded in OpenScape Voice."
            ::= { hiQAccountMgmtFaultMgt 13 }


hiPathSIPCounterAboveHighThld NOTIFICATION-TYPE
            OBJECTS { rtpEvtSequenceNumberIndex,
                      rtpEvtCurrId,
                      rtpEvtSet ,                     --230
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The event counter has exceeded the high alarm threshold for the type identified
                        by FaultyObject." 
            ::= { hiQSipFaultMgmt 1 }

hiPathSIPCounterAboveLowThld NOTIFICATION-TYPE
            OBJECTS { rtpEvtSequenceNumberIndex,
                      rtpEvtCurrId,
                      rtpEvtSet ,                     --230
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The event counter has exceeded the low alarm threshold for the type identified
                        by FaultyObject." 
            ::= { hiQSipFaultMgmt 2 }

hiPathSIPCounterBelowThld NOTIFICATION-TYPE
            OBJECTS { rtpEvtSequenceNumberIndex,
                      rtpEvtCurrId,
                      rtpEvtSet ,                     --230
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The event counter is now below the threshold allowed for the type identified by
                        FaultyObject." 
            ::= { hiQSipFaultMgmt 3 }

hiQCacHighThreshTrap NOTIFICATION-TYPE
            OBJECTS { rtpEvtSequenceNumberIndex,
                      rtpEvtCurrId,
                      rtpEvtSet ,                     --231
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report a CaC specific major alarm" 
            ::= { hiQCacFaultMgt 1 }

hiQCacLowThreshTrap NOTIFICATION-TYPE
            OBJECTS { rtpEvtSequenceNumberIndex,
                      rtpEvtCurrId,
                      rtpEvtSet ,                     --231
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report a CaC specific clear alarm." 
            ::= { hiQCacFaultMgt 2 }


hiQTestCallGeneratorOkTrap NOTIFICATION-TYPE
            OBJECTS { rtpEvtSequenceNumberIndex,
                      rtpEvtCurrId,
                      rtpEvtSet ,                     --233
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Call processing is working on this node." 
            ::= { hiQTcgFaultMgt 1 }

hiQTestCallGeneratorProvErrTrap NOTIFICATION-TYPE
            OBJECTS { rtpEvtSequenceNumberIndex,
                      rtpEvtCurrId,
                      rtpEvtSet ,                     --233
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The test call feature has been disabled due to invalid provisioning data." 
            ::= { hiQTcgFaultMgt 2 }

hiQTestCallGenOverloadDetTrap NOTIFICATION-TYPE
            OBJECTS { rtpEvtSequenceNumberIndex,
                      rtpEvtCurrId,
                      rtpEvtSet ,                     --233
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The test call generator has encountered overload for more than the specified
                        number of minutes." 
            ::= { hiQTcgFaultMgt 3 }

hiQTestCallGeneratorNotOkTrap NOTIFICATION-TYPE
            OBJECTS { rtpEvtSequenceNumberIndex,
                      rtpEvtCurrId,
                      rtpEvtSet ,                     --233
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The test call generator has encountered call processing failures. SW processes
                        will be restarted." 
            ::= { hiQTcgFaultMgt 4 }

hiQTestCallGenNotOkProcRestart NOTIFICATION-TYPE
            OBJECTS { rtpEvtSequenceNumberIndex,
                      rtpEvtCurrId,
                      rtpEvtSet ,                     --233
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Still no active call processing after process restarts." 
            ::= { hiQTcgFaultMgt 5 }

hiQTestCallGenNotOkNodeRestart NOTIFICATION-TYPE
            OBJECTS { rtpEvtSequenceNumberIndex,
                      rtpEvtCurrId,
                      rtpEvtSet ,                     --233
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "After a node restart callp is still not working. The node is taken out of
                        service (level-3) to allow the partner node to continue call processing." 
            ::= { hiQTcgFaultMgt 6 }

hiQRollingProcessRestart NOTIFICATION-TYPE
            OBJECTS { rtpEvtSequenceNumberIndex,
                      rtpEvtCurrId,
                      rtpEvtSet ,                     --234
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "This event is used to report that a process monitored by the RTP node manager is
                        restarting frequently." 
            ::= { hiQPlatformFaultMgmt 1 }

hiQRollingProcessRestartAlarmReset NOTIFICATION-TYPE
            OBJECTS { rtpEvtSequenceNumberIndex,
                      rtpEvtCurrId,
                      rtpEvtSet ,                     --234
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The rolling process restart alarm for the process is cleared and will be
                        regenerated if the alarm condition still persists." 
            ::= { hiQPlatformFaultMgmt 2 }

hiQNoMoreRollingProcessRestarts NOTIFICATION-TYPE
            OBJECTS { rtpEvtSequenceNumberIndex,
                      rtpEvtCurrId,
                      rtpEvtSet ,                     --234
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "No more rolling process restarts occurred during the last monitored time
                        interval." 
            ::= { hiQPlatformFaultMgmt 3 }

hiQNodeRecoveryByRestart NOTIFICATION-TYPE
            OBJECTS { rtpEvtSequenceNumberIndex,
                      rtpEvtCurrId,
                      rtpEvtSet ,                     --234
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A condition that warrants restarting the node in an attempt to clear an error
                        condition has been detected and the node will now be restarted." 
            ::= { hiQPlatformFaultMgmt 4 }

hiQNodeDownAfterFailedRecovery NOTIFICATION-TYPE
            OBJECTS { rtpEvtSequenceNumberIndex,
                      rtpEvtCurrId,
                      rtpEvtSet ,                     --234
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Since the reported problem could not be resolved by a node restart, the node is
                        being stopped." 
            ::= { hiQPlatformFaultMgmt 5 }

hiQNodeRecovery NOTIFICATION-TYPE
            OBJECTS { rtpEvtSequenceNumberIndex,
                      rtpEvtCurrId,
                      rtpEvtSet ,                     --234
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "After a node restart, the problem that triggered the restart has not occurred
                        again within the specified time interval." 
            ::= { hiQPlatformFaultMgmt 6 }

hiQNodeRecoveryFailed NOTIFICATION-TYPE
            OBJECTS { rtpEvtSequenceNumberIndex,
                      rtpEvtCurrId,
                      rtpEvtSet ,                     --234
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "After a node restart, the problem that triggered the restart occurred again. 
                        This alarm is cleared and the node is brought down, raising a different alarm." 
            ::= { hiQPlatformFaultMgmt 7 }

hiQSwapSpaceFull NOTIFICATION-TYPE
            OBJECTS { rtpEvtSequenceNumberIndex,
                      rtpEvtCurrId,
                      rtpEvtSet ,                     --234
                      rtpEvtNum ,                     --8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Swap Space Utilization is above the defined threshold."
            ::= { hiQPlatformFaultMgmt 8 }

hiQSwapSpaceAlarmReset NOTIFICATION-TYPE
            OBJECTS { rtpEvtSequenceNumberIndex,
                      rtpEvtCurrId,
                      rtpEvtSet ,                     --234
                      rtpEvtNum ,                     --9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The current SwapSpaceFull alarm is cleared. It will be regenerated if the alarm condition still exists."
            ::= { hiQPlatformFaultMgmt 9 }

hiQSwapSpaceOk NOTIFICATION-TYPE
            OBJECTS { rtpEvtSequenceNumberIndex,
                      rtpEvtCurrId,
                      rtpEvtSet ,                     --234
                      rtpEvtNum ,                     --10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The Swap Space Utilization is below the defined threshold."
            ::= { hiQPlatformFaultMgmt 10 }

hiQRebootBecauseStopRTPHasFailedPreviously NOTIFICATION-TYPE
            OBJECTS { rtpEvtSequenceNumberIndex,
                      rtpEvtCurrId,
                      rtpEvtSet ,                     --234
                      rtpEvtNum ,                     --11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The OSB SW node has not been properly deactivated in the past.
                          The node has therefore been rebooted as part of the srxctrl activation." 
            ::= { hiQPlatformFaultMgmt 11 }

hiQRapidStatStarting NOTIFICATION-TYPE
            OBJECTS { rtpEvtSequenceNumberIndex,
                      rtpEvtCurrId,
                      rtpEvtSet ,                     --235
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "RapidStat is starting. All potentially reported alarms by a previously run RapidStat are cleared. They will be re-generated if found again."
            ::= { hiQRapidStatFaultMgt 1 }

hiQRapidStatWarningsFound NOTIFICATION-TYPE
            OBJECTS { rtpEvtSequenceNumberIndex,
                      rtpEvtCurrId,
                      rtpEvtSet ,                     --235
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "RapidStat has generated warnings."
            ::= { hiQRapidStatFaultMgt 2 }

hiQRapidStatErrorsFound NOTIFICATION-TYPE
            OBJECTS { rtpEvtSequenceNumberIndex,
                      rtpEvtCurrId,
                      rtpEvtSet ,                     --235
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "RapidStat has found errors."
            ::= { hiQRapidStatFaultMgt 3 }

hiQRapidStatSevereErrorsFound NOTIFICATION-TYPE
            OBJECTS { rtpEvtSequenceNumberIndex,
                      rtpEvtCurrId,
                      rtpEvtSet ,                     --235
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "RapidStat has found severe errors."
            ::= { hiQRapidStatFaultMgt 4 }

hiQRapidStatVerySevereErrorsFound NOTIFICATION-TYPE
            OBJECTS { rtpEvtSequenceNumberIndex,
                      rtpEvtCurrId,
                      rtpEvtSet ,                     --235
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "RapidStat has found very severe errors."
            ::= { hiQRapidStatFaultMgt 5 }

hiQEmergencyCallIdTrap NOTIFICATION-TYPE
            OBJECTS { rtpEvtSequenceNumberIndex,
                      rtpEvtCurrId,
                      rtpEvtSet ,                     --250
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "The OSV server is processing an Emergency Call."
            ::= { hiQNotificationMgt 1 }


hiqCertificateExpirationWarning NOTIFICATION-TYPE
            OBJECTS { rtpEvtSequenceNumberIndex,
                      rtpEvtCurrId,
                      rtpEvtSet ,                     --236
                      rtpEvtNum ,                     --1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A certificate installed on OSV will expire soon."
            ::= { hiQInterfaceSecurityFaultMgmt 1 }

hiqCertificateRemovedOrUpdated NOTIFICATION-TYPE
            OBJECTS { rtpEvtSequenceNumberIndex,
                      rtpEvtCurrId,
                      rtpEvtSet ,                     --236
                      rtpEvtNum ,                     --2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "Removal or update of a certificate that is about to expire causes a clearance of the previous error condition."
            ::= { hiQInterfaceSecurityFaultMgmt 2 }

hiqCertificateExpired NOTIFICATION-TYPE
            OBJECTS { rtpEvtSequenceNumberIndex,
                      rtpEvtCurrId,
                      rtpEvtSet ,                     --236
                      rtpEvtNum ,                     --3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A certificate installed on OSV is expired or revoked.."
            ::= { hiQInterfaceSecurityFaultMgmt 3 }

hiqCRLDownloadFailure NOTIFICATION-TYPE
            OBJECTS { rtpEvtSequenceNumberIndex,
                      rtpEvtCurrId,
                      rtpEvtSet ,                     --236
                      rtpEvtNum ,                     --4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A CRL issued by a Certification Authority could not be downloaded due to network problems 
                          or problems at the download server."
            ::= { hiQInterfaceSecurityFaultMgmt 4 }

hiqCRLRemovedOrUpdated NOTIFICATION-TYPE
            OBJECTS { rtpEvtSequenceNumberIndex,
                      rtpEvtCurrId,
                      rtpEvtSet ,                     --236
                      rtpEvtNum ,                     --5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A CRL issued by a Certification Authority was removed or downloaded after network problems 
                          or problems at the download server were resolved or successfully copied from the partner 
                          node and is now valid and ready for use."
            ::= { hiQInterfaceSecurityFaultMgmt 5 }

hiqCRLExpired NOTIFICATION-TYPE
            OBJECTS { rtpEvtSequenceNumberIndex,
                      rtpEvtCurrId,
                      rtpEvtSet ,                     --236
                      rtpEvtNum ,                     --6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A CRL issued by a Certification Authority is expired."
            ::= { hiQInterfaceSecurityFaultMgmt 6 }

hiqCRLInvalid NOTIFICATION-TYPE
            OBJECTS { rtpEvtSequenceNumberIndex,
                      rtpEvtCurrId,
                      rtpEvtSet ,                     --236
                      rtpEvtNum ,                     --7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A CRL issued by a Certification Authority is invalid."
            ::= { hiQInterfaceSecurityFaultMgmt 7 }

hiqCRLCopyFailure NOTIFICATION-TYPE
            OBJECTS { rtpEvtSequenceNumberIndex,
                      rtpEvtCurrId,
                      rtpEvtSet ,                     --236
                      rtpEvtNum ,                     --8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A CRL issued by a Certification Authority could not be copied from the partner node."
            ::= { hiQInterfaceSecurityFaultMgmt 8 }

hiqTLSConnectionAcceptWithoutCRLCheck NOTIFICATION-TYPE
            OBJECTS { rtpEvtSequenceNumberIndex,
                      rtpEvtCurrId,
                      rtpEvtSet ,                     --236
                      rtpEvtNum ,                     --9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A CRL check was not performed on a TLS connection.  The TLS connection was accepted 
                          though, but this warning is issued to raise awareness.  The warning should only 
                          occur for a short time and will clear automatically once the CRL has been downloaded."
            ::= { hiQInterfaceSecurityFaultMgmt 9 }

hiqCRLCheckOnTLSConnectionOK NOTIFICATION-TYPE
            OBJECTS { rtpEvtSequenceNumberIndex,
                      rtpEvtCurrId,
                      rtpEvtSet ,                     --236
                      rtpEvtNum ,                     --10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A CRL check was performed on a TLS connection that had an alarm that a CRL check did not occur yet."
            ::= { hiQInterfaceSecurityFaultMgmt 10 }

hiqTLSConnectionClearedRevokedCert NOTIFICATION-TYPE
            OBJECTS { rtpEvtSequenceNumberIndex,
                      rtpEvtCurrId,
                      rtpEvtSet ,                     --236
                      rtpEvtNum ,                     --11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A TLS connection was cleared because a revoked certificate is used to establish the connection."
            ::= { hiQInterfaceSecurityFaultMgmt 11 }

hiqTLSSIPIdentityMismatch NOTIFICATION-TYPE
            OBJECTS { rtpEvtSequenceNumberIndex,
                      rtpEvtCurrId,
                      rtpEvtSet ,                     --236
                      rtpEvtNum ,                     --12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId,
                      rtpClusterName
            }
            STATUS current
            DESCRIPTION  "A TLS connection was refused because the certificate of a different server was used to initiate the connection."
            ::= { hiQInterfaceSecurityFaultMgmt 12 }

END
