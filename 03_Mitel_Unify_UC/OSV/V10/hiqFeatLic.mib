HIQ-FEAT-LIC-MIB    DEFINITIONS ::= BEGIN

-- ==================================================================
--  Copyright © Unify Software and Solutions GmbH & Co. KG
--  All Rights Reserved.
--
--  Reproduction of this document is authorized on condition that
--  this copyright notice is included.
--
--  This MIB document embodies proprietary intellectual property.
--  of Unify GmbH & Co. KG, which retains all title and
--  ownership in this MIB, including any revisions.
--
--  This module will be extended, as required.
--
--  Unify GmbH & Co. KG reserves the right to make changes
--  in specification and other information contained in this
--  document without prior notice. The reader should consult
--  Unify GmbH & Co. KG to determine whether any such
--  changes have been made.
--
--  Copyright © Unify Software and Solutions GmbH & Co. KG
-- ==================================================================

-- ==================================================================
-- Revision History
--  04/10/08      C. Chatzidimitriou        FRN3208. Cleanup of MIBS
--  06/12/2008    C. Chatzidimitriou        Updated MIB to be fully compatible with SNMPv2N3208
--  09/15/2008     G.Kouris                 FRN3211
--  10/22/2013     G.Kouris                 Incorporate new Brand Name
-- ==================================================================

IMPORTS
   MODULE-IDENTITY, OBJECT-TYPE, OBJECT-IDENTITY, Integer32
        FROM SNMPv2-SMI
   surpassRtp
    FROM SURPASS-RTP-MIB
   hiq8000Admin
        FROM SURPASS-RTP-ADMIN-MIB;

-- ==================================================================

hiqFeatLic   MODULE-IDENTITY
        LAST-UPDATED "202205231753Z"
        ORGANIZATION "Unify Software and Solutions GmbH & Co. KG"
        CONTACT-INFO "http://www.unify.com/us/Home/Internet/web/us/Home/contact-us.aspx" 
        DESCRIPTION
           "This MIB describes the end-user licenses features for
            all devices (HIQ, HIPATH, PS)." 

        REVISION "201509141224Z"
        DESCRIPTION
            "Updated the MIB with the new Brand Name"

        ::= { hiq8000Admin 5 }

        -- ******************************************
        -- MIB OBJECT Declarations:
        -- ******************************************

       hiqFeatLicTrunkSessionGroup OBJECT-IDENTITY
                STATUS current
                DESCRIPTION
                "The SIP Trunking Session License Group."
                ::= { hiqFeatLic 1 }

       hiqFeatDynamicLicenseGroup OBJECT-IDENTITY
                STATUS current
                DESCRIPTION
                "The Dynamic License Group has read-only objects to identify the
                 number of available Dynamic licenses, the number of licenses
                 currently In Use, the maximum value of 'In Use' licenses during the
                 previous 24 hours, the number of customer violations and the number
                 of Licenses Rejections per DN per hour.
                 Also it includes a read-write object that controls the barrier 
                 over which the system generates warnings to notify the administrator
                 that usage is close to the system's capacity."
                ::= { hiqFeatLic 2 } 

       hiqFeatOSMOLicenseGroup OBJECT-IDENTITY
                STATUS current
                DESCRIPTION
                "The Openscape mobile (OSMO) License Group."
                ::= { hiqFeatLic 3 }

       hiqFeatEncryptLicenseGroup OBJECT-IDENTITY
                STATUS current
                DESCRIPTION
                "The Encryption License Group."
                ::= { hiqFeatLic 4 }

       hiqFeatBasicLicenseGroup OBJECT-IDENTITY
                STATUS current
                DESCRIPTION
                "The Basic License Group."
                ::= { hiqFeatLic 5 }

       hiqFeatEssentialLicenseGroup OBJECT-IDENTITY
                STATUS current
                DESCRIPTION
                "The Essential License Group."
                ::= { hiqFeatLic 6 }

       hiqFeatUnifyPhoneLicenseGroup OBJECT-IDENTITY
                STATUS current
                DESCRIPTION
                "The Unify Phone License Group."
                ::= { hiqFeatLic 7 }

        -- ************************************
        -- SIP Trunking Session License Objects:
        -- ************************************


        hiqFeatLicTrunkSessionLicenses OBJECT-TYPE
                SYNTAX  Integer32
                MAX-ACCESS  read-only
                STATUS      obsolete
                DESCRIPTION
            "The licenses assigned to the system. This object change only when
             installing new licensing files. The parameter is valid in both ITU
             and ANSI variants."
                  ::= { hiqFeatLicTrunkSessionGroup 1 }

        hiqFeatLicTrunkAverageUsage OBJECT-TYPE
                SYNTAX  Integer32
                MAX-ACCESS  read-only
                STATUS      obsolete
                DESCRIPTION
            "The average usage within one hour. License Manager will take snapshots 
             of current usage counter every 5 minutes and get the average of the
             values during an hour. The parameter is valid in both ITU and ANSI variants."
                  ::= { hiqFeatLicTrunkSessionGroup 2 }

        hiqFeatLicTrunkMaxAverageUsage OBJECT-TYPE
                SYNTAX  Integer32
                MAX-ACCESS  read-only
                STATUS      obsolete
                DESCRIPTION
            "The maximum average usage within one hour, during a 24h period. The parameter
             is valid in both ITU and ANSI variants."
                  ::= { hiqFeatLicTrunkSessionGroup 3 }

        hiqFeatLicTrunkCustomerViolations OBJECT-TYPE
                SYNTAX  Integer32
                MAX-ACCESS  read-only
                STATUS      obsolete
                DESCRIPTION
            "This object holds the number of Trunking Session usage violation detected.
             The License Manager detects violations based on the maximum 1h average usage.
             The parameter is valid in both ITU and ANSI variants."
                  ::= { hiqFeatLicTrunkSessionGroup 4 }

        hiqFeatLicTrunkViolationLimit OBJECT-TYPE
                SYNTAX  Integer32
                MAX-ACCESS  read-only
                STATUS      obsolete
                DESCRIPTION
            "This object holds the number of usage violations the system allows, before
             activating the enforcement. The parameter is valid in both ITU and ANSI variants."
                  ::= { hiqFeatLicTrunkSessionGroup 5 }

        hiqFeatLicTrunkWarnThresLic  OBJECT-TYPE
                SYNTAX Integer32 (0..100)
                MAX-ACCESS read-only
                STATUS     obsolete
                DESCRIPTION "Warning Threshold for Trunking Session licensing.
                             It controls the barrier over which the system generates warnings
                             to notify administrator that usage is close to system's capacity.
                             The parameter is valid in both ITU and ANSI variants."
                DEFVAL { 95 }
                ::= { hiqFeatLicTrunkSessionGroup 6 }

    -- *********************************
        -- Dynamic License Objects: 
        -- *********************************

        hiqFeatLicDynamicAvailable OBJECT-TYPE
                SYNTAX Integer32
                MAX-ACCESS read-only
                STATUS current
                DESCRIPTION
                   "This object represents the number of Dynamic licenses that are
                available in the system. It is calculated by the license manager
                using the formula: Purchased - In Use."
                ::= { hiqFeatDynamicLicenseGroup 1 }

        hiqFeatLicDynamicInUse OBJECT-TYPE
                SYNTAX Integer32
                MAX-ACCESS read-only
                STATUS     current
                DESCRIPTION
                   "This object represents the number of Dynamic licenses currently in use
                    in the system. There is One Home DN per Dynamic license. This value must
                be less or equal to the number of Dynamic licenses Purchased."
                ::= { hiqFeatDynamicLicenseGroup 2 }

        hiqFeatLicDynamicMaxInUse OBJECT-TYPE
                SYNTAX Integer32
                MAX-ACCESS read-only
                STATUS     current
                DESCRIPTION
                   "This number represents the maximum usage of Dynamic licenses over the
                    last 24 hour period."
                ::= { hiqFeatDynamicLicenseGroup 3 }

        hiqFeatLicDynamicViolations OBJECT-TYPE
                SYNTAX Integer32
                MAX-ACCESS read-only
                STATUS     current
                DESCRIPTION
                   "This object is a counter holding the number of usage violations. 
                    License Manager detects Dynamic licensing violations based on the maximum
                    usage. Therefore, system counts one violation per day maximum, regardless
                    of how many times the actual usage exceeded the licensing limits during that
                    day. If this number exceeds the violation limit, the system activates the 
                    license enforcement. The default violation limit is 10 and this number cannot 
                    be modified by the system Administrator."
                ::= { hiqFeatDynamicLicenseGroup 4 }

        hiqFeatLicDynamicViolationsLimit OBJECT-TYPE
                SYNTAX Integer32
                MAX-ACCESS read-only
                STATUS     current
                DESCRIPTION
                   "This is the number of usage violations the system allows,before activating the
                    enforcement. This value cannot be modified by the system administrator"
                ::= { hiqFeatDynamicLicenseGroup 5 }

        hiqFeatLicDynamicRejections OBJECT-TYPE
                SYNTAX Integer32
                MAX-ACCESS read-only
                STATUS     obsolete
                DESCRIPTION
                   "-- Dynamic licensing not currently supported --

                This object holds the number of License rejections per DN per hour due to 
                    Dynamic Session licensing. This counter is calculated using the formula:
                Rejections/number of DNs."
                ::= { hiqFeatDynamicLicenseGroup 6 }

        hiqFeatLicDynWarningThreshold OBJECT-TYPE
                SYNTAX  Integer32 (0..100)
                MAX-ACCESS read-only
                STATUS     obsolete
                DESCRIPTION
                   "-- Dynamic licensing not currently supported --

                This object holds a system-wide RTP parameter that controls the barrier over
                which the system generates warnings to notify the administrator that usage
                is close to the system's capacity. The default value is 95. This means that when
                activated licenses are over the 95% of the assigned licenses, the system generates 
                a warning. License Manager checks for changes of this parameter every 1h."
                DEFVAL { 95 }
                ::= { hiqFeatDynamicLicenseGroup 7 }

    -- *********************************
        -- OSMO License Objects: 
        -- *********************************

        hiqFeatLicOSMOLicensesAssigned OBJECT-TYPE
                SYNTAX Integer32
                MAX-ACCESS read-only
                STATUS     current
                DESCRIPTION
        "This is the number of OSMO licenses assigned to the system"
                ::= { hiqFeatOSMOLicenseGroup 1 } 

        hiqFeatLicOSMOLicensesInUse OBJECT-TYPE
                SYNTAX Integer32
                MAX-ACCESS read-only
                STATUS     current
                DESCRIPTION
        "This is the number of OSMO licenses currently in use"
                ::= { hiqFeatOSMOLicenseGroup 2 }  

        hiqFeatLicOSMOMaxInUsedOver24Hour OBJECT-TYPE
                SYNTAX Integer32
                MAX-ACCESS read-only
                STATUS     current
                DESCRIPTION
        "This is the maximum number of OSMO licenses used over the last 24 hour period"
                ::= { hiqFeatOSMOLicenseGroup 3 }
           
        -- *********************************
        -- Encryption License Objects: 
        -- *********************************

        hiqFeatLicEncryptLicensesAssigned OBJECT-TYPE
                SYNTAX Integer32
                MAX-ACCESS read-only
                STATUS     current
                DESCRIPTION
        "This is the number of Encryption licenses available in the license file"
                ::= { hiqFeatEncryptLicenseGroup 1 } 

        hiqFeatLicEncryptLicensesInUse OBJECT-TYPE
                SYNTAX Integer32
                MAX-ACCESS read-only
                STATUS     current
                DESCRIPTION
        "This is the number of Encryption licenses currently in use"
                ::= { hiqFeatEncryptLicenseGroup 2 }

        hiqFeatLicEncryptMaxInUsedOver24Hour OBJECT-TYPE
                SYNTAX Integer32
                MAX-ACCESS read-only
                STATUS     current
                DESCRIPTION
        "This is the maximum number of Encryption licenses used over the last 24 hour period"
                ::= { hiqFeatEncryptLicenseGroup 3 }

        -- *********************************
        -- Basic License Objects: 
        -- *********************************

        hiqFeatLicBasicLicensesAvailable OBJECT-TYPE
                SYNTAX Integer32
                MAX-ACCESS read-only
                STATUS     current
                DESCRIPTION
        "Number of Basic licenses available in the license file"
                ::= { hiqFeatBasicLicenseGroup 1 }

        hiqFeatLicBasicLicensesInUse OBJECT-TYPE
                SYNTAX Integer32
                MAX-ACCESS read-only
                STATUS     current
                DESCRIPTION
        "Number of Basic licenses currently in use"
                ::= { hiqFeatBasicLicenseGroup 2 }

        hiqFeatLicBasicLicensesUsedOver24Hour OBJECT-TYPE
                SYNTAX Integer32
                MAX-ACCESS read-only
                STATUS     current
                DESCRIPTION
        "Maximum Number of Basic licenses used over the last 24 hour period"
                ::= { hiqFeatBasicLicenseGroup 3 }

        -- *********************************
        -- Essential License Objects: 
        -- *********************************

        hiqFeatLicEssentialLicensesAvailable OBJECT-TYPE
                SYNTAX Integer32
                MAX-ACCESS read-only
                STATUS     current
                DESCRIPTION
        "Number of Essential licenses available in the license file"
                ::= { hiqFeatEssentialLicenseGroup 1 }

        hiqFeatLicEssentialLicensesInUse OBJECT-TYPE
                SYNTAX Integer32
                MAX-ACCESS read-only
                STATUS     current
                DESCRIPTION
        "Number of Essential licenses currently in use"
                ::= { hiqFeatEssentialLicenseGroup 2 }

        hiqFeatLicEssentialLicensesUsedOver24Hour OBJECT-TYPE
                SYNTAX Integer32
                MAX-ACCESS read-only
                STATUS     current
                DESCRIPTION
        "Maximum Number of Essential licenses used over the last 24 hour period"
                ::= { hiqFeatEssentialLicenseGroup 3 }

        -- *********************************
        -- Unify Phone License Objects:
        -- *********************************

        hiqFeatLicUnifyPhoneLicensesAvailable OBJECT-TYPE
                SYNTAX Integer32
                MAX-ACCESS read-only
                STATUS     current
                DESCRIPTION
        "Number of available Unify Phone licenses assigned to the system"
                ::= { hiqFeatUnifyPhoneLicenseGroup 1 }

        hiqFeatLicUnifyPhoneLicensesInUse OBJECT-TYPE
                SYNTAX Integer32
                MAX-ACCESS read-only
                STATUS     current
                DESCRIPTION
        "Number of Unify Phone licenses currently in use to the system"
                ::= { hiqFeatUnifyPhoneLicenseGroup 2 }

        hiqFeatLicUnifyPhoneLicensesUsedOver24Hour OBJECT-TYPE
                SYNTAX Integer32
                MAX-ACCESS read-only
                STATUS     current
                DESCRIPTION
        "Maximum Number of Unify Phone licenses used over the last 24 hour period"
                ::= { hiqFeatUnifyPhoneLicenseGroup 3 }


END
