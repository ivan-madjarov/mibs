--
-- ==================================================================
--  Copyright © Unify GmbH & Co. KG
--
--  All Rights Reserved.
--
--  Reproduction of this document is authorized on condition that
--  this copyright notice is included.
--
--  This MIB document embodies proprietary intellectual property. 
--  of Unify GmbH & Co. KG, which retains all title and
--  ownership in this MIB, including any revisions.
--
--  This module will be extended, as required.
--
--  Unify GmbH & Co. KG reserves the right to make 
--  changes in specification and other information contained in this 
--  document without prior notice. The reader should consult 
--  Unify GmbH & Co. KG to determine whether any such
--  changes have been made.
--
--  Copyright © Unify GmbH & Co. KG
-- ==================================================================
--
-- **************************************************************************
-- Revision History
-- 08/01/02     K. Teelucksingh       Initial code
-- 05/08/03     Polly Yu              Updated copyright text  
-- 06/12/08     C. Chatzidimitriou    Updated MIB to be fully compatible with SNMPv2
-- 10/22/2013   G.Kouris              Incorporate new Brand Name
--
-- **************************************************************************

SURPASS-RTP-MIB DEFINITIONS ::= BEGIN

-- **************************************************************************
IMPORTS
    MODULE-IDENTITY, OBJECT-IDENTITY, enterprises                          
         FROM SNMPv2-SMI;  

-- **************************************************************************

--
-- Siemens-specific branch
-- surpass = 1.3.6.1.4.1.4329.2.18
--
   surpassRtp MODULE-IDENTITY
        LAST-UPDATED "201611251624Z"
        ORGANIZATION "Unify Software and Solutions GmbH & Co. KG"
        CONTACT-INFO "http://www.unify.com/us/Home/Internet/web/us/Home/contact-us.aspx"
        DESCRIPTION
            "This is the top level identity for Surpass RTP
             (Resilient Telco Platform) based products and Managed 
             Objects. "
             
        REVISION     "201509141224Z"
        DESCRIPTION
                     "Updated the MIB with the new Brand Name"

        ::= { surpass 2 }
         
    siemens OBJECT-IDENTITY
        STATUS current
        DESCRIPTION
            "The authoritative identity of the enterprise Unify GmbH."
        ::= { enterprises 4329 }

    iandcAdmin OBJECT-IDENTITY
        STATUS current
        DESCRIPTION
            "The Unify I&C product-specific MIBs."
        ::= { siemens 2 }

    surpass OBJECT-IDENTITY
        STATUS current
        DESCRIPTION
            "The authoritative identity of the I&C Surpass products."
        ::= { iandcAdmin  18 }

    surpassRtpProducts OBJECT-IDENTITY
        STATUS current
        DESCRIPTION
            "The top-level registry for Unify
             Surpass RTP-based products."
        ::= { surpassRtp 1 }

    surpassRtpAdmin OBJECT-IDENTITY
        STATUS current
        DESCRIPTION
            "The top-level registry  for Unify 
             Surpass RTP-based MIBs. "
        ::= { surpassRtp 2 }

END
