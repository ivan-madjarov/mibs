HIQ-ADMIN-MIB         DEFINITIONS ::= BEGIN

-- ==================================================================
--  Copyright © Unify GmbH & Co. KG
--
--  All Rights Reserved.
--
--  Reproduction of this document is authorized on condition that
--  this copyright notice is included.
--
--  This MIB document embodies proprietary intellectual property. 
--  of Unify GmbH & Co. KG, which retains all title and
--  ownership in this MIB, including any revisions.
--
--  This module will be extended, as required.
--
--  Unify GmbH & Co. KG reserves the right to make 
--  changes in specification and other information contained in this 
--  document without prior notice. The reader should consult 
--  Unify GmbH & Co. KG to determine whether any such
--  changes have been made.
--
--  Copyright © Unify GmbH & Co. KG
-- ==================================================================

-- **************************************************************************
-- Revision History
--
-- 04/10/08    C. Chatzidimitriou     FRN3208. Cleanup of MIBS      
-- 06/12/08    C. Chatzidimitriou     Updated MIB to be fully compatible with SNMPv2
-- 10/21/2013  G.Kouris               Incorporate new Brand Name  
--
-- **************************************************************************

IMPORTS
   MODULE-IDENTITY, Integer32
        FROM SNMPv2-SMI
   surpassRtp
	FROM SURPASS-RTP-MIB
   surpassRtpAdmin
        FROM SURPASS-RTP-ADMIN-MIB
   TEXTUAL-CONVENTION
        FROM SNMPv2-TC;

-- **************************************************************************

hiq8000Admin MODULE-IDENTITY
        LAST-UPDATED "201611251142Z"
        ORGANIZATION "Unify Software and Solutions GmbH & Co. KG"
        CONTACT-INFO "http://www.unify.com/us/Home/Internet/web/us/Home/contact-us.aspx"

        DESCRIPTION "This is the MIB module that describes 
                     the hiQ8000 managed objects. The
                     hiQ8000 was formerly called Unisphere SRX3000)."
        
        REVISION     "201509141224Z"
        DESCRIPTION
                     "Updated the MIB with the new Brand Name"

        ::= { surpassRtpAdmin 1 }

SrxRowCountType ::= TEXTUAL-CONVENTION
           STATUS   current
           DESCRIPTION "Max size for table row count"
           SYNTAX Integer32 (0..2147483647)

SrxOnOffType ::= TEXTUAL-CONVENTION
           STATUS   current
           DESCRIPTION "Indicates the values of on and off variables."
           SYNTAX INTEGER {on(1),off(2)}

IkeKeyGenMethod ::= TEXTUAL-CONVENTION
           STATUS   current
           DESCRIPTION "The key Generation method for IKE"
           SYNTAX INTEGER {automatic(1),userinput(2)}

IkeKeyType ::= TEXTUAL-CONVENTION
           STATUS   current
           DESCRIPTION "The type of key to be used "
           SYNTAX INTEGER {ascii(1),hex(2)}

IkeKeyLength ::= TEXTUAL-CONVENTION
           STATUS   current
           DESCRIPTION "The length of the IKE key being used"
           SYNTAX Integer32 (16..200)

IkeKey ::= TEXTUAL-CONVENTION
           STATUS   current
           DESCRIPTION "The  IKE key being used"
           SYNTAX OCTET STRING(SIZE(16..200))

NameType ::= TEXTUAL-CONVENTION
           STATUS current
           DESCRIPTION "Defines the size of the Name field."
           SYNTAX OCTET STRING(SIZE(0..63))

-- **************************************************************************
-- hiPath8000 Managed Objects Object Identifiers
-- **************************************************************************

usSrxUce                  OBJECT IDENTIFIER ::= { hiq8000Admin 1 }

usSrxSip                  OBJECT IDENTIFIER ::= { hiq8000Admin 2 }

usSrxMgcp                 OBJECT IDENTIFIER ::= { hiq8000Admin 3 }

usSrxService              OBJECT IDENTIFIER ::= { hiq8000Admin 4 }

hiqFeatLic                OBJECT IDENTIFIER ::= { hiq8000Admin 5 }

hiqTraps                  OBJECT IDENTIFIER ::= { hiq8000Admin 47 } -- 47 is used for legacy reasons

END
