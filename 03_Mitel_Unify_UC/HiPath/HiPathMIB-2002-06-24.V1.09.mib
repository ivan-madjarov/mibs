HiPath-MIB DEFINITIONS ::= BEGIN
    IMPORTS
        MODULE-IDENTITY, OBJECT-TYPE, NOTIFICATION-TYPE, Integer32, 
        Counter32 
       FROM SNMPv2-SMI
        TEXTUAL-CONVENTION, DisplayString, DateAndTime 
       FROM SNMPv2-TC
        enterprises
       FROM RFC1155-SMI;

    siemens OBJECT IDENTIFIER ::= { enterprises 4329 }
    iandc   OBJECT IDENTIFIER ::= { siemens 2 }
    
    hiPathMIB MODULE-IDENTITY
    LAST-UPDATED "200206240000Z" --  June,24 2002
    ORGANIZATION 
      "Materna Information & Communicaton Networks"
    
    CONTACT-INFO 
         "Postal: Andreas van Almsick
                 Materna Informations&Communications
                 Vosskuhle 37
                 44141 Dortmund
                 Germany
         Email:  Andreas.vanAlmsick@materna.de"

        DESCRIPTION
                "This MIB is used in Siemens HiPath enabled applications 
                and components; 
		200107060000Z: Version 1.0
		200206240000Z: Version 1.1" 
            
    ::= { iandc 22 }

    --********************************************--
    --*** textual conventions ********************--
    --********************************************--
    -- encoding for Severity:
    -- 1 = unknown
    -- 2 = normal, installed
    -- 3 = warning
    -- 4 = minor
    -- 5 = major
    -- 6 = critical
    -- 7 = unmanaged
    -- 8 = restricted
    -- 9 = testing
    --10 = disabled
    ----------------------------
    
    Severity ::= INTEGER { unknown(1), normal(2), 
                           warning(3), minor(4), 
                           major(5), critical(6), 
			   unmanaged(7), restricted(8), 
			   testing(9), disabled(10) }

    Boolean ::= INTEGER { true(1), false(2) }
               
    --*************************--
    --*** Group Definitions ***--
    --*************************--

    hiPathHmhGroup           OBJECT IDENTIFIER ::= { hiPathMIB 1 }
    hiPathHiaGroup           OBJECT IDENTIFIER ::= { hiPathMIB 2 }
    hiPathHmpGroup           OBJECT IDENTIFIER ::= { hiPathMIB 3 }

    --** allows to specify sub MIBs  *****************************--
    hiPathMibs               OBJECT IDENTIFIER ::= { hiPathMIB 4 }
    --***********************************************************--
    --** known sub MIBs:
    --** hiPathLicenseMib ::= 1
    --************************************************************--

    hiPathEvtGroup           OBJECT IDENTIFIER ::= { hiPathMIB 10 }
    hiPathTrapGroup          OBJECT IDENTIFIER ::= { hiPathMIB 90 }
    hiPathComplianceModules  OBJECT IDENTIFIER ::= { hiPathMIB 91 }
    hiPathGroups             OBJECT IDENTIFIER ::= { hiPathMIB 92 }

    --*******************************************--
    --********HiPath Host Group *****************--
    --*******************************************--
    sysDesrc OBJECT-TYPE
        SYNTAX                  DisplayString
        MAX-ACCESS              read-write
        STATUS                  current
        DESCRIPTION
            "A (short) Description of the component"
        ::= { hiPathHmhGroup 1 }
    
    sysContact OBJECT-TYPE
        SYNTAX                  DisplayString
        MAX-ACCESS              read-write
        STATUS                  current
        DESCRIPTION
            "The responsible administrator"
        ::= { hiPathHmhGroup 2 }

    sysObjectID OBJECT-TYPE
        SYNTAX                  OBJECT IDENTIFIER
        MAX-ACCESS              read-only
        STATUS                  current
        DESCRIPTION
            "The object id assigned to this HiPath device. It is
            introduced because the MIB-2 object id could be used to
            identify the OS.  Therefore it is possible to identify a
            specialized HiPath component. If the HiPath MIB is used by
            an embedded system, this OID should be equal to the MIB-2
            sysObjectID entry."  
        ::= { hiPathHmhGroup 3 }
    
    sysLocation OBJECT-TYPE
        SYNTAX                  DisplayString
        MAX-ACCESS              read-write
        STATUS                  current
        DESCRIPTION
           "The location of the component. If sysLocation starts with
           'HiPath:' the remainder of the String is interpreted as
           /network//subnetwork and the component will be placed on a
           related submap by HiPath FM.

            E.g. 'HiPath:/europe/germany//region south/munich'.  This
            entry is introduced because the sysLocationEntry on a
            PC-Hardware could be for differnet reasons. If both
            entries (MIB-2 and HiPathMIB) start with 'HiPath:' the
            HiPathMIB entry superseeds the MIB-2 entry."
        ::= { hiPathHmhGroup 4 }

    agentVersion OBJECT-TYPE 
        SYNTAX                  DisplayString
        MAX-ACCESS              read-only
        STATUS                  current
        DESCRIPTION
            "The Version of the SNMP agent"
        ::= { hiPathHmhGroup 5 }
    
    mibVersion OBJECT-TYPE
        SYNTAX                  DisplayString
        MAX-ACCESS              read-only
        STATUS                  current
        DESCRIPTION
            "The version of the HiPath Information Base (now
            200206240000Z)" 
        ::= { hiPathHmhGroup 6 }
    
    hostname OBJECT-TYPE
        SYNTAX                  DisplayString
        MAX-ACCESS              read-only
        STATUS                  current
        DESCRIPTION
            "The hostname is included in the HiPath MIB to be
            indedependent from the MIB2. If hostname in MIB2 and
            HiPath MIB differ, the hostname given in the HiPath MIB
            superseds the hostname given in the MIB2" 
        ::= { hiPathHmhGroup 7 }

    sysState OBJECT-TYPE
        SYNTAX                  Severity
        MAX-ACCESS              read-only
        STATUS                  current
        DESCRIPTION
            "The state of the component"
        ::= { hiPathHmhGroup 8 }
    
    sysStateReset OBJECT-TYPE
        SYNTAX                  Integer32
        MAX-ACCESS              read-write
        STATUS                  current
        DESCRIPTION
            "If this variable is written, the state is reset to
            'normal'."
        ::= { hiPathHmhGroup 9 }
    
    sysArch OBJECT-TYPE
        SYNTAX                  DisplayString
        MAX-ACCESS              read-only
        STATUS                  current
        DESCRIPTION
            "The architecture of the host. E.g. x86, sunUltra, ..."
        ::= { hiPathHmhGroup 10 }
    
    osName OBJECT-TYPE
        SYNTAX                  DisplayString
        MAX-ACCESS              read-only
        STATUS                  current
        DESCRIPTION
            "The name of the operating system.  E.g. Windows, Solaris,
            ..."
        ::= { hiPathHmhGroup 11 }
    
    osVersion OBJECT-TYPE
        SYNTAX                  DisplayString
        MAX-ACCESS              read-only
        STATUS                  current
        DESCRIPTION
            "The verson of the operating System.  E.g 5.0 for
            Windows2000"
        ::= { hiPathHmhGroup 12 }
    
    sysMgmtURL OBJECT-TYPE
        SYNTAX                  DisplayString
        MAX-ACCESS              read-only
        STATUS                  current
        DESCRIPTION
            "Points to an page with gives access to the element
            manager of the component if available."
        ::= { hiPathHmhGroup 13 }
    
    sysDocURL OBJECT-TYPE
        SYNTAX                  DisplayString
        MAX-ACCESS              read-only
        STATUS                  current
        DESCRIPTION
            "Points to the documentation"
        ::= { hiPathHmhGroup 14 }

    sysIconURL OBJECT-TYPE
        SYNTAX                  DisplayString
        MAX-ACCESS              read-only
        STATUS                  current
        DESCRIPTION
            "Points to a file, which describes the location of the
            shape and the pixmaps for the icons to be used to display
            the compoent on the desktop map."
        ::= { hiPathHmhGroup 15 }

    sysTimezone OBJECT-TYPE
        SYNTAX                  DisplayString
        MAX-ACCESS              read-only
        STATUS                  current
        DESCRIPTION
            "The timezone where the system is located. It can be used
            to compute the local time from time entries in the
            evtTable and the traps.

	    The string has to be a valid Timezone string which can be
	    intepreted eg. by the JAVA Timzone class. Eg. 'GMT+1' for
	    Germany"
        ::= { hiPathHmhGroup 16 }


    sysVersion OBJECT-TYPE
        SYNTAX                  DisplayString
        MAX-ACCESS              read-only
        STATUS                  current
        DESCRIPTION
            "Version of the system."
        ::= { hiPathHmhGroup 17 }

    sysAppRegNumber OBJECT-TYPE
        SYNTAX                  Integer32
        MAX-ACCESS              read-only
        STATUS                  current
        DESCRIPTION 
	    "Number of entries in the sysAppRegTable"
        ::= { hiPathHmhGroup 18 }
    
    sysAppRegTable OBJECT-TYPE
        SYNTAX                  SEQUENCE OF SysAppRegTableEntry
        MAX-ACCESS              not-accessible
        STATUS                  current
        DESCRIPTION
           "This table contains URLs that point to HiPath application
           registration files and corresponding property file for
           localization. Filenames shall be constructed from templates

	    	    <sysObjectID>-<file version>.xml
		    <sysObjectID>-<file version>_<locale>.properties

            Filenames must not contain dots (.), except the ones from
            the template.  sysObjectID shall be written as 1-2-3-4 for
            oid 1.2.3.4.
		    
            File version will be compared to existing application
            registration files on the HiPath Mgmt Server. If file
            version is greater than existing file's file version, the
            new file will be downloaded.
            
	    Registration files use XML-syntax and shall end with the
	    suffix .xml.  Property files have Java property file
	    syntax and shall end with .properties.
	   
	    Application Registration is described in the technical
	    documentations of HiPath interfaces. The sysObjectID
	    prefix ensures a single application registration for each
	    kind of HiPath Device."
        ::= { hiPathHmhGroup 19 }

    sysAppRegTableEntry OBJECT-TYPE
        SYNTAX                  SysAppRegTableEntry
        MAX-ACCESS              not-accessible
        STATUS                  current
        DESCRIPTION
            "A (conceptionanl) entry for the sysAppRegTable."
	INDEX                   { sysAppRegIndex }
        ::= { sysAppRegTable 1 }

    SysAppRegTableEntry ::= SEQUENCE {
         sysAppRegIndex            Integer32,
         sysAppRegURL              DisplayString }
 
    sysAppRegIndex OBJECT-TYPE
        SYNTAX                  Integer32
	MAX-ACCESS              read-only
	STATUS                  current
	DESCRIPTION 
	    "Table index"
	::= { sysAppRegTableEntry 1 }

    sysAppRegURL OBJECT-TYPE
        SYNTAX                  DisplayString
        MAX-ACCESS              read-only
        STATUS                  current
        DESCRIPTION
            "An URL to a application registration file or a property
            file that is used for localization."
        ::= { sysAppRegTableEntry 2 }

    sysOperatingMode OBJECT-TYPE
        SYNTAX                  DisplayString
	MAX-ACCESS              read-only
	STATUS                  current
	DESCRIPTION
            "Some devices can have different operation modes. This
            string is appended to the label on the HiPath Desktop to
            show the operation mode of this device."
	::= { hiPathHmhGroup 20 }

    --********************************************--
    --*********HiPath Application Group***********--
    --********************************************--

    appNumber OBJECT-TYPE
        SYNTAX                  Integer32
        MAX-ACCESS              read-only
        STATUS                  current
        DESCRIPTION 
	    "Number of entries in the appTable"
        ::= { hiPathHiaGroup 1 }
    
    appTable OBJECT-TYPE
        SYNTAX                  SEQUENCE OF AppTableEntry
        MAX-ACCESS              not-accessible
        STATUS                  current
        DESCRIPTION
            "This table contains the installed HiPath enabled
            applications."
        ::= { hiPathHiaGroup 2 }

    appTableEntry OBJECT-TYPE
        SYNTAX                  AppTableEntry
        MAX-ACCESS              not-accessible
        STATUS                  current
        DESCRIPTION
            "A (conceptionanl) entry for the appTable."
        INDEX                   {appName}
        ::= { appTable 1 }

    AppTableEntry ::= SEQUENCE {
         appName                DisplayString,
         appDescr               DisplayString,
         appContact             DisplayString,
         appVersion             DisplayString,
         appState               Severity,
         appStateReset          Integer32,
         appMgmtURL             DisplayString,
         appDocURL              DisplayString,
         appIconURL             DisplayString,
	 appId                  DisplayString}
        
    appName OBJECT-TYPE
        SYNTAX                  DisplayString
        MAX-ACCESS              read-only
        STATUS                  current
        DESCRIPTION
            "The application name."
        ::= { appTableEntry 1 }
    
    appDescr OBJECT-TYPE
        SYNTAX                  DisplayString
        MAX-ACCESS              read-write
        STATUS                  current
        DESCRIPTION
            "A (short) description of the application."
        ::= { appTableEntry 2 }

    appContact OBJECT-TYPE
        SYNTAX                  DisplayString
        MAX-ACCESS              read-write
        STATUS                  current
        DESCRIPTION
            "Information about the responsible administrator.
            e.g. Name and phone"
        ::= { appTableEntry 3 }
    
    appVersion OBJECT-TYPE
        SYNTAX                  DisplayString
        MAX-ACCESS              read-only
        STATUS                  current
        DESCRIPTION           
            "The version of the installed application."
        ::= { appTableEntry 4 }

    appState OBJECT-TYPE
        SYNTAX                  Severity
        MAX-ACCESS              read-only
        STATUS                  current
        DESCRIPTION           
            "The current state of the application."
        ::= { appTableEntry 5 }
    
    appStateReset OBJECT-TYPE
        SYNTAX                  Integer32
        MAX-ACCESS              read-write
        STATUS                  current
        DESCRIPTION
            "If this variable is written,
            appState is reset to normal(2)"
        ::= { appTableEntry 6 }

    appMgmtURL OBJECT-TYPE 
        SYNTAX                  DisplayString
        MAX-ACCESS              read-only
        STATUS                  current
        DESCRIPTION
            "Points to a page which gives access to the applications
            element manager if available."
        ::= { appTableEntry 7 }
    
    appDocURL OBJECT-TYPE
        SYNTAX                  DisplayString
        MAX-ACCESS              read-only
        STATUS                  current
        DESCRIPTION
            "Points to the online documentation for this
            application."
        ::= { appTableEntry 8 }
    
    appIconURL OBJECT-TYPE
        SYNTAX                  DisplayString
        MAX-ACCESS              read-only
        STATUS                  current
        DESCRIPTION
            "Points to a file, which describes where to find the shape
            and the pixmaps for the icons to be used to display the
            application on the desktop map."
        ::= { appTableEntry 9 }

    appId OBJECT-TYPE
        SYNTAX                  DisplayString
        MAX-ACCESS              read-only
        STATUS                  current
        DESCRIPTION
            "A technical id of the application. This id shall not be
            changed, even if the marketing name of the application
            changes."
        ::= { appTableEntry 10 }


    appExecNumber OBJECT-TYPE
        SYNTAX                  Integer32
        MAX-ACCESS              read-only
        STATUS                  current
        DESCRIPTION
            "Number of entries in the executable table"
        ::= { hiPathHiaGroup 3 }
    
    appExecTable OBJECT-TYPE
        SYNTAX                  SEQUENCE OF AppExecTableEntry
        MAX-ACCESS              not-accessible
        STATUS                  current
        DESCRIPTION
            "This table describes where to find the executeables for
            the applications."
        ::= { hiPathHiaGroup 4 }

    appExecTableEntry OBJECT-TYPE
        SYNTAX                  AppExecTableEntry
        MAX-ACCESS              not-accessible
        STATUS                  current 
        DESCRIPTION
            "(conceptionanl) appExecTable row"
        INDEX { appExecIdx, appExecAppName }
        ::= { appExecTable 1 }

    AppExecTableEntry ::= SEQUENCE {
          appExecIdx            Integer32,
          appExecAppName        DisplayString,
          appExecutable         DisplayString }
            
    appExecIdx OBJECT-TYPE
        SYNTAX                  Integer32
        MAX-ACCESS              read-only
        STATUS                  current
        DESCRIPTION
            "A (configured) index for the executable."
        ::= { appExecTableEntry 1 }

    appExecAppName OBJECT-TYPE
        SYNTAX                  DisplayString
        MAX-ACCESS              read-only
        STATUS                  current
        DESCRIPTION
            "The application this executable belongs to.
            Can be used as index for the appTable."
        ::= { appExecTableEntry 2 }
    
    appExecutable OBJECT-TYPE
        SYNTAX                  DisplayString
        MAX-ACCESS              read-only
        STATUS                  current
        DESCRIPTION
            "Describes where to find the executable (in URL syntax)
            E.g. file:/opt/HiPath/bin/collecting"
        ::= { appExecTableEntry 3 }

    --***********************************************--
    --** HiPath Process Group ***********************--
    --***********************************************--

    processNumber OBJECT-TYPE
        SYNTAX                  Integer32
        MAX-ACCESS              read-only
        STATUS                  current
        DESCRIPTION
            "Number of Entries in the processTable"     
        ::= { hiPathHmpGroup 1 }

    processTable OBJECT-TYPE
        SYNTAX                  SEQUENCE OF ProcessTableEntry
        MAX-ACCESS              not-accessible
        STATUS                  current
        DESCRIPTION
            "This table contains an entry for each process which is
            assumed to be running (services). This table can be read
            as processes configuration."
        ::= { hiPathHmpGroup 2 }
        
    processTableEntry OBJECT-TYPE
        SYNTAX                  ProcessTableEntry
        MAX-ACCESS              not-accessible
        STATUS                  current
        DESCRIPTION
            "(Conceptionanl) processTable entry."
        INDEX { processApp, processIndex }
        ::= { processTable 1 }

    ProcessTableEntry ::= SEQUENCE {
        processApp              DisplayString,
        processIndex            Integer32,
        processPID              Integer32,
        processParameter        DisplayString,
        processExecutable       Integer32,
        processUp               Boolean,
        processState            Severity,
        processStateReset       Integer32,
        processMgmtURL          DisplayString,
        processDocURL           DisplayString,
        processIconURL          DisplayString }

    processApp OBJECT-TYPE
        SYNTAX                  DisplayString
        MAX-ACCESS              read-only
        STATUS                  current
        DESCRIPTION     
            "The application the process belongs to."
        ::= { processTableEntry 1 }

    processIndex OBJECT-TYPE
        SYNTAX                  Integer32
        MAX-ACCESS              read-only
        STATUS                  current
        DESCRIPTION
            "An unique index."
        ::= { processTableEntry 2 }

    processPID OBJECT-TYPE      
        SYNTAX                  Integer32
        MAX-ACCESS              read-only
        STATUS                  current
        DESCRIPTION
            "The PID assigned to process by the operating system.  0
            if the process is down."
        ::= { processTableEntry 3 }

    processParameter OBJECT-TYPE
        SYNTAX                  DisplayString
        MAX-ACCESS              read-only
        STATUS                  current   
        DESCRIPTION
            "The (command line) paramters of the process."
        ::= { processTableEntry 4 }
    
    processExecutable OBJECT-TYPE
        SYNTAX                  Integer32
        MAX-ACCESS              read-only
        STATUS                  current
        DESCRIPTION
            "Index of the executeable in the appExecTable"
        ::= { processTableEntry 5 }

    processUp OBJECT-TYPE
        SYNTAX                  Boolean
        MAX-ACCESS              read-only
        STATUS                  current
        DESCRIPTION
            "'True' if the process is running, false if the process is
            configured but not running. If false there should be
            always a failure state on this process."
        ::= { processTableEntry 6 }

    processState OBJECT-TYPE
        SYNTAX                  Severity
        MAX-ACCESS              read-only
        STATUS                  current
        DESCRIPTION           
            "The current state of the process."
        ::= { processTableEntry 7 }
    
    processStateReset OBJECT-TYPE
        SYNTAX                  Integer32
        MAX-ACCESS              read-write
        STATUS                  current
        DESCRIPTION
            "If this variable is written, processState is reset to
            normal(2)"
        ::= { processTableEntry 8 }
    
    processMgmtURL OBJECT-TYPE 
        SYNTAX                  DisplayString
        MAX-ACCESS              read-only
        STATUS                  current
        DESCRIPTION
            "Points to an page with gives access to the processes
            element manager if available."
        ::= { processTableEntry 9 }
    
    processDocURL OBJECT-TYPE
        SYNTAX                  DisplayString
        MAX-ACCESS              read-only
        STATUS                  current
        DESCRIPTION
            "Points to the online documentation for this process."
        ::= { processTableEntry 10 }
    
    processIconURL OBJECT-TYPE
        SYNTAX                  DisplayString
        MAX-ACCESS              read-only
        STATUS                  current
        DESCRIPTION
            "Points to a file, which describes where to find the shape
            and the pixmaps for the icons to be used to display the
            process on the desktop map."
        ::= { processTableEntry 11 }

   
    --************************************************--
    --** evtTable and evtHistoryTable provide       **--
    --** different views on the same data           **--
    --** evtTable is index by evtApp,evtProcess and **--
    --** evtLogIndex to access entries for a        **--
    --** specific process or application.           **--
    --** evtHistoryTable is index only by           **--
    --** evtLogIndex to be accessed in temporary    **--
    --** order.                                     **--
    --************************************************--
    
    evtNumber OBJECT-TYPE
        SYNTAX                  Integer32
        MAX-ACCESS              read-only
        STATUS                  current
        DESCRIPTION
            "The number of entries in the evtTable and the
            evtHistoryTable."
        ::= { hiPathEvtGroup 1 }

    evtTable OBJECT-TYPE
        SYNTAX                  SEQUENCE OF EvtTableEntry
        MAX-ACCESS              not-accessible
        STATUS                  current
        DESCRIPTION
            "This table contains an entry for each sent trap."
        ::= { hiPathEvtGroup 2 }

    evtTableEntry OBJECT-TYPE
        SYNTAX                  EvtTableEntry
        MAX-ACCESS              not-accessible
        STATUS                  current
        DESCRIPTION
            "A (conceptional) row in the evtTable"
        INDEX { evtAppName, evtProcess, evtLogIndex }
        ::= { evtTable 1 }

    EvtTableEntry ::= SEQUENCE {
        evtAppName              DisplayString,
        evtProcess              Integer32,
        evtLogIndex             Integer32,
        evtOID                  OBJECT IDENTIFIER,
        evtDate                 DateAndTime,
        evtSeverity             Severity,
        evtDescr                DisplayString }

    evtAppName OBJECT-TYPE
        SYNTAX                  DisplayString
        MAX-ACCESS              read-only
        STATUS                  current
        DESCRIPTION   
            "The application this event was caused by. Empty String if
            event occured on host/component level."
        ::= { evtTableEntry 1 }

    evtProcess OBJECT-TYPE
        SYNTAX                  Integer32
        MAX-ACCESS              read-only
        STATUS                  current
        DESCRIPTION
            "The process this event was caused by. 0 if the event was
            not caused by a process.  Events which are not caused by
            permanent processes are mapped to the application!"
        ::= { evtTableEntry 2 }

    evtLogIndex OBJECT-TYPE
        SYNTAX                  Integer32
        MAX-ACCESS              read-only
        STATUS                  current
        DESCRIPTION
            "The sequence of indexes increases in temporary order."
        ::= { evtTableEntry 3}
    
    evtOID OBJECT-TYPE
        SYNTAX                  OBJECT IDENTIFIER
        MAX-ACCESS              read-only
        STATUS                  current
        DESCRIPTION
            "The OID of the trap that was sent for this event.
            E.g. if a hiPathHostDown trap was sent, the entry for that
            trap should be '1.3.6.1.4.1.4329.2.22.90.2'"
        ::= { evtTableEntry 4 }

    evtDate OBJECT-TYPE
        SYNTAX                  DateAndTime
        MAX-ACCESS              read-only
        STATUS                  current
        DESCRIPTION    
            "The time this event occured in UTC."
        ::= { evtTableEntry 5 }
    
    evtSeverity OBJECT-TYPE
        SYNTAX                  Severity
        MAX-ACCESS              read-only       
        STATUS                  current
        DESCRIPTION            
            "The severity of this event"
        ::= { evtTableEntry 6 }
    
    evtDescr OBJECT-TYPE
        SYNTAX                  DisplayString
        MAX-ACCESS              read-only
        STATUS                  current 
        DESCRIPTION
            "A textual, human readable description of 
            the event."
        ::= { evtTableEntry 7 }

    evtHistoryTable OBJECT-TYPE
        SYNTAX                  SEQUENCE OF EvtHistoryTableEntry
        MAX-ACCESS              not-accessible
        STATUS                  current
        DESCRIPTION
            "This Table contains an entry for each sent trap."
        ::= { hiPathEvtGroup 3 }

    evtHistoryTableEntry OBJECT-TYPE
        SYNTAX                  EvtHistoryTableEntry
        MAX-ACCESS              not-accessible
        STATUS                  current
        DESCRIPTION
            "A (conceptionanl) row in the evtTable"
        INDEX { evtLogIndex }
        ::= { evtHistoryTable 1 }

    EvtHistoryTableEntry ::= SEQUENCE {
        evtHistoryAppName       DisplayString,
        evtHistoryProcess       Integer32,
        evtHistoryLogIndex      Integer32,
        evtHistoryOID           OBJECT IDENTIFIER,
        evtHistoryDate          DateAndTime,
        evtHistorySeverity      Severity,
        evtHistoryDescr         DisplayString }

    evtHistoryAppName OBJECT-TYPE
        SYNTAX                  DisplayString
        MAX-ACCESS              read-only
        STATUS                  current
        DESCRIPTION   
            "The application this event was caused by. Empty String if
            event occured on host/component level."
        ::= { evtHistoryTableEntry 1 }

    evtHistoryProcess OBJECT-TYPE
        SYNTAX                  Integer32
        MAX-ACCESS              read-only
        STATUS                  current
        DESCRIPTION
            "The process this event was caused by. 0 if the event was
            not caused by a process.  Events which are not caused by
            permanent processes are mapped to the application!"
        ::= { evtHistoryTableEntry 2 }

    evtHistoryLogIndex OBJECT-TYPE
        SYNTAX                  Integer32
        MAX-ACCESS              read-only
        STATUS                  current
        DESCRIPTION
            "Unique index"
        ::= { evtHistoryTableEntry 3}
    
    evtHistoryOID OBJECT-TYPE
        SYNTAX                  OBJECT IDENTIFIER
        MAX-ACCESS              read-only
        STATUS                  current
        DESCRIPTION
            "The OID of trap, which was sent for this event."
        ::= { evtHistoryTableEntry 4 }

    evtHistoryDate OBJECT-TYPE
        SYNTAX                  DateAndTime
        MAX-ACCESS              read-only
        STATUS                  current
        DESCRIPTION    
            "the time this event occured in UTC."
        ::= { evtHistoryTableEntry 5 }
    
    evtHistorySeverity OBJECT-TYPE
        SYNTAX                  Severity
        MAX-ACCESS              read-only       
        STATUS                  current
        DESCRIPTION            
            "The severity of this event"
        ::= { evtHistoryTableEntry 6 }
    
    evtHistoryDescr OBJECT-TYPE
        SYNTAX                  DisplayString
        MAX-ACCESS              read-only
        STATUS                  current 
        DESCRIPTION
            "A textual, human readable description of 
            the event."
        ::= { evtHistoryTableEntry 7 }

   
    --**********************************************--
    --*** HiPath Traps *****************************--
    --**********************************************--

    hiPathTrapCounter OBJECT-TYPE
        SYNTAX                  Counter32
        MAX-ACCESS              read-only
        STATUS                  current
        DESCRIPTION
             "This counter is increased whenever a trap is sent. It is
             used by the manangement application to discover lost
             traps"
        ::= { hiPathTrapGroup 99 }

    hiPathTrapSeverity OBJECT-TYPE
        SYNTAX                  Severity
        MAX-ACCESS              not-accessible
        STATUS                  current
        DESCRIPTION
            "The Severity of the trap. This Severity can be different
            to the status of the object!"
    ::= { hiPathTrapGroup 100 }
        
    --*********************************************--
    --******** HMH Traps **************************--
    --*********************************************--   

    hiPathHostUp NOTIFICATION-TYPE
    OBJECTS                     { hostname, evtHistoryDate, evtHistoryDescr }
    STATUS                      current
    DESCRIPTION
        "A hiPathHostUp trap signifies that a host with HiPath MIB
        agent is coming up."
    ::= { hiPathTrapGroup 1 }

    hiPathHostDown NOTIFICATION-TYPE
        OBJECTS                 { hostname, evtHistoryDate, evtHistoryDescr }
        STATUS                  current
        DESCRIPTION
            "A hiPathHostDown trap signifies that a host with HiPath
            MIB agent is going down."
        ::= { hiPathTrapGroup 2 }

    hiPathHostStatusChange NOTIFICATION-TYPE
        OBJECTS                 { hostname, sysState, evtHistoryDate,
                                  evtHistoryDescr, hiPathTrapSeverity }
        STATUS                  current
        DESCRIPTION
            "A hiPathHostStatusChange trap signifies that the status
            of the HiPath host has changed due host trouble (The MIB
            can be used for new hardware components. Those components
            could have its own error management). If the error
            disappears there shall be hiPathHostStatusChange trap
            too."
        ::= { hiPathTrapGroup 3 }

    --*********************************************--
    --******** HIA Traps **************************--
    --*********************************************--
    
    hiPathApplicationInstalled NOTIFICATION-TYPE
        OBJECTS                 { hostname, appName, evtHistoryDate,
                                  evtHistoryDescr }
        STATUS                  current
        DESCRIPTION
            "A hiPathApplicationInstalled trap signifies a new
            installed HiPath enabled application."
        ::= { hiPathTrapGroup 4 }

    hiPathApplicationDeinstalled NOTIFICATION-TYPE
        OBJECTS                 { hostname, appName, evtHistoryDate,
                                  evtHistoryDescr }
        STATUS                  current
        DESCRIPTION
            "A hiPathApplicationDeinstalled trap signifies the
            deinstallation of an HiPath enabled application."
        ::= { hiPathTrapGroup 5 }

    hiPathApplicationStatusChange NOTIFICATION-TYPE
        OBJECTS                 { hostname, appName, appState, evtHistoryDate,
                                  evtHistoryDescr, hiPathTrapSeverity}
        STATUS                  current
        DESCRIPTION
            "A hiPathApplicationStatusChange trap a status change of a
            HiPath enabled application. This trap is sent, if a
            process wich is not of service type, causes trouble. If
            the error state disappears there shall be a
            hiPathApplicationStatusChange trap too."
        ::= { hiPathTrapGroup 6 }

    --*********************************************--
    --******** HMP Traps **************************--
    --*********************************************--

    hiPathProcessUp NOTIFICATION-TYPE
        OBJECTS                 { hostname, 
                                  appName, 
                                  processIndex, 
                                  evtHistoryDate,
                                  evtHistoryDescr }
        STATUS                  current
        DESCRIPTION
            "A hiPathProcessUp trap signifies an starting HiPath
            enabled process."  ::= { hiPathTrapGroup 7 }
    hiPathProcessDown NOTIFICATION-TYPE
        OBJECTS                 { hostname, 
                                  appName, 
                                  processIndex, 
                                  evtHistoryDate,
                                  evtHistoryDescr }
        STATUS                  current
        DESCRIPTION
           "A hiPathProcessDown trap signifies an down going HiPath
           enabled process."
        ::= { hiPathTrapGroup 8 }

    hiPathProcessStatusChange NOTIFICATION-TYPE

        OBJECTS { hostname, appName, processIndex, processState,
                  evtHistoryDate, evtHistoryDescr, 
                  hiPathTrapSeverity } 
        STATUS                  current 
        DESCRIPTION 
            "A hiPathProcessStatusChange trap signifies a status
            change for a HiPath enabled process."  
        ::= { hiPathTrapGroup 9 }

    -- hiPathCompliance Statements --
    hiPathCompliance MODULE-COMPLIANCE
        STATUS                  current
        DESCRIPTION
            "The requirement for conformance to the HiPath MIB"
        MODULE -- this module
        MANDATORY-GROUPS { 
           hiPathHmhGroupCompliance, 
           hiPathHiaGroupCompliance, 
           hiPathHmpGroupCompliance,
           hiPathEvtGroupCompliance,
           hiPathTrapGroupCompliance }
        ::= { hiPathComplianceModules 1 }

    hiPathHmhGroupCompliance OBJECT-GROUP
        OBJECTS { sysDesrc, sysContact, sysObjectID, sysLocation,
                  agentVersion, mibVersion, hostname, sysState, 
                  sysArch, sysOperatingMode, sysAppRegTable, osName, osVersion}
        STATUS                  current
        DESCRIPTION
            "The HiPath Managed Host Group"
        ::= {hiPathGroups 1 }
        
    hiPathHiaGroupCompliance OBJECT-GROUP
        OBJECTS { appNumber, appTable, appTableEntry, appName,
                  appDescr, appContact, appVersion, appState,
                  appExecNumber, appExecTable, appExecTableEntry,
                  appExecIdx, appExecutable, appId }
        STATUS                  current
        DESCRIPTION
            "The HiPath Application Group."
        ::= { hiPathGroups 2 }
    
    hiPathHmpGroupCompliance OBJECT-GROUP
        OBJECTS { processNumber, processTable, processTableEntry,
                  processApp, processIndex, processPID, processParameter,
                  processExecutable, processUp, processState }
        STATUS                  current
        DESCRIPTION
            "The HiPath Process Group"
        ::= { hiPathGroups 3 }
                  
    hiPathEvtGroupCompliance OBJECT-GROUP
        OBJECTS { evtNumber, 
                  evtTable, evtTableEntry, evtAppName, evtProcess, 
                  evtLogIndex, evtOID, evtDate, evtSeverity, evtDescr,
                  evtHistoryTable, evtHistoryTableEntry, evtHistoryAppName,
                  evtHistoryProcess, evtHistoryLogIndex, evtHistoryOID,
                  evtHistoryDate, evtHistorySeverity, evtHistoryDescr }
        STATUS                  current
        DESCRIPTION 
            "The HiPath Event Group."
        ::= { hiPathGroups 10 }

    hiPathTrapGroupCompliance OBJECT-GROUP
        OBJECTS { hiPathTrapCounter }
        STATUS                  current
        DESCRIPTION 
            "The HiPath Trap Group."
        ::= { hiPathGroups 90 }
END
