-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


MX-MBLDP-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixHardware
    FROM MX-SMI2;

mbLdpMIB MODULE-IDENTITY
 LAST-UPDATED   "0802210000Z"
 ORGANIZATION " Mediatrix Telecom, Inc. "
 CONTACT-INFO " Mediatrix Telecom, Inc.
                4229, Garlock Street
                Sherbrooke (Quebec)
                Canada
                Phone: (819) 829-8749
                "
 DESCRIPTION  " MbLdp


                "
 -- ****************************************************************************
 
 -- Revision history
 -- ****************************************************************************
 REVISION       "0802210000Z"
 DESCRIPTION  " Initial Revision "
 REVISION       "0905260000Z"
 DESCRIPTION  " Renamed the Mediatrix 4102 plus product name to Mediatrix 4102S
                "
 REVISION       "1005100000Z"
 DESCRIPTION  " Added ResetButtonManagement "
 REVISION       "1012100000Z"
 DESCRIPTION  " Added Eth group including PortsConfiguration "
 REVISION       "1102220000Z"
 DESCRIPTION  " Added RingManagement "
 REVISION       "1205170000Z"
 DESCRIPTION  " Deprecated HiddenButtonEnable, ResetButtonManagement,
                RingManagement, Eth, NotificationsGroup and ConfigurationGroup.
                "
 ::= { mediatrixHardware 40103 }

mbLdpMIBObjects OBJECT IDENTIFIER ::= { mbLdpMIB 1 }

-- Scalar:Reset/Default Button Management

resetButtonManagement OBJECT-TYPE
 SYNTAX        INTEGER { all(100) , disablePartialReset(200) }
 MAX-ACCESS    read-write
 STATUS        deprecated
 DESCRIPTION " Reset/Default Button Management

               Configures the actions allowed on the reset/default button.

                 * All: All the actions are allowed: reset, partial reset and
                   factory reset.
                 * DisablePartialReset: All actions are allowed except the
                   partial reset.

               The reset action restarts the unit.

               The partial reset action provides a way to contact the unit in a
               known and static state while keeping most of the configuration
               unchanged.

               The factory reset action reverts the unit back to its default
               factory settings.


               "
 DEFVAL        { all }
 ::= { mbLdpMIBObjects 100 }

-- Scalar:Ring Management

ringManagement OBJECT-TYPE
 SYNTAX        INTEGER { cascade(100) , simultaneous(200) }
 MAX-ACCESS    read-write
 STATUS        deprecated
 DESCRIPTION " Ring Management

               Ring management determines how to ring more than one port.

                 * Cascade: FXS ports are prevented from ringing at the same
                   time in order to reduce the peak power usage of the device.
                 * Simultaneous: All ports are ringing at the same time.


               "
 DEFVAL        { cascade }
 ::= { mbLdpMIBObjects 200 }

-- ****************************************************************************

-- Group:Eth

-- ****************************************************************************

eth OBJECT IDENTIFIER
 ::= { mbLdpMIBObjects 10000 }
 -- Scalar:Ports Configuration

 portsConfiguration OBJECT-TYPE
  SYNTAX        INTEGER { separate(100) , bridge(200) }
  MAX-ACCESS    read-write
  STATUS        deprecated
  DESCRIPTION " Ports Configuration

                Configures how each port provides a link interface.

                  * Separate: Each Ethernet port provides an independent link
                    interface. This is the required configuration for IP
                    Routing.
                  * Bridge: Both Ethernet ports are bridged together and
                    provide a single link interface.


                "
  DEFVAL        { separate }
  ::= { eth 100 }

-- End of group:Eth

-- ****************************************************************************

-- Group:Notification Messages Configuration

-- ****************************************************************************

notificationsGroup OBJECT IDENTIFIER
 ::= { mbLdpMIBObjects 60010 }
 -- Scalar:Minimal Severity of Notification

 minSeverity OBJECT-TYPE
  SYNTAX        INTEGER { disable(0) , debug(100) , info(200) , warning(300) ,
                error(400) , critical (500) }
  MAX-ACCESS    read-write
  STATUS        deprecated
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { mbLdpMIBObjects 60020 }
 -- Scalar:Need Restart

 needRestartInfo OBJECT-TYPE
  SYNTAX        INTEGER { no(0) , yes(100) }
  MAX-ACCESS    read-only
  STATUS        deprecated
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
