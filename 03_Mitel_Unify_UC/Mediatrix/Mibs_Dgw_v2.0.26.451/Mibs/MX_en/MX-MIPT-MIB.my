-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


MX-MIPT-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

miptMIB MODULE-IDENTITY
 LAST-UPDATED   "0511290000Z"
 ORGANIZATION " Mediatrix Telecom, Inc. "
 CONTACT-INFO " Mediatrix Telecom, Inc.
                4229, Garlock Street
                Sherbrooke (Quebec)
                Canada
                Phone: (819) 829-8749
                "
 DESCRIPTION  " Media IP Transport

                The Media IP Transport service allows to configure the voice
                and data capabilities of each endpoint.
                "
 -- ****************************************************************************
 
 -- Revision history
 -- ****************************************************************************
 REVISION       "0511290000Z"
 DESCRIPTION  " Initial Revision "
 REVISION       "0707110000Z"
 DESCRIPTION  " Modified the
                DefaultCodecVsBearerCapabilitiesMapping.InformationTransferCap
                and DefaultCodecVsBearerCapabilitiesMapping.Codec DisplayDoc
                tag content. Added the
                DefaultCodecVsBearerCapabilitiesMapping.MappingType variable. "
 REVISION       "0708230000Z"
 DESCRIPTION  " Added minimum and maximum values used for predefined jitter
                buffer configuration. "
 REVISION       "0712050000Z"
 DESCRIPTION  " Added SecurityGroup and IpTransportSrtpBasePort. Fixed codec
                ptime description. "
 REVISION       "0801100000Z"
 DESCRIPTION  " Added DspTracingGroup and DspTracingEnable variable. "
 REVISION       "0803050000Z"
 DESCRIPTION  " Modify PcmCapture description. "
 REVISION       "0803260000Z"
 DESCRIPTION  " Added AllowUnsecureT38WithSrtp. "
 REVISION       "0806190000Z"
 DESCRIPTION  " Added StatisticsGroup. "
 REVISION       "0807060000Z"
 DESCRIPTION  " Added DspStatsGroup. "
 REVISION       "0808070000Z"
 DESCRIPTION  " Added a new clear channel codec named X-CCD Clear Channel and
                all the variables related to it. All these new variables are
                under the CodecXCCDGroup. "
 REVISION       "0808270000Z"
 DESCRIPTION  " Modify PcmCapture description. "
 REVISION       "0901230000Z"
 DESCRIPTION  " Add KeyManagement variable. "
 REVISION       "0907200000Z"
 DESCRIPTION  " Added DefaultCodecT38DetectionThreshold and
                EpSpecificCodecT38.DetectionThreshold variables. "
 REVISION       "0909080000Z"
 DESCRIPTION  " Updated PcmCaptureEndpoint and DspStatsFilter descriptions. "
 REVISION       "0910300000Z"
 DESCRIPTION  " Updated the description of the DspTracingEnable variable to
                match the description in Dgw 1.1 "
 REVISION       "0912210000Z"
 DESCRIPTION  " Modified the datarange of the CodecClearModeDataPriority,
                CodecClearChannelDataPriority and CodecXCCDDataPriority
                variables. "
 REVISION       "1004130000Z"
 DESCRIPTION  " Added InteropGroup and InteropGroup.EnforceSymmetricRtpEnable
                variable. "
 REVISION       "1009300000Z"
 DESCRIPTION  " Added variables to configure the jitter buffer when in voice
                band data. "
 REVISION       "1012200000Z"
 DESCRIPTION  " Added InteropDtmfRtpInitialPacketQty variable. "
 REVISION       "1110260000Z"
 DESCRIPTION  " Changed PcmCaptureIpAddr variable data type. "
 REVISION       "1301170000Z"
 DESCRIPTION  " Added ChannelStatistics table. "
 REVISION       "1303260000Z"
 DESCRIPTION  " Changed the default min ptime value for uLaw, aLaw, G.726 and
                G.729 to 30ms. "
 ::= { mediatrixServices 1600 }

miptMIBObjects OBJECT IDENTIFIER ::= { miptMIB 1 }

-- ****************************************************************************

-- Group:Voice Codec

-- ****************************************************************************

codecGroup OBJECT IDENTIFIER
 ::= { miptMIBObjects 100 }
 -- Scalar:Default Generic VAD Configuration

 defaultCodecGenericVoiceActivityDetection OBJECT-TYPE
  SYNTAX        INTEGER { disable(100) , transparent(200) , conservative(300)
                }
  MAX-ACCESS    read-write
  STATUS        current
  DESCRIPTION " Default Generic VAD Configuration

                If Voice Activity Detection (VAD) is enabled, then speech
                frames are only sent during talkspurts (periods of audio
                activity).

                During silence periods, no speech frames are sent, but Comfort
                Noise (CN) packets containing information about background
                noise may be sent (see draft-ietf-avt-rtp-cn-05.txt). This
                variable specifies the sensitivity of the VAD algorithm to
                silence periods.

                The generic VAD is used by codecs without built-in VAD like
                G.711 and G.726.

                  * Disable: VAD disabled.
                  * Transparent: VAD enabled - low sensitivity to silence
                    periods.
                  * Conservative: VAD enabled - normal sensitivity to silence
                    periods.

                If a specific configuration is set in the
                EpSpecificCodec.GenericVoiceActivityDetection variable and the
                EpSpecificCodec.EnableConfig variable is set to 'Enable', then
                it overrides the current default configuration.


                "
  DEFVAL        { conservative }
  ::= { codecGroup 100 }

 -- ***************************************************************************
 
 -- Table:Endpoint Specific Voice Codec Configuration

 -- ***************************************************************************
 
 epSpecificCodecTable OBJECT-TYPE
  SYNTAX                SEQUENCE OF EpSpecificCodecEntry
  MAX-ACCESS            not-accessible
  STATUS                current
  DESCRIPTION        "  Endpoint Specific Voice Codec Configuration

                        Endpoint specific configuration.
                        "
  ::= { codecGroup 200 }
  epSpecificCodecEntry OBJECT-TYPE
   SYNTAX        EpSpecificCodecEntry
   MAX-ACCESS    not-accessible
   STATUS        current
   DESCRIPTION " A row in table Endpoint Specific Voice Codec Configuration .
                 "
   INDEX         {
                   epSpecificCodecEpId
                 }

   ::= { epSpecificCodecTable 1 }

  EpSpecificCodecEntry ::= SEQUENCE
  {
    epSpecificCodecEpId                          OCTET STRING,
    epSpecificCodecEnableConfig                  MxEnableState,
    epSpecificCodecGenericVoiceActivityDetection INTEGER
  }

  -- Index:Endpoint Identifier

  epSpecificCodecEpId OBJECT-TYPE
   SYNTAX        OCTET STRING
   MAX-ACCESS    read-only
   STATUS        current
   DESCRIPTION " Endpoint Identifier

                 String that identifies an endpoint in other tables.
                 "
   ::= { epSpecificCodecEntry 100 }

  -- Columnar:Enable Configuration

  epSpecificCodecEnableConfig OBJECT-TYPE
   SYNTAX        MxEnableState
   MAX-ACCESS    read-write
   STATUS        current
   DESCRIPTION " Enable Configuration

                 Defines the configuration to use for a specific endpoint.

                   * Disable: The endpoint uses the default configuration as
                     defined in the DefaultCodecGenericVoiceActivityDetection
                     variable.
                   * Enable: The endpoint uses the specific configuration as
                     defined in the
                     EpSpecificCodec.GenericVoiceActivityDetection variable.


                 "
   DEFVAL        { disable }
   ::= { epSpecificCodecEntry 200 }

  -- Columnar:Endpoint Specific G.711 VAD Configuraion

  epSpecificCodecGenericVoiceActivityDetection OBJECT-TYPE
   SYNTAX        INTEGER { disable(100) , transparent(200) , conservative(300)
                 }
   MAX-ACCESS    read-write
   STATUS        current
   DESCRIPTION " Endpoint Specific G.711 VAD Configuraion

                 If Voice Activity Detection (VAD) is enabled, then speech
                 frames are only sent during talkspurts (periods of audio
                 activity).

                 During silence periods, no speech frames are sent, but
                 Comfort Noise (CN) packets containing information about
                 background noise may be sent (see
                 draft-ietf-avt-rtp-cn-05.txt). This variable specifies the
                 sensitivity of the VAD algorithm to silence periods.

                 The generic VAD is used by codecs without built-in VAD like
                 G.711 and G.726.

                   * Disable: VAD disabled.
                   * Transparent: VAD enabled - low sensitivity to silence
                     periods.
                   * Conservative: VAD enabled - normal sensitivity to silence
                     periods.

                 This configuration overrides the default configuration set in
                 the DefaultCodecGenericVoiceActivityDetection variable if the
                 EpSpecificCodec.EnableConfig variable is set to 'Enable'.


                 "
   DEFVAL        { conservative }
   ::= { epSpecificCodecEntry 300 }


 -- End of table:Endpoint Specific Voice Codec Configuration

 -- ***************************************************************************
 
 -- Group:G.711 Voice Codec

 -- ***************************************************************************
 
 codecG711Group OBJECT IDENTIFIER
  ::= { codecGroup 300 }
  -- ***************************************************************************
  
  -- Group:G.711 Mu-Law Voice Codec Group

  -- ***************************************************************************
  
  codecG711MulawGroup OBJECT IDENTIFIER
   ::= { codecG711Group 100 }
   -- Scalar:Default G.711 Mu-Law Enable/Disable Configuration for Voice

   defaultCodecG711MulawVoiceEnable OBJECT-TYPE
    SYNTAX        MxEnableState
    MAX-ACCESS    read-write
    STATUS        current
    DESCRIPTION " Default G.711 Mu-Law Enable/Disable Configuration for Voice

                  Indicates if the codec can be selected for voice transmission.
                  If enabled, this codec is listed as supported for this
                  specific endpoint. Otherwise, it is ignored.

                  PCMA and PCMU are specified in ITU-T Recommendation G.711.
                  Audio data is encoded as eight bits per sample, after
                  logarithmic scaling. PCMU denotes mu-law scaling, PCMA A-law
                  scaling.

                  This codec uses generic voice activity detection. See the
                  DefaultCodecGenericVoiceActivityDetection and
                  EpSpecificCodec.GenericVoiceActivityDetection variables.

                  This codec always uses the RTP transport.

                  If a specific configuration is set in the
                  EpSpecificCodecG711Mulaw.VoiceEnable variable and the
                  EpSpecificCodecG711Mulaw.EnableConfig variable is set to
                  'Enable', then it overrides the current default configuration.


                  "
    DEFVAL        { enable }
    ::= { codecG711MulawGroup 100 }

   -- Scalar:Default G.711 Mu-Law Priority Configuration for Voice

   defaultCodecG711MulawVoicePriority OBJECT-TYPE
    SYNTAX        Unsigned32 ( 0..10 )
    MAX-ACCESS    read-write
    STATUS        current
    DESCRIPTION " Default G.711 Mu-Law Priority Configuration for Voice

                  Indicates the priority of this voice codec versus the other
                  voice codecs. The voice codec with the highest priority will
                  be offered first when an outgoing call is initiated. This
                  priority is not used in incoming call.

                  The application uses an internal order for codecs with the
                  same priority.

                  10 is the highest priority and 0 the lowest.

                  If a specific configuration is set in the
                  EpSpecificCodecG711Mulaw.VoicePriority variable and the
                  EpSpecificCodecG711Mulaw.EnableConfig variable is set to
                  'Enable', then it overrides the current default configuration.


                  "
    DEFVAL        { 0 }
    ::= { codecG711MulawGroup 200 }

   -- Scalar:Default G.711 Mu-Law Enable/Disable Configuration for Data

   defaultCodecG711MulawDataEnable OBJECT-TYPE
    SYNTAX        MxEnableState
    MAX-ACCESS    read-write
    STATUS        current
    DESCRIPTION " Default G.711 Mu-Law Enable/Disable Configuration for Data

                  Indicates if the codec can be selected for data transmission.
                  If enabled, this codec is listed as supported for this
                  specific endpoint. Otherwise, it is ignored.

                  If a specific configuration is set in the
                  EpSpecificCodecG711Mulaw.DataEnable variable and the
                  EpSpecificCodecG711Mulaw.EnableConfig variable is set to
                  'Enable', then it overrides the current default configuration.


                  "
    DEFVAL        { enable }
    ::= { codecG711MulawGroup 300 }

   -- Scalar:Default G.711 Mu-Law Priority Configuration for Data

   defaultCodecG711MulawDataPriority OBJECT-TYPE
    SYNTAX        Unsigned32 ( 0..10 )
    MAX-ACCESS    read-write
    STATUS        current
    DESCRIPTION " Default G.711 Mu-Law Priority Configuration for Data

                  Indicates the priority of this data codec versus the other
                  data codecs. The data codec with the highest priority will be
                  offered first when an outgoing call is initiated. This
                  priority is not used in incoming call.

                  The application uses an internal order for codecs with the
                  same priority.

                  10 is the highest priority and 0 the lowest.

                  If a specific configuration is set in the
                  EpSpecificCodecG711Mulaw.DataPriority variable and the
                  EpSpecificCodecG711Mulaw.EnableConfig variable is set to
                  'Enable', then it overrides the current default configuration.


                  "
    DEFVAL        { 0 }
    ::= { codecG711MulawGroup 400 }

   -- Scalar:Default G.711 Mu-Law Minimum Packetization Period Configuration

   defaultCodecG711MulawMinPTime OBJECT-TYPE
    SYNTAX        Unsigned32 ( 10..30 )
    MAX-ACCESS    read-write
    STATUS        current
    DESCRIPTION " Default G.711 Mu-Law Minimum Packetization Period
                  Configuration

                  Lower boundary for the packetization period of the given
                  codec.

                  PCMU -> (10 ms..30 ms)

                  This value is expressed in ms, with increments of 10 ms.

                  For reception, the range is extended from 10 ms to 100 ms with
                  increments of 1 ms only if the stream is not encrypted (SRTP).

                  If a specific configuration is set in the
                  EpSpecificCodecG711Mulaw.MinPTime variable and the
                  EpSpecificCodecG711Mulaw.EnableConfig variable is set to
                  'Enable', then it overrides the current default configuration.


                  "
    DEFVAL        { 30 }
    ::= { codecG711MulawGroup 500 }

   -- Scalar:Default G.711 Mu-Law Maximum Packetization Period Configuration

   defaultCodecG711MulawMaxPTime OBJECT-TYPE
    SYNTAX        Unsigned32 ( 10..30 )
    MAX-ACCESS    read-write
    STATUS        current
    DESCRIPTION " Default G.711 Mu-Law Maximum Packetization Period
                  Configuration

                  Upper boundary for the packetization period of the given
                  codec.

                  PCMU -> (10 ms..30 ms)

                  This value is expressed in ms, with increments of 10 ms.

                  For reception, the range is extended from 10 ms to 100 ms with
                  increments of 1 ms only if the stream is not encrypted (SRTP).

                  If a specific configuration is set in the
                  EpSpecificCodecG711Mulaw.MaxPTime variable and the
                  EpSpecificCodecG711Mulaw.EnableConfig variable is set to
                  'Enable', then it overrides the current default configuration.


                  "
    DEFVAL        { 30 }
    ::= { codecG711MulawGroup 600 }

   -- ***************************************************************************
   
   -- Table:Endpoint Specific Voice Codec Configuration

   -- ***************************************************************************
   
   epSpecificCodecG711MulawTable OBJECT-TYPE
    SYNTAX                  SEQUENCE OF EpSpecificCodecG711MulawEntry
    MAX-ACCESS              not-accessible
    STATUS                  current
    DESCRIPTION          "  Endpoint Specific Voice Codec Configuration

                            Endpoint specific configuration.
                            "
    ::= { codecG711MulawGroup 700 }
    epSpecificCodecG711MulawEntry OBJECT-TYPE
     SYNTAX        EpSpecificCodecG711MulawEntry
     MAX-ACCESS    not-accessible
     STATUS        current
     DESCRIPTION " A row in table Endpoint Specific Voice Codec Configuration .
                   "
     INDEX         {
                     epSpecificCodecG711MulawEpId
                   }

     ::= { epSpecificCodecG711MulawTable 1 }

    EpSpecificCodecG711MulawEntry ::= SEQUENCE
    {
      epSpecificCodecG711MulawEpId          OCTET STRING,
      epSpecificCodecG711MulawEnableConfig  MxEnableState,
      epSpecificCodecG711MulawVoiceEnable   MxEnableState,
      epSpecificCodecG711MulawVoicePriority Unsigned32,
      epSpecificCodecG711MulawDataEnable    MxEnableState,
      epSpecificCodecG711MulawDataPriority  Unsigned32,
      epSpecificCodecG711MulawMinPTime      Unsigned32,
      epSpecificCodecG711MulawMaxPTime      Unsigned32
    }

    -- Index:Endpoint Identifier

    epSpecificCodecG711MulawEpId OBJECT-TYPE
     SYNTAX        OCTET STRING
     MAX-ACCESS    read-only
     STATUS        current
     DESCRIPTION " Endpoint Identifier

                   String that identifies an endpoint in other tables.
                   "
     ::= { epSpecificCodecG711MulawEntry 100 }

    -- Columnar:Enable Configuration

    epSpecificCodecG711MulawEnableConfig OBJECT-TYPE
     SYNTAX        MxEnableState
     MAX-ACCESS    read-write
     STATUS        current
     DESCRIPTION " Enable Configuration

                   Defines the configuration to use for a specific endpoint.

                     * Disable: The endpoint uses the default configuration as
                       defined in the DefaultCodecG711MulawVoiceEnable,
                       DefaultCodecG711MulawVoicePriority,
                       DefaultCodecG711MulawDataEnable,
                       DefaultCodecG711MulawDataPriority,
                       DefaultCodecG711MulawMinPTime and
                       DefaultCodecG711MulawMaxPTime variables.
                     * Enable: The endpoint uses the specific configuration as
                       defined in the EpSpecificCodecG711Mulaw.VoiceEnable,
                       EpSpecificCodecG711Mulaw.VoicePriority,
                       EpSpecificCodecG711Mulaw.DataEnable,
                       EpSpecificCodecG711Mulaw.DataPriority,
                       EpSpecificCodecG711Mulaw.MinPTime and
                       EpSpecificCodecG711Mulaw.MaxPTime variables.


                   "
     DEFVAL        { disable }
     ::= { epSpecificCodecG711MulawEntry 200 }

    -- Columnar:Endpoint Specific G.711 Mu-Law Enable/Disable Configuration for
    -- Voice

    epSpecificCodecG711MulawVoiceEnable OBJECT-TYPE
     SYNTAX        MxEnableState
     MAX-ACCESS    read-write
     STATUS        current
     DESCRIPTION " Endpoint Specific G.711 Mu-Law Enable/Disable Configuration
                   for Voice

                   Indicates if the codec can be selected for voice
                   transmission. If enabled, this codec is listed as supported
                   for this specific endpoint. Otherwise, it is ignored.

                   PCMA and PCMU are specified in ITU-T Recommendation G.711.
                   Audio data is encoded as eight bits per sample, after
                   logarithmic scaling. PCMU denotes mu-law scaling, PCMA A-law
                   scaling.

                   This codec uses generic voice activity detection. See the
                   DefaultCodecGenericVoiceActivityDetection and
                   EpSpecificCodec.GenericVoiceActivityDetection variables.

                   This codec always uses the RTP transport.

                   This configuration overrides the default configuration set in
                   the DefaultCodecG711MulawVoiceEnable variable if the
                   EpSpecificCodecG711Mulaw.EnableConfig variable is set to
                   'Enable'.


                   "
     DEFVAL        { enable }
     ::= { epSpecificCodecG711MulawEntry 300 }

    -- Columnar:Endpoint Specific G.711 Mu-Law Priority Configuration for Voice

    epSpecificCodecG711MulawVoicePriority OBJECT-TYPE
     SYNTAX        Unsigned32 ( 0..10 )
     MAX-ACCESS    read-write
     STATUS        current
     DESCRIPTION " Endpoint Specific G.711 Mu-Law Priority Configuration for
                   Voice

                   Indicates the priority of this voice codec versus the other
                   voice codecs. The voice codec with the highest priority will
                   be offered first when an outgoing call is initiated. This
                   priority is not used in incoming calls.

                   The application uses an internal order for codecs with the
                   same priority.

                   10 is the highest priority and 0 the lowest.

                   This configuration overrides the default configuration set in
                   the DefaultCodecG711MulawVoicePriority variable if the
                   EpSpecificCodecG711Mulaw.EnableConfig variable is set to
                   'Enable'.


                   "
     DEFVAL        { 0 }
     ::= { epSpecificCodecG711MulawEntry 400 }

    -- Columnar:Endpoint Specific G.711 Mu-Law Enable/Disable Configuration for
    -- Data

    epSpecificCodecG711MulawDataEnable OBJECT-TYPE
     SYNTAX        MxEnableState
     MAX-ACCESS    read-write
     STATUS        current
     DESCRIPTION " Endpoint Specific G.711 Mu-Law Enable/Disable Configuration
                   for Data

                   Indicates if the codec can be selected for data transmission.
                   If enabled, this codec is listed as supported for this
                   specific endpoint. Otherwise, it is ignored.

                   This configuration overrides the default configuration set in
                   the DefaultCodecG711MulawDataEnable variable if the
                   EpSpecificCodecG711Mulaw.EnableConfig variable is set to
                   'Enable'.


                   "
     DEFVAL        { enable }
     ::= { epSpecificCodecG711MulawEntry 500 }

    -- Columnar:Endpoint Specific G.711 Mu-Law Priority Configuration for Data

    epSpecificCodecG711MulawDataPriority OBJECT-TYPE
     SYNTAX        Unsigned32 ( 0..10 )
     MAX-ACCESS    read-write
     STATUS        current
     DESCRIPTION " Endpoint Specific G.711 Mu-Law Priority Configuration for
                   Data

                   Indicates the priority of this data codec versus the other
                   data codecs. The data codec with the highest priority will be
                   offered first when an outgoing call is initiated. This
                   priority is not used in incoming calls.

                   The application uses an internal order for codecs with the
                   same priority.

                   10 is the highest priority and 0 the lowest.

                   This configuration overrides the default configuration set in
                   the DefaultCodecG711MulawDataPriority variable if the
                   EpSpecificCodecG711Mulaw.EnableConfig variable is set to
                   'Enable'.


                   "
     DEFVAL        { 0 }
     ::= { epSpecificCodecG711MulawEntry 600 }

    -- Columnar:Endpoint Specific G.711 Mu-Law Minimum Packetization Period
    -- Configuration

    epSpecificCodecG711MulawMinPTime OBJECT-TYPE
     SYNTAX        Unsigned32 ( 10..30 )
     MAX-ACCESS    read-write
     STATUS        current
     DESCRIPTION " Endpoint Specific G.711 Mu-Law Minimum Packetization Period
                   Configuration

                   Lower boundary for the packetization period of the given
                   codec.

                   PCMU -> (10 ms..30 ms)

                   This value is expressed in ms, with increments of 10 ms.

                   For reception, the range is extended from 10 ms to 100 ms
                   with increments of 1 ms only if the stream is not encrypted
                   (SRTP).

                   This configuration overrides the default configuration set in
                   the DefaultCodecG711MulawMinPTime variable if the
                   EpSpecificCodecG711Mulaw.EnableConfig variable is set to
                   'Enable'.


                   "
     DEFVAL        { 30 }
     ::= { epSpecificCodecG711MulawEntry 700 }

    -- Columnar:Endpoint Specific G.711 Mu-Law Maximum Packetization Period
    -- Configuration

    epSpecificCodecG711MulawMaxPTime OBJECT-TYPE
     SYNTAX        Unsigned32 ( 10..30 )
     MAX-ACCESS    read-write
     STATUS        current
     DESCRIPTION " Endpoint Specific G.711 Mu-Law Maximum Packetization Period
                   Configuration

                   Upper boundary for the packetization period of the given
                   codec.

                   PCMU -> (10 ms..30 ms)

                   This value is expressed in ms, with increments of 10 ms.

                   For reception, the range is extended from 10 ms to 100 ms
                   with increments of 1 ms only if the stream is not encrypted
                   (SRTP).

                   This configuration overrides the default configuration set in
                   the DefaultCodecG711MulawMaxPTime variable if the
                   EpSpecificCodecG711Mulaw.EnableConfig variable is set to
                   'Enable'.


                   "
     DEFVAL        { 30 }
     ::= { epSpecificCodecG711MulawEntry 800 }


   -- End of table:Endpoint Specific Voice Codec Configuration

  -- End of group:G.711 Mu-Law Voice Codec Group

  -- ***************************************************************************
  
  -- Group:G.711 A-law Voice Codec Group

  -- ***************************************************************************
  
  codecG711AlawGroup OBJECT IDENTIFIER
   ::= { codecG711Group 200 }
   -- Scalar:Default G.711 A-law Enable/Disable Configuration for Voice

   defaultCodecG711AlawVoiceEnable OBJECT-TYPE
    SYNTAX        MxEnableState
    MAX-ACCESS    read-write
    STATUS        current
    DESCRIPTION " Default G.711 A-law Enable/Disable Configuration for Voice

                  Indicates if the codec can be selected for voice transmission.
                  If enabled, this codec is listed as supported for this
                  specific endpoint. Otherwise, it is ignored.

                  PCMA and PCMU are specified in ITU-T Recommendation G.711.
                  Audio data is encoded as eight bits per sample, after
                  logarithmic scaling. PCMU denotes mu-law scaling, PCMA A-law
                  scaling.

                  This codec uses generic voice activity detection. See the
                  DefaultCodecGenericVoiceActivityDetection and
                  EpSpecificCodec.GenericVoiceActivityDetection variables.

                  This codec always uses the RTP transport.

                  If a specific configuration is set in the
                  EpSpecificCodecG711Alaw.VoiceEnable variable and the
                  EpSpecificCodecG711Alaw.EnableConfig variable is set to
                  'Enable', then it overrides the current default configuration.


                  "
    DEFVAL        { enable }
    ::= { codecG711AlawGroup 100 }

   -- Scalar:Default G.711 A-Law Priority Configuration for Voice

   defaultCodecG711AlawVoicePriority OBJECT-TYPE
    SYNTAX        Unsigned32 ( 0..10 )
    MAX-ACCESS    read-write
    STATUS        current
    DESCRIPTION " Default G.711 A-Law Priority Configuration for Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  If a specific configuration is set in the
                  EpSpecificCodecG711Alaw.VoicePriority variable and the
                  EpSpecificCodecG711Alaw.EnableConfig variable is set to
                  'Enable', then it overrides the current default configuration.


                  "
    DEFVAL        { 0 }
    ::= { codecG711AlawGroup 200 }

   -- Scalar:Default G.711 A-Law Enable/Disable Configuration for Data

   defaultCodecG711AlawDataEnable OBJECT-TYPE
    SYNTAX        MxEnableState
    MAX-ACCESS    read-write
    STATUS        current
    DESCRIPTION " Default G.711 A-Law Enable/Disable Configuration for Data

                  Indicates if the codec can be selected for data transmission.
                  If enabled, this codec is listed as supported for this
                  specific endpoint. Otherwise, it is ignored.

                  If a specific configuration is set in the
                  EpSpecificCodecG711Alaw.DataEnable variable and the
                  EpSpecificCodecG711Alaw.EnableConfig variables is set to
                  'Enable', then it overrides the current default configuration.


                  "
    DEFVAL        { enable }
    ::= { codecG711AlawGroup 300 }

   -- Scalar:Default G.711 A-Law Priority Configuration for Data

   defaultCodecG711AlawDataPriority OBJECT-TYPE
    SYNTAX        Unsigned32 ( 0..10 )
    MAX-ACCESS    read-write
    STATUS        current
    DESCRIPTION " Default G.711 A-Law Priority Configuration for Data

                  Indicates the priority of this data codec versus the other
                  data codecs. The data codec with the highest priority will be
                  offered first when an outgoing call is initiated. This
                  priority is not used in incoming calls.

                  The application uses an internal order for codecs with the
                  same priority.

                  10 is the highest priority and 0 the lowest.

                  If a specific configuration is set in the
                  EpSpecificCodecG711Alaw.DataPriority variable and the
                  EpSpecificCodecG711Alaw.EnableConfig variable is set to
                  'Enable', then it overrides the current default configuration.


                  "
    DEFVAL        { 0 }
    ::= { codecG711AlawGroup 400 }

   -- Scalar:Default G.711 A-Law Minimum Packetization Period Configuration

   defaultCodecG711AlawMinPTime OBJECT-TYPE
    SYNTAX        Unsigned32 ( 10..30 )
    MAX-ACCESS    read-write
    STATUS        current
    DESCRIPTION " Default G.711 A-Law Minimum Packetization Period Configuration

                  Lower boundary for the packetization period of the given
                  codec.

                  PCMA -> (10 ms..30 ms)

                  This value is expressed in ms, with increments of 10 ms.

                  For reception, the range is extended from 10 ms to 100 ms with
                  increments of 1 ms only if the stream is not encrypted (SRTP).

                  If a specific configuration is set in the
                  EpSpecificCodecG711Alaw.MinPTime variable and the
                  EpSpecificCodecG711Alaw.EnableConfig variable is set to
                  'Enable', then it overrides the current default configuration.


                  "
    DEFVAL        { 30 }
    ::= { codecG711AlawGroup 500 }

   -- Scalar:Default G.711 A-Law Maximum Packetization Period Configuration

   defaultCodecG711AlawMaxPTime OBJECT-TYPE
    SYNTAX        Unsigned32 ( 10..30 )
    MAX-ACCESS    read-write
    STATUS        current
    DESCRIPTION " Default G.711 A-Law Maximum Packetization Period Configuration

                  Upper boundary for the packetization period of the given
                  codec.

                  PCMA -> (10 ms..30 ms)

                  This value is expressed in ms, with increments of 10 ms.

                  For reception, the range is extended from 10 ms to 100m s with
                  increments of 1 ms only if the stream is not encrypted (SRTP).

                  If a specific configuration is set in the
                  EpSpecificCodecG711Alaw.MaxPTime variable and the
                  EpSpecificCodecG711Alaw.EnableConfig variable is set to
                  'Enable', then it overrides the current default configuration.


                  "
    DEFVAL        { 30 }
    ::= { codecG711AlawGroup 600 }

   -- ***************************************************************************
   
   -- Table:Endpoint Specific Voice Codec Configuration

   -- ***************************************************************************
   
   epSpecificCodecG711AlawTable OBJECT-TYPE
    SYNTAX                 SEQUENCE OF EpSpecificCodecG711AlawEntry
    MAX-ACCESS             not-accessible
    STATUS                 current
    DESCRIPTION         "  Endpoint Specific Voice Codec Configuration

                           Endpoint specific configuration.
                           "
    ::= { codecG711AlawGroup 700 }
    epSpecificCodecG711AlawEntry OBJECT-TYPE
     SYNTAX        EpSpecificCodecG711AlawEntry
     MAX-ACCESS    not-accessible
     STATUS        current
     DESCRIPTION " A row in table Endpoint Specific Voice Codec Configuration .
                   "
     INDEX         {
                     epSpecificCodecG711AlawEpId
                   }

     ::= { epSpecificCodecG711AlawTable 1 }

    EpSpecificCodecG711AlawEntry ::= SEQUENCE
    {
      epSpecificCodecG711AlawEpId          OCTET STRING,
      epSpecificCodecG711AlawEnableConfig  MxEnableState,
      epSpecificCodecG711AlawVoiceEnable   MxEnableState,
      epSpecificCodecG711AlawVoicePriority Unsigned32,
      epSpecificCodecG711AlawDataEnable    MxEnableState,
      epSpecificCodecG711AlawDataPriority  Unsigned32,
      epSpecificCodecG711AlawMinPTime      Unsigned32,
      epSpecificCodecG711AlawMaxPTime      Unsigned32
    }

    -- Index:Endpoint Identifier

    epSpecificCodecG711AlawEpId OBJECT-TYPE
     SYNTAX        OCTET STRING
     MAX-ACCESS    read-only
     STATUS        current
     DESCRIPTION " Endpoint Identifier

                   String that identifies an endpoint in other tables.
                   "
     ::= { epSpecificCodecG711AlawEntry 100 }

    -- Columnar:Enable Configuration

    epSpecificCodecG711AlawEnableConfig OBJECT-TYPE
     SYNTAX        MxEnableState
     MAX-ACCESS    read-write
     STATUS        current
     DESCRIPTION " Enable Configuration

                   Defines the configuration to use for a specific endpoint.

                     * Disable: The endpoint uses the default configuration as
                       defined in the DefaultCodecG711AlawVoiceEnable,
                       DefaultCodecG711AlawVoicePriority,
                       DefaultCodecG711AlawDataEnable,
                       DefaultCodecG711AlawDataPriority,
                       DefaultCodecG711AlawMinPTime and
                       DefaultCodecG711AlawMaxPTime variables.
                     * Enable: The endpoint uses the specific configuration as
                       defined in the EpSpecificCodecG711Alaw.VoiceEnable,
                       EpSpecificCodecG711Alaw.VoicePriority,
                       EpSpecificCodecG711Alaw.DataEnable,
                       EpSpecificCodecG711Alaw.DataPriority,
                       EpSpecificCodecG711Alaw.MinPTime and
                       EpSpecificCodecG711Alaw.MaxPTime variables.


                   "
     DEFVAL        { disable }
     ::= { epSpecificCodecG711AlawEntry 200 }

    -- Columnar:Endpoint Specific G.711 A-Law Enable/Disable Configuration for
    -- Voice

    epSpecificCodecG711AlawVoiceEnable OBJECT-TYPE
     SYNTAX        MxEnableState
     MAX-ACCESS    read-write
     STATUS        current
     DESCRIPTION " Endpoint Specific G.711 A-Law Enable/Disable Configuration
                   for Voice

                   Indicates if the codec can be selected for voice
                   transmission. If enabled, this codec is listed as supported
                   for this specific endpoint. Otherwise, it is ignored.

                   PCMA and PCMU are specified in ITU-T Recommendation G.711.
                   Audio data is encoded as eight bits per sample, after
                   logarithmic scaling. PCMU denotes mu-law scaling, PCMA A-law
                   scaling.

                   This codec uses generic voice activity detection. See the
                   DefaultCodecGenericVoiceActivityDetection and
                   EpSpecificCodec.GenericVoiceActivityDetection variables.

                   This codec always uses the RTP transport.

                   This configuration overrides the default configuration set in
                   the DefaultCodecG711AlawVoiceEnable variable if the
                   EpSpecificCodecG711Alaw.EnableConfig variable is set to
                   'Enable'.


                   "
     DEFVAL        { enable }
     ::= { epSpecificCodecG711AlawEntry 300 }

    -- Columnar:Endpoint Specific G.711 A-Law Priority Configuration for Voice

    epSpecificCodecG711AlawVoicePriority OBJECT-TYPE
     SYNTAX        Unsigned32 ( 0..10 )
     MAX-ACCESS    read-write
     STATUS        current
     DESCRIPTION " Endpoint Specific G.711 A-Law Priority Configuration for
                   Voice

                   Indicates the priority of this voice codec versus the other
                   voice codecs. The voice codec with the highest priority will
                   be offered first when an outgoing call is initiated. This
                   priority is not used in incoming calls.

                   The application uses an internal order for codecs with the
                   same priority.

                   10 is the highest priority and 0 the lowest.

                   This configuration overrides the default configuration set in
                   the DefaultCodecG711AlawVoicePriority variable if the
                   EpSpecificCodecG711Alaw.EnableConfig variable is set to
                   'Enable'.


                   "
     DEFVAL        { 0 }
     ::= { epSpecificCodecG711AlawEntry 400 }

    -- Columnar:Endpoint Specific G.711 A-Law Enable/Disable Configuration for
    -- Data

    epSpecificCodecG711AlawDataEnable OBJECT-TYPE
     SYNTAX        MxEnableState
     MAX-ACCESS    read-write
     STATUS        current
     DESCRIPTION " Endpoint Specific G.711 A-Law Enable/Disable Configuration
                   for Data

                   Indicates if the codec can be selected for data transmission.
                   If enabled, this codec is listed as supported for this
                   specific endpoint. Otherwise, it is ignored.

                   This configuration overrides the default configuration set in
                   the DefaultCodecG711AlawDataEnable variable if the
                   EpSpecificCodecG711Alaw.EnableConfig variable is set to
                   'Enable'.


                   "
     DEFVAL        { enable }
     ::= { epSpecificCodecG711AlawEntry 500 }

    -- Columnar:Endpoint Specific G.711 A-Law Priority Configuration for Data

    epSpecificCodecG711AlawDataPriority OBJECT-TYPE
     SYNTAX        Unsigned32 ( 0..10 )
     MAX-ACCESS    read-write
     STATUS        current
     DESCRIPTION " Endpoint Specific G.711 A-Law Priority Configuration for Data

                   Indicates the priority of this data codec versus the other
                   data codecs. The data codec with the highest priority will be
                   offered first when an outgoing call is initiated. This
                   priority is not used in incoming calls.

                   The application uses an internal order for codecs with the
                   same priority.

                   10 is the highest priority and 0 the lowest.

                   This configuration overrides the default configuration set in
                   the DefaultCodecG711AlawDataPriority variable if the
                   EpSpecificCodecG711Alaw.EnableConfig variable is set to
                   'Enable'.


                   "
     DEFVAL        { 0 }
     ::= { epSpecificCodecG711AlawEntry 600 }

    -- Columnar:Endpoint Specific G.711 A-Law Minimum Packetization Period
    -- Configuration

    epSpecificCodecG711AlawMinPTime OBJECT-TYPE
     SYNTAX        Unsigned32 ( 10..30 )
     MAX-ACCESS    read-write
     STATUS        current
     DESCRIPTION " Endpoint Specific G.711 A-Law Minimum Packetization Period
                   Configuration

                   Lower boundary for the packetization period of the given
                   codec.

                   PCMA -> (10 ms..30 ms)

                   This value is expressed in ms, with increments of 10 ms.

                   For reception, the range is extended from 10 ms to 100 ms
                   with increments of 1 ms only if the stream is not encrypted
                   (SRTP).

                   This configuration overrides the default configuration set in
                   the DefaultCodecG711AlawMinPTime variable if the
                   EpSpecificCodecG711Alaw.EnableConfig variable is set to
                   'Enable'.


                   "
     DEFVAL        { 30 }
     ::= { epSpecificCodecG711AlawEntry 700 }

    -- Columnar:Endpoint Specific G.711 A-Law Maximum Packetization Period
    -- Configuration

    epSpecificCodecG711AlawMaxPTime OBJECT-TYPE
     SYNTAX        Unsigned32 ( 10..30 )
     MAX-ACCESS    read-write
     STATUS        current
     DESCRIPTION " Endpoint Specific G.711 A-Law Maximum Packetization Period
                   Configuration

                   Upper boundary for the packetization period of the given
                   codec.

                   PCMA -> (10 ms..30 ms)

                   This value is expressed in ms, with increments of 10 ms.

                   For reception, the range is extended from 10 ms to 100 ms
                   with increments of 1 ms only if the stream is not encrypted
                   (SRTP).

                   This configuration overrides the default configuration set in
                   the DefaultCodecG711AlawMaxPTime variable if the
                   EpSpecificCodecG711Alaw.EnableConfig variable is set to
                   'Enable'.


                   "
     DEFVAL        { 30 }
     ::= { epSpecificCodecG711AlawEntry 800 }


   -- End of table:Endpoint Specific Voice Codec Configuration

  -- End of group:G.711 A-law Voice Codec Group

 -- End of group:G.711 Voice Codec

 -- ***************************************************************************
 
 -- Group:G.723 Voice Codec Group

 -- ***************************************************************************
 
 codecG723Group OBJECT IDENTIFIER
  ::= { codecGroup 400 }
  -- Scalar:Default G.723.1 Enable/Disable Configuration for Voice

  defaultCodecG723VoiceEnable OBJECT-TYPE
   SYNTAX        MxEnableState
   MAX-ACCESS    read-write
   STATUS        current
   DESCRIPTION " Default G.723.1 Enable/Disable Configuration for Voice

                 Indicates if the codec can be selected for voice transmission.
                 If enabled, this codec is listed as supported for this
                 specific endpoint. Otherwise, it is ignored.

                 G.723.1 is specified in ITU Recommendation G.723.1, Dual-rate
                 speech coder for multimedia communications transmitting at 5.3
                 and 6.3 kbit/s. This Recommendation specifies a coded
                 representation that can be used for compressing the speech
                 signal component of multi-media services at a very low bit
                 rate. Audio is encoded in 30 ms frames. A G.723.1 frame can be
                 one of three sizes: 24 octets (6.3 kb/s frame), 20 octets (5.3
                 kb/s frame), or 4 octets. These 4-octet frames are called SID
                 frames (Silence Insertion Descriptor) and are used to specify
                 comfort noise parameters.

                 This codec always uses the RTP transport.

                 If a specific configuration is set in the
                 EpSpecificCodecG723.VoiceEnable variable and the
                 EpSpecificCodecG723.EnableConfig variable is set to 'Enable',
                 then it overrides the current default configuration.


                 "
   DEFVAL        { enable }
   ::= { codecG723Group 100 }

  -- Scalar:Default G.723 Priority Configuration for Voice

  defaultCodecG723VoicePriority OBJECT-TYPE
   SYNTAX        Unsigned32 ( 0..10 )
   MAX-ACCESS    read-write
   STATUS        current
   DESCRIPTION " Default G.723 Priority Configuration for Voice

                 Indicates the priority of this voice codec versus the other
                 voice codecs. The voice codec with the highest priority will
                 be offered first when an outgoing call is initiated. This
                 priority is not used in incoming calls.

                 The application uses an internal order for codecs with the
                 same priority.

                 10 is the highest priority and 0 the lowest.

                 If a specific configuration is set in the
                 EpSpecificCodecG723.VoicePriority variable and the
                 EpSpecificCodecG723.EnableConfig variable is set to 'Enable',
                 then it overrides the current default configuration.


                 "
   DEFVAL        { 0 }
   ::= { codecG723Group 200 }

  -- Scalar:Default G.723.1 Bit Rate

  defaultCodecG723Bitrate OBJECT-TYPE
   SYNTAX        INTEGER { rate53kbps(100) , rate63kbps(200) }
   MAX-ACCESS    read-write
   STATUS        current
   DESCRIPTION " Default G.723.1 Bit Rate

                 Indicates the G.723.1 bit rate to use.

                 If a specific configuration is set in the
                 EpSpecificCodecG723.Bitrate variable and the
                 EpSpecificCodecG723.EnableConfig variable is set to 'Enable',
                 then it overrides the current default configuration.


                 "
   DEFVAL        { rate63kbps }
   ::= { codecG723Group 300 }

  -- Scalar:Default G.723.1 Minimum Packetization Period Configuration

  defaultCodecG723MinPTime OBJECT-TYPE
   SYNTAX        Unsigned32 ( 30..30 | 60..60 )
   MAX-ACCESS    read-write
   STATUS        current
   DESCRIPTION " Default G.723.1 Minimum Packetization Period Configuration

                 Lower boundary for the packetization period of the given
                 codec.

                 G.723 -> (30 ms|60 ms)

                 This value is expressed in ms, with increments of 30 ms.

                 For reception, the range is extended from 30 ms to 120 ms with
                 increments of 30 ms only if the stream is not encrypted
                 (SRTP).

                 If a specific configuration is set in the
                 EpSpecificCodecG723.MinPTime variable and the
                 EpSpecificCodecG723.EnableConfig variable is set to 'Enable',
                 then it overrides the current default configuration.


                 "
   DEFVAL        { 30 }
   ::= { codecG723Group 400 }

  -- Scalar:Default G.723.1 Maximum Packetization Period Configuration

  defaultCodecG723MaxPTime OBJECT-TYPE
   SYNTAX        Unsigned32 ( 30..30 | 60..60 )
   MAX-ACCESS    read-write
   STATUS        current
   DESCRIPTION " Default G.723.1 Maximum Packetization Period Configuration

                 Upper boundary for the packetization period of the given
                 codec.

                 G.723 -> (30 ms|60 ms)

                 This value is expressed in ms, with increments of 30 ms.

                 For reception, the range is extended from 30 ms to 120 ms with
                 increments of 30 ms only if the stream is not encrypted
                 (SRTP).

                 If a specific configuration is set in the
                 EpSpecificCodecG723.MaxPTime variable and the
                 EpSpecificCodecG723.EnableConfig variable is set to 'Enable',
                 then it overrides the current default configuration.


                 "
   DEFVAL        { 60 }
   ::= { codecG723Group 500 }

  -- ***************************************************************************
  
  -- Table:Endpoint Specific Voice Codec Configuration

  -- ***************************************************************************
  
  epSpecificCodecG723Table OBJECT-TYPE
   SYNTAX                      SEQUENCE OF EpSpecificCodecG723Entry
   MAX-ACCESS                  not-accessible
   STATUS                      current
   DESCRIPTION              "  Endpoint Specific Voice Codec Configuration

                               Endpoint specific configuration.
                               "
   ::= { codecG723Group 700 }
   epSpecificCodecG723Entry OBJECT-TYPE
    SYNTAX        EpSpecificCodecG723Entry
    MAX-ACCESS    not-accessible
    STATUS        current
    DESCRIPTION " A row in table Endpoint Specific Voice Codec Configuration .
                  "
    INDEX         {
                    epSpecificCodecG723EpId
                  }

    ::= { epSpecificCodecG723Table 1 }

   EpSpecificCodecG723Entry ::= SEQUENCE
   {
     epSpecificCodecG723EpId          OCTET STRING,
     epSpecificCodecG723EnableConfig  MxEnableState,
     epSpecificCodecG723VoiceEnable   MxEnableState,
     epSpecificCodecG723VoicePriority Unsigned32,
     epSpecificCodecG723Bitrate       INTEGER,
     epSpecificCodecG723MinPTime      Unsigned32,
     epSpecificCodecG723MaxPTime      Unsigned32
   }

   -- Index:Endpoint Identifier

   epSpecificCodecG723EpId OBJECT-TYPE
    SYNTAX        OCTET STRING
    MAX-ACCESS    read-only
    STATUS        current
    DESCRIPTION " Endpoint Identifier

                  String that identifies an endpoint in other tables.
                  "
    ::= { epSpecificCodecG723Entry 100 }

   -- Columnar:Enable Configuration

   epSpecificCodecG723EnableConfig OBJECT-TYPE
    SYNTAX        MxEnableState
    MAX-ACCESS    read-write
    STATUS        current
    DESCRIPTION " Enable Configuration

                  Defines the configuration to use for a specific endpoint.

                    * Disable: The endpoint uses the default configuration as
                      defined in the DefaultCodecG723VoiceEnable,
                      DefaultCodecG723VoicePriority, DefaultCodecG723Bitrate,
                      DefaultCodecG723MinPTime, DefaultCodecG723MaxPTime and
                      DefaultCodecG723VoiceActivityDetection variables.
                    * Enable: The endpoint uses the specific configuration as
                      defined in the EpSpecificCodecG723.VoiceEnable,
                      EpSpecificCodecG723.VoicePriority,
                      EpSpecificCodecG723.Bitrate,
                      EpSpecificCodecG723.MinPTime,
                      EpSpecificCodecG723.MaxPTime and
                      EpSpecificCodecG723.VoiceActivityDetection variables.


                  "
    DEFVAL        { disable }
    ::= { epSpecificCodecG723Entry 200 }

   -- Columnar:Endpoint Specific G.723.1 Enable/Disable Configuration for Voice

   epSpecificCodecG723VoiceEnable OBJECT-TYPE
    SYNTAX        MxEnableState
    MAX-ACCESS    read-write
    STATUS        current
    DESCRIPTION " Endpoint Specific G.723.1 Enable/Disable Configuration for
                  Voice

                  Indicates if the codec can be selected for voice
                  transmission. If enabled, this codec is listed as supported
                  for this specific endpoint. Otherwise, it is ignored.

                  G.723.1 is specified in ITU Recommendation G.723.1, Dual-rate
                  speech coder for multimedia communications transmitting at
                  5.3 and 6.3 kbit/s. This Recommendation specifies a coded
                  representation that can be used for compressing the speech
                  signal component of multi-media services at a very low bit
                  rate. Audio is encoded in 30 ms frames. A G.723.1 frame can
                  be one of three sizes: 24 octets (6.3 kb/s frame), 20 octets
                  (5.3 kb/s frame), or 4 octets. These 4-octet frames are
                  called SID frames (Silence Insertion Descriptor) and are used
                  to specify comfort noise parameters.

                  This codec always uses the RTP transport.

                  This configuration overrides the default configuration set in
                  the DefaultCodecG723VoiceEnable variable if the
                  EpSpecificCodecG723.EnableConfig variable is set to 'Enable'.


                  "
    DEFVAL        { enable }
    ::= { epSpecificCodecG723Entry 300 }

   -- Columnar:Endpoint Specific G.723 Priority Configuration for Voice

   epSpecificCodecG723VoicePriority OBJECT-TYPE
    SYNTAX        Unsigned32 ( 0..10 )
    MAX-ACCESS    read-write
    STATUS        current
    DESCRIPTION " Endpoint Specific G.723 Priority Configuration for Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  This configuration overrides the default configuration set in
                  the DefaultCodecG723VoicePriority variable if the
                  EpSpecificCodecG723.EnableConfig variable is set to 'Enable'.


                  "
    DEFVAL        { 0 }
    ::= { epSpecificCodecG723Entry 400 }

   -- Columnar:Endpoint Specific G.723.1 Bit Rate

   epSpecificCodecG723Bitrate OBJECT-TYPE
    SYNTAX        INTEGER { rate53kbps(100) , rate63kbps(200) }
    MAX-ACCESS    read-write
    STATUS        current
    DESCRIPTION " Endpoint Specific G.723.1 Bit Rate

                  Indicates the G.723.1 bit rate to use.

                  This configuration overrides the default configuration set in
                  the DefaultCodecG723Bitrate variable if the
                  EpSpecificCodecG723.EnableConfig variable is set to 'Enable'.


                  "
    DEFVAL        { rate63kbps }
    ::= { epSpecificCodecG723Entry 500 }

   -- Columnar:Endpoint Specific G.723.1 Minimum Packetization Period
   -- Configuration

   epSpecificCodecG723MinPTime OBJECT-TYPE
    SYNTAX        Unsigned32 ( 30..30 | 60..60 )
    MAX-ACCESS    read-write
    STATUS        current
    DESCRIPTION " Endpoint Specific G.723.1 Minimum Packetization Period
                  Configuration

                  Lower boundary for the packetization period of the given
                  codec.

                  G.723 -> (30 ms|60 ms)

                  This value is expressed in ms, with increments of 30 ms.

                  For reception, the range is extended from 30 ms to 120 ms
                  with increments of 30 ms only if the stream is not encrypted
                  (SRTP).

                  This configuration overrides the default configuration set in
                  the DefaultCodecG723MinPTime variable if the
                  EpSpecificCodecG723.EnableConfig variable is set to 'Enable'.


                  "
    DEFVAL        { 30 }
    ::= { epSpecificCodecG723Entry 600 }

   -- Columnar:Endpoint Specific G.723.1 Maximum Packetization Period
   -- Configuration

   epSpecificCodecG723MaxPTime OBJECT-TYPE
    SYNTAX        Unsigned32 ( 30..30 | 60..60 )
    MAX-ACCESS    read-write
    STATUS        current
    DESCRIPTION " Endpoint Specific G.723.1 Maximum Packetization Period
                  Configuration

                  Upper boundary for the packetization period of the given
                  codec.

                  G.723 -> (30 ms|60 ms)

                  This value is expressed in ms, with increments of 30 ms.

                  For reception, the range is extended from 30 ms to 120 ms
                  with increments of 30 ms only if the stream is not encrypted
                  (SRTP).

                  This configuration overrides the default configuration set in
                  the DefaultCodecG723MaxPTime variable if the
                  EpSpecificCodecG723.EnableConfig variable is set to 'Enable'.


                  "
    DEFVAL        { 60 }
    ::= { epSpecificCodecG723Entry 700 }


  -- End of table:Endpoint Specific Voice Codec Configuration

 -- End of group:G.723 Voice Codec Group

 -- ***************************************************************************
 
 -- Group:G.726 Voice Codec Group

 -- ***************************************************************************
 
 codecG726Group OBJECT IDENTIFIER
  ::= { codecGroup 500 }
  -- ***************************************************************************
  
  -- Group:G.726 16 Kbit/s Voice Codec Group

  -- ***************************************************************************
  
  codecG726r16kbpsGroup OBJECT IDENTIFIER
   ::= { codecG726Group 100 }
   -- Scalar:Default G.726 16 Kbit/s Enable/Disable Configuration

   defaultCodecG726r16kbpsVoiceEnable OBJECT-TYPE
    SYNTAX        MxEnableState
    MAX-ACCESS    read-write
    STATUS        current
    DESCRIPTION " Default G.726 16 Kbit/s Enable/Disable Configuration

                  Indicates if the codec can be selected for voice transmission.
                  If enabled, this codec is listed as supported for this
                  specific endpoint. Otherwise, it is ignored.

                    * Disable: Disable G.726 at 16 kbps.
                    * Enable: Enable G.726 at 16 kbps.

                  G.726 is specified in ITU-T Recommendation G.726: 40, 32, 24,
                  16 kbit/s adaptive differential pulse code modulation (ADPCM).
                  It describes the algorithm recommended for conversion of a
                  single 64 kbit/s A-law or U-law PCM channel encoded at 8000
                  samples/sec to and from a 40, 32, 24, or 16 kbit/s channel.
                  The conversion is applied to the PCM stream using an Adaptive
                  Differential Pulse Code Modulation (ADPCM) transcoding
                  technique.

                  This codec uses generic voice activity detection. See the
                  DefaultCodecGenericVoiceActivityDetection and
                  EpSpecificCodec.GenericVoiceActivityDetection variables.

                  This codec always uses the RTP transport.

                  If a specific configuration is set in the
                  EpSpecificCodecG726r16kbps.VoiceEnable variable and the
                  EpSpecificCodecG726r16kbps.EnableConfig variable is set to
                  'Enable', then it overrides the current default configuration.


                  "
    DEFVAL        { disable }
    ::= { codecG726r16kbpsGroup 100 }

   -- Scalar:Default G.726 16 Kbit/s Priority Configuration for Voice

   defaultCodecG726r16kbpsVoicePriority OBJECT-TYPE
    SYNTAX        Unsigned32 ( 0..10 )
    MAX-ACCESS    read-write
    STATUS        current
    DESCRIPTION " Default G.726 16 Kbit/s Priority Configuration for Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  If a specific configuration is set in the
                  EpSpecificCodecG726r16kbps.VoicePriority variable and the
                  EpSpecificCodecG726r16kbps.EnableConfig variable is set to
                  'Enable', then it overrides the current default configuration.


                  "
    DEFVAL        { 0 }
    ::= { codecG726r16kbpsGroup 200 }

   -- Scalar:Default G.726 16 Kbit/s Payload Type

   defaultCodecG726r16kbpsPayloadType OBJECT-TYPE
    SYNTAX        Unsigned32 ( 96..127 )
    MAX-ACCESS    read-write
    STATUS        current
    DESCRIPTION " Default G.726 16 Kbit/s Payload Type

                  Determines the actual RTP dynamic payload type used in an
                  initial offer when enabling G.726 at 16 kbps for voice and
                  data transmission.

                  The payload types available are as per RFC 3551.

                  If a specific configuration is set in the
                  EpSpecificCodecG726r16kbps.PayloadType variable and the
                  EpSpecificCodecG726r16kbps.EnableConfig variable is set to
                  'Enable', then it overrides the current default configuration.


                  "
    DEFVAL        { 97 }
    ::= { codecG726r16kbpsGroup 300 }

   -- Scalar:Default G.726 16 Kbit/s Minimum Packetization Period Configuration

   defaultCodecG726r16kbpsMinPTime OBJECT-TYPE
    SYNTAX        Unsigned32 ( 10..30 )
    MAX-ACCESS    read-write
    STATUS        current
    DESCRIPTION " Default G.726 16 Kbit/s Minimum Packetization Period
                  Configuration

                  Lower boundary for the packetization period of the given
                  codec.

                  G.726 at 16 kbps -> (10 ms..30 ms)

                  This value is expressed in ms, with increments of 10 ms.

                  For reception, the range is extended from 10 ms to 100 ms with
                  increments of 1 ms only if the stream is not encrypted (SRTP).

                  If a specific configuration is set in the
                  EpSpecificCodecG726r16kbps.MinPTime variable and the
                  EpSpecificCodecG726r16kbps.EnableConfig variable is set to
                  'Enable', then it overrides the current default configuration.


                  "
    DEFVAL        { 30 }
    ::= { codecG726r16kbpsGroup 400 }

   -- Scalar:Default G.726 16 Kbit/s Maximum Packetization Period Configuration

   defaultCodecG726r16kbpsMaxPTime OBJECT-TYPE
    SYNTAX        Unsigned32 ( 10..30 )
    MAX-ACCESS    read-write
    STATUS        current
    DESCRIPTION " Default G.726 16 Kbit/s Maximum Packetization Period
                  Configuration

                  Upper boundary for the packetization period of the given
                  codec.

                  G.726 at 16 kbps -> (10 ms..30 ms)

                  This value is expressed in ms, with increments of 10 ms.

                  For reception, the range is extended from 10 ms to 100 ms with
                  increments of 1 ms only if the stream is not encrypted (SRTP).

                  If a specific configuration is set in the
                  EpSpecificCodecG726r16kbps.MaxPTime variable and the
                  EpSpecificCodecG726r16kbps.EnableConfig variable is set to
                  'Enable', then it overrides the current default configuration.


                  "
    DEFVAL        { 30 }
    ::= { codecG726r16kbpsGroup 500 }

   -- ***************************************************************************
   
   -- Table:Endpoint Specific Voice Codec Configuration

   -- ***************************************************************************
   
   epSpecificCodecG726r16kbpsTable OBJECT-TYPE
    SYNTAX                    SEQUENCE OF EpSpecificCodecG726r16kbpsEntry
    MAX-ACCESS                not-accessible
    STATUS                    current
    DESCRIPTION            "  Endpoint Specific Voice Codec Configuration

                              Endpoint specific configuration.
                              "
    ::= { codecG726r16kbpsGroup 600 }
    epSpecificCodecG726r16kbpsEntry OBJECT-TYPE
     SYNTAX        EpSpecificCodecG726r16kbpsEntry
     MAX-ACCESS    not-accessible
     STATUS        current
     DESCRIPTION " A row in table Endpoint Specific Voice Codec Configuration .
                   "
     INDEX         {
                     epSpecificCodecG726r16kbpsEpId
                   }

     ::= { epSpecificCodecG726r16kbpsTable 1 }

    EpSpecificCodecG726r16kbpsEntry ::= SEQUENCE
    {
      epSpecificCodecG726r16kbpsEpId          OCTET STRING,
      epSpecificCodecG726r16kbpsEnableConfig  MxEnableState,
      epSpecificCodecG726r16kbpsVoiceEnable   MxEnableState,
      epSpecificCodecG726r16kbpsVoicePriority Unsigned32,
      epSpecificCodecG726r16kbpsPayloadType   Unsigned32,
      epSpecificCodecG726r16kbpsMinPTime      Unsigned32,
      epSpecificCodecG726r16kbpsMaxPTime      Unsigned32
    }

    -- Index:Endpoint Identifier

    epSpecificCodecG726r16kbpsEpId OBJECT-TYPE
     SYNTAX        OCTET STRING
     MAX-ACCESS    read-only
     STATUS        current
     DESCRIPTION " Endpoint Identifier

                   String that identifies an endpoint in other tables.
                   "
     ::= { epSpecificCodecG726r16kbpsEntry 100 }

    -- Columnar:Enable Configuration

    epSpecificCodecG726r16kbpsEnableConfig OBJECT-TYPE
     SYNTAX        MxEnableState
     MAX-ACCESS    read-write
     STATUS        current
     DESCRIPTION " Enable Configuration

                   Defines the configuration to use for a specific endpoint.

                     * Disable: The endpoint uses the default configuration as
                       defined in the DefaultCodecG726r16kbpsVoiceEnable,
                       DefaultCodecG726r16kbpsVoicePriority,
                       DefaultCodecG726r16kbpsPayloadType,
                       DefaultCodecG726r16kbpsMinPTime and
                       DefaultCodecG726r16kbpsMaxPTime variables.
                     * Enable: The endpoint uses the specific configuration as
                       defined in the EpSpecificCodecG726r16kbps.VoiceEnable,
                       EpSpecificCodecG726r16kbps.VoicePriority,
                       EpSpecificCodecG726r16kbps.PayloadType,
                       EpSpecificCodecG726r16kbps.MinPTime and
                       EpSpecificCodecG726r16kbps.MaxPTime variables.


                   "
     DEFVAL        { disable }
     ::= { epSpecificCodecG726r16kbpsEntry 200 }

    -- Columnar:Endpoint Specific G.726 16 Kbit/s Enable/Disable Configuration
    -- for Voice

    epSpecificCodecG726r16kbpsVoiceEnable OBJECT-TYPE
     SYNTAX        MxEnableState
     MAX-ACCESS    read-write
     STATUS        current
     DESCRIPTION " Endpoint Specific G.726 16 Kbit/s Enable/Disable
                   Configuration for Voice

                   Indicates if the codec can be selected for voice
                   transmission. If enabled, this codec is listed as supported
                   for this specific endpoint. Otherwise, it is ignored.

                     * Disable: Disable G.726 at 16 kbps.
                     * Enable: Enable G.726 at 16 kbps.

                   G.726 is specified in ITU-T Recommendation G.726: 40, 32, 24,
                   16 kbit/s adaptive differential pulse code modulation
                   (ADPCM). It describes the algorithm recommended for
                   conversion of a single 64 kbit/s A-law or U-law PCM channel
                   encoded at 8000 samples/sec to and from a 40, 32, 24, or 16
                   kbit/s channel. The conversion is applied to the PCM stream
                   using an Adaptive Differential Pulse Code Modulation (ADPCM)
                   transcoding technique.

                   This codec uses generic voice activity detection. See the
                   DefaultCodecGenericVoiceActivityDetection and
                   EpSpecificCodec.GenericVoiceActivityDetection variables.

                   This codec always uses the RTP transport.

                   This configuration overrides the default configuration set in
                   the DefaultCodecG726r16kbpsVoiceEnable variable if the
                   EpSpecificCodecG726r16kbps.EnableConfig variable is set to
                   'Enable'.


                   "
     DEFVAL        { disable }
     ::= { epSpecificCodecG726r16kbpsEntry 300 }

    -- Columnar:Endpoint Specific G.726 16 Kbit/s Priority Configuration for
    -- Voice

    epSpecificCodecG726r16kbpsVoicePriority OBJECT-TYPE
     SYNTAX        Unsigned32 ( 0..10 )
     MAX-ACCESS    read-write
     STATUS        current
     DESCRIPTION " Endpoint Specific G.726 16 Kbit/s Priority Configuration for
                   Voice

                   Indicates the priority of this voice codec versus the other
                   voice codecs. The voice codec with the highest priority will
                   be offered first when an outgoing call is initiated. This
                   priority is not used in incoming calls.

                   The application uses an internal order for codecs with the
                   same priority.

                   10 is the highest priority and 0 the lowest.

                   This configuration overrides the default configuration set in
                   the DefaultCodecG726r16kbpsVoicePriority variable if the
                   EpSpecificCodecG726r16kbps.EnableConfig variable is set to
                   'Enable'.


                   "
     DEFVAL        { 0 }
     ::= { epSpecificCodecG726r16kbpsEntry 400 }

    -- Columnar:Endpoint Specific G.726 16 Kbit/s Payload Type

    epSpecificCodecG726r16kbpsPayloadType OBJECT-TYPE
     SYNTAX        Unsigned32 ( 96..127 )
     MAX-ACCESS    read-write
     STATUS        current
     DESCRIPTION " Endpoint Specific G.726 16 Kbit/s Payload Type

                   Determines the actual RTP dynamic payload type used in an
                   initial offer when enabling G.726 at 16 kbps for voice and
                   data transmission.

                   The payload types available are as per RFC 3551.

                   This configuration overrides the default configuration set in
                   the DefaultCodecG726r16kbpsPayloadType variable if the
                   EpSpecificCodecG726r16kbps.EnableConfig variable is set to
                   'Enable'.


                   "
     DEFVAL        { 97 }
     ::= { epSpecificCodecG726r16kbpsEntry 500 }

    -- Columnar:Endpoint Specific G.726 16 Kbit/s Minimum Packetization Period
    -- Configuration

    epSpecificCodecG726r16kbpsMinPTime OBJECT-TYPE
     SYNTAX        Unsigned32 ( 10..30 )
     MAX-ACCESS    read-write
     STATUS        current
     DESCRIPTION " Endpoint Specific G.726 16 Kbit/s Minimum Packetization
                   Period Configuration

                   Lower boundary for the packetization period of the given
                   codec.

                   G.726 at 16 kbps -> (10 ms..30 ms)

                   This value is expressed in ms, with increments of 10 ms.

                   For reception, the range is extended from 10 ms to 100 ms
                   with increments of 1 ms only if the stream is not encrypted
                   (SRTP).

                   This configuration overrides the default configuration set in
                   the DefaultCodecG726r16kbpsMinPTime variable if the
                   EpSpecificCodecG726r16kbps.EnableConfig variable is set to
                   'Enable'.


                   "
     DEFVAL        { 30 }
     ::= { epSpecificCodecG726r16kbpsEntry 600 }

    -- Columnar:Endpoint Specific G.726 16 Kbit/s Maximum Packetization Period
    -- Configuration

    epSpecificCodecG726r16kbpsMaxPTime OBJECT-TYPE
     SYNTAX        Unsigned32 ( 10..30 )
     MAX-ACCESS    read-write
     STATUS        current
     DESCRIPTION " Endpoint Specific G.726 16 Kbit/s Maximum Packetization
                   Period Configuration

                   Upper boundary for the packetization period of the given
                   codec.

                   G.726 at 16 kbps -> (10 ms..30 ms)

                   This value is expressed in ms, with increments of 10 ms.

                   For reception, the range is extended from 10 ms to 100 ms
                   with increments of 1 ms only if the stream is not encrypted
                   (SRTP).

                   This configuration overrides the default configuration set in
                   the DefaultCodecG726r16kbpsMaxPTime variable if the
                   EpSpecificCodecG726r16kbps.EnableConfig variable is set to
                   'Enable'.


                   "
     DEFVAL        { 30 }
     ::= { epSpecificCodecG726r16kbpsEntry 700 }


   -- End of table:Endpoint Specific Voice Codec Configuration

  -- End of group:G.726 16 Kbit/s Voice Codec Group

  -- ***************************************************************************
  
  -- Group:G.726 24 Kbit/s Voice Codec Group

  -- ***************************************************************************
  
  codecG726r24kbpsGroup OBJECT IDENTIFIER
   ::= { codecG726Group 200 }
   -- Scalar:Default G.726 24 Kbit/s Enable/Disable Configuration for Voice

   defaultCodecG726r24kbpsVoiceEnable OBJECT-TYPE
    SYNTAX        MxEnableState
    MAX-ACCESS    read-write
    STATUS        current
    DESCRIPTION " Default G.726 24 Kbit/s Enable/Disable Configuration for Voice

                  Indicates if the codec can be selected for voice transmission.
                  If enabled, this codec is listed as supported for this
                  specific endpoint. Otherwise, it is ignored.

                    * Disable: Disable G.726 at 24 kbps.
                    * Enable: Enable G.726 at 24 kbps.

                  G.726 is specified in ITU-T Recommendation G.726: 40, 32, 24,
                  16 kbit/s adaptive differential pulse code modulation (ADPCM).
                  It describes the algorithm recommended for conversion of a
                  single 64 kbit/s A-law or U-law PCM channel encoded at 8000
                  samples/sec to and from a 40, 32, 24, or 16 kbit/s channel.
                  The conversion is applied to the PCM stream using an Adaptive
                  Differential Pulse Code Modulation (ADPCM) transcoding
                  technique.

                  This codec uses generic voice activity detection. See the
                  DefaultCodecGenericVoiceActivityDetection and
                  EpSpecificCodec.GenericVoiceActivityDetection variables.

                  This codec always uses the RTP transport.

                  If a specific configuration is set in the
                  EpSpecificCodecG726r24kbps.VoiceEnable variable and the
                  EpSpecificCodecG726r24kbps.EnableConfig variable is set to
                  'Enable', then it overrides the current default configuration.


                  "
    DEFVAL        { disable }
    ::= { codecG726r24kbpsGroup 100 }

   -- Scalar:Default G.726 24 Kbit/s Priority Configuration for Voice

   defaultCodecG726r24kbpsVoicePriority OBJECT-TYPE
    SYNTAX        Unsigned32 ( 0..10 )
    MAX-ACCESS    read-write
    STATUS        current
    DESCRIPTION " Default G.726 24 Kbit/s Priority Configuration for Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  If a specific configuration is set in the
                  EpSpecificCodecG726r24kbps.VoicePriority variable and the
                  EpSpecificCodecG726r24kbps.EnableConfig variable is set to
                  'Enable', then it overrides the current default configuration.


                  "
    DEFVAL        { 0 }
    ::= { codecG726r24kbpsGroup 200 }

   -- Scalar:Default G.726 24 Kbit/s Payload Type

   defaultCodecG726r24kbpsPayloadType OBJECT-TYPE
    SYNTAX        Unsigned32 ( 96..127 )
    MAX-ACCESS    read-write
    STATUS        current
    DESCRIPTION " Default G.726 24 Kbit/s Payload Type

                  When enabling G.726 at 24 kbps for voice and data
                  transmission, this variable determines the actual RTP dynamic
                  payload type used in an initial offer.

                  The payload types available are as per RFC 3551.

                  If a specific configuration is set in the
                  EpSpecificCodecG726r24kbps.PayloadType variable and the
                  EpSpecificCodecG726r24kbps.EnableConfig variable is set to
                  'Enable', then it overrides the current default configuration.


                  "
    DEFVAL        { 98 }
    ::= { codecG726r24kbpsGroup 300 }

   -- Scalar:Default G.726 24 Kbit/s Minimum Packetization Period Configuration

   defaultCodecG726r24kbpsMinPTime OBJECT-TYPE
    SYNTAX        Unsigned32 ( 10..30 )
    MAX-ACCESS    read-write
    STATUS        current
    DESCRIPTION " Default G.726 24 Kbit/s Minimum Packetization Period
                  Configuration

                  Lower boundary for the packetization period of the given
                  codec.

                  G.726 at 24 kbps -> (10 ms..30 ms)

                  This value is expressed in ms, with increments of 10 ms.

                  For reception, the range is extended from 10 ms to 100 ms with
                  increments of 1 ms only if the stream is not encrypted (SRTP).

                  If a specific configuration is set in the
                  EpSpecificCodecG726r24kbps.MinPTime variable and the
                  EpSpecificCodecG726r24kbps.EnableConfig variable is set to
                  'Enable', then it overrides the current default configuration.


                  "
    DEFVAL        { 30 }
    ::= { codecG726r24kbpsGroup 400 }

   -- Scalar:Default G.726 24 Kbit/s Maximum Packetization Period Configuration

   defaultCodecG726r24kbpsMaxPTime OBJECT-TYPE
    SYNTAX        Unsigned32 ( 10..30 )
    MAX-ACCESS    read-write
    STATUS        current
    DESCRIPTION " Default G.726 24 Kbit/s Maximum Packetization Period
                  Configuration

                  Upper boundary for the packetization period of the given
                  codec.

                  G.726 at 24 kbps -> (10 ms..30 ms)

                  This value is expressed in ms, with increments of 10 ms.

                  For reception, the range is extended from 10 ms to 100 ms with
                  increments of 1 ms only if the stream is not encrypted (SRTP).

                  If a specific configuration is set in the
                  EpSpecificCodecG726r24kbps.MaxPTime variable and the
                  EpSpecificCodecG726r24kbps.EnableConfig variable is set to
                  'Enable', then it overrides the current default configuration.


                  "
    DEFVAL        { 30 }
    ::= { codecG726r24kbpsGroup 500 }

   -- ***************************************************************************
   
   -- Table:Endpoint Specific Voice Codec Configuration

   -- ***************************************************************************
   
   epSpecificCodecG726r24kbpsTable OBJECT-TYPE
    SYNTAX                    SEQUENCE OF EpSpecificCodecG726r24kbpsEntry
    MAX-ACCESS                not-accessible
    STATUS                    current
    DESCRIPTION            "  Endpoint Specific Voice Codec Configuration

                              Endpoint specific configuration.
                              "
    ::= { codecG726r24kbpsGroup 600 }
    epSpecificCodecG726r24kbpsEntry OBJECT-TYPE
     SYNTAX        EpSpecificCodecG726r24kbpsEntry
     MAX-ACCESS    not-accessible
     STATUS        current
     DESCRIPTION " A row in table Endpoint Specific Voice Codec Configuration .
                   "
     INDEX         {
                     epSpecificCodecG726r24kbpsEpId
                   }

     ::= { epSpecificCodecG726r24kbpsTable 1 }

    EpSpecificCodecG726r24kbpsEntry ::= SEQUENCE
    {
      epSpecificCodecG726r24kbpsEpId          OCTET STRING,
      epSpecificCodecG726r24kbpsEnableConfig  MxEnableState,
      epSpecificCodecG726r24kbpsVoiceEnable   MxEnableState,
      epSpecificCodecG726r24kbpsVoicePriority Unsigned32,
      epSpecificCodecG726r24kbpsPayloadType   Unsigned32,
      epSpecificCodecG726r24kbpsMinPTime      Unsigned32,
      epSpecificCodecG726r24kbpsMaxPTime      Unsigned32
    }

    -- Index:Endpoint Identifier

    epSpecificCodecG726r24kbpsEpId OBJECT-TYPE
     SYNTAX        OCTET STRING
     MAX-ACCESS    read-only
     STATUS        current
     DESCRIPTION " Endpoint Identifier

                   String that identifies an endpoint in other tables.
                   "
     ::= { epSpecificCodecG726r24kbpsEntry 100 }

    -- Columnar:Enable Configuration

    epSpecificCodecG726r24kbpsEnableConfig OBJECT-TYPE
     SYNTAX        MxEnableState
     MAX-ACCESS    read-write
     STATUS        current
     DESCRIPTION " Enable Configuration

                   Defines the configuration to use for a specific endpoint.

                     * Disable: The endpoint uses the default configuration as
                       defined in the DefaultCodecG726r24kbpsVoiceEnable,
                       DefaultCodecG726r24kbpsVoicePriority,
                       DefaultCodecG726r24kbpsPayloadType,
                       DefaultCodecG726r24kbpsMinPTime and
                       DefaultCodecG726r24kbpsMaxPTime variables.
                     * Enable: The endpoint uses the specific configuration as
                       defined in the EpSpecificCodecG726r24kbps.VoiceEnable,
                       EpSpecificCodecG726r24kbps.VoicePriority,
                       EpSpecificCodecG726r24kbps.PayloadType,
                       EpSpecificCodecG726r24kbps.MinPTime and
                       EpSpecificCodecG726r24kbps.MaxPTime variable.


                   "
     DEFVAL        { disable }
     ::= { epSpecificCodecG726r24kbpsEntry 200 }

    -- Columnar:Endpoint Specific G.726 24 Kbit/s Enable/Disable Configuration
    -- for Voice

    epSpecificCodecG726r24kbpsVoiceEnable OBJECT-TYPE
     SYNTAX        MxEnableState
     MAX-ACCESS    read-write
     STATUS        current
     DESCRIPTION " Endpoint Specific G.726 24 Kbit/s Enable/Disable
                   Configuration for Voice

                   Indicates if the codec can be selected for voice
                   transmission. If enabled, this codec is listed as supported
                   for this specific endpoint. Otherwise, it is ignored.

                     * Disable: Disable G.726 at 24 kbps.
                     * Enable: Enable G.726 at 24 kbps.

                   G.726 is specified in ITU-T Recommendation G.726: 40, 32, 24,
                   16 kbit/s adaptive differential pulse code modulation
                   (ADPCM). It describes the algorithm recommended for
                   conversion of a single 64 kbit/s A-law or U-law PCM channel
                   encoded at 8000 samples/sec to and from a 40, 32, 24, or 16
                   kbit/s channel. The conversion is applied to the PCM stream
                   using an Adaptive Differential Pulse Code Modulation (ADPCM)
                   transcoding technique.

                   This codec uses generic voice activity detection. See the
                   DefaultCodecGenericVoiceActivityDetection and
                   EpSpecificCodec.GenericVoiceActivityDetection variables.

                   This codec always uses the RTP transport.

                   This configuration overrides the default configuration set in
                   the DefaultCodecG726r24kbpsVoiceEnable variable if the
                   EpSpecificCodecG726r24kbps.EnableConfig variable is set to
                   'Enable'.


                   "
     DEFVAL        { disable }
     ::= { epSpecificCodecG726r24kbpsEntry 300 }

    -- Columnar:Endpoint Specific G.726 24 Kbit/s Priority Configuration for
    -- Voice

    epSpecificCodecG726r24kbpsVoicePriority OBJECT-TYPE
     SYNTAX        Unsigned32 ( 0..10 )
     MAX-ACCESS    read-write
     STATUS        current
     DESCRIPTION " Endpoint Specific G.726 24 Kbit/s Priority Configuration for
                   Voice

                   Indicates the priority of this voice codec versus the other
                   voice codecs. The voice codec with the highest priority will
                   be offered first when an outgoing call is initiated. This
                   priority is not used in incoming calls.

                   The application uses an internal order for codecs with the
                   same priority.

                   10 is the highest priority and 0 the lowest.

                   This configuration overrides the default configuration set in
                   the DefaultCodecG726r24kbpsVoicePriority variable if the
                   EpSpecificCodecG726r24kbps.EnableConfig variable is set to
                   'Enable'.


                   "
     DEFVAL        { 0 }
     ::= { epSpecificCodecG726r24kbpsEntry 400 }

    -- Columnar:Endpoint Specific G.726 24 Kbit/s Payload Type

    epSpecificCodecG726r24kbpsPayloadType OBJECT-TYPE
     SYNTAX        Unsigned32 ( 96..127 )
     MAX-ACCESS    read-write
     STATUS        current
     DESCRIPTION " Endpoint Specific G.726 24 Kbit/s Payload Type

                   Determines the actual RTP dynamic payload type used in an
                   initial offer when enabling G.726 at 24 kbps for voice and
                   data transmission.

                   The payload types available are as per RFC 3551.

                   This configuration overrides the default configuration set in
                   the DefaultCodecG726r24kbpsPayloadType variable if the
                   EpSpecificCodecG726r24kbps.EnableConfig variable is set to
                   'Enable'.


                   "
     DEFVAL        { 98 }
     ::= { epSpecificCodecG726r24kbpsEntry 500 }

    -- Columnar:Endpoint Specific G.726 24 Kbit/s Minimum Packetization Period
    -- Configuration

    epSpecificCodecG726r24kbpsMinPTime OBJECT-TYPE
     SYNTAX        Unsigned32 ( 10..30 )
     MAX-ACCESS    read-write
     STATUS        current
     DESCRIPTION " Endpoint Specific G.726 24 Kbit/s Minimum Packetization
                   Period Configuration

                   Lower boundary for the packetization period of the given
                   codec.

                   G.726 at 24 kbps -> (10 ms..30 ms)

                   This value is expressed in ms, with increments of 10 ms.

                   For reception, the range is extended from 10 ms to 100 ms
                   with increments of 1 ms only if the stream is not encrypted
                   (SRTP).

                   This configuration overrides the default configuration set in
                   the DefaultCodecG726r24kbpsMinPTime variable if the
                   EpSpecificCodecG726r24kbps.EnableConfig variable is set to
                   'Enable'.


                   "
     DEFVAL        { 30 }
     ::= { epSpecificCodecG726r24kbpsEntry 600 }

    -- Columnar:Endpoint Specific G.726 24 Kbit/s Maximum Packetization Period
    -- Configuration

    epSpecificCodecG726r24kbpsMaxPTime OBJECT-TYPE
     SYNTAX        Unsigned32 ( 10..30 )
     MAX-ACCESS    read-write
     STATUS        current
     DESCRIPTION " Endpoint Specific G.726 24 Kbit/s Maximum Packetization
                   Period Configuration

                   Upper boundary for the packetization period of the given
                   codec.

                   G.726 at 24 kbps -> (10 ms..30 ms)

                   This value is expressed in ms, with increments of 10 ms.

                   For reception, the range is extended from 10 ms to 100 ms
                   with increments of 1 ms only if the stream is not encrypted
                   (SRTP).

                   This configuration overrides the default configuration set in
                   the DefaultCodecG726r24kbpsMaxPTime variable if the
                   EpSpecificCodecG726r24kbps.EnableConfig variable is set to
                   'Enable'.


                   "
     DEFVAL        { 30 }
     ::= { epSpecificCodecG726r24kbpsEntry 700 }


   -- End of table:Endpoint Specific Voice Codec Configuration

  -- End of group:G.726 24 Kbit/s Voice Codec Group

  -- ***************************************************************************
  
  -- Group:G.726 32 Kbit/s Voice Codec Group

  -- ***************************************************************************
  
  codecG726r32kbpsGroup OBJECT IDENTIFIER
   ::= { codecG726Group 300 }
   -- Scalar:Default G.726 32 Kbit/s Enable/Disable Configuration for Voice

   defaultCodecG726r32kbpsVoiceEnable OBJECT-TYPE
    SYNTAX        MxEnableState
    MAX-ACCESS    read-write
    STATUS        current
    DESCRIPTION " Default G.726 32 Kbit/s Enable/Disable Configuration for Voice

                  Indicates if the codec can be selected for voice transmission.
                  If enabled, this codec is listed as supported for this
                  specific endpoint. Otherwise, it is ignored.

                    * Disable: Disable G.726 at 32 kbps.
                    * Enable: Enable G.726 at 32 kbps.

                  G.726 is specified in ITU-T Recommendation G.726: 40, 32, 24,
                  16 kbit/s adaptive differential pulse code modulation (ADPCM).
                  It describes the algorithm recommended for conversion of a
                  single 64 kbit/s A-law or U-law PCM channel encoded at 8000
                  samples/sec to and from a 40, 32, 24, or 16 kbit/s channel.
                  The conversion is applied to the PCM stream using an Adaptive
                  Differential Pulse Code Modulation (ADPCM) transcoding
                  technique.

                  This codec uses generic voice activity detection. See the
                  DefaultCodecGenericVoiceActivityDetection and
                  EpSpecificCodec.GenericVoiceActivityDetection variables.

                  This codec always uses the RTP transport.


                  "
    DEFVAL        { disable }
    ::= { codecG726r32kbpsGroup 100 }

   -- Scalar:Default G.726 32 Kbit/s Priority Configuration for Voice

   defaultCodecG726r32kbpsVoicePriority OBJECT-TYPE
    SYNTAX        Unsigned32 ( 0..10 )
    MAX-ACCESS    read-write
    STATUS        current
    DESCRIPTION " Default G.726 32 Kbit/s Priority Configuration for Voice

                  Indicates the priority of this voice codec versus the other
                  voice codecs. The voice codec with the à highest priority will
                  be offered first when an outgoing call is initiated. This
                  priority is not used in incoming calls.

                  The application uses an internal order for codecs with the
                  same priority.

                  10 is the highest priority and 0 the lowest.

                  If a specific configuration is set in the
                  EpSpecificCodecG726r32kbps.VoiceEnable variable and the
                  EpSpecificCodecG726r32kbps.EnableConfig variable is set to
                  'Enable', then it overrides the current default configuration.


                  "
    DEFVAL        { 0 }
    ::= { codecG726r32kbpsGroup 200 }

   -- Scalar:Default G.726 32 Kbit/s Enable/Disable Configuration for Data

   defaultCodecG726r32kbpsDataEnable OBJECT-TYPE
    SYNTAX        MxEnableState
    MAX-ACCESS    read-write
    STATUS        current
    DESCRIPTION " Default G.726 32 Kbit/s Enable/Disable Configuration for Data

                  Indicates if the codec can be selected for data transmission.
                  If enabled, this codec is listed as supported for this
                  specific endpoint. Otherwise, it is ignored.

                    * Disable: Disable G.726 at 32 kbps.
                    * Enable: Enable G.726 at 32 kbps.

                  If a specific configuration is set in the
                  EpSpecificCodecG726r32kbps.DataEnable variable and the
                  EpSpecificCodecG726r32kbps.EnableConfig variable is set to
                  'Enable', then it overrides the current default configuration.


                  "
    DEFVAL        { disable }
    ::= { codecG726r32kbpsGroup 300 }

   -- Scalar:Default G.726 32 Kbit/s Priority Configuration for Data

   defaultCodecG726r32kbpsDataPriority OBJECT-TYPE
    SYNTAX        Unsigned32 ( 0..10 )
    MAX-ACCESS    read-write
    STATUS        current
    DESCRIPTION " Default G.726 32 Kbit/s Priority Configuration for Data

                  Indicates the priority of this data codec versus the other
                  data codecs. The data codec with the highest priority will be
                  offered first when an outgoing call is initiated. This
                  priority is not used in incoming calls.

                  The application uses an internal order for codecs with the
                  same priority.

                  10 is the highest priority and 0 the lowest.

                  If a specific configuration is set in the
                  EpSpecificCodecG726r32kbps.DataPriority variable and the
                  EpSpecificCodecG726r32kbps.EnableConfig variable is set to
                  'Enable', then it overrides the current default configuration.


                  "
    DEFVAL        { 0 }
    ::= { codecG726r32kbpsGroup 400 }

   -- Scalar:Default G.726 32 Kbit/s Payload Type

   defaultCodecG726r32kbpsPayloadType OBJECT-TYPE
    SYNTAX        Unsigned32 ( 96..127 )
    MAX-ACCESS    read-write
    STATUS        current
    DESCRIPTION " Default G.726 32 Kbit/s Payload Type

                  Determines the actual RTP dynamic payload type used in an
                  initial offer when enabling G.726 at 32 kbps for voice and
                  data transmission.

                  The payload types available are as per RFC 3551.

                  If a specific configuration is set in the
                  EpSpecificCodecG726r32kbps.PayloadType variable and the
                  EpSpecificCodecG726r32kbps.EnableConfig variable is set to
                  'Enable', then it overrides the current default configuration.


                  "
    DEFVAL        { 99 }
    ::= { codecG726r32kbpsGroup 500 }

   -- Scalar:Default G.726 32 Kbit/s Minimum Packetization Period Configuration

   defaultCodecG726r32kbpsMinPTime OBJECT-TYPE
    SYNTAX        Unsigned32 ( 10..30 )
    MAX-ACCESS    read-write
    STATUS        current
    DESCRIPTION " Default G.726 32 Kbit/s Minimum Packetization Period
                  Configuration

                  Lower boundary for the packetization period of the given
                  codec.

                  G.726 at 32 kbps -> (10 ms..30 ms)

                  This value is expressed in ms, with increments of 10 ms.

                  For reception, the range is extended from 10 ms to 100 ms with
                  increments of 1 ms only if the stream is not encrypted (SRTP).

                  If a specific configuration is set in the
                  EpSpecificCodecG726r32kbps.MinPTime variable and the
                  EpSpecificCodecG726r32kbps.EnableConfig variable is set to
                  'Enable', then it overrides the current default configuration.


                  "
    DEFVAL        { 30 }
    ::= { codecG726r32kbpsGroup 600 }

   -- Scalar:Default G.726 32 Kbit/s Maximum Packetization Period Configuration

   defaultCodecG726r32kbpsMaxPTime OBJECT-TYPE
    SYNTAX        Unsigned32 ( 10..30 )
    MAX-ACCESS    read-write
    STATUS        current
    DESCRIPTION " Default G.726 32 Kbit/s Maximum Packetization Period
                  Configuration

                  Upper boundary for the packetization period of the given
                  codec.

                  G.726 at 32 kbps -> (10 ms..30 ms)

                  This value is expressed in ms, with increments of 10 ms.

                  For reception, the range is extended from 10 ms to 100 ms with
                  increments of 1 ms only if the stream is not encrypted (SRTP).

                  If a specific configuration is set in the
                  EpSpecificCodecG726r32kbps.MaxPTime variable and the
                  EpSpecificCodecG726r32kbps.EnableConfig variable is set to
                  'Enable', then it overrides the current default configuration.


                  "
    DEFVAL        { 30 }
    ::= { codecG726r32kbpsGroup 700 }

   -- ***************************************************************************
   
   -- Table:Endpoint Specific Voice Codec Configuration

   -- ***************************************************************************
   
   epSpecificCodecG726r32kbpsTable OBJECT-TYPE
    SYNTAX                    SEQUENCE OF EpSpecificCodecG726r32kbpsEntry
    MAX-ACCESS                not-accessible
    STATUS                    current
    DESCRIPTION            "  Endpoint Specific Voice Codec Configuration

                              Endpoint specific configuration.
                              "
    ::= { codecG726r32kbpsGroup 800 }
    epSpecificCodecG726r32kbpsEntry OBJECT-TYPE
     SYNTAX        EpSpecificCodecG726r32kbpsEntry
     MAX-ACCESS    not-accessible
     STATUS        current
     DESCRIPTION " A row in table Endpoint Specific Voice Codec Configuration .
                   "
     INDEX         {
                     epSpecificCodecG726r32kbpsEpId
                   }

     ::= { epSpecificCodecG726r32kbpsTable 1 }

    EpSpecificCodecG726r32kbpsEntry ::= SEQUENCE
    {
      epSpecificCodecG726r32kbpsEpId          OCTET STRING,
      epSpecificCodecG726r32kbpsEnableConfig  MxEnableState,
      epSpecificCodecG726r32kbpsVoiceEnable   MxEnableState,
      epSpecificCodecG726r32kbpsVoicePriority Unsigned32,
      epSpecificCodecG726r32kbpsDataEnable    MxEnableState,
      epSpecificCodecG726r32kbpsDataPriority  Unsigned32,
      epSpecificCodecG726r32kbpsPayloadType   Unsigned32,
      epSpecificCodecG726r32kbpsMinPTime      Unsigned32,
      epSpecificCodecG726r32kbpsMaxPTime      Unsigned32
    }

    -- Index:Endpoint Identifier

    epSpecificCodecG726r32kbpsEpId OBJECT-TYPE
     SYNTAX        OCTET STRING
     MAX-ACCESS    read-only
     STATUS        current
     DESCRIPTION " Endpoint Identifier

                   String that identifies an endpoint in other tables.
                   "
     ::= { epSpecificCodecG726r32kbpsEntry 100 }

    -- Columnar:Enable Configuration

    epSpecificCodecG726r32kbpsEnableConfig OBJECT-TYPE
     SYNTAX        MxEnableState
     MAX-ACCESS    read-write
     STATUS        current
     DESCRIPTION " Enable Configuration

                   Defines the configuration to use for a specific endpoint.

                     * Disable: The endpoint uses the default configuration as
                       defined in the DefaultCodecG726r32kbpsVoiceEnable,
                       DefaultCodecG726r32kbpsVoicePriority,
                       DefaultCodecG726r32kbpsDataEnable,
                       DefaultCodecG726r32kbpsDataPriority,
                       DefaultCodecG726r32kbpsPayloadType,
                       DefaultCodecG726r32kbpsMinPTime and
                       DefaultCodecG726r32kbpsMaxPTime variables.
                     * Enable: The endpoint uses the specific configuration as
                       defined in the EpSpecificCodecG726r32kbps.VoiceEnable,
                       EpSpecificCodecG726r32kbps.VoicePriority,
                       EpSpecificCodecG726r32kbps.DataEnable,
                       EpSpecificCodecG726r32kbps.DataPriority,
                       EpSpecificCodecG726r32kbps.PayloadType,
                       EpSpecificCodecG726r32kbps.MinPTime and
                       EpSpecificCodecG726r32kbps.MaxPTime variables.


                   "
     DEFVAL        { disable }
     ::= { epSpecificCodecG726r32kbpsEntry 200 }

    -- Columnar:Endpoint Specific G.726 32 Kbit/s Enable/Disable Configuration
    -- for Voice

    epSpecificCodecG726r32kbpsVoiceEnable OBJECT-TYPE
     SYNTAX        MxEnableState
     MAX-ACCESS    read-write
     STATUS        current
     DESCRIPTION " Endpoint Specific G.726 32 Kbit/s Enable/Disable
                   Configuration for Voice

                   Indicates if the codec can be selected for voice
                   transmission. If enabled, this codec is listed as supported
                   for this specific endpoint. Otherwise, it is ignored.

                     * Disable: Disable G.726 at 32 kbps.
                     * Enable: Enable G.726 at 32 kbps.

                   G.726 is specified in ITU-T Recommendation G.726: 40, 32, 24,
                   16 kbit/s adaptive differential pulse code modulation
                   (ADPCM). It describes the algorithm recommended for
                   conversion of a single 64 kbit/s A-law or U-law PCM channel
                   encoded at 8000 samples/sec to and from a 40, 32, 24, or 16
                   kbit/s channel. The conversion is applied to the PCM stream
                   using an Adaptive Differential Pulse Code Modulation (ADPCM)
                   transcoding technique.

                   This codec uses generic voice activity detection. See the
                   DefaultCodecGenericVoiceActivityDetection and
                   EpSpecificCodec.GenericVoiceActivityDetection variables.

                   This codec always uses the RTP transport.

                   This configuration overrides the default configuration set in
                   the DefaultCodecG726r32kbpsVoiceEnable variable if the
                   EpSpecificCodecG726r32kbps.EnableConfig variable is set to
                   'Enable'.


                   "
     DEFVAL        { disable }
     ::= { epSpecificCodecG726r32kbpsEntry 300 }

    -- Columnar:Endpoint Specific G.726 32 Kbit/s Priority Configuration for
    -- Voice

    epSpecificCodecG726r32kbpsVoicePriority OBJECT-TYPE
     SYNTAX        Unsigned32 ( 0..10 )
     MAX-ACCESS    read-write
     STATUS        current
     DESCRIPTION " Endpoint Specific G.726 32 Kbit/s Priority Configuration for
                   Voice

                   Indicates the priority of this voice codec versus the other
                   voice codecs. The voice codec with the highest priority will
                   be offered first when an outgoing call is initiated. This
                   priority is not used in incoming calls.

                   The application uses an internal order for codecs with the
                   same priority.

                   10 is the highest priority and 0 the lowest.

                   This configuration overrides the default configuration set in
                   the DefaultCodecG726r32kbpsVoicePriority variable if the
                   EpSpecificCodecG726r32kbps.EnableConfig variable is set to
                   'Enable'.


                   "
     DEFVAL        { 0 }
     ::= { epSpecificCodecG726r32kbpsEntry 400 }

    -- Columnar:Endpoint Specific G.726 32 Kbit/s Enable/Disable Configuration
    -- for Data

    epSpecificCodecG726r32kbpsDataEnable OBJECT-TYPE
     SYNTAX        MxEnableState
     MAX-ACCESS    read-write
     STATUS        current
     DESCRIPTION " Endpoint Specific G.726 32 Kbit/s Enable/Disable
                   Configuration for Data

                   Indicates if the codec can be selected for data transmission.
                   If enabled, this codec is listed as supported for this
                   specific endpoint. Otherwise, it is ignored.

                     * Disable: Disable G.726 at 32 kbps.
                     * Enable: Enable G.726 at 32 kbps.

                   This configuration overrides the default configuration set in
                   the DefaultCodecG726r32kbpsDataEnable variable if the
                   EpSpecificCodecG726r32kbps.EnableConfig variable is set to
                   'Enable'.


                   "
     DEFVAL        { disable }
     ::= { epSpecificCodecG726r32kbpsEntry 500 }

    -- Columnar:Endpoint Specific G.726 32 Kbit/s Priority Configuration for
    -- Data

    epSpecificCodecG726r32kbpsDataPriority OBJECT-TYPE
     SYNTAX        Unsigned32 ( 0..10 )
     MAX-ACCESS    read-write
     STATUS        current
     DESCRIPTION " Endpoint Specific G.726 32 Kbit/s Priority Configuration for
                   Data

                   Indicates the priority of this data codec versus the other
                   data codecs. The data codec with the highest priority will be
                   offered first when an outgoing call is initiated. This
                   priority is not used in incoming calls.

                   The application uses an internal order for codecs with the
                   same priority.

                   10 is the highest priority and 0 the lowest.

                   This configuration overrides the default configuration set in
                   the DefaultCodecG726r32kbpsDataPriority variable if the
                   EpSpecificCodecG726r32kbps.EnableConfig variable is set to
                   'Enable'.


                   "
     DEFVAL        { 0 }
     ::= { epSpecificCodecG726r32kbpsEntry 600 }

    -- Columnar:Endpoint Specific G.726 32 Kbit/s Payload Type

    epSpecificCodecG726r32kbpsPayloadType OBJECT-TYPE
     SYNTAX        Unsigned32 ( 96..127 )
     MAX-ACCESS    read-write
     STATUS        current
     DESCRIPTION " Endpoint Specific G.726 32 Kbit/s Payload Type

                   Determines the actual RTP dynamic payload type used in an
                   initial offer when enabling G.726 at 32 kbps for voice and
                   data transmission.

                   The payload types available are as per RFC 3551.

                   This configuration overrides the default configuration set in
                   the DefaultCodecG726r32kbpsPayloadType variable if the
                   EpSpecificCodecG726r32kbps.EnableConfig variable is set to
                   'Enable'.


                   "
     DEFVAL        { 99 }
     ::= { epSpecificCodecG726r32kbpsEntry 700 }

    -- Columnar:Endpoint Specific G.726 32 Kbit/s Minimum Packetization Period
    -- Configuration

    epSpecificCodecG726r32kbpsMinPTime OBJECT-TYPE
     SYNTAX        Unsigned32 ( 10..30 )
     MAX-ACCESS    read-write
     STATUS        current
     DESCRIPTION " Endpoint Specific G.726 32 Kbit/s Minimum Packetization
                   Period Configuration

                   Lower boundary for the packetization period of the given
                   codec.

                   G.726 at 32 kbps -> (10 ms..30 ms)

                   This value is expressed in ms, with increments of 10 ms.

                   For reception, the range is extended from 10 ms to 100 ms
                   with increments of 1 ms only if the stream is not encrypted
                   (SRTP).

                   This configuration overrides the default configuration set in
                   the DefaultCodecG726r32kbpsMinPTime variable if the
                   EpSpecificCodecG726r32kbps.EnableConfig variable is set to
                   'Enable'.


                   "
     DEFVAL        { 30 }
     ::= { epSpecificCodecG726r32kbpsEntry 800 }

    -- Columnar:Endpoint Specific G.726 32 Kbit/s Maximum Packetization Period
    -- Configuration

    epSpecificCodecG726r32kbpsMaxPTime OBJECT-TYPE
     SYNTAX        Unsigned32 ( 10..30 )
     MAX-ACCESS    read-write
     STATUS        current
     DESCRIPTION " Endpoint Specific G.726 32 Kbit/s Maximum Packetization
                   Period Configuration

                   Upper boundary for the packetization period of the given
                   codec.

                   G.726 at 32 kbps -> (10 ms..30 ms)

                   This value is expressed in ms, with increments of 10 ms.

                   For reception, the range is extended from 10 ms to 100 ms
                   with increments of 1 ms only if the stream is not encrypted
                   (SRTP).

                   This configuration overrides the default configuration set in
                   the DefaultCodecG726r32kbpsMaxPTime variable if the
                   EpSpecificCodecG726r32kbps.EnableConfig variable is set to
                   'Enable'.


                   "
     DEFVAL        { 30 }
     ::= { epSpecificCodecG726r32kbpsEntry 900 }


   -- End of table:Endpoint Specific Voice Codec Configuration

  -- End of group:G.726 32 Kbit/s Voice Codec Group

  -- ***************************************************************************
  
  -- Group:G.726 40 Kbit/s Voice Codec Group

  -- ***************************************************************************
  
  codecG726r40kbpsGroup OBJECT IDENTIFIER
   ::= { codecG726Group 400 }
   -- Scalar:Default G.726 40 Kbit/s Enable/Disable Configuration for Voice

   defaultCodecG726r40kbpsVoiceEnable OBJECT-TYPE
    SYNTAX        MxEnableState
    MAX-ACCESS    read-write
    STATUS        current
    DESCRIPTION " Default G.726 40 Kbit/s Enable/Disable Configuration for Voice

                  Indicates if the codec can be selected for voice transmission.
                  If enabled, this codec is listed as supported for this
                  specific endpoint. Otherwise, it is ignored.

                    * Disable: Disable G.726 at 40 kbps.
                    * Enable: Enable G.726 at 40 kbps.

                  G.726 is specified in ITU-T Recommendation G.726: 40, 32, 24,
                  16 kbit/s adaptive differential pulse code modulation (ADPCM).
                  It describes the algorithm recommended for conversion of a
                  single 64 kbit/s A-law or U-law PCM channel encoded at 8000
                  samples/sec to and from a 40, 32, 24, or 16 kbit/s channel.
                  The conversion is applied to the PCM stream using an Adaptive
                  Differential Pulse Code Modulation (ADPCM) transcoding
                  technique.

                  This codec uses generic voice activity detection. See the
                  DefaultCodecGenericVoiceActivityDetection and
                  EpSpecificCodec.GenericVoiceActivityDetection variables.

                  This codec always uses the RTP transport.

                  If a specific configuration is set in the
                  EpSpecificCodecG726r40kbps.VoiceEnable variable and the
                  EpSpecificCodecG726r40kbps.EnableConfig variable is set to
                  'Enable', then it overrides the current default configuration.


                  "
    DEFVAL        { disable }
    ::= { codecG726r40kbpsGroup 100 }

   -- Scalar:Default G.726 40 Kbit/s Priority Configuration for Voice

   defaultCodecG726r40kbpsVoicePriority OBJECT-TYPE
    SYNTAX        Unsigned32 ( 0..10 )
    MAX-ACCESS    read-write
    STATUS        current
    DESCRIPTION " Default G.726 40 Kbit/s Priority Configuration for Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  If a specific configuration is set in the
                  EpSpecificCodecG726r40kbps.VoicePriority variable and the
                  EpSpecificCodecG726r40kbps.EnableConfig variable is set to
                  'Enable', then it overrides the current default configuration.


                  "
    DEFVAL        { 0 }
    ::= { codecG726r40kbpsGroup 200 }

   -- Scalar:Default G.726 40 Kbit/s Enable/Disable Configuration for Data

   defaultCodecG726r40kbpsDataEnable OBJECT-TYPE
    SYNTAX        MxEnableState
    MAX-ACCESS    read-write
    STATUS        current
    DESCRIPTION " Default G.726 40 Kbit/s Enable/Disable Configuration for Data

                  Indicates if the codec can be selected for data transmission.
                  If enabled, this codec is listed as supported for this
                  specific endpoint. Otherwise, it is ignored.

                    * Disable: Disable G.726 at 40 kbps.
                    * Enable: Enable G.726 at 40 kbps.

                  If a specific configuration is set in the
                  EpSpecificCodecG726r40kbps.DataEnable variable and the
                  EpSpecificCodecG726r40kbps.EnableConfig variable is set to
                  'Enable', then it overrides the current default configuration.


                  "
    DEFVAL        { disable }
    ::= { codecG726r40kbpsGroup 300 }

   -- Scalar:Default G.726 40 Kbit/s Priority Configuration for Data

   defaultCodecG726r40kbpsDataPriority OBJECT-TYPE
    SYNTAX        Unsigned32 ( 0..10 )
    MAX-ACCESS    read-write
    STATUS        current
    DESCRIPTION " Default G.726 40 Kbit/s Priority Configuration for Data

                  Indicates the priority of this data codec versus the other
                  data codecs. The data codec with the highest priority will be
                  offered first when an outgoing call is initiated. This
                  priority is not used in incoming calls.

                  The application uses an internal order for codecs with the
                  same priority.

                  10 is the highest priority and 0 the lowest.

                  If a specific configuration is set in the
                  EpSpecificCodecG726r40kbps.DataPriority variable and the
                  EpSpecificCodecG726r40kbps.EnableConfig variable is set to
                  'Enable', then it overrides the current default configuration.


                  "
    DEFVAL        { 0 }
    ::= { codecG726r40kbpsGroup 400 }

   -- Scalar:Default G.726 40 Kbit/s Payload Type

   defaultCodecG726r40kbpsPayloadType OBJECT-TYPE
    SYNTAX        Unsigned32 ( 96..127 )
    MAX-ACCESS    read-write
    STATUS        current
    DESCRIPTION " Default G.726 40 Kbit/s Payload Type

                  Setermines the actual RTP dynamic payload type used in an
                  initial offer when enabling G.726 at 40 kbps for voice and
                  data transmission.

                  The payload types available are as per RFC 3551.

                  If a specific configuration is set in the
                  EpSpecificCodecG726r40kbps.PayloadType variable and the
                  EpSpecificCodecG726r40kbps.EnableConfig variable is set to
                  'Enable', then it overrides the current default configuration.


                  "
    DEFVAL        { 100 }
    ::= { codecG726r40kbpsGroup 500 }

   -- Scalar:Default G.726 40 Kbit/s Minimum Packetization Period Configuration

   defaultCodecG726r40kbpsMinPTime OBJECT-TYPE
    SYNTAX        Unsigned32 ( 10..30 )
    MAX-ACCESS    read-write
    STATUS        current
    DESCRIPTION " Default G.726 40 Kbit/s Minimum Packetization Period
                  Configuration

                  Lower boundary for the packetization period of the given
                  codec.

                  G.726 at 40 kbps -> (10 ms..30 ms)

                  This value is expressed in ms, with increments of 10 ms.

                  For reception, the range is extended from 10 ms to 100 ms with
                  increments of 1 ms only if the stream is not encrypted (SRTP).

                  If a specific configuration is set in the
                  EpSpecificCodecG726r40kbps.MinPTime variable and the
                  EpSpecificCodecG726r40kbps.EnableConfig variable is set to
                  'Enable', then it overrides the current default configuration.


                  "
    DEFVAL        { 30 }
    ::= { codecG726r40kbpsGroup 600 }

   -- Scalar:Default G.726 40 Kbit/s Maximum Packetization Period Configuration

   defaultCodecG726r40kbpsMaxPTime OBJECT-TYPE
    SYNTAX        Unsigned32 ( 10..30 )
    MAX-ACCESS    read-write
    STATUS        current
    DESCRIPTION " Default G.726 40 Kbit/s Maximum Packetization Period
                  Configuration

                  Upper boundary for the packetization period of the given
                  codec.

                  G.726 at 40 kbps -> (10 ms..30 ms)

                  This value is expressed in ms, with increments of 10 ms.

                  For reception, the range is extended from 10 ms to 100 ms with
                  increments of 1 ms only if the stream is not encrypted (SRTP).

                  If a specific configuration is set in the
                  EpSpecificCodecG726r40kbps.MaxPTime variable and the
                  EpSpecificCodecG726r40kbps.EnableConfig variable is set to
                  'Enable', then it overrides the current default configuration.


                  "
    DEFVAL        { 30 }
    ::= { codecG726r40kbpsGroup 700 }

   -- ***************************************************************************
   
   -- Table:Endpoint Specific Voice Codec Configuration

   -- ***************************************************************************
   
   epSpecificCodecG726r40kbpsTable OBJECT-TYPE
    SYNTAX                    SEQUENCE OF EpSpecificCodecG726r40kbpsEntry
    MAX-ACCESS                not-accessible
    STATUS                    current
    DESCRIPTION            "  Endpoint Specific Voice Codec Configuration

                              Endpoint specific configuration.
                              "
    ::= { codecG726r40kbpsGroup 800 }
    epSpecificCodecG726r40kbpsEntry OBJECT-TYPE
     SYNTAX        EpSpecificCodecG726r40kbpsEntry
     MAX-ACCESS    not-accessible
     STATUS        current
     DESCRIPTION " A row in table Endpoint Specific Voice Codec Configuration .
                   "
     INDEX         {
                     epSpecificCodecG726r40kbpsEpId
                   }

     ::= { epSpecificCodecG726r40kbpsTable 1 }

    EpSpecificCodecG726r40kbpsEntry ::= SEQUENCE
    {
      epSpecificCodecG726r40kbpsEpId          OCTET STRING,
      epSpecificCodecG726r40kbpsEnableConfig  MxEnableState,
      epSpecificCodecG726r40kbpsVoiceEnable   MxEnableState,
      epSpecificCodecG726r40kbpsVoicePriority Unsigned32,
      epSpecificCodecG726r40kbpsDataEnable    MxEnableState,
      epSpecificCodecG726r40kbpsDataPriority  Unsigned32,
      epSpecificCodecG726r40kbpsPayloadType   Unsigned32,
      epSpecificCodecG726r40kbpsMinPTime      Unsigned32,
      epSpecificCodecG726r40kbpsMaxPTime      Unsigned32
    }

    -- Index:Endpoint Identifier

    epSpecificCodecG726r40kbpsEpId OBJECT-TYPE
     SYNTAX        OCTET STRING
     MAX-ACCESS    read-only
     STATUS        current
     DESCRIPTION " Endpoint Identifier

                   String that identifies an endpoint in other tables.
                   "
     ::= { epSpecificCodecG726r40kbpsEntry 100 }

    -- Columnar:Enable Configuration

    epSpecificCodecG726r40kbpsEnableConfig OBJECT-TYPE
     SYNTAX        MxEnableState
     MAX-ACCESS    read-write
     STATUS        current
     DESCRIPTION " Enable Configuration

                   Defines the configuration to use for a specific endpoint.

                     * Disable: The endpoint uses the default configuration as
                       defined in the DefaultCodecG726r40kbpsVoiceEnable,
                       DefaultCodecG726r40kbpsVoicePriority,
                       DefaultCodecG726r40kbpsDataEnable,
                       DefaultCodecG726r40kbpsDataPriority,
                       DefaultCodecG726r40kbpsPayloadType,
                       DefaultCodecG726r40kbpsMinPTime and
                       DefaultCodecG726r40kbpsMaxPTime variables.
                     * Enable: The endpoint uses the specific configuration as
                       defined in the EpSpecificCodecG726r40kbps.VoiceEnable,
                       EpSpecificCodecG726r40kbps.VoicePriority,
                       EpSpecificCodecG726r40kbps.DataEnable,
                       EpSpecificCodecG726r40kbps.DataPriority,
                       EpSpecificCodecG726r40kbps.PayloadType,
                       EpSpecificCodecG726r40kbps.MinPTime and
                       EpSpecificCodecG726r40kbps.MaxPTime variable.


                   "
     DEFVAL        { disable }
     ::= { epSpecificCodecG726r40kbpsEntry 200 }

    -- Columnar:Endpoint Specific G.726 40 Kbit/s Enable/Disable Configuration
    -- of Voice

    epSpecificCodecG726r40kbpsVoiceEnable OBJECT-TYPE
     SYNTAX        MxEnableState
     MAX-ACCESS    read-write
     STATUS        current
     DESCRIPTION " Endpoint Specific G.726 40 Kbit/s Enable/Disable
                   Configuration of Voice

                   Indicates if the codec can be selected for voice
                   transmission. If enabled, this codec is listed as supported
                   for this specific endpoint. Otherwise, it is ignored.

                     * Disable: Disable G.726 at 40 kbps.
                     * Enable: Enable G.726 at 40 kbps.

                   G.726 is specified in ITU-T Recommendation G.726: 40, 32, 24,
                   16 kbit/s adaptive differential pulse code modulation
                   (ADPCM). It describes the algorithm recommended for
                   conversion of a single 64 kbit/s A-law or U-law PCM channel
                   encoded at 8000 samples/sec to and from a 40, 32, 24, or 16
                   kbit/s channel. The conversion is applied to the PCM stream
                   using an Adaptive Differential Pulse Code Modulation (ADPCM)
                   transcoding technique.

                   This codec uses generic voice activity detection. See the
                   DefaultCodecGenericVoiceActivityDetection and
                   EpSpecificCodec.GenericVoiceActivityDetection variables.

                   This codec always uses the RTP transport.

                   This configuration overrides the default configuration set in
                   the DefaultCodecG726r40kbpsVoiceEnable variable if the
                   EpSpecificCodecG726r40kbps.EnableConfig variable is set to
                   'Enable'.


                   "
     DEFVAL        { disable }
     ::= { epSpecificCodecG726r40kbpsEntry 300 }

    -- Columnar:Endpoint Specific G.726 40 Kbit/s Priority Configuration for
    -- Voice

    epSpecificCodecG726r40kbpsVoicePriority OBJECT-TYPE
     SYNTAX        Unsigned32 ( 0..10 )
     MAX-ACCESS    read-write
     STATUS        current
     DESCRIPTION " Endpoint Specific G.726 40 Kbit/s Priority Configuration for
                   Voice

                   Indicates the priority of this voice codec versus the other
                   voice codecs. The voice codec with the highest priority will
                   be offered first when an outgoing call is initiated. This
                   priority is not used in incoming calls.

                   The application uses an internal order for codecs with the
                   same priority.

                   10 is the highest priority and 0 the lowest.

                   This configuration overrides the default configuration set in
                   the DefaultCodecG726r40kbpsVoicePriority variable if the
                   EpSpecificCodecG726r40kbps.EnableConfig variable is set to
                   'Enable'.


                   "
     DEFVAL        { 0 }
     ::= { epSpecificCodecG726r40kbpsEntry 400 }

    -- Columnar:Endpoint Specific G.726 40 Kbit/s Enable/Disable Configuration
    -- of Data

    epSpecificCodecG726r40kbpsDataEnable OBJECT-TYPE
     SYNTAX        MxEnableState
     MAX-ACCESS    read-write
     STATUS        current
     DESCRIPTION " Endpoint Specific G.726 40 Kbit/s Enable/Disable
                   Configuration of Data

                   Indicates if the codec can be selected for data transmission.
                   If enabled, this codec is listed as supported for this
                   specific endpoint. Otherwise, it is ignored.

                     * Disable: Disable G.726 at 40 kbps.
                     * Enable: Enable G.726 at 40 kbps.

                   This configuration overrides the default configuration set in
                   the DefaultCodecG726r40kbpsDataEnable variable if the
                   EpSpecificCodecG726r40kbps.EnableConfig variable is set to
                   'Enable'.


                   "
     DEFVAL        { disable }
     ::= { epSpecificCodecG726r40kbpsEntry 500 }

    -- Columnar:Default G.726 40 Kbit/s Priority Configuration for Data

    epSpecificCodecG726r40kbpsDataPriority OBJECT-TYPE
     SYNTAX        Unsigned32 ( 0..10 )
     MAX-ACCESS    read-write
     STATUS        current
     DESCRIPTION " Default G.726 40 Kbit/s Priority Configuration for Data

                   Indicates the priority of this data codec versus the other
                   data codecs. The data codec with the highest priority will be
                   offered first when an outgoing call is initiated. This
                   priority is not used in incoming calls.

                   The application uses an internal order for codecs with the
                   same priority.

                   10 is the highest priority and 0 the lowest.

                   This configuration overrides the default configuration set in
                   the DefaultCodecG726r40kbpsDataPriority variable if the
                   EpSpecificCodecG726r40kbps.EnableConfig variable is set to
                   'Enable'.


                   "
     DEFVAL        { 0 }
     ::= { epSpecificCodecG726r40kbpsEntry 600 }

    -- Columnar:Endpoint Specific G.726 40 Kbit/s Payload Type

    epSpecificCodecG726r40kbpsPayloadType OBJECT-TYPE
     SYNTAX        Unsigned32 ( 96..127 )
     MAX-ACCESS    read-write
     STATUS        current
     DESCRIPTION " Endpoint Specific G.726 40 Kbit/s Payload Type

                   Determines the actual RTP dynamic payload type used in an
                   initial offer when enabling G.726 at 40 kbps for voice and
                   data transmission.

                   The payload types available are as per RFC 3551.

                   This configuration overrides the default configuration set in
                   the DefaultCodecG726r40kbpsPayloadType variable if the
                   EpSpecificCodecG726r40kbps.EnableConfig variable is set to
                   'Enable'.


                   "
     DEFVAL        { 100 }
     ::= { epSpecificCodecG726r40kbpsEntry 700 }

    -- Columnar:Endpoint Specific G.726 40 Kbit/s Minimum Packetization Period
    -- Configuration

    epSpecificCodecG726r40kbpsMinPTime OBJECT-TYPE
     SYNTAX        Unsigned32 ( 10..30 )
     MAX-ACCESS    read-write
     STATUS        current
     DESCRIPTION " Endpoint Specific G.726 40 Kbit/s Minimum Packetization
                   Period Configuration

                   Lower boundary for the packetization period of the given
                   codec.

                   G.726 at 40 kbps -> (10 ms..30 ms)

                   This value is expressed in ms, with increments of 10 ms.

                   For reception, the range is extended from 10 ms to 100 ms
                   with increments of 1 ms only if the stream is not encrypted
                   (SRTP).

                   This configuration overrides the default configuration set in
                   the DefaultCodecG726r40kbpsMinPTime variable if the
                   EpSpecificCodecG726r40kbps.EnableConfig variable is set to
                   'Enable'.


                   "
     DEFVAL        { 30 }
     ::= { epSpecificCodecG726r40kbpsEntry 800 }

    -- Columnar:Endpoint Specific G.726 40 Kbit/s Maximum Packetization Period
    -- Configuration

    epSpecificCodecG726r40kbpsMaxPTime OBJECT-TYPE
     SYNTAX        Unsigned32 ( 10..30 )
     MAX-ACCESS    read-write
     STATUS        current
     DESCRIPTION " Endpoint Specific G.726 40 Kbit/s Maximum Packetization
                   Period Configuration

                   Upper boundary for the packetization period of the given
                   codec.

                   G.726 at 40 kbps -> (10 ms..30 ms)

                   This value is expressed in ms, with increments of 10 ms.

                   For reception, the range is extended from 10 ms to 100 ms
                   with increments of 1 ms only if the stream is not encrypted
                   (SRTP).

                   This configuration overrides the default configuration set in
                   the DefaultCodecG726r40kbpsMaxPTime variable if the
                   EpSpecificCodecG726r40kbps.EnableConfig variable is set to
                   'Enable'.


                   "
     DEFVAL        { 30 }
     ::= { epSpecificCodecG726r40kbpsEntry 900 }


   -- End of table:Endpoint Specific Voice Codec Configuration

  -- End of group:G.726 40 Kbit/s Voice Codec Group

 -- End of group:G.726 Voice Codec Group

 -- ***************************************************************************
 
 -- Group:G.729 Voice Codec Group

 -- ***************************************************************************
 
 codecG729Group OBJECT IDENTIFIER
  ::= { codecGroup 600 }
  -- Scalar:Default G.729 Enable/Disable Configuration

  defaultCodecG729VoiceEnable OBJECT-TYPE
   SYNTAX        MxEnableState
   MAX-ACCESS    read-write
   STATUS        current
   DESCRIPTION " Default G.729 Enable/Disable Configuration

                 Indicates if the codec can be selected for voice transmission.
                 If enabled, this codec is listed as supported for this
                 specific endpoint. Otherwise, it is ignored.

                 G729 is specified in ITU-T Recommendation G.729, Coding of
                 speech at 8 kbit/s using conjugate structure-algebraic code
                 excited linear prediction (CS-ACELP). For all data rates, the
                 sampling frequency (and RTP timestamp clock rate) is 8000 Hz.
                 A voice activity detector (VAD) and comfort noise generator
                 (CNG) algorithm in Annex B of G.729 is RECOMMENDED for digital
                 simultaneous voice and data applications and can be used in
                 conjunction with G.729 or G.729 Annex A. A G.729 or G.729
                 Annex A frame contains 10 octets, while the G.729 Annex B
                 comfort noise frame occupies 2 octets.

                 This codec always uses the RTP transport.

                 If a specific configuration is set in the
                 EpSpecificCodecG729.VoiceEnable variable and the
                 EpSpecificCodecG729.EnableConfig variable is set to 'Enable',
                 then it overrides the current default configuration.


                 "
   DEFVAL        { enable }
   ::= { codecG729Group 100 }

  -- Scalar:Default G.729 Priority Configuration for Voice

  defaultCodecG729VoicePriority OBJECT-TYPE
   SYNTAX        Unsigned32 ( 0..10 )
   MAX-ACCESS    read-write
   STATUS        current
   DESCRIPTION " Default G.729 Priority Configuration for Voice

                 Indicates the priority of this voice codec versus the other
                 voice codecs. The voice codec with the highest priority will
                 be offered first when an outgoing call is initiated. This
                 priority is not used in incoming calls.

                 The application uses an internal order for codecs with the
                 same priority.

                 10 is the highest priority and 0 the lowest.

                 If a specific configuration is set in the
                 EpSpecificCodecG729.VoicePriority variable and the
                 EpSpecificCodecG729.EnableConfig variable is set to 'Enable',
                 then it overrides the current default configuration.


                 "
   DEFVAL        { 0 }
   ::= { codecG729Group 200 }

  -- Scalar:Default G.729 Minimum Packetization Period Configuration

  defaultCodecG729MinPTime OBJECT-TYPE
   SYNTAX        Unsigned32 ( 20..20 | 30..30 | 40..40 | 50..50 | 60..60 |
                 70..70 | 80..80 )
   MAX-ACCESS    read-write
   STATUS        current
   DESCRIPTION " Default G.729 Minimum Packetization Period Configuration

                 Lower boundary for the packetization period of the given
                 codec.

                 G.729 -> (20 ms|30 ms|40 ms|50 ms|60 ms|70 ms|80 ms)

                 This value is expressed in ms, with increments of 10 ms.

                 For reception, the range is extended from 10 ms to 100 ms with
                 increments of 10 ms only if the stream is not encrypted
                 (SRTP).

                 If a specific configuration is set in the
                 EpSpecificCodecG729.MinPTime variable and the
                 EpSpecificCodecG729.EnableConfig variable is set to 'Enable',
                 then it overrides the current default configuration.


                 "
   DEFVAL        { 30 }
   ::= { codecG729Group 300 }

  -- Scalar:Default G.729 Maximum Packetization Period Configuration

  defaultCodecG729MaxPTime OBJECT-TYPE
   SYNTAX        Unsigned32 ( 20..20 | 30..30 | 40..40 | 50..50 | 60..60 |
                 70..70 | 80..80 )
   MAX-ACCESS    read-write
   STATUS        current
   DESCRIPTION " Default G.729 Maximum Packetization Period Configuration

                 Upper boundary for the packetization period of the given
                 codec.

                 G.729 -> (20 ms|30 ms|40 ms|50 ms|60 ms|70 ms|80 ms)

                 This value is expressed in ms, with increments of 10 ms.

                 For reception, the range is extended from 10 ms to 100 ms with
                 increments of 10 ms only if the stream is not encrypted
                 (SRTP).

                 If a specific configuration is set in the
                 EpSpecificCodecG729.MaxPTime variable and the
                 EpSpecificCodecG729.EnableConfig variable is set to 'Enable',
                 then it overrides the current default configuration.


                 "
   DEFVAL        { 80 }
   ::= { codecG729Group 400 }

  -- Scalar:Default G.729 VAD Configuration

  defaultCodecG729VoiceActivityDetection OBJECT-TYPE
   SYNTAX        MxEnableState
   MAX-ACCESS    read-write
   STATUS        current
   DESCRIPTION " Default G.729 VAD Configuration

                 If Voice Activity Detection (VAD) is enabled, then speech
                 frames are only sent during talkspurts (periods of audio
                 activity).

                 During silence periods, no speech frames are sent, but Comfort
                 Noise (CN) packets containing information about background
                 noise may be sent in accordance with annex B of G.729.

                   * Disable: G.729 uses annex A only.
                   * Enable: G.729 annex A is used with annex B.

                 If a specific configuration is set in the
                 EpSpecificCodecG729.VoiceActivityDetection variable and the
                 EpSpecificCodecG729.EnableConfig variable is set to 'Enable',
                 then it overrides the current default configuration.


                 "
   DEFVAL        { enable }
   ::= { codecG729Group 500 }

  -- ***************************************************************************
  
  -- Table:Endpoint Specific Voice Codec Configuration

  -- ***************************************************************************
  
  epSpecificCodecG729Table OBJECT-TYPE
   SYNTAX                      SEQUENCE OF EpSpecificCodecG729Entry
   MAX-ACCESS                  not-accessible
   STATUS                      current
   DESCRIPTION              "  Endpoint Specific Voice Codec Configuration

                               Endpoint specific configuration.
                               "
   ::= { codecG729Group 600 }
   epSpecificCodecG729Entry OBJECT-TYPE
    SYNTAX        EpSpecificCodecG729Entry
    MAX-ACCESS    not-accessible
    STATUS        current
    DESCRIPTION " A row in table Endpoint Specific Voice Codec Configuration .
                  "
    INDEX         {
                    epSpecificCodecG729EpId
                  }

    ::= { epSpecificCodecG729Table 1 }

   EpSpecificCodecG729Entry ::= SEQUENCE
   {
     epSpecificCodecG729EpId                   OCTET STRING,
     epSpecificCodecG729EnableConfig           MxEnableState,
     epSpecificCodecG729VoiceEnable            MxEnableState,
     epSpecificCodecG729VoicePriority          Unsigned32,
     epSpecificCodecG729MinPTime               Unsigned32,
     epSpecificCodecG729MaxPTime               Unsigned32,
     epSpecificCodecG729VoiceActivityDetection MxEnableState
   }

   -- Index:Endpoint Identifier

   epSpecificCodecG729EpId OBJECT-TYPE
    SYNTAX        OCTET STRING
    MAX-ACCESS    read-only
    STATUS        current
    DESCRIPTION " Endpoint Identifier

                  String that identifies an endpoint in other tables.
                  "
    ::= { epSpecificCodecG729Entry 100 }

   -- Columnar:Enable Configuration

   epSpecificCodecG729EnableConfig OBJECT-TYPE
    SYNTAX        MxEnableState
    MAX-ACCESS    read-write
    STATUS        current
    DESCRIPTION " Enable Configuration

                  Defines the configuration to use for a specific endpoint.

                    * Disable: The endpoint uses the default configuration as
                      defined in the DefaultCodecG729VoiceEnable,
                      DefaultCodecG729VoicePriority, DefaultCodecG729MinPTime,
                      DefaultCodecG729MaxPTime and
                      DefaultCodecG729VoiceActivityDetection variables.
                    * Enable: The endpoint uses the specific configuration as
                      defined in the EpSpecificCodecG729.EnableVoice
                      EpSpecificCodecG729.VoicePriority,
                      EpSpecificCodecG729.MinPTime,
                      EpSpecificCodecG729.MaxPTime and
                      EpSpecificCodecG729.VoiceActivityDetection variables.


                  "
    DEFVAL        { disable }
    ::= { epSpecificCodecG729Entry 200 }

   -- Columnar:Endpoint Specific G.729 Enable/Disable Configuration for Voice

   epSpecificCodecG729VoiceEnable OBJECT-TYPE
    SYNTAX        MxEnableState
    MAX-ACCESS    read-write
    STATUS        current
    DESCRIPTION " Endpoint Specific G.729 Enable/Disable Configuration for
                  Voice

                  Indicates if the codec can be selected for voice
                  transmission. If enabled, this codec is listed as supported
                  for this specific endpoint. Otherwise, it is ignored.

                  G729 is specified in ITU-T Recommendation G.729, Coding of
                  speech at 8 kbit/s using conjugate structure-algebraic code
                  excited linear prediction (CS-ACELP). For all data rates, the
                  sampling frequency (and RTP timestamp clock rate) is 8000 Hz.
                  A voice activity detector (VAD) and comfort noise generator
                  (CNG) algorithm in Annex B of G.729 is RECOMMENDED for
                  digital simultaneous voice and data applications and can be
                  used in conjunction with G.729 or G.729 Annex A. A G.729 or
                  G.729 Annex A frame contains 10 octets, while the G.729 Annex
                  B comfort noise frame occupies 2 octets.

                  This codec always uses the RTP transport.

                  This configuration overrides the default configuration set in
                  the DefaultCodecG729VoiceEnable variable if the
                  EpSpecificCodecG729.EnableConfig variable is set to 'Enable'.


                  "
    DEFVAL        { enable }
    ::= { epSpecificCodecG729Entry 300 }

   -- Columnar:Endpoint Specific G.729 Priority Configuration for Voice

   epSpecificCodecG729VoicePriority OBJECT-TYPE
    SYNTAX        Unsigned32 ( 0..10 )
    MAX-ACCESS    read-write
    STATUS        current
    DESCRIPTION " Endpoint Specific G.729 Priority Configuration for Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  This configuration overrides the default configuration set in
                  the DefaultCodecG729VoicePriority variable if the
                  EpSpecificCodecG729.EnableConfig variable is set to 'Enable'.


                  "
    DEFVAL        { 0 }
    ::= { epSpecificCodecG729Entry 400 }

   -- Columnar:Endpoint Specific G.729 Minimum Packetization Period
   -- Configuration

   epSpecificCodecG729MinPTime OBJECT-TYPE
    SYNTAX        Unsigned32 ( 20..20 | 30..30 | 40..40 | 50..50 | 60..60 |
                  70..70 | 80..80 )
    MAX-ACCESS    read-write
    STATUS        current
    DESCRIPTION " Endpoint Specific G.729 Minimum Packetization Period
                  Configuration

                  Lower boundary for the packetization period of the given
                  codec.

                  G.729 -> (20 ms|30 ms|40 ms|50 ms|60 ms|70 ms|80 ms)

                  This value is expressed in ms, with increments of 10 ms.

                  For reception, the range is extended from 10 ms to 100 ms
                  with increments of 10 ms only if the stream is not encrypted
                  (SRTP).

                  This configuration overrides the default configuration set in
                  the DefaultCodecG729MinPTime variable if the
                  EpSpecificCodecG729.EnableConfig variable is set to 'Enable'.


                  "
    DEFVAL        { 30 }
    ::= { epSpecificCodecG729Entry 500 }

   -- Columnar:Endpoint Specific G.729 Maximum Packetization Period
   -- Configuration

   epSpecificCodecG729MaxPTime OBJECT-TYPE
    SYNTAX        Unsigned32 ( 20..20 | 30..30 | 40..40 | 50..50 | 60..60 |
                  70..70 | 80..80 )
    MAX-ACCESS    read-write
    STATUS        current
    DESCRIPTION " Endpoint Specific G.729 Maximum Packetization Period
                  Configuration

                  Upper boundary for the packetization period of the given
                  codec.

                  G.729 -> (20 ms|30 ms|40 ms|50 ms|60 ms|70 ms|80 ms)

                  This value is expressed in ms, with increments of 10 ms.

                  For reception, the range is extended from 10 ms to 100 ms
                  with increments of 10 ms only if the stream is not encrypted
                  (SRTP).

                  This configuration overrides the default configuration set in
                  the DefaultCodecG729MaxPTime variable if the
                  EpSpecificCodecG729.EnableConfig variable is set to 'Enable'.


                  "
    DEFVAL        { 80 }
    ::= { epSpecificCodecG729Entry 600 }

   -- Columnar:Endpoint Specific G.729 VAD Configuration

   epSpecificCodecG729VoiceActivityDetection OBJECT-TYPE
    SYNTAX        MxEnableState
    MAX-ACCESS    read-write
    STATUS        current
    DESCRIPTION " Endpoint Specific G.729 VAD Configuration

                  If Voice Activity Detection (VAD) is enabled, then speech
                  frames are only sent during talkspurts (periods of audio
                  activity).

                  During silence periods, no speech frames are sent, but
                  Comfort Noise (CN) packets containing information about
                  background noise may be sent in accordance with annex B of
                  G.729.

                    * Disable: G.729 uses annex A only.
                    * Enable: G.729 annex A is used with annex B.

                  This configuration overrides the default configuration set in
                  the DefaultCodecG729VoiceActivityDetection variable if the
                  EpSpecificCodecG729.EnableConfig variable is set to 'Enable'.


                  "
    DEFVAL        { enable }
    ::= { epSpecificCodecG729Entry 700 }


  -- End of table:Endpoint Specific Voice Codec Configuration

 -- End of group:G.729 Voice Codec Group

 -- ***************************************************************************
 
 -- Group:T.38 Codec Related Configuration Group

 -- ***************************************************************************
 
 codecT38Group OBJECT IDENTIFIER
  ::= { codecGroup 700 }
  -- Scalar:Default T.38 Enable/Disable Configuration for Data

  defaultCodecT38DataEnable OBJECT-TYPE
   SYNTAX        MxEnableState
   MAX-ACCESS    read-write
   STATUS        current
   DESCRIPTION " Default T.38 Enable/Disable Configuration for Data

                 If enabled, the T.38 protocol is used for fax transmission.

                 If a specific configuration is set in the
                 EpSpecificCodecT38.DataEnable variable and the
                 EpSpecificCodecT38.EnableConfig variable is set to 'Enable',
                 then it overrides the current default configuration.


                 "
   DEFVAL        { enable }
   ::= { codecT38Group 100 }

  -- Scalar: Default T.38 Priority Configuration for Data

  defaultCodecT38DataPriority OBJECT-TYPE
   SYNTAX        Unsigned32 ( 10..10 )
   MAX-ACCESS    read-write
   STATUS        current
   DESCRIPTION " Default T.38 Priority Configuration for Data

                 Indicates the priority of this data codec versus the other
                 data codecs. The data codec with the highest priority will be
                 offered first when an outgoing call is initiated. This
                 priority is not used in incoming calls.

                 The application uses an internal order for codecs with the
                 same priority.

                 10 is the highest priority and 0 the lowest.

                 If a specific configuration is set in the
                 EpSpecificCodecT38.DataPriority variable and the
                 EpSpecificCodecT38.EnableConfig variable is set to 'Enable',
                 then it overrides the current default configuration.


                 "
   DEFVAL        { 10 }
   ::= { codecT38Group 200 }

  -- Scalar:Default T.38 Protection Level

  defaultCodecT38RedundancyLevel OBJECT-TYPE
   SYNTAX        Unsigned32 ( 1..5 )
   MAX-ACCESS    read-write
   STATUS        current
   DESCRIPTION " Default T.38 Protection Level

                 Number of redundancy packets. This is the standard redundancy
                 offered by T.38.

                 Refer to the DefaultCodecT38FinalFramesRedundancy variable for
                 additional T.38 reliability options.

                 If a specific configuration is set in the
                 EpSpecificCodecT38.RedundancyLevel variable and the
                 EpSpecificCodecT38.EnableConfig variable is set to 'Enable',
                 then it overrides the current default configuration.


                 "
   DEFVAL        { 3 }
   ::= { codecT38Group 400 }

  -- Scalar:Default T.38 Redundancy for Final Frame

  defaultCodecT38FinalFramesRedundancy OBJECT-TYPE
   SYNTAX        Unsigned32 ( 0..3 )
   MAX-ACCESS    read-write
   STATUS        current
   DESCRIPTION " Default T.38 Redundancy for Final Frame

                 Defines the number of times T.38 packets will be
                 retransmitted. This only applies to the T.38 packets where the
                 PrimaryUDPTL contains the following T.38 data type:
                 HDLC_SIG_END, HDLC_FCS_OK_SIG_END, HDLC_FCS_BAD_SIG_END and
                 T4_NON_ECM_SIG_END.

                 Refer to the DefaultCodecT38ProtectionLevel variable for
                 standard T.38 reliability options.


                 "
   DEFVAL        { 0 }
   ::= { codecT38Group 500 }

  -- Scalar:Default T.38 No Signal Enable/Disable Configuration.

  defaultCodecT38NoSignalEnable OBJECT-TYPE
   SYNTAX        MxEnableState
   MAX-ACCESS    read-write
   STATUS        current
   DESCRIPTION " Default T.38 No Signal Enable/Disable Configuration.

                 Enables/disables the sending of T.38 no-signal packets. When
                 enabled, the unit ensures that, during a T.38 fax
                 transmission, data is sent out at least every time the
                 DefaultCodecT38NoSignalTimeout delay expires. In the absence
                 of meaningful data to send, no-signal packets are output.
                 "
   DEFVAL        { disable }
   ::= { codecT38Group 600 }

  -- Scalar:Default T.38 No Signal Timeout

  defaultCodecT38NoSignalTimeout OBJECT-TYPE
   SYNTAX        Unsigned32 ( 1..2147483647 )
   MAX-ACCESS    read-write
   STATUS        current
   DESCRIPTION " Default T.38 No Signal Timeout

                 The period, in seconds, at which no-signal packets are sent
                 during a T.38 transmission, in the absence of valid data.
                 "
   DEFVAL        { 1 }
   ::= { codecT38Group 700 }

  -- Scalar:Default T.38 Detection Threshold

  defaultCodecT38DetectionThreshold OBJECT-TYPE
   SYNTAX        INTEGER { default(100) , low(200) , lowest(300) }
   MAX-ACCESS    read-write
   STATUS        current
   DESCRIPTION " Default T.38 Detection Threshold

                 Sets the T.38 input signal detection threshold. Lowering the
                 threshold allows detecting lower amplitude fax signals.

                   * Default: (-26dB)
                   * Low: (-31dB)
                   * Lowest: (-43dB)

                 If a specific configuration is set in the
                 EpSpecificCodecT38.DetectionThreshold variable and the
                 EpSpecificCodecT38.EnableConfig variable is set to 'Enable',
                 then it overrides the current default configuration.


                 "
   DEFVAL        { default }
   ::= { codecT38Group 750 }

  -- ***************************************************************************
  
  -- Table:Endpoint Specific Voice Codec Configuration

  -- ***************************************************************************
  
  epSpecificCodecT38Table OBJECT-TYPE
   SYNTAX               SEQUENCE OF EpSpecificCodecT38Entry
   MAX-ACCESS           not-accessible
   STATUS               current
   DESCRIPTION       "  Endpoint Specific Voice Codec Configuration

                        Endpoint specific configuration.
                        "
   ::= { codecT38Group 800 }
   epSpecificCodecT38Entry OBJECT-TYPE
    SYNTAX        EpSpecificCodecT38Entry
    MAX-ACCESS    not-accessible
    STATUS        current
    DESCRIPTION " A row in table Endpoint Specific Voice Codec Configuration .
                  "
    INDEX         {
                    epSpecificCodecT38EpId
                  }

    ::= { epSpecificCodecT38Table 1 }

   EpSpecificCodecT38Entry ::= SEQUENCE
   {
     epSpecificCodecT38EpId               OCTET STRING,
     epSpecificCodecT38EnableConfig       MxEnableState,
     epSpecificCodecT38DataEnable         MxEnableState,
     epSpecificCodecT38DataPriority       Unsigned32,
     epSpecificCodecT38RedundancyLevel    Unsigned32,
     epSpecificCodecT38DetectionThreshold INTEGER
   }

   -- Index:Endpoint Identifier

   epSpecificCodecT38EpId OBJECT-TYPE
    SYNTAX        OCTET STRING
    MAX-ACCESS    read-only
    STATUS        current
    DESCRIPTION " Endpoint Identifier

                  String that identifies an endpoint in other tables.
                  "
    ::= { epSpecificCodecT38Entry 100 }

   -- Columnar:Enable Configuration

   epSpecificCodecT38EnableConfig OBJECT-TYPE
    SYNTAX        MxEnableState
    MAX-ACCESS    read-write
    STATUS        current
    DESCRIPTION " Enable Configuration

                  Defines the configuration to use for a specific endpoint.

                    * Disable: The endpoint uses the default configuration as
                      defined in the DefaultCodecT38DataEnable,
                      DefaultCodecT38DataPriority and
                      DefaultCodecT38RedundancyLevel variables.
                    * Enable: The endpoint uses the specific configuration as
                      defined in the EpSpecificCodecT38.DataEnable,
                      EpSpecificCodecT38.DataPriority and
                      EpSpecificCodecT38.RedundancyLevel variables.


                  "
    DEFVAL        { disable }
    ::= { epSpecificCodecT38Entry 200 }

   -- Columnar:Endpoint Specific T.38 Enable/Disable Configuration for Data

   epSpecificCodecT38DataEnable OBJECT-TYPE
    SYNTAX        MxEnableState
    MAX-ACCESS    read-write
    STATUS        current
    DESCRIPTION " Endpoint Specific T.38 Enable/Disable Configuration for Data

                  If enabled, the T.38 protocol is used for fax transmission.

                  This configuration overrides the default configuration set in
                  the DefaultCodecT38DataEnable variable if the
                  EpSpecificCodecT38.EnableConfig variable is set to 'Enable'.


                  "
    DEFVAL        { enable }
    ::= { epSpecificCodecT38Entry 300 }

   -- Columnar:Endpoint Specific T.38 Priority Configuration for Data

   epSpecificCodecT38DataPriority OBJECT-TYPE
    SYNTAX        Unsigned32 ( 10..10 )
    MAX-ACCESS    read-write
    STATUS        current
    DESCRIPTION " Endpoint Specific T.38 Priority Configuration for Data

                  Indicates the priority of this data codec versus the other
                  data codecs. The data codec with the highest priority will be
                  offered first when an outgoing call is initiated. This
                  priority is not used in incoming calls.

                  The application uses an internal order for codecs with the
                  same priority.

                  10 is the highest priority and 0 the lowest.

                  This configuration overrides the default configuration set in
                  the DefaultCodecT38DataPriority variable if the
                  EpSpecificCodecT38.EnableConfig variable is set to 'Enable'.


                  "
    DEFVAL        { 10 }
    ::= { epSpecificCodecT38Entry 400 }

   -- Columnar:Endpoint Specific T.38 Protection Level.

   epSpecificCodecT38RedundancyLevel OBJECT-TYPE
    SYNTAX        Unsigned32 ( 1..5 )
    MAX-ACCESS    read-write
    STATUS        current
    DESCRIPTION " Endpoint Specific T.38 Protection Level.

                  Number of redundancy packets. This is the standard redundancy
                  offered by T.38.

                  Refer to the DefaultCodecT38FinalFramesRedundancy variable
                  for additional T.38 reliability options.

                  This configuration overrides the default configuration set in
                  the DefaultCodecT38RedundancyLevel variable if the
                  EpSpecificCodecT38.EnableConfig variable is set to 'Enable'.


                  "
    DEFVAL        { 3 }
    ::= { epSpecificCodecT38Entry 600 }

   -- Columnar:Endpoint Specific T.38 Detection Threshold

   epSpecificCodecT38DetectionThreshold OBJECT-TYPE
    SYNTAX        INTEGER { default(100) , low(200) , lowest(300) }
    MAX-ACCESS    read-write
    STATUS        current
    DESCRIPTION " Endpoint Specific T.38 Detection Threshold

                  Sets the T.38 input signal detection threshold. Lowering the
                  threshold allows detecting lower amplitude fax signals.

                    * Default: (-26dB)
                    * Low: (-31dB)
                    * Lowest: (-43dB)

                  This configuration overrides the default configuration set in
                  the DefaultCodecT38DetectionThreshold variable if the
                  EpSpecificCodecT38.EnableConfig variable is set to 'Enable'.


                  "
    DEFVAL        { default }
    ::= { epSpecificCodecT38Entry 700 }


  -- End of table:Endpoint Specific Voice Codec Configuration

 -- End of group:T.38 Codec Related Configuration Group

 -- ***************************************************************************
 
 -- Group:Clear Channel Codec Related Configuration Group

 -- ***************************************************************************
 
 codecClearModeGroup OBJECT IDENTIFIER
  ::= { codecGroup 800 }
  -- Scalar:Default Clear Mode Enable/Disable Configuration for Voice

  defaultCodecClearModeVoiceEnable OBJECT-TYPE
   SYNTAX        MxEnableState
   MAX-ACCESS    read-write
   STATUS        current
   DESCRIPTION " Default Clear Mode Enable/Disable Configuration for Voice

                 Indicates if the codec can be selected for voice transmission.
                 If enabled, this codec is listed as supported for this
                 specific endpoint. Otherwise, it is ignored.

                 Clear Mode is a method to carry 64 kbit/s channel data
                 transparently in RTP packets as defined in RFC 4040.

                 This codec always uses the RTP transport.

                 If a specific configuration is set in the
                 EpSpecificCodecClearMode.VoiceEnable variable and the
                 EpSpecificCodecClearMode.EnableConfig variable is set to
                 'Enable', then it overrides the current default configuration.


                 "
   DEFVAL        { disable }
   ::= { codecClearModeGroup 100 }

  -- Scalar:Default Clear Mode Priority Configuration for Voice

  defaultCodecClearModeVoicePriority OBJECT-TYPE
   SYNTAX        Unsigned32 ( 0..10 )
   MAX-ACCESS    read-write
   STATUS        current
   DESCRIPTION " Default Clear Mode Priority Configuration for Voice

                 Indicates the priority of this voice codec versus the other
                 voice codecs. The voice codec with the highest priority will
                 be offered first when an outgoing call is initiated. This
                 priority is not used in incoming calls.

                 The application uses an internal order for codecs with the
                 same priority.

                 10 is the highest priority and 0 the lowest.

                 If a specific configuration is set in the
                 EpSpecificCodecClearMode.VoicePriority variable and the
                 EpSpecificCodecClearMode.EnableConfig variable is set to
                 'Enable', then it overrides the current default configuration.


                 "
   DEFVAL        { 0 }
   ::= { codecClearModeGroup 200 }

  -- Scalar:Default Clear Mode Enable/Disable Configuration for Data

  defaultCodecClearModeDataEnable OBJECT-TYPE
   SYNTAX        MxEnableState
   MAX-ACCESS    read-write
   STATUS        current
   DESCRIPTION " Default Clear Mode Enable/Disable Configuration for Data

                 If enabled, the Clear Mode protocol is used for data
                 transmission.

                 The data transmission for this codec can be triggered by the
                 detection of a fax/modem tone or if the properties of the call
                 indicate that it was for data.

                 Clear Mode is a method to carry 64 kbit/s channel data
                 transparently in RTP packets as defined in RFC 4040.

                 This codec always uses the RTP transport.

                 If a specific configuration is set in the
                 EpSpecificCodecClearMode.DataEnable variable and the
                 EpSpecificCodecClearMode.EnableConfig variable is set to
                 'Enable', then it overrides the current default configuration.


                 "
   DEFVAL        { disable }
   ::= { codecClearModeGroup 300 }

  -- Scalar: Default Clear Mode Priority Configuration for Data

  defaultCodecClearModeDataPriority OBJECT-TYPE
   SYNTAX        Unsigned32 ( 0..10 )
   MAX-ACCESS    read-write
   STATUS        current
   DESCRIPTION " Default Clear Mode Priority Configuration for Data

                 Indicates the priority of this data codec versus the other
                 data codecs. The data codec with the highest priority will be
                 offered first when an outgoing call is initiated. This
                 priority is not used in incoming calls.

                 The application uses an internal order for codecs with the
                 same priority.

                 10 is the highest priority and 0 the lowest.

                 If a specific configuration is set in the
                 EpSpecificCodecClearMode.DataPriority variable and the
                 EpSpecificCodecClearMode.EnableConfig variable is set to
                 'Enable', then it overrides the current default configuration.


                 "
   DEFVAL        { 10 }
   ::= { codecClearModeGroup 400 }

  -- Scalar:Default Clear Mode Payload Type

  defaultCodecClearModePayloadType OBJECT-TYPE
   SYNTAX        Unsigned32 ( 96..127 )
   MAX-ACCESS    read-write
   STATUS        current
   DESCRIPTION " Default Clear Mode Payload Type

                 When enabling Clear Mode for voice and data transmission, this
                 variable determines the actual RTP dynamic payload type used
                 in an initial offer.

                 The payload types available are as per RFC 3551.

                 If a specific configuration is set in the
                 EpSpecificCodecClearMode.PayloadType variable and the
                 EpSpecificCodecClearMode.EnableConfig variable is set to
                 'Enable', then it overrides the current default configuration.


                 "
   DEFVAL        { 124 }
   ::= { codecClearModeGroup 500 }

  -- Scalar:Default Clear Mode Minimum Packetization Period Configuration

  defaultCodecClearModeMinPTime OBJECT-TYPE
   SYNTAX        Unsigned32 ( 10..30 )
   MAX-ACCESS    read-write
   STATUS        current
   DESCRIPTION " Default Clear Mode Minimum Packetization Period Configuration

                 Lower boundary for the packetization period of the given
                 codec.

                 Clear Mode -> (10 ms..30 ms)

                 This value is expressed in ms, with increments of 10 ms.

                 For reception, the range is extended from 10 ms to 100 ms with
                 increments of 1 ms only if the stream is not encrypted (SRTP).

                 If a specific configuration is set in the
                 EpSpecificCodecClearMode.MinPTime variable and the
                 EpSpecificCodecClearMode.EnableConfig variable is set to
                 'Enable', then it overrides the current default configuration.


                 "
   DEFVAL        { 10 }
   ::= { codecClearModeGroup 600 }

  -- Scalar:Default Clear Mode Maximum Packetization Period Configuration

  defaultCodecClearModeMaxPTime OBJECT-TYPE
   SYNTAX        Unsigned32 ( 10..30 )
   MAX-ACCESS    read-write
   STATUS        current
   DESCRIPTION " Default Clear Mode Maximum Packetization Period Configuration

                 Upper boundary for the packetization period of the given
                 codec.

                 Clear Mode -> (10 ms..30 ms)

                 This value is expressed in ms, with increments of 10 ms.

                 For reception, the range is extended from 10 ms to 100 ms with
                 increments of 1 ms only if the stream is not encrypted (SRTP).

                 If a specific configuration is set in the
                 EpSpecificCodecClearMode.MaxPTime variable and the
                 EpSpecificCodecClearMode.EnableConfig variable is set to
                 'Enable', then it overrides the current default configuration.


                 "
   DEFVAL        { 30 }
   ::= { codecClearModeGroup 700 }

  -- ***************************************************************************
  
  -- Table:Endpoint Specific Voice Codec Configuration

  -- ***************************************************************************
  
  epSpecificCodecClearModeTable OBJECT-TYPE
   SYNTAX                  SEQUENCE OF EpSpecificCodecClearModeEntry
   MAX-ACCESS              not-accessible
   STATUS                  current
   DESCRIPTION          "  Endpoint Specific Voice Codec Configuration

                           Endpoint specific configuration.
                           "
   ::= { codecClearModeGroup 800 }
   epSpecificCodecClearModeEntry OBJECT-TYPE
    SYNTAX        EpSpecificCodecClearModeEntry
    MAX-ACCESS    not-accessible
    STATUS        current
    DESCRIPTION " A row in table Endpoint Specific Voice Codec Configuration .
                  "
    INDEX         {
                    epSpecificCodecClearModeEpId
                  }

    ::= { epSpecificCodecClearModeTable 1 }

   EpSpecificCodecClearModeEntry ::= SEQUENCE
   {
     epSpecificCodecClearModeEpId          OCTET STRING,
     epSpecificCodecClearModeEnableConfig  MxEnableState,
     epSpecificCodecClearModeVoiceEnable   MxEnableState,
     epSpecificCodecClearModeVoicePriority Unsigned32,
     epSpecificCodecClearModeDataEnable    MxEnableState,
     epSpecificCodecClearModeDataPriority  Unsigned32,
     epSpecificCodecClearModePayloadType   Unsigned32,
     epSpecificCodecClearModeMinPTime      Unsigned32,
     epSpecificCodecClearModeMaxPTime      Unsigned32
   }

   -- Index:Endpoint Identifier

   epSpecificCodecClearModeEpId OBJECT-TYPE
    SYNTAX        OCTET STRING
    MAX-ACCESS    read-only
    STATUS        current
    DESCRIPTION " Endpoint Identifier

                  String that identifies an endpoint in other tables.
                  "
    ::= { epSpecificCodecClearModeEntry 100 }

   -- Columnar:Enable Configuration

   epSpecificCodecClearModeEnableConfig OBJECT-TYPE
    SYNTAX        MxEnableState
    MAX-ACCESS    read-write
    STATUS        current
    DESCRIPTION " Enable Configuration

                  Defines the configuration to use for a specific endpoint.

                    * Disable: The endpoint uses the default configuration as
                      defined in the DefaultCodecClearModeVoiceEnable,
                      DefaultCodecClearModeVoicePriority,
                      DefaultCodecClearModeDataEnable,
                      DefaultCodecClearModeDataPriority,
                      DefaultCodecClearModePayloadType,
                      DefaultCodecClearModeMinPTime and
                      DefaultCodecClearModeMaxPTime.
                    * Enable: The endpoint uses the specific configuration as
                      defined in the EpSpecificCodecClearMode.VoiceEnable,
                      EpSpecificCodecClearMode.VoicePriority,
                      EpSpecificCodecClearMode.DataPriority,
                      EpSpecificCodecClearMode.DataPriority,
                      EpSpecificCodecClearMode.PayloadType,
                      EpSpecificCodecClearMode.MinPTime and
                      EpSpecificCodecClearMode.MaxPTime.


                  "
    DEFVAL        { disable }
    ::= { epSpecificCodecClearModeEntry 200 }

   -- Columnar:Endpoint Specific Clear Mode Enable/Disable Configuration for
   -- Voice

   epSpecificCodecClearModeVoiceEnable OBJECT-TYPE
    SYNTAX        MxEnableState
    MAX-ACCESS    read-write
    STATUS        current
    DESCRIPTION " Endpoint Specific Clear Mode Enable/Disable Configuration for
                  Voice

                  Indicates if the codec can be selected for voice
                  transmission. If enabled, this codec is listed as supported
                  for this specific endpoint. Otherwise, it is ignored.

                  Clear Mode is a method to carry 64 kbit/s channel data
                  transparently in RTP packets as defined in RFC 4040.

                  This codec always uses the RTP transport.

                  This configuration overrides the default configuration set in
                  the DefaultCodecClearModeVoiceEnable variable if the
                  EpSpecificCodecClearMode.EnableConfig variable is set to
                  'Enable'.


                  "
    DEFVAL        { disable }
    ::= { epSpecificCodecClearModeEntry 300 }

   -- Columnar:Endpoint Specific Clear Mode Priority Configuration for Voice

   epSpecificCodecClearModeVoicePriority OBJECT-TYPE
    SYNTAX        Unsigned32 ( 0..10 )
    MAX-ACCESS    read-write
    STATUS        current
    DESCRIPTION " Endpoint Specific Clear Mode Priority Configuration for Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  This configuration overrides the default configuration set in
                  the DefaultCodecClearModeVoicePriority variable if the
                  EpSpecificCodecClearMode.EnableConfig variable is set to
                  'Enable'.


                  "
    DEFVAL        { 0 }
    ::= { epSpecificCodecClearModeEntry 400 }

   -- Columnar:Endpoint Specific Clear Mode Enable/Disable Configuration for
   -- Data

   epSpecificCodecClearModeDataEnable OBJECT-TYPE
    SYNTAX        MxEnableState
    MAX-ACCESS    read-write
    STATUS        current
    DESCRIPTION " Endpoint Specific Clear Mode Enable/Disable Configuration for
                  Data

                  If enabled, the Clear Mode protocol is used for fax
                  transmission.

                  This configuration overrides the default configuration set in
                  the DefaultCodecClearModeDataEnable variable if the
                  EpSpecificCodecClearMode.EnableConfig variable is set to
                  'Enable'.


                  "
    DEFVAL        { disable }
    ::= { epSpecificCodecClearModeEntry 500 }

   -- Columnar:Endpoint Specific Clear Mode Priority Configuration for Data

   epSpecificCodecClearModeDataPriority OBJECT-TYPE
    SYNTAX        Unsigned32 ( 0..10 )
    MAX-ACCESS    read-write
    STATUS        current
    DESCRIPTION " Endpoint Specific Clear Mode Priority Configuration for Data

                  Indicates the priority of this data codec versus the other
                  data codecs. The data codec with the highest priority will be
                  offered first when an outgoing call is initiated. This
                  priority is not used in incoming calls.

                  The application uses an internal order for codecs with the
                  same priority.

                  10 is the highest priority and 0 the lowest.

                  This configuration overrides the default configuration set in
                  the DefaultCodecClearModeDataPriority variable if the
                  EpSpecificCodecClearMode.EnableConfig variable is set to
                  'Enable'.


                  "
    DEFVAL        { 10 }
    ::= { epSpecificCodecClearModeEntry 600 }

   -- Columnar:Endpoint Specific Clear Mode Payload Type

   epSpecificCodecClearModePayloadType OBJECT-TYPE
    SYNTAX        Unsigned32 ( 96..127 )
    MAX-ACCESS    read-write
    STATUS        current
    DESCRIPTION " Endpoint Specific Clear Mode Payload Type

                  When enabling Clear Mode for voice and data transmission,
                  this variable determines the actual RTP dynamic payload type
                  used in an initial offer.

                  The payload types available are as per RFC 3551.

                  This configuration overrides the default configuration set in
                  the DefaultCodecClearModePayloadType variable if the
                  EpSpecificCodecClearMode.EnableConfig variable is set to
                  'Enable'.


                  "
    DEFVAL        { 124 }
    ::= { epSpecificCodecClearModeEntry 700 }

   -- Columnar:Endpoint Specific Clear Mode Minimum Packetization Period
   -- Configuration

   epSpecificCodecClearModeMinPTime OBJECT-TYPE
    SYNTAX        Unsigned32 ( 10..30 )
    MAX-ACCESS    read-write
    STATUS        current
    DESCRIPTION " Endpoint Specific Clear Mode Minimum Packetization Period
                  Configuration

                  Lower boundary for the packetization period of the given
                  codec.

                  Clear Mode -> (10 ms..30 ms)

                  This value is expressed in ms, with increments of 10 ms.

                  For reception, the range is extended from 10 ms to 100 ms
                  with increments of 1 ms only if the stream is not encrypted
                  (SRTP).

                  This configuration overrides the default configuration set in
                  the DefaultCodecClearModeMinPTime variable if the
                  EpSpecificCodecClearMode.EnableConfig variable is set to
                  'Enable'.


                  "
    DEFVAL        { 10 }
    ::= { epSpecificCodecClearModeEntry 800 }

   -- Columnar:Endpoint Specific Clear Mode Maximum Packetization Period
   -- Configuration

   epSpecificCodecClearModeMaxPTime OBJECT-TYPE
    SYNTAX        Unsigned32 ( 10..30 )
    MAX-ACCESS    read-write
    STATUS        current
    DESCRIPTION " Endpoint Specific Clear Mode Maximum Packetization Period
                  Configuration

                  Upper boundary for the packetization period of the given
                  codec.

                  Clear Mode -> (10 ms..30 ms)

                  This value is expressed in ms, with increments of 10 ms.

                  For reception, the range is extended from 10 ms to 100 ms
                  with increments of 1 ms only if the stream is not encrypted
                  (SRTP).

                  This configuration overrides the default configuration set in
                  the DefaultCodecClearModeMaxPTime variable if the
                  EpSpecificCodecClearMode.EnableConfig variable is set to
                  'Enable'.


                  "
    DEFVAL        { 30 }
    ::= { epSpecificCodecClearModeEntry 900 }


  -- End of table:Endpoint Specific Voice Codec Configuration

 -- End of group:Clear Channel Codec Related Configuration Group

 -- ***************************************************************************
 
 -- Group:Clear Channel Codec Related Configuration Group

 -- ***************************************************************************
 
 codecClearChannelGroup OBJECT IDENTIFIER
  ::= { codecGroup 900 }
  -- Scalar:Default Clear Channel Enable/Disable Configuration for Voice

  defaultCodecClearChannelVoiceEnable OBJECT-TYPE
   SYNTAX        MxEnableState
   MAX-ACCESS    read-write
   STATUS        current
   DESCRIPTION " Default Clear Channel Enable/Disable Configuration for Voice

                 Indicates if the codec can be selected for voice transmission.
                 If enabled, this codec is listed as supported for this
                 specific endpoint. Otherwise, it is ignored.

                 Clear Channel is a method to carry 64 kbit/s channel data
                 transparently in RTP packets. This codec behaves like the
                 Clear Mode as defined in RFC 4040, but it uses
                 'X-CLEAR-CHANNEL' instead of 'CLEARMODE' in the codec
                 negotiation.

                 This codec always uses the RTP transport.

                 If a specific configuration is set in the
                 EpSpecificCodecClearChannel.VoiceEnable variable and the
                 EpSpecificCodecClearChannel.EnableConfig variable is set to
                 'Enable', then it overrides the current default configuration.


                 "
   DEFVAL        { disable }
   ::= { codecClearChannelGroup 100 }

  -- Scalar:Default Clear Channel Priority Configuration for Voice

  defaultCodecClearChannelVoicePriority OBJECT-TYPE
   SYNTAX        Unsigned32 ( 0..10 )
   MAX-ACCESS    read-write
   STATUS        current
   DESCRIPTION " Default Clear Channel Priority Configuration for Voice

                 Indicates the priority of this voice codec versus the other
                 voice codecs. The voice codec with the highest priority will
                 be offered first when an outgoing call is initiated. This
                 priority is not used in incoming calls.

                 The application uses an internal order for codecs with the
                 same priority.

                 10 is the highest priority and 0 the lowest.

                 If a specific configuration is set in the
                 EpSpecificCodecClearChannel.VoicePriority variable and the
                 EpSpecificCodecClearChannel.EnableConfig variable is set to
                 'Enable', then it overrides the current default configuration.


                 "
   DEFVAL        { 0 }
   ::= { codecClearChannelGroup 200 }

  -- Scalar:Default Clear Channel Enable/Disable Configuration for Data

  defaultCodecClearChannelDataEnable OBJECT-TYPE
   SYNTAX        MxEnableState
   MAX-ACCESS    read-write
   STATUS        current
   DESCRIPTION " Default Clear Channel Enable/Disable Configuration for Data

                 If enabled, the Clear Channel protocol is used for data
                 transmission.

                 Clear Channel is a method to carry 64 kbit/s channel data
                 transparently in RTP packets. This codec behaves like the
                 Clear Mode as defined in RFC 4040, but it uses
                 'X-CLEAR-CHANNEL' instead of 'CLEARMODE' in the codec
                 negotiation.

                 Clear Channel is a method to carry 64 kbit/s channel data
                 transparently in RTP packets as defined in RFC 4040.

                 This codec always uses the RTP transport.

                 If a specific configuration is set in the
                 EpSpecificCodecClearChannel.DataEnable variable and the
                 EpSpecificCodecClearChannel.EnableConfig variable is set to
                 'Enable', then it overrides the current default configuration.


                 "
   DEFVAL        { disable }
   ::= { codecClearChannelGroup 300 }

  -- Scalar:Default Clear Channel Priority Configuration for Data

  defaultCodecClearChannelDataPriority OBJECT-TYPE
   SYNTAX        Unsigned32 ( 0..10 )
   MAX-ACCESS    read-write
   STATUS        current
   DESCRIPTION " Default Clear Channel Priority Configuration for Data

                 Indicates the priority of this data codec versus the other
                 data codecs. The data codec with the highest priority will be
                 offered first when an outgoing call is initiated. This
                 priority is not used in incoming calls.

                 The application uses an internal order for codecs with the
                 same priority.

                 10 is the highest priority and 0 the lowest.

                 If a specific configuration is set in the
                 EpSpecificCodecClearChannel.DataPriority variable and the
                 EpSpecificCodecClearChannel.EnableConfig variable is set to
                 'Enable', then it overrides the current default configuration.


                 "
   DEFVAL        { 10 }
   ::= { codecClearChannelGroup 400 }

  -- Scalar:Default Clear Channel Payload Type

  defaultCodecClearChannelPayloadType OBJECT-TYPE
   SYNTAX        Unsigned32 ( 96..127 )
   MAX-ACCESS    read-write
   STATUS        current
   DESCRIPTION " Default Clear Channel Payload Type

                 When enabling Clear Channel for voice and data transmission,
                 this variable determines the actual RTP dynamic payload type
                 used in an initial offer.

                 The payload types available are as per RFC 3551.

                 If a specific configuration is set in the
                 EpSpecificCodecClearChannel.PayloadType variable and the
                 EpSpecificCodecClearChannel.EnableConfig variable is set to
                 'Enable', then it overrides the current default configuration.


                 "
   DEFVAL        { 125 }
   ::= { codecClearChannelGroup 500 }

  -- Scalar:Default Clear Channel Minimum Packetization Period Configuration

  defaultCodecClearChannelMinPTime OBJECT-TYPE
   SYNTAX        Unsigned32 ( 10..30 )
   MAX-ACCESS    read-write
   STATUS        current
   DESCRIPTION " Default Clear Channel Minimum Packetization Period
                 Configuration

                 Lower boundary for the packetization period of the given
                 codec.

                 Clear Channel -> (10 ms..30 ms)

                 This value is expressed in ms, with increments of 10 ms.

                 For reception, the range is extended from 10 ms to 100 ms with
                 increments of 1 ms only if the stream is not encrypted (SRTP).

                 If a specific configuration is set in the
                 EpSpecificCodecClearChannel.MinPTime variable and the
                 EpSpecificCodecClearChannel.EnableConfig variable is set to
                 'Enable', then it overrides the current default configuration.


                 "
   DEFVAL        { 10 }
   ::= { codecClearChannelGroup 600 }

  -- Scalar:Default Clear Channel Maximum Packetization Period Configuration

  defaultCodecClearChannelMaxPTime OBJECT-TYPE
   SYNTAX        Unsigned32 ( 10..30 )
   MAX-ACCESS    read-write
   STATUS        current
   DESCRIPTION " Default Clear Channel Maximum Packetization Period
                 Configuration

                 Upper boundary for the packetization period of the given
                 codec.

                 Clear Channel -> (10 ms..30 ms)

                 This value is expressed in ms, with increments of 10 ms.

                 For reception, the range is extended from 10 ms to 100 ms with
                 increments of 1 ms only if the stream is not encrypted (SRTP).

                 If a specific configuration is set in the
                 EpSpecificCodecClearChannel.MaxPTime variable and the
                 EpSpecificCodecClearChannel.EnableConfig variable is set to
                 'Enable', then it overrides the current default configuration.


                 "
   DEFVAL        { 30 }
   ::= { codecClearChannelGroup 700 }

  -- ***************************************************************************
  
  -- Table:Endpoint Specific Voice Codec Configuration

  -- ***************************************************************************
  
  epSpecificCodecClearChannelTable OBJECT-TYPE
   SYNTAX                  SEQUENCE OF EpSpecificCodecClearChannelEntry
   MAX-ACCESS              not-accessible
   STATUS                  current
   DESCRIPTION          "  Endpoint Specific Voice Codec Configuration

                           Endpoint specific configuration.
                           "
   ::= { codecClearChannelGroup 800 }
   epSpecificCodecClearChannelEntry OBJECT-TYPE
    SYNTAX        EpSpecificCodecClearChannelEntry
    MAX-ACCESS    not-accessible
    STATUS        current
    DESCRIPTION " A row in table Endpoint Specific Voice Codec Configuration .
                  "
    INDEX         {
                    epSpecificCodecClearChannelEpId
                  }

    ::= { epSpecificCodecClearChannelTable 1 }

   EpSpecificCodecClearChannelEntry ::= SEQUENCE
   {
     epSpecificCodecClearChannelEpId          OCTET STRING,
     epSpecificCodecClearChannelEnableConfig  MxEnableState,
     epSpecificCodecClearChannelVoiceEnable   MxEnableState,
     epSpecificCodecClearChannelVoicePriority Unsigned32,
     epSpecificCodecClearChannelDataEnable    MxEnableState,
     epSpecificCodecClearChannelDataPriority  Unsigned32,
     epSpecificCodecClearChannelPayloadType   Unsigned32,
     epSpecificCodecClearChannelMinPTime      Unsigned32,
     epSpecificCodecClearChannelMaxPTime      Unsigned32
   }

   -- Index:Endpoint Identifier

   epSpecificCodecClearChannelEpId OBJECT-TYPE
    SYNTAX        OCTET STRING
    MAX-ACCESS    read-only
    STATUS        current
    DESCRIPTION " Endpoint Identifier

                  String that identifies an endpoint in other tables.
                  "
    ::= { epSpecificCodecClearChannelEntry 100 }

   -- Columnar:Enable Configuration

   epSpecificCodecClearChannelEnableConfig OBJECT-TYPE
    SYNTAX        MxEnableState
    MAX-ACCESS    read-write
    STATUS        current
    DESCRIPTION " Enable Configuration

                  Defines the configuration to use for a specific endpoint.

                    * Disable: The endpoint uses the default configuration as
                      defined in the DefaultCodecClearChannelVoiceEnable,
                      DefaultCodecClearChannelVoicePriority,
                      DefaultCodecClearChannelDataEnable,
                      DefaultCodecClearChannelDataPriority,
                      DefaultCodecClearChannelPayloadType,
                      DefaultCodecClearChannelMinPTime and
                      DefaultCodecClearChannelMaxPTime.
                    * Enable: The endpoint uses the specific configuration as
                      defined in the EpSpecificCodecClearChannel.VoiceEnable,
                      EpSpecificCodecClearChannel.VoicePriority,
                      EpSpecificCodecClearChannel.DataPriority,
                      EpSpecificCodecClearChannel.DataPriority,
                      EpSpecificCodecClearChannel.PayloadType,
                      EpSpecificCodecClearChannel.MinPTime and
                      EpSpecificCodecClearChannel.MaxPTime.


                  "
    DEFVAL        { disable }
    ::= { epSpecificCodecClearChannelEntry 200 }

   -- Columnar:Endpoint Specific Clear Channel Enable/Disable Configuration for
   -- Voice

   epSpecificCodecClearChannelVoiceEnable OBJECT-TYPE
    SYNTAX        MxEnableState
    MAX-ACCESS    read-write
    STATUS        current
    DESCRIPTION " Endpoint Specific Clear Channel Enable/Disable Configuration
                  for Voice

                  Indicates if the codec can be selected for voice
                  transmission. If enabled, this codec is listed as supported
                  for this specific endpoint. Otherwise, it is ignored.

                  X Clear Cahnnel is a method to carry 64 kbit/s channel data
                  transparently in RTP packets. This codec behaves like the
                  Clear Mode as defined in RFC 4040, but it uses
                  'X-CLEAR-CHANNEL' instead of 'CLEARMODE' the in codec
                  negotiation.

                  This codec always uses the RTP transport.

                  This configuration overrides the default configuration set in
                  the DefaultCodecClearChannelVoiceEnable variable if the
                  EpSpecificCodecClearChannel.EnableConfig variable is set to
                  'Enable'.


                  "
    DEFVAL        { disable }
    ::= { epSpecificCodecClearChannelEntry 300 }

   -- Columnar:Endpoint Specific Clear Channel Priority Configuration for Voice

   epSpecificCodecClearChannelVoicePriority OBJECT-TYPE
    SYNTAX        Unsigned32 ( 0..10 )
    MAX-ACCESS    read-write
    STATUS        current
    DESCRIPTION " Endpoint Specific Clear Channel Priority Configuration for
                  Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  This configuration overrides the default configuration set in
                  the DefaultCodecClearChannelVoicePriority variable if the
                  EpSpecificCodecClearChannel.EnableConfig variable is set to
                  'Enable'.


                  "
    DEFVAL        { 0 }
    ::= { epSpecificCodecClearChannelEntry 400 }

   -- Columnar:Endpoint Specific Clear Channel Enable/Disable Configuration for
   -- Data

   epSpecificCodecClearChannelDataEnable OBJECT-TYPE
    SYNTAX        MxEnableState
    MAX-ACCESS    read-write
    STATUS        current
    DESCRIPTION " Endpoint Specific Clear Channel Enable/Disable Configuration
                  for Data

                  If enabled, the Clear Channel protocol is used for fax
                  transmission.

                  Clear Channel is a method to carry 64 kbit/s channel data
                  transparently in RTP packets. This codec behaves like the
                  Clear Mode as defined in RFC 4040, but it uses
                  'X-CLEAR-CHANNEL' instead of 'CLEARMODE' the in codec
                  negotiation.

                  This configuration overrides the default configuration set in
                  the DefaultCodecClearChannelDataEnable variable if the
                  EpSpecificCodecClearChannel.EnableConfig variable is set to
                  'Enable'.


                  "
    DEFVAL        { disable }
    ::= { epSpecificCodecClearChannelEntry 500 }

   -- Columnar:Endpoint Specific Clear Channel Priority Configuration for Data

   epSpecificCodecClearChannelDataPriority OBJECT-TYPE
    SYNTAX        Unsigned32 ( 0..10 )
    MAX-ACCESS    read-write
    STATUS        current
    DESCRIPTION " Endpoint Specific Clear Channel Priority Configuration for
                  Data

                  Indicates the priority of this data codec versus the other
                  data codecs. The data codec with the highest priority will be
                  offered first when an outgoing call is initiated. This
                  priority is not used in incoming calls.

                  The application uses an internal order for codecs with the
                  same priority.

                  10 is the highest priority and 0 the lowest.

                  This configuration overrides the default configuration set in
                  the DefaultCodecClearChannelDataPriority variable if the
                  EpSpecificCodecClearChannel.EnableConfig variable is set to
                  'Enable'.


                  "
    DEFVAL        { 10 }
    ::= { epSpecificCodecClearChannelEntry 600 }

   -- Columnar:Endpoint Specific Clear Channel Payload Type

   epSpecificCodecClearChannelPayloadType OBJECT-TYPE
    SYNTAX        Unsigned32 ( 96..127 )
    MAX-ACCESS    read-write
    STATUS        current
    DESCRIPTION " Endpoint Specific Clear Channel Payload Type

                  When enabling Clear Channel for voice and data transmission,
                  this variable determines the actual RTP dynamic payload type
                  used in an initial offer.

                  The payload types available are as per RFC 3551.

                  This configuration overrides the default configuration set in
                  the DefaultCodecClearChannelPayloadType variable if the
                  EpSpecificCodecClearChannel.EnableConfig variable is set to
                  'Enable'.


                  "
    DEFVAL        { 125 }
    ::= { epSpecificCodecClearChannelEntry 700 }

   -- Columnar:Endpoint Specific Clear Channel Minimum Packetization Period
   -- Configuration

   epSpecificCodecClearChannelMinPTime OBJECT-TYPE
    SYNTAX        Unsigned32 ( 10..30 )
    MAX-ACCESS    read-write
    STATUS        current
    DESCRIPTION " Endpoint Specific Clear Channel Minimum Packetization Period
                  Configuration

                  Lower boundary for the packetization period of the given
                  codec.

                  Clear Channel -> (10 ms..30 ms)

                  This value is expressed in ms, with increments of 10 ms.

                  For reception, the range is extended from 10 ms to 100 ms
                  with increments of 1 ms only if the stream is not encrypted
                  (SRTP).

                  This configuration overrides the default configuration set in
                  the DefaultCodecClearChannelMinPTime variable if the
                  EpSpecificCodecClearChannel.EnableConfig variable is set to
                  'Enable'.


                  "
    DEFVAL        { 10 }
    ::= { epSpecificCodecClearChannelEntry 800 }

   -- Columnar:Endpoint Specific Clear Channel Maximum Packetization Period
   -- Configuration

   epSpecificCodecClearChannelMaxPTime OBJECT-TYPE
    SYNTAX        Unsigned32 ( 10..30 )
    MAX-ACCESS    read-write
    STATUS        current
    DESCRIPTION " Endpoint Specific Clear Channel Maximum Packetization Period
                  Configuration

                  Upper boundary for the packetization period of the given
                  codec.

                  Clear Channel -> (10 ms..30 ms)

                  This value is expressed in ms, with increments of 10 ms.

                  For reception, the range is extended from 10 ms to 100 ms
                  with increments of 1 ms only if the stream is not encrypted
                  (SRTP).

                  This configuration overrides the default configuration set in
                  the DefaultCodecClearChannelMaxPTime variable if the
                  EpSpecificCodecClearChannel.EnableConfig variable is set to
                  'Enable'.


                  "
    DEFVAL        { 30 }
    ::= { epSpecificCodecClearChannelEntry 900 }


  -- End of table:Endpoint Specific Voice Codec Configuration

 -- End of group:Clear Channel Codec Related Configuration Group

 -- ***************************************************************************
 
 -- Group:X-CCD Clear Channel Codec Related Configuration Group

 -- ***************************************************************************
 
 codecXCCDGroup OBJECT IDENTIFIER
  ::= { codecGroup 1000 }
  -- Scalar:Default X-CCD Clear Channel Enable/Disable Configuration for Voice

  defaultCodecXCCDVoiceEnable OBJECT-TYPE
   SYNTAX        MxEnableState
   MAX-ACCESS    read-write
   STATUS        current
   DESCRIPTION " Default X-CCD Clear Channel Enable/Disable Configuration for
                 Voice

                 Indicates if the codec can be selected for voice transmission.
                 If enabled, this codec is listed as supported for this
                 specific endpoint. Otherwise, it is ignored.

                 X-CCD clear channel is a method to carry 64 kbit/s channel
                 data transparently in RTP packets as defined in RFC 4040.

                 This codec always uses the RTP transport.

                 If a specific configuration is set in the
                 EpSpecificCodecXCCD.VoiceEnable variable and the
                 EpSpecificCodecXCCD.EnableConfig variable is set to 'Enable',
                 then it overrides the current default configuration.


                 "
   DEFVAL        { disable }
   ::= { codecXCCDGroup 100 }

  -- Scalar:Default X-CCD Clear Channel Priority Configuration for Voice

  defaultCodecXCCDVoicePriority OBJECT-TYPE
   SYNTAX        Unsigned32 ( 0..10 )
   MAX-ACCESS    read-write
   STATUS        current
   DESCRIPTION " Default X-CCD Clear Channel Priority Configuration for Voice

                 Indicates the priority of this voice codec versus the other
                 voice codecs. The voice codec with the highest priority will
                 be offered first when an outgoing call is initiated. This
                 priority is not used in incoming calls.

                 The application uses an internal order for codecs with the
                 same priority.

                 10 is the highest priority and 0 the lowest.

                 If a specific configuration is set in the
                 EpSpecificCodecXCCD.VoicePriority variable and the
                 EpSpecificCodecXCCD.EnableConfig variable is set to 'Enable',
                 then it overrides the current default configuration.


                 "
   DEFVAL        { 0 }
   ::= { codecXCCDGroup 200 }

  -- Scalar:Default X-CCD Clear Channel Enable/Disable Configuration for Data

  defaultCodecXCCDDataEnable OBJECT-TYPE
   SYNTAX        MxEnableState
   MAX-ACCESS    read-write
   STATUS        current
   DESCRIPTION " Default X-CCD Clear Channel Enable/Disable Configuration for
                 Data

                 If enabled, the X-CCD Clear Channel protocol is used for data
                 transmission.

                 The data transmission for this codec can be triggered by the
                 detection of a fax/modem tone or if the properties of the call
                 indicate that it was for data.

                 X-CCD Clear Channel is a method to carry 64 kbit/s channel
                 data transparently in RTP packets as defined in RFC 4040.

                 This codec always uses the RTP transport.

                 If a specific configuration is set in the
                 EpSpecificCodecXCCD.DataEnable variable and the
                 EpSpecificCodecXCCD.EnableConfig variable is set to 'Enable',
                 then it overrides the current default configuration.


                 "
   DEFVAL        { disable }
   ::= { codecXCCDGroup 300 }

  -- Scalar: Default X-CCD Clear Channel Priority Configuration for Data

  defaultCodecXCCDDataPriority OBJECT-TYPE
   SYNTAX        Unsigned32 ( 0..10 )
   MAX-ACCESS    read-write
   STATUS        current
   DESCRIPTION " Default X-CCD Clear Channel Priority Configuration for Data

                 Indicates the priority of this data codec versus the other
                 data codecs. The data codec with the highest priority will be
                 offered first when an outgoing call is initiated. This
                 priority is not used in incoming calls.

                 The application uses an internal order for codecs with the
                 same priority.

                 10 is the highest priority and 0 the lowest.

                 If a specific configuration is set in the
                 EpSpecificCodecXCCD.DataPriority variable and the
                 EpSpecificCodecXCCD.EnableConfig variable is set to 'Enable',
                 then it overrides the current default configuration.


                 "
   DEFVAL        { 10 }
   ::= { codecXCCDGroup 400 }

  -- Scalar:Default X-CCD Clear Channel Payload Type

  defaultCodecXCCDPayloadType OBJECT-TYPE
   SYNTAX        Unsigned32 ( 96..127 )
   MAX-ACCESS    read-write
   STATUS        current
   DESCRIPTION " Default X-CCD Clear Channel Payload Type

                 When enabling X-CCD Clear Channel for voice and data
                 transmission, this variable determines the actual RTP dynamic
                 payload type used in an initial offer.

                 The payload types available are as per RFC 3551.

                 If a specific configuration is set in the
                 EpSpecificCodecXCCD.PayloadType variable and the
                 EpSpecificCodecXCCD.EnableConfig variable is set to 'Enable',
                 then it overrides the current default configuration.


                 "
   DEFVAL        { 126 }
   ::= { codecXCCDGroup 500 }

  -- Scalar:Default X-CCD Clear Channel Minimum Packetization Period
  -- Configuration

  defaultCodecXCCDMinPTime OBJECT-TYPE
   SYNTAX        Unsigned32 ( 10..30 )
   MAX-ACCESS    read-write
   STATUS        current
   DESCRIPTION " Default X-CCD Clear Channel Minimum Packetization Period
                 Configuration

                 Lower boundary for the packetization period of the given
                 codec.

                 X-CCD Clear Channel -> (10 ms..30 ms)

                 This value is expressed in ms, with increments of 1 ms.

                 If a specific configuration is set in the
                 EpSpecificCodecXCCD.MinPTime variable and the
                 EpSpecificCodecXCCD.EnableConfig variable is set to 'Enable',
                 then it overrides the current default configuration.


                 "
   DEFVAL        { 10 }
   ::= { codecXCCDGroup 600 }

  -- Scalar:Default X-CCD Clear Channel Maximum Packetization Period
  -- Configuration

  defaultCodecXCCDMaxPTime OBJECT-TYPE
   SYNTAX        Unsigned32 ( 10..30 )
   MAX-ACCESS    read-write
   STATUS        current
   DESCRIPTION " Default X-CCD Clear Channel Maximum Packetization Period
                 Configuration

                 Upper boundary for the packetization period of the given
                 codec.

                 X-CCD Clear Channel -> (10 ms..30 ms)

                 This value is expressed in ms, with increments of 1 ms.

                 If a specific configuration is set in the
                 EpSpecificCodecXCCD.MaxPTime variable and the
                 EpSpecificCodecXCCD.EnableConfig variable is set to 'Enable',
                 then it overrides the current default configuration.


                 "
   DEFVAL        { 30 }
   ::= { codecXCCDGroup 700 }

  -- ***************************************************************************
  
  -- Table:Endpoint Specific Voice Codec Configuration

  -- ***************************************************************************
  
  epSpecificCodecXCCDTable OBJECT-TYPE
   SYNTAX                  SEQUENCE OF EpSpecificCodecXCCDEntry
   MAX-ACCESS              not-accessible
   STATUS                  current
   DESCRIPTION          "  Endpoint Specific Voice Codec Configuration

                           Endpoint specific configuration.
                           "
   ::= { codecXCCDGroup 800 }
   epSpecificCodecXCCDEntry OBJECT-TYPE
    SYNTAX        EpSpecificCodecXCCDEntry
    MAX-ACCESS    not-accessible
    STATUS        current
    DESCRIPTION " A row in table Endpoint Specific Voice Codec Configuration .
                  "
    INDEX         {
                    epSpecificCodecXCCDEpId
                  }

    ::= { epSpecificCodecXCCDTable 1 }

   EpSpecificCodecXCCDEntry ::= SEQUENCE
   {
     epSpecificCodecXCCDEpId          OCTET STRING,
     epSpecificCodecXCCDEnableConfig  MxEnableState,
     epSpecificCodecXCCDVoiceEnable   MxEnableState,
     epSpecificCodecXCCDVoicePriority Unsigned32,
     epSpecificCodecXCCDDataEnable    MxEnableState,
     epSpecificCodecXCCDDataPriority  Unsigned32,
     epSpecificCodecXCCDPayloadType   Unsigned32,
     epSpecificCodecXCCDMinPTime      Unsigned32,
     epSpecificCodecXCCDMaxPTime      Unsigned32
   }

   -- Index:Endpoint Identifier

   epSpecificCodecXCCDEpId OBJECT-TYPE
    SYNTAX        OCTET STRING
    MAX-ACCESS    read-only
    STATUS        current
    DESCRIPTION " Endpoint Identifier

                  String that identifies an endpoint in other tables.
                  "
    ::= { epSpecificCodecXCCDEntry 100 }

   -- Columnar:Enable Configuration

   epSpecificCodecXCCDEnableConfig OBJECT-TYPE
    SYNTAX        MxEnableState
    MAX-ACCESS    read-write
    STATUS        current
    DESCRIPTION " Enable Configuration

                  Defines the configuration to use for a specific endpoint.

                    * Disable: The endpoint uses the default configuration as
                      defined in the DefaultCodecXCCDVoiceEnable,
                      DefaultCodecXCCDVoicePriority,
                      DefaultCodecXCCDDataEnable, DefaultCodecXCCDDataPriority,
                      DefaultCodecXCCDPayloadType, DefaultCodecXCCDMinPTime and
                      DefaultCodecXCCDMaxPTime.
                    * Enable: The endpoint uses the specific configuration as
                      defined in the EpSpecificCodecXCCD.VoiceEnable,
                      EpSpecificCodecXCCD.VoicePriority,
                      EpSpecificCodecXCCD.DataPriority,
                      EpSpecificCodecXCCD.DataPriority,
                      EpSpecificCodecXCCD.PayloadType,
                      EpSpecificCodecXCCD.MinPTime and
                      EpSpecificCodecXCCD.MaxPTime.


                  "
    DEFVAL        { disable }
    ::= { epSpecificCodecXCCDEntry 200 }

   -- Columnar:Endpoint Specific X-CCD Clear Channel Enable/Disable
   -- Configuration for Voice

   epSpecificCodecXCCDVoiceEnable OBJECT-TYPE
    SYNTAX        MxEnableState
    MAX-ACCESS    read-write
    STATUS        current
    DESCRIPTION " Endpoint Specific X-CCD Clear Channel Enable/Disable
                  Configuration for Voice

                  Indicates if the codec can be selected for voice
                  transmission. If enabled, this codec is listed as supported
                  for this specific endpoint. Otherwise, it is ignored.

                  X-CCD Clear Channel is a method to carry 64 kbit/s channel
                  data transparently in RTP packets as defined in RFC 4040.

                  This codec always uses the RTP transport.

                  This configuration overrides the default configuration set in
                  the DefaultCodecXCCDVoiceEnable variable if the
                  EpSpecificCodecXCCD.EnableConfig variable is set to 'Enable'.


                  "
    DEFVAL        { disable }
    ::= { epSpecificCodecXCCDEntry 300 }

   -- Columnar:Endpoint Specific X-CCD Clear Channel Priority Configuration for
   -- Voice

   epSpecificCodecXCCDVoicePriority OBJECT-TYPE
    SYNTAX        Unsigned32 ( 0..10 )
    MAX-ACCESS    read-write
    STATUS        current
    DESCRIPTION " Endpoint Specific X-CCD Clear Channel Priority Configuration
                  for Voice

                  Indicates the priority of this voice codec versus the other
                  voice codecs. The voice codec with the highest priority will
                  be offered first when an outgoing call is initiated. This
                  priority is not used in incoming calls.

                  The application uses an internal order for codecs with the
                  same priority.

                  10 is the highest priority and 0 the lowest.

                  This configuration overrides the default configuration set in
                  the DefaultCodecXCCDVoicePriority variable if the
                  EpSpecificCodecXCCD.EnableConfig variable is set to 'Enable'.


                  "
    DEFVAL        { 0 }
    ::= { epSpecificCodecXCCDEntry 400 }

   -- Columnar:Endpoint Specific X-CCD Clear Channel Enable/Disable
   -- Configuration for Data

   epSpecificCodecXCCDDataEnable OBJECT-TYPE
    SYNTAX        MxEnableState
    MAX-ACCESS    read-write
    STATUS        current
    DESCRIPTION " Endpoint Specific X-CCD Clear Channel Enable/Disable
                  Configuration for Data

                  If enabled, the X-CCD Clear Channel protocol is used for fax
                  transmission.

                  This configuration overrides the default configuration set in
                  the DefaultCodecXCCDDataEnable variable if the
                  EpSpecificCodecXCCD.EnableConfig variable is set to 'Enable'.


                  "
    DEFVAL        { disable }
    ::= { epSpecificCodecXCCDEntry 500 }

   -- Columnar:Endpoint Specific X-CCD Clear Channel Priority Configuration for
   -- Data

   epSpecificCodecXCCDDataPriority OBJECT-TYPE
    SYNTAX        Unsigned32 ( 0..10 )
    MAX-ACCESS    read-write
    STATUS        current
    DESCRIPTION " Endpoint Specific X-CCD Clear Channel Priority Configuration
                  for Data

                  Indicates the priority of this data codec versus the other
                  data codecs. The data codec with the highest priority will be
                  offered first when an outgoing call is initiated. This
                  priority is not used in incoming calls.

                  The application uses an internal order for codecs with the
                  same priority.

                  10 is the highest priority and 0 the lowest.

                  This configuration overrides the default configuration set in
                  the DefaultCodecXCCDDataPriority variable if the
                  EpSpecificCodecXCCD.EnableConfig variable is set to 'Enable'.


                  "
    DEFVAL        { 10 }
    ::= { epSpecificCodecXCCDEntry 600 }

   -- Columnar:Endpoint Specific X-CCD Clear Channel Payload Type

   epSpecificCodecXCCDPayloadType OBJECT-TYPE
    SYNTAX        Unsigned32 ( 96..127 )
    MAX-ACCESS    read-write
    STATUS        current
    DESCRIPTION " Endpoint Specific X-CCD Clear Channel Payload Type

                  When enabling X-CCD Clear Channel for voice and data
                  transmission, this variable determines the actual RTP dynamic
                  payload type used in an initial offer.

                  The payload types available are as per RFC 3551.

                  This configuration overrides the default configuration set in
                  the DefaultCodecXCCDPayloadType variable if the
                  EpSpecificCodecXCCD.EnableConfig variable is set to 'Enable'.


                  "
    DEFVAL        { 126 }
    ::= { epSpecificCodecXCCDEntry 700 }

   -- Columnar:Endpoint Specific X-CCD Clear Channel Minimum Packetization
   -- Period Configuration

   epSpecificCodecXCCDMinPTime OBJECT-TYPE
    SYNTAX        Unsigned32 ( 10..30 )
    MAX-ACCESS    read-write
    STATUS        current
    DESCRIPTION " Endpoint Specific X-CCD Clear Channel Minimum Packetization
                  Period Configuration

                  Lower boundary for the packetization period of the given
                  codec.

                  X-CCD Clear Channel -> (10 ms..30 ms)

                  This value is expressed in ms, with increments of 1 ms.

                  This configuration overrides the default configuration set in
                  the DefaultCodecXCCDMinPTime variable if the
                  EpSpecificCodecXCCD.EnableConfig variable is set to 'Enable'.


                  "
    DEFVAL        { 10 }
    ::= { epSpecificCodecXCCDEntry 800 }

   -- Columnar:Endpoint Specific X-CCD Clear Channel Maximum Packetization
   -- Period Configuration

   epSpecificCodecXCCDMaxPTime OBJECT-TYPE
    SYNTAX        Unsigned32 ( 10..30 )
    MAX-ACCESS    read-write
    STATUS        current
    DESCRIPTION " Endpoint Specific X-CCD Clear Channel Maximum Packetization
                  Period Configuration

                  Upper boundary for the packetization period of the given
                  codec.

                  X-CCD Clear Channel -> (10 ms..30 ms)

                  This value is expressed in ms, with increments of 1 ms.

                  This configuration overrides the default configuration set in
                  the DefaultCodecXCCDMaxPTime variable if the
                  EpSpecificCodecXCCD.EnableConfig variable is set to 'Enable'.


                  "
    DEFVAL        { 30 }
    ::= { epSpecificCodecXCCDEntry 900 }


  -- End of table:Endpoint Specific Voice Codec Configuration

 -- End of group:X-CCD Clear Channel Codec Related Configuration Group

-- End of group:Voice Codec

-- ****************************************************************************

-- Group:Data Related Configuration Group

-- ****************************************************************************

jitterBufferGroup OBJECT IDENTIFIER
 ::= { miptMIBObjects 200 }
 -- Scalar:Default Jitter Bufffer Level

 defaultJitterBufferLevel OBJECT-TYPE
  SYNTAX        INTEGER { optimizeLatency(100) , normal(200) , optimizeQuality
                (300) , faxModem(400) , custom(500) }
  MAX-ACCESS    read-write
  STATUS        current
  DESCRIPTION " Default Jitter Bufffer Level

                Jitter is an abrupt and unwanted variation of one or more
                signal characteristics, such as the interval between
                successive pulses or the frequency or phase of successive
                cycles. An adaptive jitter buffer usually consists of an
                elastic buffer in which the signal is temporarily stored and
                then retransmitted at a rate based on the average rate of the
                incoming signal.

                  * OptimizeLatency: The jitter buffer is set to the lowest
                    effective value to minimize the latency. Voice cut can be
                    heard if the network is not optimal. (min = 10 ms, max =
                    40 ms)
                  * Normal: The jitter buffer tries to find a good compromise
                    between the latency and the voice quality. This setting is
                    recommended in private networks. (min = 30 ms, max = 90
                    ms)
                  * OptimizeQuality: The jitter buffer is set to a high value
                    to minimize the voice cuts at cost of high latency. This
                    setting is recommended in public networks. (min = 50 ms,
                    max = 125 ms)
                  * FaxModem: The jitter buffer is set to maximum. The Fax/
                    Modem transmission is very sensitive to voice cuts but not
                    to latency, so the fax has a better chance of success with
                    a high buffer. (min = 70 ms, max = 135 ms)
                  * Custom: The jitter buffer uses the configuration of the
                    'DefaultJitterBufferCustomMinLength' and
                    'DefaultJitterBufferCustomMaxLength' variables.

                If a specific configuration is set in the
                EpSpecificJitterBuffer.Level variable and the
                EpSpecificJitterBuffer.EnableConfig variable is set to
                'Enable', then it overrides the current default configuration.


                "
  DEFVAL        { normal }
  ::= { jitterBufferGroup 100 }

 -- Scalar:Default Custom Jitter Buffer Minimal Length

 defaultJitterBufferCustomMinLength OBJECT-TYPE
  SYNTAX        Unsigned32 ( 0..135 )
  MAX-ACCESS    read-write
  STATUS        current
  DESCRIPTION " Default Custom Jitter Buffer Minimal Length

                The jitter buffer minimal length (in milliseconds) is the
                delay the jitter buffer tries to maintain.

                The minimal jitter buffer MUST be equal to or smaller than the
                maximal jitter buffer.

                The minimal jitter buffer should be a multiple of ptime.

                This value is used only when the DefaultJitterBufferLevel
                variable is set to 'Custom'

                If a specific configuration is set in the
                EpSpecificJitterBuffer.CustomMinLength variable and the
                EpSpecificJitterBuffer.EnableConfig variable is set to
                'Enable', then it overrides the current default configuration.


                "
  DEFVAL        { 30 }
  ::= { jitterBufferGroup 200 }

 -- Scalar:Default Custom Jitter Buffer Maximal Length

 defaultJitterBufferCustomMaxLength OBJECT-TYPE
  SYNTAX        Unsigned32 ( 0..135 )
  MAX-ACCESS    read-write
  STATUS        current
  DESCRIPTION " Default Custom Jitter Buffer Maximal Length

                The jitter buffer maximal length (in milliseconds) is the
                highest delay the jitter buffer is allowed to introduce.

                The maximal jitter buffer MUST be equal to or greater than the
                minimal jitter buffer.

                The maximal jitter buffer should be a multiple of ptime.

                The maximal jitter buffer should be equal to or greater than
                the minimal jitter buffer + (4 * ptime).

                This value is used only when the DefaultJitterBufferLevel
                variable is set to 'Custom'

                If a specific configuration is set in the
                EpSpecificJitterBuffer.CustomMaxLength variable and the
                EpSpecificJitterBuffer.EnableConfig variable is set to
                'Enable', then it overrides the current default configuration.


                "
  DEFVAL        { 125 }
  ::= { jitterBufferGroup 300 }

 -- Scalar:Default Voiceband Data Custom Jitter Buffer Minimal Length

 defaultVbdJitterBufferCustomMinLength OBJECT-TYPE
  SYNTAX        Unsigned32 ( 0..135 )
  MAX-ACCESS    read-write
  STATUS        current
  DESCRIPTION " Default Voiceband Data Custom Jitter Buffer Minimal Length

                The jitter buffer minimal length (in milliseconds) is the
                delay the jitter buffer tries to maintain.

                See the DefaultVbdJitterBufferType description for an
                explanation of the adaptive jitter buffer.

                The minimal jitter buffer MUST be equal to or smaller than the
                voiceband data maximal jitter buffer.

                The minimal jitter buffer should be a multiple of ptime.

                This value is used only when the DefaultJitterBufferLevel
                variable is set to 'Custom'

                This value is ignored when the DefaultVbdJitterBufferType
                variable is set to 'Fixed'

                If a specific configuration is set in the
                EpSpecificJitterBuffer.CustomVbdMinLength variable and the
                EpSpecificJitterBuffer.EnableConfig variable is set to
                'Enable', then it overrides the current default configuration.


                "
  DEFVAL        { 0 }
  ::= { jitterBufferGroup 310 }

 -- Scalar:Default Voiceband Data Custom Jitter Buffer Nominal Length

 defaultVbdJitterBufferCustomNomLength OBJECT-TYPE
  SYNTAX        Unsigned32 ( 0..135 )
  MAX-ACCESS    read-write
  STATUS        current
  DESCRIPTION " Default Voiceband Data Custom Jitter Buffer Nominal Length

                The jitter buffer nominal length (in milliseconds) is the
                delay the jitter buffer uses when a call begins. The delay
                then varies depending on the type of jitter buffer.

                See the DefaultVbdJitterBufferType description for an
                explanation of the fixed and adaptive jitter buffer.

                In adaptive mode, the nominal jitter buffer should be equal to
                (voice band data minimal jitter buffer + voice band data
                maximal jitter buffer) / 2.

                This value is used only when the DefaultJitterBufferLevel
                variable is set to 'Custom'

                If a specific configuration is set in the
                EpSpecificJitterBuffer.CustomVbdNomLength variable and the
                EpSpecificJitterBuffer.EnableConfig variable is set to
                'Enable', then it overrides the current default configuration.


                "
  DEFVAL        { 67 }
  ::= { jitterBufferGroup 320 }

 -- Scalar:Default Voiceband Data Custom Jitter Buffer Maximal Length

 defaultVbdJitterBufferCustomMaxLength OBJECT-TYPE
  SYNTAX        Unsigned32 ( 0..135 )
  MAX-ACCESS    read-write
  STATUS        current
  DESCRIPTION " Default Voiceband Data Custom Jitter Buffer Maximal Length

                The jitter buffer maximal length (in milliseconds) is the
                highest delay the jitter buffer is allowed to introduce.

                The maximal jitter buffer MUST be equal to or greater than the
                minimal jitter buffer.

                The maximal jitter buffer should be a multiple of ptime.

                The maximal jitter buffer should be equal to or greater than
                voiceband data minimal jitter buffer + (4 * ptime) in adaptive
                mode.

                This value is used only when the DefaultJitterBufferLevel
                variable is set to 'Custom'

                If a specific configuration is set in the
                EpSpecificJitterBuffer.CustomVbdMaxLength variable and the
                EpSpecificJitterBuffer.EnableConfig variable is set to
                'Enable', then it overrides the current default configuration.


                "
  DEFVAL        { 135 }
  ::= { jitterBufferGroup 330 }

 -- Scalar:Default Voiceband Data Custom Jitter Buffer Type

 defaultVbdJitterBufferType OBJECT-TYPE
  SYNTAX        INTEGER { adaptiveImmediately(100) , adaptiveSilence(200) ,
                fixed(300) }
  MAX-ACCESS    read-write
  STATUS        current
  DESCRIPTION " Default Voiceband Data Custom Jitter Buffer Type

                Algorithm to use for managing the jitter buffer during a call.
                DefaultVbdJitterBufferCustomNomLength serves as the delay at
                the beginning of the call and might be adapted afterwards
                based on the selected algorithm.

                  * AdaptiveImmediately: The nominal delay varies based on the
                    estimated packet jitter. Playout adjustment is done
                    immediately when the actual delay goes out of bounds of a
                    small window around the moving nominal delay.
                  * AdaptiveSilence: The nominal delay varies based on the
                    estimated packet jitter. Playout adjustment is done based
                    on the actual delay going out of bounds of a small window
                    around the moving nominal delay. The adjustment is
                    deferred until silence is detected (either from playout
                    buffer underflow or by analysis of packet content).
                    Playout adjustment is also done when overflow or underflow
                    events occur.
                  * Fixed: The nominal delay is fixed to the value of
                    DefaultVbdJitterBufferCustomNomLength and does not change
                    thereafter. Playout adjustment is done when overflow or
                    underflow events occur.

                If a specific configuration is set in the
                EpSpecificJitterBuffer.CustomVbdJitterBufferType variable and
                the EpSpecificJitterBuffer.EnableConfig variable is set to
                'Enable', then it overrides the current default configuration.


                "
  DEFVAL        { fixed }
  ::= { jitterBufferGroup 340 }

 -- ***************************************************************************
 
 -- Table:Endpoint Specific Jitter Buffer Configuration

 -- ***************************************************************************
 
 epSpecificJitterBufferTable OBJECT-TYPE
  SYNTAX                   SEQUENCE OF EpSpecificJitterBufferEntry
  MAX-ACCESS               not-accessible
  STATUS                   current
  DESCRIPTION           "  Endpoint Specific Jitter Buffer Configuration

                           Endpoint specific configuration.
                           "
  ::= { jitterBufferGroup 400 }
  epSpecificJitterBufferEntry OBJECT-TYPE
   SYNTAX        EpSpecificJitterBufferEntry
   MAX-ACCESS    not-accessible
   STATUS        current
   DESCRIPTION " A row in table Endpoint Specific Jitter Buffer Configuration
                 . "
   INDEX         {
                   epSpecificJitterBufferEpId
                 }

   ::= { epSpecificJitterBufferTable 1 }

  EpSpecificJitterBufferEntry ::= SEQUENCE
  {
    epSpecificJitterBufferEpId                      OCTET STRING,
    epSpecificJitterBufferEnableConfig              MxEnableState,
    epSpecificJitterBufferLevel                     INTEGER,
    epSpecificJitterBufferCustomMinLength           Unsigned32,
    epSpecificJitterBufferCustomMaxLength           Unsigned32,
    epSpecificJitterBufferCustomVbdMinLength        Unsigned32,
    epSpecificJitterBufferCustomVbdNomLength        Unsigned32,
    epSpecificJitterBufferCustomVbdMaxLength        Unsigned32,
    epSpecificJitterBufferCustomVbdJitterBufferType INTEGER
  }

  -- Index:Endpoint Identifier

  epSpecificJitterBufferEpId OBJECT-TYPE
   SYNTAX        OCTET STRING
   MAX-ACCESS    read-only
   STATUS        current
   DESCRIPTION " Endpoint Identifier

                 String that identifies an endpoint in other tables.
                 "
   ::= { epSpecificJitterBufferEntry 100 }

  -- Columnar:Enable Configuration

  epSpecificJitterBufferEnableConfig OBJECT-TYPE
   SYNTAX        MxEnableState
   MAX-ACCESS    read-write
   STATUS        current
   DESCRIPTION " Enable Configuration

                 Defines the configuration to use for a specific endpoint.

                   * Disable: The endpoint uses the default configuration as
                     defined in the DefaultJitterBufferLevel,
                     DefaultJitterBufferCustomMinLength and
                     DefaultJitterBufferCustomMaxLength variables.
                   * Enable: The endpoint uses the specific configuration as
                     defined in the EpSpecificJitterBuffer.Level,
                     EpSpecificJitterBuffer.CustomMinLength and
                     EpSpecificJitterBuffer.CustomMaxLength variables.


                 "
   DEFVAL        { disable }
   ::= { epSpecificJitterBufferEntry 200 }

  -- Columnar:Endpoint Specific Jitter Buffer Level

  epSpecificJitterBufferLevel OBJECT-TYPE
   SYNTAX        INTEGER { optimizeLatency(100) , normal(200) ,
                 optimizeQuality(300) , faxModem(400) , custom(500) }
   MAX-ACCESS    read-write
   STATUS        current
   DESCRIPTION " Endpoint Specific Jitter Buffer Level

                 Jitter is an abrupt and unwanted variation of one or more
                 signal characteristics, such as the interval between
                 successive pulses or the frequency or phase of successive
                 cycles. An adaptive jitter buffer usually consists of an
                 elastic buffer in which the signal is temporarily stored and
                 then retransmitted at a rate based on the average rate of the
                 incoming signal.

                   * OptimizeLatency: The jitter buffer is set to the lowest
                     effective value to minimize the latency. Voice cut can be
                     heard if the network is not optimal. (min = 10 ms, max =
                     40 ms)
                   * Normal: The jitter buffer tries to find a good compromise
                     between the latency and the voice quality. This setting
                     is recommended in private networks. (min = 30 ms, max =
                     90 ms)
                   * OptimizeQuality: The jitter buffer is set to a high value
                     to minimize the voice cuts at cost of high latency. This
                     setting is recommended in public networks. (min = 50 ms,
                     max = 120 ms)
                   * FaxModem: The jitter buffer is set to maximum. The Fax/
                     Modem transmission is very sensitive to voice cuts but
                     not to latency, so the fax has a better chance of success
                     with a high buffer. (min = 70 ms, max = 135 ms)
                   * Custom: The jitter buffer uses the configuration of the
                     DefaultJitterBufferCustomMinLength and
                     DefaultJitterBufferCustomMaxLength variables.

                 This configuration overrides the default configuration set in
                 the DefaultJitterBufferLevel variable if the
                 EpSpecificJitterBuffer.EnableConfig variable is set to
                 'Enable'.


                 "
   DEFVAL        { normal }
   ::= { epSpecificJitterBufferEntry 300 }

  -- Columnar:Endpoint Specific Custom Jitter Buffer Minimal Length

  epSpecificJitterBufferCustomMinLength OBJECT-TYPE
   SYNTAX        Unsigned32 ( 0..135 )
   MAX-ACCESS    read-write
   STATUS        current
   DESCRIPTION " Endpoint Specific Custom Jitter Buffer Minimal Length

                 The jitter buffer minimal length (in milliseconds) is the
                 delay the jitter buffer tries to maintain.

                 The minimal jitter buffer MUST be equal to or smaller than
                 the maximal jitter buffer.

                 The minimal jitter buffer should be a multiple of ptime.

                 This value is used only when the Level variable is set to
                 'Custom'.

                 This configuration overrides the default configuration set in
                 the DefaultJitterBufferCustomMinLength variable if the
                 EpSpecificJitterBuffer.EnableConfig variable is set to
                 'Enable'.


                 "
   DEFVAL        { 30 }
   ::= { epSpecificJitterBufferEntry 400 }

  -- Columnar:Endpoint Specific Custom Jitter Buffer Maximal Length

  epSpecificJitterBufferCustomMaxLength OBJECT-TYPE
   SYNTAX        Unsigned32 ( 0..135 )
   MAX-ACCESS    read-write
   STATUS        current
   DESCRIPTION " Endpoint Specific Custom Jitter Buffer Maximal Length

                 The jitter buffer maximal length (in milliseconds) is the
                 highest delay the jitter buffer is allowed to introduce.

                 The maximal jitter buffer MUST be equal to or greater than
                 the minimal jitter buffer.

                 The maximal jitter buffer should be a multiple of ptime.

                 The maximal jitter buffer should be equal to or greater than
                 minimal jitter buffer + 4 * ptime.

                 This value is used only when the Level variable is set to
                 'Custom'.

                 This configuration overrides the default configuration set in
                 the DefaultJitterBufferCustomMaxLength variable if the
                 EpSpecificJitterBuffer.EnableConfig variable is set to
                 'Enable'.


                 "
   DEFVAL        { 125 }
   ::= { epSpecificJitterBufferEntry 500 }

  -- Columnar:Endpoint Specific Custom Voiceband Data Jitter Buffer Minimal
  -- Length

  epSpecificJitterBufferCustomVbdMinLength OBJECT-TYPE
   SYNTAX        Unsigned32 ( 0..135 )
   MAX-ACCESS    read-write
   STATUS        current
   DESCRIPTION " Endpoint Specific Custom Voiceband Data Jitter Buffer Minimal
                 Length

                 The jitter buffer minimal length (in milliseconds) is the
                 delay the jitter buffer tries to maintain.

                 See the CustomVbdJitterBufferType description for an
                 explanation of the adaptive jitter buffer.

                 The minimal jitter buffer MUST be equal to or smaller than
                 the voiceband data maximal jitter buffer.

                 The minimal jitter buffer should be a multiple of ptime.

                 This value is used only when the Level variable is set to
                 'Custom'.

                 This value is ignored when the CustomVbdJitterBufferType
                 variable is set to 'Fixed'

                 This configuration overrides the default configuration set in
                 the DefaultVbdJitterBufferCustomMinLength variable if the
                 EpSpecificJitterBuffer.EnableConfig variable is set to
                 'Enable'.


                 "
   DEFVAL        { 0 }
   ::= { epSpecificJitterBufferEntry 600 }

  -- Columnar:Endpoint Specific Custom Voiceband Data Jitter Buffer Nominal
  -- Length

  epSpecificJitterBufferCustomVbdNomLength OBJECT-TYPE
   SYNTAX        Unsigned32 ( 0..135 )
   MAX-ACCESS    read-write
   STATUS        current
   DESCRIPTION " Endpoint Specific Custom Voiceband Data Jitter Buffer Nominal
                 Length

                 The jitter buffer nominal length (in milliseconds) is the
                 delay the jitter buffer uses when a call begins. The delay
                 then varies depending on the type of jitter buffer.

                 See the CustomVbdJitterBufferType description for an
                 explanation of the fixed and adaptive jitter buffer.

                 In adaptive mode, the nominal jitter buffer should be equal
                 to (voice band data minimal jitter buffer + voice band data
                 maximal jitter buffer) / 2.

                 This value is used only when the Level variable is set to
                 'Custom'.

                 This configuration overrides the default configuration set in
                 the DefaultVbdJitterBufferCustomNomLength variable if the
                 EpSpecificJitterBuffer.EnableConfig variable is set to
                 'Enable'.


                 "
   DEFVAL        { 67 }
   ::= { epSpecificJitterBufferEntry 700 }

  -- Columnar:Endpoint Specific Custom Voiceband Data Jitter Buffer Maximal
  -- Length

  epSpecificJitterBufferCustomVbdMaxLength OBJECT-TYPE
   SYNTAX        Unsigned32 ( 0..135 )
   MAX-ACCESS    read-write
   STATUS        current
   DESCRIPTION " Endpoint Specific Custom Voiceband Data Jitter Buffer Maximal
                 Length

                 The jitter buffer maximal length (in milliseconds) is the
                 highest delay the jitter buffer is allowed to introduce.

                 The maximal jitter buffer MUST be equal to or greater than
                 the minimal jitter buffer.

                 The maximal jitter buffer should be a multiple of ptime.

                 The maximal jitter buffer should be equal to or greater than
                 voiceband data minimal jitter buffer + (4 * ptime) in
                 adaptive mode.

                 This value is used only when the Level variable is set to
                 'Custom'.

                 This configuration overrides the default configuration set in
                 the DefaultVbdJitterBufferCustomMaxLength variable if the
                 EpSpecificJitterBuffer.EnableConfig variable is set to
                 'Enable'.


                 "
   DEFVAL        { 125 }
   ::= { epSpecificJitterBufferEntry 800 }

  -- Columnar:Endpoint Specific Custom Voiceband Data Jitter Buffer Type

  epSpecificJitterBufferCustomVbdJitterBufferType OBJECT-TYPE
   SYNTAX        INTEGER { adaptiveImmediately(100) , adaptiveSilence(200) ,
                 fixed(300) }
   MAX-ACCESS    read-write
   STATUS        current
   DESCRIPTION " Endpoint Specific Custom Voiceband Data Jitter Buffer Type

                 Algorithm to use for managing the jitter buffer during a
                 call. CustomVbdNomLength serves as the delay at the beginning
                 of the call and might be adapted afterwards based on the
                 selected algorithm.

                   * AdaptiveImmediately: The nominal delay varies based on
                     the estimated packet jitter. Playout adjustment is done
                     immediately when the actual delay goes out of bounds of a
                     small window around the moving nominal delay.
                   * AdaptiveSilence: The nominal delay varies based on the
                     estimated packet jitter. Playout adjustment is done based
                     on the actual delay going out of bounds of a small window
                     around the moving nominal delay. The adjustment is
                     deferred until silence is detected (either from playout
                     buffer underflow or by analysis of packet content).
                     Playout adjustment is also done when overflow or
                     underflow events occur.
                   * Fixed: The nominal delay is fixed to the value of
                     DefaultVbdJitterBufferCustomNomLength and does not change
                     thereafter. Playout adjustment is done when overflow or
                     underflow events occur.

                 This configuration overrides the default configuration set in
                 the DefaultVbdJitterBufferType variable if the
                 EpSpecificJitterBuffer.EnableConfig variable is set to
                 'Enable'.


                 "
   DEFVAL        { fixed }
   ::= { epSpecificJitterBufferEntry 900 }


 -- End of table:Endpoint Specific Jitter Buffer Configuration

-- End of group:Data Related Configuration Group

-- ****************************************************************************

-- Group:DTMF Transport Group

-- ****************************************************************************

dtmfTransportGroup OBJECT IDENTIFIER
 ::= { miptMIBObjects 300 }
 -- Scalar:Default DTMF Transport Method Configuration

 defaultDtmfTransportMethod OBJECT-TYPE
  SYNTAX        INTEGER { inBand(100) , outOfBandUsingRtp(200) ,
                outOfBandUsingSignalingProtocol(300) ,
                signalingProtocolDependent(400) }
  MAX-ACCESS    read-write
  STATUS        current
  DESCRIPTION " Default DTMF Transport Method Configuration

                Type of DTMF transport. If 'SignalingProtocolDependent' is
                selected, the signaling protocol has the control to select the
                DTMF transport mode.

                If a specific configuration is set in the
                EpSpecificDtmfTransport.Method variable and the
                EpSpecificDtmfTransport.EnableConfig variable is set to
                'Enable', then it overrides the current default configuration.


                "
  DEFVAL        { inBand }
  ::= { dtmfTransportGroup 100 }

 -- Scalar:Default DTMF Transport Payload Type

 defaultDtmfTransportPayloadType OBJECT-TYPE
  SYNTAX        Unsigned32 ( 96..127 )
  MAX-ACCESS    read-write
  STATUS        current
  DESCRIPTION " Default DTMF Transport Payload Type

                Determines the actual RTP dynamic payload type used for
                telephone-event in an initial offer when selecting the
                'OutOfBandUsingRtp' DTMF transport mode (see the
                DefaultDtmfTransportMethod variable). The payload types
                available are as per RFC 1890.

                If a specific configuration is set in the
                EpSpecificDtmfTransport.PayloadType variable and the
                EpSpecificDtmfTransport.EnableConfig variable is set to
                'Enable', then it overrides the current default configuration.


                "
  DEFVAL        { 96 }
  ::= { dtmfTransportGroup 200 }

 -- ***************************************************************************
 
 -- Table:Endpoint Specific Voice Codec Configuration

 -- ***************************************************************************
 
 epSpecificDtmfTransportTable OBJECT-TYPE
  SYNTAX               SEQUENCE OF EpSpecificDtmfTransportEntry
  MAX-ACCESS           not-accessible
  STATUS               current
  DESCRIPTION        " Endpoint Specific Voice Codec Configuration

                       Endpoint specific configuration.
                       "
  ::= { dtmfTransportGroup 300 }
  epSpecificDtmfTransportEntry OBJECT-TYPE
   SYNTAX        EpSpecificDtmfTransportEntry
   MAX-ACCESS    not-accessible
   STATUS        current
   DESCRIPTION " A row in table Endpoint Specific Voice Codec Configuration .
                 "
   INDEX         {
                   epSpecificDtmfTransportEpId
                 }

   ::= { epSpecificDtmfTransportTable 1 }

  EpSpecificDtmfTransportEntry ::= SEQUENCE
  {
    epSpecificDtmfTransportEpId         OCTET STRING,
    epSpecificDtmfTransportEnableConfig MxEnableState,
    epSpecificDtmfTransportMethod       INTEGER,
    epSpecificDtmfTransportPayloadType  Unsigned32
  }

  -- Index:Endpoint Identifier

  epSpecificDtmfTransportEpId OBJECT-TYPE
   SYNTAX        OCTET STRING
   MAX-ACCESS    read-only
   STATUS        current
   DESCRIPTION " Endpoint Identifier

                 String that identifies an endpoint in other tables.
                 "
   ::= { epSpecificDtmfTransportEntry 100 }

  -- Columnar:Enable Configuration

  epSpecificDtmfTransportEnableConfig OBJECT-TYPE
   SYNTAX        MxEnableState
   MAX-ACCESS    read-write
   STATUS        current
   DESCRIPTION " Enable Configuration

                 Defines the configuration to use for a specific endpoint.

                   * Disable: The endpoint uses the default configuration as
                     defined in the DefaultDtmfTransportMethod and
                     DefaultDtmfTransportPayloadType variables.
                   * Enable: The endpoint uses the specific configuration as
                     defined in the EpSpecificDtmfTransport.Method and
                     EpSpecificDtmfTransport.PayloadType variables.


                 "
   DEFVAL        { disable }
   ::= { epSpecificDtmfTransportEntry 200 }

  -- Columnar:Endpoint Specific DTMF Transport Method Configuration

  epSpecificDtmfTransportMethod OBJECT-TYPE
   SYNTAX        INTEGER { inBand(100) , outOfBandUsingRtp(200) ,
                 outOfBandUsingSignalingProtocol(300) ,
                 signalingProtocolDependent(400) }
   MAX-ACCESS    read-write
   STATUS        current
   DESCRIPTION " Endpoint Specific DTMF Transport Method Configuration

                 Type of DTMF transport. If 'SignalingProtocolDependent' is
                 selected, the signaling protocol has the control to select
                 the DTMF transport mode.

                 This configuration overrides the default configuration set in
                 the DefaultDtmfTransportMethod variable if the
                 EpSpecificDtmfTransport.EnableConfig variable is set to
                 'Enable'.


                 "
   DEFVAL        { inBand }
   ::= { epSpecificDtmfTransportEntry 300 }

  -- Columnar:Endpoint Specific DTMF Transport Payload Type

  epSpecificDtmfTransportPayloadType OBJECT-TYPE
   SYNTAX        Unsigned32 ( 96..127 )
   MAX-ACCESS    read-write
   STATUS        current
   DESCRIPTION " Endpoint Specific DTMF Transport Payload Type

                 Determines the actual RTP dynamic payload type used for
                 telephone-event in an initial offer when selecting the
                 'OutOfBandUsingRtp' DTMF transport mode (see the Method
                 variable). The payload types available are as per RFC 1890.

                 This configuration overrides the default configuration set in
                 the DefaultDtmfTransportPayloadType variable if the
                 EpSpecificDtmfTransport.EnableConfig variable is set to
                 'Enable'.


                 "
   DEFVAL        { 96 }
   ::= { epSpecificDtmfTransportEntry 400 }


 -- End of table:Endpoint Specific Voice Codec Configuration

-- End of group:DTMF Transport Group

-- ****************************************************************************

-- Group:IP Transport

-- ****************************************************************************

ipTransportGroup OBJECT IDENTIFIER
 ::= { miptMIBObjects 400 }
 -- ***************************************************************************
 
 -- Group:RTP

 -- ***************************************************************************
 
 ipTransportRtpGroup OBJECT IDENTIFIER
  ::= { ipTransportGroup 100 }
  -- Scalar:RTP IP Transport Base Port

  ipTransportRtpBasePort OBJECT-TYPE
   SYNTAX        Unsigned32 ( 1025..64535 )
   MAX-ACCESS    read-write
   STATUS        current
   DESCRIPTION " RTP IP Transport Base Port

                 UDP base port for the RTP/RTCP protocols.

                 The RTP/RTCP ports are allocated starting from this base port.
                 RTP ports number are even and RTCP ports number are odd.

                 The unit may use two or four RTP/RTCP ports per FXS/FXO
                 endpoint.

                 It uses two ports in case of a standard call, while it uses
                 four ports in other types of calls such as a conference call,
                 a call transfer, etc.

                 Example: let's say that a unit has two FXS endpoints and the
                 base port is defined on 5004:

                   * if there is currently no ongoing call and FXS endpoint 1
                     has an incoming or outgoing call, it will use the RTP/RTCP
                     ports 5004 and 5005.
                   * if there is currently a standard call on FXS endpoint 1
                     and FXS endpoint 2 has a conference call, then FXS
                     endpoint 2 will use the RTP/RTCP ports 5006, 5007, 5008,
                     and 5009, which are the next available ports.


                 "
   DEFVAL        { 5004 }
   ::= { ipTransportRtpGroup 100 }

  -- Scalar:SRTP IP Transport Base Port

  ipTransportSrtpBasePort OBJECT-TYPE
   SYNTAX        Unsigned32 ( 1025..64535 )
   MAX-ACCESS    read-write
   STATUS        current
   DESCRIPTION " SRTP IP Transport Base Port

                 UDP base port for the SRTP/SRTCP protocols.

                 The SRTP/SRTCP ports are allocated starting from this base
                 port. SRTP ports number are even and SRTCP ports number are
                 odd.

                 Using the same base port for IpTransportRtpBasePort and
                 IpTransportSrtpBasePort does not conflict.

                 Refer to the documentation of IpTransportRtpBasePort for more
                 details.


                 "
   DEFVAL        { 5004 }
   ::= { ipTransportRtpGroup 200 }

 -- End of group:RTP

 -- ***************************************************************************
 
 -- Group:T.38

 -- ***************************************************************************
 
 ipTransportT38Group OBJECT IDENTIFIER
  ::= { ipTransportGroup 200 }
  -- Scalar:T.38 IP Transport Base Port

  ipTransportT38BasePort OBJECT-TYPE
   SYNTAX        Unsigned32 ( 1025..64535 )
   MAX-ACCESS    read-write
   STATUS        current
   DESCRIPTION " T.38 IP Transport Base Port

                 T.38 base port.

                 The T.38 ports are allocated starting from this base port. The
                 units use as many T.38 ports as the number of FXS/FXO
                 endpoints.

                 Example: let's say that a unit has two FXS endpoints and the
                 base port is defined on 6004:

                   * if there is currently no ongoing call and FXS endpoint 1
                     has an incoming or outgoing call, it will use the T.38
                     port 6004.
                   * if there is currently a call on FXS endpoint 1 and FXS
                     endpoint 2 has an incoming or outgoing call, then FXS
                     endpoint 2 will use the T.38 port 6005.


                 "
   DEFVAL        { 6004 }
   ::= { ipTransportT38Group 100 }

 -- End of group:T.38

-- End of group:IP Transport

-- *****************************************************************************

-- Group:Codec vs. Bearer Capabilities Mapping

-- *****************************************************************************

codecVsBearerCapabilitiesMapping OBJECT IDENTIFIER
 ::= { miptMIBObjects 500 }
 -- *****************************************************************************
 
 -- Table:Codec vs. Bearer Capabilities Mapping

 -- *****************************************************************************
 
 defaultCodecVsBearerCapabilitiesMappingTable OBJECT-TYPE
  SYNTAX        SEQUENCE OF DefaultCodecVsBearerCapabilitiesMappingEntry
  MAX-ACCESS    not-accessible
  STATUS        current
  DESCRIPTION " Codec vs. Bearer Capabilities Mapping

                Codec to prioritize in the outgoing INVITE when the incoming SETUP's
                ITC matches the configured one. The ITC value to set in the outgoing
                SETUP's bearer capabilities when the incoming INVITE's codec matches
                the configured one.
                "
  ::= { codecVsBearerCapabilitiesMapping 100 }
  defaultCodecVsBearerCapabilitiesMappingEntry OBJECT-TYPE
   SYNTAX        DefaultCodecVsBearerCapabilitiesMappingEntry
   MAX-ACCESS    not-accessible
   STATUS        current
   DESCRIPTION " A row in table Codec vs. Bearer Capabilities Mapping . "
   INDEX         {
                   defaultCodecVsBearerCapabilitiesMappingIndex
                 }

   ::= { defaultCodecVsBearerCapabilitiesMappingTable 1 }

  DefaultCodecVsBearerCapabilitiesMappingEntry ::= SEQUENCE
  {
    defaultCodecVsBearerCapabilitiesMappingIndex                  Unsigned32,
    defaultCodecVsBearerCapabilitiesMappingEnableMap              MxEnableState,
    defaultCodecVsBearerCapabilitiesMappingCodec                  INTEGER,
    defaultCodecVsBearerCapabilitiesMappingInformationTransferCap INTEGER,
    defaultCodecVsBearerCapabilitiesMappingMappingType            INTEGER
  }

  -- Index:Codec vs. Bearer Capabilities Index

  defaultCodecVsBearerCapabilitiesMappingIndex OBJECT-TYPE
   SYNTAX        Unsigned32 ( 1..3 )
   MAX-ACCESS    read-only
   STATUS        current
   DESCRIPTION " Codec vs. Bearer Capabilities Index

                 Index of the current Codec vs. Bearer match.
                 "
   ::= { defaultCodecVsBearerCapabilitiesMappingEntry 100 }

  -- Columnar:Default Enable Map

  defaultCodecVsBearerCapabilitiesMappingEnableMap OBJECT-TYPE
   SYNTAX        MxEnableState
   MAX-ACCESS    read-write
   STATUS        current
   DESCRIPTION " Default Enable Map

                 Defines if the outgoing codecs priority or selection should reflect
                 the incoming ITC and vice versa.

                   * Disable: The codecs order in the outgoing INVITE follows the
                     codec priority. The ITC in the outgoing SETUP is not modified.
                   * Enable: When the ITC value in the incoming SETUP matches
                     DefaultCodecVsBearerCapabilitiesMapping.InformationTransferCap
                     and the DefaultCodecVsBearerCapabilitiesMapping.MappingType is
                     set to Prioritize the first codec in the outgoing INVITE is
                     DefaultCodecVsBearerCapabilitiesMapping.Codec. With a
                     DefaultCodecVsBearerCapabilitiesMapping.MappingType set to
                     Select, then the outgoing INVITE contains only the
                     DefaultCodecVsBearerCapabilitiesMapping.Codec. If the first
                     codec in the incoming INVITE matches
                     DefaultCodecVsBearerCapabilitiesMapping.Codec, the ITC value in
                     the outgoing SETUP is
                     DefaultCodecVsBearerCapabilitiesMapping.InformationTransferCap.


                 "
   DEFVAL        { disable }
   ::= { defaultCodecVsBearerCapabilitiesMappingEntry 200 }

  -- Columnar:Default Codec Priority

  defaultCodecVsBearerCapabilitiesMappingCodec OBJECT-TYPE
   SYNTAX        INTEGER { g711alaw(100) , g711ulaw(200) , g723(300) , g72616kbps
                 (400) , g72624kbps(500) , g72632kbps(600) , g72640kbps(700) ,
                 g729(800) , clearMode(900) , clearChannel(1000) , xCCD(1100) }
   MAX-ACCESS    read-write
   STATUS        current
   DESCRIPTION " Default Codec Priority

                 The codec to be prioritized or selected in an outgoing INVITE
                 when the incoming SETUP's ITC matches
                 DefaultCodecVsBearerCapabilitiesMapping.InformationTransferCap.
                 This codec is also checked against an incoming INVITE's priority
                 codec. If it matches, then the outgoing SETUP's ITC is set to
                 DefaultCodecVsBearerCapabilitiesMapping.InformationTransferCap.
                 See the DefaultCodecVsBearerCapabilitiesMapping.MappingType
                 variable for a description of prioritization versus selection of
                 a codec.
                 "
   DEFVAL        { g729 }
   ::= { defaultCodecVsBearerCapabilitiesMappingEntry 300 }

  -- Columnar:Default Information TransferCap

  defaultCodecVsBearerCapabilitiesMappingInformationTransferCap OBJECT-TYPE
   SYNTAX        INTEGER { audio31kHz(100) , speech(200) , unrestricted(300) }
   MAX-ACCESS    read-write
   STATUS        current
   DESCRIPTION " Default Information TransferCap

                 The ITC value to be set in the outgoing SETUP when the incoming
                 INVITE's priority codec matches
                 DefaultCodecVsBearerCapabilitiesMapping.Codec. This value is
                 also checked against an incoming SETUP's bearer capabilities. If
                 it matches, then the outgoing INVITE's prioritized or selected
                 codec is set to DefaultCodecVsBearerCapabilitiesMapping.Codec.
                 See the DefaultCodecVsBearerCapabilitiesMapping.MappingType
                 variable for a description of prioritization versus selection of
                 a codec.

                 There is one exception to the above description; any incoming
                 ISDN call using UDI (Unrestricted Digital) will ignore the
                 DefaultCodecVsBearerCapabilitiesMapping entries with the
                 InformationTransferCap set to Unrestricted(300). When such an
                 ISDN call is incoming, the outgoing SIP INVITE will offer PCMA
                 or PCMU, depending on the ISDN port 'Preferred Encoding Scheme'
                 value.


                 "
   DEFVAL        { speech }
   ::= { defaultCodecVsBearerCapabilitiesMappingEntry 400 }

  -- Columnar:Mapping Type

  defaultCodecVsBearerCapabilitiesMappingMappingType OBJECT-TYPE
   SYNTAX        INTEGER { prioritize(100) , select(200) }
   MAX-ACCESS    read-write
   STATUS        current
   DESCRIPTION " Mapping Type


                   * Prioritize: the DefaultCodecVsBearerCapabilitiesMapping.Codec
                     is set on top of the list in an outgoing INVITE when the
                     incoming SETUP's ITC matches
                     DefaultCodecVsBearerCapabilitiesMapping.InformationTransferCap.
                   * Select: the DefaultCodecVsBearerCapabilitiesMapping.Codec is
                     the only codec offered in an outgoing INVITE when the incoming
                     SETUP's ITC matches
                     DefaultCodecVsBearerCapabilitiesMapping.InformationTransferCap.


                 "
   DEFVAL        { prioritize }
   ::= { defaultCodecVsBearerCapabilitiesMappingEntry 500 }


 -- End of table:Codec vs. Bearer Capabilities Mapping

-- End of group:Codec vs. Bearer Capabilities Mapping

-- ****************************************************************************

-- Group:Security Related Configuration Group

-- ****************************************************************************

securityGroup OBJECT IDENTIFIER
 ::= { miptMIBObjects 600 }
 -- Scalar:Default RTP Mode

 defaultSecurityRtpMode OBJECT-TYPE
  SYNTAX        INTEGER { unsecure(100) , secure(200) , secureWithFallback
                (300) }
  MAX-ACCESS    read-write
  STATUS        current
  DESCRIPTION " Default RTP Mode

                Defines the RTP payload mode (secure or not secure).

                  * Unsecure: Only RTP.
                  * Secure: Only SRTP.
                  * SecureWithFallback: SRTP with RTP fallback if the peer
                    does not support security.


                "
  DEFVAL        { unsecure }
  ::= { securityGroup 100 }

 -- Scalar:Default Key Management Protocol

 defaultSecurityKeyManagement OBJECT-TYPE
  SYNTAX        INTEGER { mikey(100) , sdes(200) }
  MAX-ACCESS    read-write
  STATUS        current
  DESCRIPTION " Default Key Management Protocol

                Defines the key management protocol for SRTP.

                  * Mikey: Use MIKEY (Multimedia Internet KEYing - RFC 3830).
                  * Sdes: Use SDES (Security DEScriptions - RFC 4568).

                Note that this variable has no effect if the RtpMode variable
                is set to 'Unsecure'.


                "
  DEFVAL        { mikey }
  ::= { securityGroup 150 }

 -- Scalar:Default Encryption Type

 defaultSecurityRtpEncryption OBJECT-TYPE
  SYNTAX        INTEGER { null(100) , aesCm128(200) }
  MAX-ACCESS    read-write
  STATUS        current
  DESCRIPTION " Default Encryption Type

                Defines the encryption type to be used with SRTP.

                  * Null: No encryption. Use only for debug. This value is
                    ignored when the DefaultSecurityKeyManagement variable is
                    set to 'Sdes'.
                  * AesCm128: AES (Advanced Encryption Standard) Counter Mode
                    128 bits.

                Note that this variable has no effect if the RtpMode variable
                is set to 'Unsecure'.


                "
  DEFVAL        { aesCm128 }
  ::= { securityGroup 200 }

 -- Scalar:Allow Unsecure T38 with Secure RTP

 allowUnsecureT38WithSrtp OBJECT-TYPE
  SYNTAX        MxEnableState
  MAX-ACCESS    read-write
  STATUS        current
  DESCRIPTION " Allow Unsecure T38 with Secure RTP

                Enables T38 even if the call has been established previously
                in SRTP.

                  * Disable: T38 disabled for SRTP calls.
                  * Enable: T38 enabled for SRTP calls. Beware that enabling
                    this variable opens a security hole, because T38 is an
                    unsecure protocol.

                Note that this variable has no effect if the RtpMode variable
                is set to 'Unsecure'.


                "
  DEFVAL        { disable }
  ::= { securityGroup 300 }

 -- ***************************************************************************
 
 -- Table:Endpoint Specific Security Configuration

 -- ***************************************************************************
 
 epSpecificSecurityTable OBJECT-TYPE
  SYNTAX             SEQUENCE OF EpSpecificSecurityEntry
  MAX-ACCESS         not-accessible
  STATUS             current
  DESCRIPTION      " Endpoint Specific Security Configuration

                     Endpoint specific configuration.
                     "
  ::= { securityGroup 400 }
  epSpecificSecurityEntry OBJECT-TYPE
   SYNTAX        EpSpecificSecurityEntry
   MAX-ACCESS    not-accessible
   STATUS        current
   DESCRIPTION " A row in table Endpoint Specific Security Configuration. "
   INDEX         {
                   epSpecificSecurityEpId
                 }

   ::= { epSpecificSecurityTable 1 }

  EpSpecificSecurityEntry ::= SEQUENCE
  {
    epSpecificSecurityEpId          OCTET STRING,
    epSpecificSecurityEnableConfig  MxEnableState,
    epSpecificSecurityRtpMode       INTEGER,
    epSpecificSecurityKeyManagement INTEGER,
    epSpecificSecurityRtpEncryption INTEGER
  }

  -- Index:Endpoint Identifier

  epSpecificSecurityEpId OBJECT-TYPE
   SYNTAX        OCTET STRING
   MAX-ACCESS    read-only
   STATUS        current
   DESCRIPTION " Endpoint Identifier

                 String that identifies an endpoint in other tables.
                 "
   ::= { epSpecificSecurityEntry 100 }

  -- Columnar:Enable Configuration

  epSpecificSecurityEnableConfig OBJECT-TYPE
   SYNTAX        MxEnableState
   MAX-ACCESS    read-write
   STATUS        current
   DESCRIPTION " Enable Configuration

                 Defines the configuration to use for a specific endpoint.

                   * Disable: The endpoint uses the default configuration as
                     defined in the DefaultSecurity.
                   * Enable: The endpoint uses the specific configuration.


                 "
   DEFVAL        { disable }
   ::= { epSpecificSecurityEntry 200 }

  -- Columnar:Endpoint Specific RTP Mode

  epSpecificSecurityRtpMode OBJECT-TYPE
   SYNTAX        INTEGER { unsecure(100) , secure(200) , secureWithFallback
                 (300) }
   MAX-ACCESS    read-write
   STATUS        current
   DESCRIPTION " Endpoint Specific RTP Mode

                 Defines the RTP payload mode (secure or not secure).

                   * Unsecure: Only RTP.
                   * Secure: Only SRTP.
                   * SecureWithFallback: SRTP with RTP fallback if the peer
                     does not support security.


                 "
   DEFVAL        { unsecure }
   ::= { epSpecificSecurityEntry 300 }

  -- Columnar:Endpoint Specific Key Management Protocol

  epSpecificSecurityKeyManagement OBJECT-TYPE
   SYNTAX        INTEGER { mikey(100) , sdes(200) }
   MAX-ACCESS    read-write
   STATUS        current
   DESCRIPTION " Endpoint Specific Key Management Protocol

                 Defines the key management protocol for SRTP.

                   * Mikey: Use MIKEY (Multimedia Internet KEYing - RFC 3830).
                   * Sdes: Use SDES (Security DEScriptions - RFC 4568).

                 Note that this variable has no effect if the RtpMode variable
                 is set to 'Unsecure'.


                 "
   DEFVAL        { mikey }
   ::= { epSpecificSecurityEntry 350 }

  -- Columnar:Endpoint Specific Encryption Type

  epSpecificSecurityRtpEncryption OBJECT-TYPE
   SYNTAX        INTEGER { null(100) , aesCm128(200) }
   MAX-ACCESS    read-write
   STATUS        current
   DESCRIPTION " Endpoint Specific Encryption Type

                 Defines the encryption type to be used with SRTP.

                   * Null: No encryption. Use only for debug. This value is
                     ignored when the KeyManagement variable is set to 'Sdes'.
                   * AesCm128: AES (Advanced Encryption Standard) Counter Mode
                     128 bits.

                 Note that this variable has no effect if the RtpMode variable
                 is set to 'Unsecure'.


                 "
   DEFVAL        { aesCm128 }
   ::= { epSpecificSecurityEntry 400 }


 -- End of table:Endpoint Specific Security Configuration

-- End of group:Security Related Configuration Group

-- ****************************************************************************

-- Group:Statistics Group

-- ****************************************************************************

statisticsGroup OBJECT IDENTIFIER
 ::= { miptMIBObjects 700 }
 -- ***************************************************************************
 
 -- Table:Last Connections Statistics

 -- ***************************************************************************
 
 lastConnectionsStatsTable OBJECT-TYPE
  SYNTAX               SEQUENCE OF LastConnectionsStatsEntry
  MAX-ACCESS           not-accessible
  STATUS               current
  DESCRIPTION        " Last Connections Statistics

                       Last 10 connections statistics.
                       "
  ::= { statisticsGroup 100 }
  lastConnectionsStatsEntry OBJECT-TYPE
   SYNTAX        LastConnectionsStatsEntry
   MAX-ACCESS    not-accessible
   STATUS        current
   DESCRIPTION " A row in table Last Connections Statistics. "
   INDEX         {
                   lastConnectionsStatsConnectionsIndex
                 }

   ::= { lastConnectionsStatsTable 1 }

  LastConnectionsStatsEntry ::= SEQUENCE
  {
    lastConnectionsStatsConnectionsIndex          Unsigned32,
    lastConnectionsStatsOctetsTransmitted         MxUInt64,
    lastConnectionsStatsOctetsReceived            MxUInt64,
    lastConnectionsStatsPacketsTransmitted        MxUInt64,
    lastConnectionsStatsPacketsReceived           MxUInt64,
    lastConnectionsStatsPacketsLost               Unsigned32,
    lastConnectionsStatsMinimumInterarrivalJitter Unsigned32,
    lastConnectionsStatsMaximumInterarrivalJitter Unsigned32,
    lastConnectionsStatsAverageInterarrivalJitter Unsigned32,
    lastConnectionsStatsMinimumLatency            Unsigned32,
    lastConnectionsStatsMaximumLatency            Unsigned32,
    lastConnectionsStatsAverageLatency            Unsigned32
  }

  -- Index:Connections Index

  lastConnectionsStatsConnectionsIndex OBJECT-TYPE
   SYNTAX        Unsigned32 ( 1..10 )
   MAX-ACCESS    read-only
   STATUS        current
   DESCRIPTION " Connections Index

                 Last 10 connections identificator.
                 "
   ::= { lastConnectionsStatsEntry 100 }

  -- Columnar:Minimum Latency

  lastConnectionsStatsMinimumLatency OBJECT-TYPE
   SYNTAX        Unsigned32
   MAX-ACCESS    read-only
   STATUS        current
   DESCRIPTION " Minimum Latency

                 Minimum latency, in milliseconds, during the connection.

                 The latency value is computed as one half of the round-trip
                 time, as measured through RTCP.


                 "
   ::= { lastConnectionsStatsEntry 1000 }

  -- Columnar:Maximum Latency

  lastConnectionsStatsMaximumLatency OBJECT-TYPE
   SYNTAX        Unsigned32
   MAX-ACCESS    read-only
   STATUS        current
   DESCRIPTION " Maximum Latency

                 Maximum latency, in milliseconds, during the connection.

                 The latency value is computed as one half of the round-trip
                 time, as measured through RTCP.


                 "
   ::= { lastConnectionsStatsEntry 1100 }

  -- Columnar:Average Latency

  lastConnectionsStatsAverageLatency OBJECT-TYPE
   SYNTAX        Unsigned32
   MAX-ACCESS    read-only
   STATUS        current
   DESCRIPTION " Average Latency

                 Average latency, in milliseconds, during the connection.

                 The latency value is computed as one half of the round-trip
                 time, as measured through RTCP


                 "
   ::= { lastConnectionsStatsEntry 1200 }

  -- Columnar:Octets Transmitted

  lastConnectionsStatsOctetsTransmitted OBJECT-TYPE
   SYNTAX        MxUInt64
   MAX-ACCESS    read-only
   STATUS        current
   DESCRIPTION " Octets Transmitted

                 Number of octets transmitted during the connection.
                 "
   ::= { lastConnectionsStatsEntry 200 }

  -- Columnar:Octets Received

  lastConnectionsStatsOctetsReceived OBJECT-TYPE
   SYNTAX        MxUInt64
   MAX-ACCESS    read-only
   STATUS        current
   DESCRIPTION " Octets Received

                 Number of octets received during the connection.
                 "
   ::= { lastConnectionsStatsEntry 300 }

  -- Columnar:Packets Transmitted

  lastConnectionsStatsPacketsTransmitted OBJECT-TYPE
   SYNTAX        MxUInt64
   MAX-ACCESS    read-only
   STATUS        current
   DESCRIPTION " Packets Transmitted

                 Number of packets transmitted during the connection..
                 "
   ::= { lastConnectionsStatsEntry 400 }

  -- Columnar:Packets Received

  lastConnectionsStatsPacketsReceived OBJECT-TYPE
   SYNTAX        MxUInt64
   MAX-ACCESS    read-only
   STATUS        current
   DESCRIPTION " Packets Received

                 Number of packets received during the connection.
                 "
   ::= { lastConnectionsStatsEntry 500 }

  -- Columnar:Packets Lost

  lastConnectionsStatsPacketsLost OBJECT-TYPE
   SYNTAX        Unsigned32
   MAX-ACCESS    read-only
   STATUS        current
   DESCRIPTION " Packets Lost

                 Number of packets lost during the connection. This value is
                 obtained by substracting the expected number of packets based
                 on the sequence number from the number of packets received.
                 "
   ::= { lastConnectionsStatsEntry 600 }

  -- Columnar:Minimum Interarrival Jitter

  lastConnectionsStatsMinimumInterarrivalJitter OBJECT-TYPE
   SYNTAX        Unsigned32
   MAX-ACCESS    read-only
   STATUS        current
   DESCRIPTION " Minimum Interarrival Jitter

                 Minimum interarrival time, in milliseconds, during the
                 connection. All RTP packets belonging to the connection and
                 received at the RTP level are considered in the calculation.
                 "
   ::= { lastConnectionsStatsEntry 700 }

  -- Columnar:Maximum Interarrival Jitter

  lastConnectionsStatsMaximumInterarrivalJitter OBJECT-TYPE
   SYNTAX        Unsigned32
   MAX-ACCESS    read-only
   STATUS        current
   DESCRIPTION " Maximum Interarrival Jitter

                 Maximum interarrival time, in milliseconds, during the
                 connection. All RTP packets belonging to the connection and
                 received at the RTP level are considered in the calculation.
                 "
   ::= { lastConnectionsStatsEntry 800 }

  -- Columnar:Average Interarrival Jitter

  lastConnectionsStatsAverageInterarrivalJitter OBJECT-TYPE
   SYNTAX        Unsigned32
   MAX-ACCESS    read-only
   STATUS        current
   DESCRIPTION " Average Interarrival Jitter

                 Average interarrival time, in milliseconds, during the
                 connection. All RTP packets belonging to the connection and
                 received at the RTP level are considered in the calculation.
                 "
   ::= { lastConnectionsStatsEntry 900 }


 -- End of table:Last Connections Statistics

 -- ***************************************************************************
 
 -- Table:Last Periods Statistics

 -- ***************************************************************************
 
 lastPeriodsStatsTable OBJECT-TYPE
  SYNTAX                       SEQUENCE OF LastPeriodsStatsEntry
  MAX-ACCESS                   not-accessible
  STATUS                       current
  DESCRIPTION               "  Last Periods Statistics

                               Last 10 periods statistics.
                               "
  ::= { statisticsGroup 200 }
  lastPeriodsStatsEntry OBJECT-TYPE
   SYNTAX        LastPeriodsStatsEntry
   MAX-ACCESS    not-accessible
   STATUS        current
   DESCRIPTION " A row in table Last Periods Statistics. "
   INDEX         {
                   lastPeriodsStatsPeriodIndex
                 }

   ::= { lastPeriodsStatsTable 1 }

  LastPeriodsStatsEntry ::= SEQUENCE
  {
    lastPeriodsStatsPeriodIndex               Unsigned32,
    lastPeriodsStatsOctetsTransmitted         MxUInt64,
    lastPeriodsStatsOctetsReceived            MxUInt64,
    lastPeriodsStatsPacketsTransmitted        MxUInt64,
    lastPeriodsStatsPacketsReceived           MxUInt64,
    lastPeriodsStatsPacketsLost               Unsigned32,
    lastPeriodsStatsMinimumInterarrivalJitter Unsigned32,
    lastPeriodsStatsMaximumInterarrivalJitter Unsigned32,
    lastPeriodsStatsAverageInterarrivalJitter Unsigned32,
    lastPeriodsStatsMinimumLatency            Unsigned32,
    lastPeriodsStatsMaximumLatency            Unsigned32,
    lastPeriodsStatsAverageLatency            Unsigned32,
    lastPeriodsStatsPeriodBeginning           OCTET STRING,
    lastPeriodsStatsPeriodEnd                 OCTET STRING
  }

  -- Index:Period Index

  lastPeriodsStatsPeriodIndex OBJECT-TYPE
   SYNTAX         Unsigned32 ( 1..10 )
   MAX-ACCESS     read-only
   STATUS         current
   DESCRIPTION  " Period Index

                  Period identificator.
                  "
   ::= { lastPeriodsStatsEntry 100 }

  -- Columnar:Minimum Latency

  lastPeriodsStatsMinimumLatency OBJECT-TYPE
   SYNTAX        Unsigned32
   MAX-ACCESS    read-only
   STATUS        current
   DESCRIPTION " Minimum Latency

                 Minimum latency, in milliseconds, during the collection
                 period. This value is the lowest latency for all connections
                 that were active during the collection period.
                 "
   ::= { lastPeriodsStatsEntry 1000 }

  -- Columnar:Maximum Latency

  lastPeriodsStatsMaximumLatency OBJECT-TYPE
   SYNTAX        Unsigned32
   MAX-ACCESS    read-only
   STATUS        current
   DESCRIPTION " Maximum Latency

                 Maximum latency, in milliseconds, during the collection
                 period. This value is the highest latency for all connections
                 that were active during the collection period.
                 "
   ::= { lastPeriodsStatsEntry 1100 }

  -- Columnar:Average Latency

  lastPeriodsStatsAverageLatency OBJECT-TYPE
   SYNTAX        Unsigned32
   MAX-ACCESS    read-only
   STATUS        current
   DESCRIPTION " Average Latency

                 Average latency, in milliseconds, during the collection
                 period. This value is the weighted average of the latency for
                 all connections that were active during the collection
                 period. For each connection, the total latency of packets
                 received during the collection period and the total number of
                 packets received during the collection period are used in the
                 weighted average calculation.
                 "
   ::= { lastPeriodsStatsEntry 1200 }

  -- Columnar:Period Start

  lastPeriodsStatsPeriodBeginning OBJECT-TYPE
   SYNTAX        OCTET STRING
   MAX-ACCESS    read-only
   STATUS        current
   DESCRIPTION " Period Start

                 Date and time of the collection period beginning.
                 "
   ::= { lastPeriodsStatsEntry 1300 }

  -- Columnar:Period End

  lastPeriodsStatsPeriodEnd OBJECT-TYPE
   SYNTAX        OCTET STRING
   MAX-ACCESS    read-only
   STATUS        current
   DESCRIPTION " Period End

                 Date and time of the collection period end.
                 "
   ::= { lastPeriodsStatsEntry 1400 }

  -- Columnar:Octets Transmitted

  lastPeriodsStatsOctetsTransmitted OBJECT-TYPE
   SYNTAX        MxUInt64
   MAX-ACCESS    read-only
   STATUS        current
   DESCRIPTION " Octets Transmitted

                 Number of octets transmitted during the collection period.
                 This value is obtained by cumulating the octets transmitted
                 in all connections that were active during the collection
                 period.
                 "
   ::= { lastPeriodsStatsEntry 200 }

  -- Columnar:Octets Received

  lastPeriodsStatsOctetsReceived OBJECT-TYPE
   SYNTAX        MxUInt64
   MAX-ACCESS    read-only
   STATUS        current
   DESCRIPTION " Octets Received

                 Number of octets received during the collection period. This
                 value is obtained by cumulating the octets received in all
                 connections that were active during the collection period.
                 "
   ::= { lastPeriodsStatsEntry 300 }

  -- Columnar:Packets Transmitted

  lastPeriodsStatsPacketsTransmitted OBJECT-TYPE
   SYNTAX        MxUInt64
   MAX-ACCESS    read-only
   STATUS        current
   DESCRIPTION " Packets Transmitted

                 Number of packets transmitted during the collection period.
                 This value is obtained by cumulating the packets transmitted
                 in all connections that were active during the collection
                 period.
                 "
   ::= { lastPeriodsStatsEntry 400 }

  -- Columnar:Packets Received

  lastPeriodsStatsPacketsReceived OBJECT-TYPE
   SYNTAX        MxUInt64
   MAX-ACCESS    read-only
   STATUS        current
   DESCRIPTION " Packets Received

                 Number of packets received during the collection period. This
                 value is obtained by cumulating the packets received in all
                 connections that were active during the collection period.
                 "
   ::= { lastPeriodsStatsEntry 500 }

  -- Columnar:Packets Lost

  lastPeriodsStatsPacketsLost OBJECT-TYPE
   SYNTAX        Unsigned32
   MAX-ACCESS    read-only
   STATUS        current
   DESCRIPTION " Packets Lost

                 Number of packets lost during the collection period. This
                 value is obtained by cumulating the packets lost in all
                 connections that were active during the collection period.
                 "
   ::= { lastPeriodsStatsEntry 600 }

  -- Columnar:Minimum Interarrival Jitter

  lastPeriodsStatsMinimumInterarrivalJitter OBJECT-TYPE
   SYNTAX        Unsigned32
   MAX-ACCESS    read-only
   STATUS        current
   DESCRIPTION " Minimum Interarrival Jitter

                 Minimum interarrival time, in milliseconds, during the
                 collection period. This value is the lowest interarrival
                 jitter for all connections that were active during the
                 collection period.
                 "
   ::= { lastPeriodsStatsEntry 700 }

  -- Columnar:Maximum Interarrival Jitter

  lastPeriodsStatsMaximumInterarrivalJitter OBJECT-TYPE
   SYNTAX        Unsigned32
   MAX-ACCESS    read-only
   STATUS        current
   DESCRIPTION " Maximum Interarrival Jitter

                 Maximum interarrival time, in milliseconds, during the
                 collection period. This value is the highest interarrival
                 jitter for all connections that were active during the
                 collection period.
                 "
   ::= { lastPeriodsStatsEntry 800 }

  -- Columnar:Average Interarrival Jitter

  lastPeriodsStatsAverageInterarrivalJitter OBJECT-TYPE
   SYNTAX        Unsigned32
   MAX-ACCESS    read-only
   STATUS        current
   DESCRIPTION " Average Interarrival Jitter

                 Average interarrival time, in milliseconds, during the
                 collection period. This value is the weighted average of the
                 interarrival jitter for all connections that were active
                 during the collection period. For each connection, the total
                 jitter of packets received during the collection period and
                 the total number of packets received during the collection
                 period are used in the weighted average calculation.
                 "
   ::= { lastPeriodsStatsEntry 900 }


 -- End of table:Last Periods Statistics

 -- ***************************************************************************
 
 -- Table:Channel Statistics

 -- ***************************************************************************
 
 channelStatisticsTable OBJECT-TYPE
  SYNTAX        SEQUENCE OF ChannelStatisticsEntry
  MAX-ACCESS    not-accessible
  STATUS        current
  DESCRIPTION " Channel Statistics

                Statistics per endpoint/channel since last reboot or
                statistics reset.
                "
  ::= { statisticsGroup 250 }
  channelStatisticsEntry OBJECT-TYPE
   SYNTAX        ChannelStatisticsEntry
   MAX-ACCESS    not-accessible
   STATUS        current
   DESCRIPTION " A row in table Channel Statistics. "
   INDEX         {
                   channelStatisticsEpChannelId
                 }

   ::= { channelStatisticsTable 1 }

  ChannelStatisticsEntry ::= SEQUENCE
  {
    channelStatisticsEpChannelId                      OCTET STRING,
    channelStatisticsPacketsSent                      Unsigned32,
    channelStatisticsPacketsReceived                  Unsigned32,
    channelStatisticsBytesSent                        Unsigned32,
    channelStatisticsBytesReceived                    Unsigned32,
    channelStatisticsAverageReceiveInterarrivalJitter Unsigned32,
    channelStatisticsReset                            INTEGER
  }

  -- Index:Endpoint and channel Identifier

  channelStatisticsEpChannelId OBJECT-TYPE
   SYNTAX        OCTET STRING
   MAX-ACCESS    read-only
   STATUS        current
   DESCRIPTION " Endpoint and channel Identifier

                 String that identifies the combination of an endpoint and a
                 channel. The endpoint name is the same as the EpId used to
                 refer to endpoints in other tables. On endpoints with
                 multiple channels, the channel number must be appended at the
                 end of the endpoint name, separated with a dash. Here are a
                 few examples:

                   * Slot3/E1T1-12 refers to endpoint Slot3/E1T1, channel 12.
                   * Phone-Fax1 refers to FXS endpoint Phone-Fax1. No channel
                     number is appended because FXS lines do not support
                     multiple channels.


                 "
   ::= { channelStatisticsEntry 100 }

  -- Columnar:Packets Sent

  channelStatisticsPacketsSent OBJECT-TYPE
   SYNTAX        Unsigned32
   MAX-ACCESS    read-only
   STATUS        current
   DESCRIPTION " Packets Sent

                 Number of packets transmitted on the channel since service
                 start. This value is obtained by cumulating the packets
                 transmitted in all the connections that ended during the
                 collection period.
                 "
   ::= { channelStatisticsEntry 200 }

  -- Columnar:Packets Received

  channelStatisticsPacketsReceived OBJECT-TYPE
   SYNTAX        Unsigned32
   MAX-ACCESS    read-only
   STATUS        current
   DESCRIPTION " Packets Received

                 Number of packets received on the channel since service
                 start. This value is obtained by cumulating the packets
                 received in all the connections that ended during the
                 collection period.
                 "
   ::= { channelStatisticsEntry 300 }

  -- Columnar:Bytes Sent

  channelStatisticsBytesSent OBJECT-TYPE
   SYNTAX        Unsigned32
   MAX-ACCESS    read-only
   STATUS        current
   DESCRIPTION " Bytes Sent

                 Number of bytes transmitted on the channel since service
                 start. This value is obtained by cumulating the bytes
                 transmitted in all the connections that ended during the
                 collection period.
                 "
   ::= { channelStatisticsEntry 400 }

  -- Columnar:Bytes Received

  channelStatisticsBytesReceived OBJECT-TYPE
   SYNTAX        Unsigned32
   MAX-ACCESS    read-only
   STATUS        current
   DESCRIPTION " Bytes Received

                 Number of bytes received on the channel since service start.
                 This value is obtained by cumulating the bytes received in
                 all the connections that ended during the collection period.
                 "
   ::= { channelStatisticsEntry 500 }

  -- Columnar:Average Receive Interarrival Jitter

  channelStatisticsAverageReceiveInterarrivalJitter OBJECT-TYPE
   SYNTAX        Unsigned32
   MAX-ACCESS    read-only
   STATUS        current
   DESCRIPTION " Average Receive Interarrival Jitter

                 Average interarrival time, in microseconds, for the channel
                 since service start. This value is based on the average
                 interarrival jitter of each call ended during the collection
                 period. The value is weighted by the duration of the calls.
                 "
   ::= { channelStatisticsEntry 600 }

  -- Row command:Reset

  channelStatisticsReset OBJECT-TYPE
   SYNTAX        INTEGER { noOp(0), reset(10) }
   MAX-ACCESS    read-write
   STATUS        current
   DESCRIPTION " Reset

                 Sets all the values of the row to zero.
                 "
   DEFVAL        { noOp }
   ::= { channelStatisticsEntry 900 }


 -- End of table:Channel Statistics

 -- Scalar:Collection Period Duration

 statsCollectionPeriodDuration OBJECT-TYPE
  SYNTAX        Unsigned32 ( 0..44640 )
  MAX-ACCESS    read-write
  STATUS        current
  DESCRIPTION " Collection Period Duration

                Specifies the collection period duration (in minutes).
                "
  DEFVAL        { 0 }
  ::= { statisticsGroup 300 }

 -- Scalar:Enable Notification Per Connection

 statsPerConnectionNotificationEnable OBJECT-TYPE
  SYNTAX        MxEnableState
  MAX-ACCESS    read-write
  STATUS        current
  DESCRIPTION " Enable Notification Per Connection

                Enables the generation of connection end statistics
                notification.

                  * Enable: Notifications are generated.
                  * Disable: Notifications are not generated.


                "
  DEFVAL        { disable }
  ::= { statisticsGroup 400 }

 -- Scalar:Enable Notification Per Period

 statsPerPeriodNotificationEnable OBJECT-TYPE
  SYNTAX        MxEnableState
  MAX-ACCESS    read-write
  STATUS        current
  DESCRIPTION " Enable Notification Per Period

                Enables the generation of period statistics notification.

                  * Enable: Notifications are generated.
                  * Disable: Notifications are not generated.


                "
  DEFVAL        { disable }
  ::= { statisticsGroup 500 }

-- End of group:Statistics Group

-- ****************************************************************************

-- Group:Interop Group

-- ****************************************************************************

interopGroup OBJECT IDENTIFIER
 ::= { miptMIBObjects 40000 }
 -- Scalar:Enforce Symmetric RTP

 enforceSymmetricRtpEnable OBJECT-TYPE
  SYNTAX        MxEnableState
  MAX-ACCESS    read-write
  STATUS        current
  DESCRIPTION " Enforce Symmetric RTP

                For each bi-directional RTP streams, enforce that incoming RTP
                packets are from the same source as the destination of
                outgoing RTP packets.

                  * Enable: Silently discard incoming RTP packets with source
                    address and port differing from the destination address
                    and port of outgoing packets.
                  * Disable: Accept packets from all sources.

                Enforcing symmetric RTP may prevent legitimate RTP streams
                coming from a media server from being processed, for example:
                Music and conferencing servers.


                "
  DEFVAL        { disable }
  ::= { interopGroup 100 }

 -- Scalar:Quantity of initial packets sent to transmit a DTMF Out-of-Band
 -- using RTP

 interopDtmfRtpInitialPacketQty OBJECT-TYPE
  SYNTAX        Unsigned32 ( 1..3 )
  MAX-ACCESS    read-write
  STATUS        current
  DESCRIPTION " Quantity of initial packets sent to transmit a DTMF
                Out-of-Band using RTP

                Specifies the quantity of packets sent at the beginning of an
                Out-of-Band DTMF using RTP. This variable also specifies the
                quantity of terminating packets that are sent at the end of
                the DTMF transmission.

                Note that this variable has an effect only if the
                DtmfTransportMethod is set to 'outOfBandUsingRtp'.


                "
  DEFVAL        { 3 }
  ::= { interopGroup 200 }

-- End of group:Interop Group

-- ****************************************************************************

-- Group:Debug Group

-- ****************************************************************************

debugGroup OBJECT IDENTIFIER
 ::= { miptMIBObjects 50000 }
 -- ***************************************************************************
 
 -- Group:PCM Capture

 -- ***************************************************************************
 
 pcmCaptureGroup OBJECT IDENTIFIER
  ::= { debugGroup 100 }
  -- Scalar:PCM Capture Enable

  pcmCaptureEnable OBJECT-TYPE
   SYNTAX        MxEnableState
   MAX-ACCESS    read-write
   STATUS        current
   DESCRIPTION " PCM Capture Enable

                 Enables PCM capture for the endpoint specified by
                 PcmCaptureEndpoint and sends the capture to the
                 PcmCaptureIpAddr host.

                 The PCM capture can be enabled/disabled on-the-fly. The
                 capture starts right away if the endpoint is already in a
                 call, or will be started the next time a call is established.


                 "
   DEFVAL        { disable }
   ::= { pcmCaptureGroup 100 }

  -- Scalar:PCM Capture Endpoint

  pcmCaptureEndpoint OBJECT-TYPE
   SYNTAX        OCTET STRING ( SIZE(0..64) )
   MAX-ACCESS    read-write
   STATUS        current
   DESCRIPTION " PCM Capture Endpoint

                 Unit's endpoint on which the PCM capture must be performed.

                 The endpoint name must match one of the epAdm/endpointTable/
                 endpointEpId list. For digital interfaces (like ISDN), a
                 '-Channel#' must be appended for the requested channel.

                 The list of endpoints is available under EpAdm.EndpointTable.
                 Valid examples (depending of the platform) are:

                   * PCM capture is to be done on channel #3 of a PRI interface
                     located in slot #2: Slot2/E1T1-3
                   * PCM capture is to be done on channel #2 of a BRI
                     interface: Bri1-2
                   * PCM capture is to be done on the 16th FXS port: Port16

                 Note that PCM capture does not support capturing on multiple
                 endpoints simultaneously.


                 "
   DEFVAL        { "" }
   ::= { pcmCaptureGroup 200 }

  -- Scalar:PCM Capture IP Address

  pcmCaptureIpAddr OBJECT-TYPE
   SYNTAX        MxIpAddress
   MAX-ACCESS    read-write
   STATUS        current
   DESCRIPTION " PCM Capture IP Address

                 IP address where the captured PCM packets should be sent.
                 "
   DEFVAL        { "" }
   ::= { pcmCaptureGroup 300 }

 -- End of group:PCM Capture

 -- ***************************************************************************
 
 -- Group:DSP Debug Traces

 -- ***************************************************************************
 
 dspTracingGroup OBJECT IDENTIFIER
  ::= { debugGroup 200 }
  -- Scalar:DSP Debug Traces Enable

  dspTracingEnable OBJECT-TYPE
   SYNTAX        MxEnableState
   MAX-ACCESS    read-write
   STATUS        current
   DESCRIPTION " DSP Debug Traces Enable

                 Activates the DSP tracing.

                 When enabled, DSP debugging traces are sent to the syslog. The
                 Diagnostic Traces must be enabled and the DSP trace level set
                 to Debug in order to see these DSP traces. Refer to the
                 Notifications and Logging Manager (Nlm) service's variables
                 DiagnosticTracesEnable and DiagnosticTracesFilter.

                 WARNING: Sensitive information may be sent in these traces.
                 Use them only for debugging. Leaving them enabled for a long
                 time is a security hole, and may also reduce system
                 performance and affect voice quality.


                 "
   DEFVAL        { disable }
   ::= { dspTracingGroup 100 }

 -- End of group:DSP Debug Traces

 -- ***************************************************************************
 
 -- Group:DSP Debug Statistics

 -- ***************************************************************************
 
 dspStatsGroup OBJECT IDENTIFIER
  ::= { debugGroup 300 }
  -- Scalar:DSP Debug Statistics Enable

  dspStatsEnable OBJECT-TYPE
   SYNTAX        MxEnableState
   MAX-ACCESS    read-write
   STATUS        current
   DESCRIPTION " DSP Debug Statistics Enable

                 Activates the DSP channel statistics.

                 When enabled, in-call statistics from the DSP channels are
                 sent to the syslog. The Diagnostic Traces must be enabled and
                 the 'Line/Line Engine' trace level set to Debug or All (nlmMIB
                 /TacGroup) in order to see these statistics.

                 See the following DspStatsInterval and DspStatsFilter
                 variables for more configuration.

                 WARNING: Enabling the DSP channel statistics might slow down
                 the system and reduce voice quality. Use only for debugging or
                 troubleshooting.


                 "
   DEFVAL        { disable }
   ::= { dspStatsGroup 100 }

  -- Scalar:DSP Debug Statistics Interval

  dspStatsInterval OBJECT-TYPE
   SYNTAX        Unsigned32 ( 0..3600 )
   MAX-ACCESS    read-write
   STATUS        current
   DESCRIPTION " DSP Debug Statistics Interval

                 The time interval, in seconds, between each statistics
                 request.

                 When greater than 0, it outputs the statistics at the interval
                 specified, and at channel closing.

                 When the interval is 0, it outputs the statistics only at
                 channel closing.


                 "
   DEFVAL        { 0 }
   ::= { dspStatsGroup 200 }

  -- Scalar:DSP Debug Statistics Filter

  dspStatsFilter OBJECT-TYPE
   SYNTAX        Unsigned32 ( 0..255 )
   MAX-ACCESS    read-write
   STATUS        current
   DESCRIPTION " DSP Debug Statistics Filter

                 Sum the values of the statistics groups wanted:

                   * DIM_STAT_ID_EC_DBG (1): Echo Canceller.
                   * DIM_STAT_ID_ERROR (2): Error.
                   * DIM_STAT_ID_FAX_RELAY (4): Fax T38.
                   * DIM_STAT_ID_RX_TX (8): Transmit/Receive.
                   * DIM_STAT_ID_SEC_RTP (16): Security SRTP.
                   * DIM_STAT_ID_VAD (32): Voice Activity Detection.
                   * DIM_STAT_ID_VQMON (64): Voice Quality Monitor.
                   * DIM_STAT_ID_VP (128): Voice Playout.

                 For example a value of 8 means DIM_STAT_ID_RX_TX statistics
                 only, a value of 12 means DIM_STAT_ID_FAX_RELAY and
                 DIM_STAT_ID_RX_TX, and a value of 255 means all groups.

                 This feature is not available on all products. Refer to the
                 Software Configuration Guide for more details.

                 WARNING: Requesting a lot of statistics might slow down the
                 system and reduce voice quality. Use only for debugging or
                 troubleshooting.


                 "
   DEFVAL        { 0 }
   ::= { dspStatsGroup 300 }

 -- End of group:DSP Debug Statistics

-- End of group:Debug Group

-- ****************************************************************************

-- Group:Notification Messages Configuration

-- ****************************************************************************

notificationsGroup OBJECT IDENTIFIER
 ::= { miptMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { miptMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
