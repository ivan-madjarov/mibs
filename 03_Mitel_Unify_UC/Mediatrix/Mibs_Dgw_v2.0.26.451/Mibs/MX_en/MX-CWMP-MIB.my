-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


MX-CWMP-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

cwmpMIB MODULE-IDENTITY
 LAST-UPDATED   "0909180000Z"
 ORGANIZATION " Mediatrix Telecom, Inc. "
 CONTACT-INFO " Mediatrix Telecom, Inc.
                4229, Garlock Street
                Sherbrooke (Quebec)
                Canada
                Phone: (819) 829-8749
                "
 DESCRIPTION  " CPE WAN Management Protocol

                The CPE WAN Management Protocol service manages the support of
                the TR-069 protocol for auto provisioning.
                "
 -- ****************************************************************************
 
 -- Revision history
 -- ****************************************************************************
 REVISION       "0909180000Z"
 DESCRIPTION  " Initial Revision "
 REVISION       "1010010000Z"
 DESCRIPTION  " Added group Tr106, added variable Tr106LanNetworkInterface "
 REVISION       "1103110000Z"
 DESCRIPTION  " Added group Tr111, added variables Tr111StunEnable,
                Tr111NatDetected, Tr111StunServerHost and
                Tr111StunKeepAlivePeriod. "
 REVISION       "1105030000Z"
 DESCRIPTION  " Added Tr111StunUsername. "
 REVISION       "1201110000Z"
 DESCRIPTION  " Added InteropGroup, added
                InteropAllowUnauthenticatedUDPConnectionRequests variable. "
 REVISION       "1201240000Z"
 DESCRIPTION  " Added Tr104 Group, added Tr104Enable variable. "
 REVISION       "1204120000Z"
 DESCRIPTION  " Added InteropParameterTypeValidation variable. "
 REVISION       "1304040000Z"
 DESCRIPTION  " Added AcsStatus and Tr111StunStatus variables. "
 REVISION       "1304180000Z"
 DESCRIPTION  " Set the secret tag for the Password variable. "
 REVISION       "1306120000Z"
 DESCRIPTION  " Added DataModel group, added NlmLocalLogLogEnable variable. "
 ::= { mediatrixServices 3900 }

cwmpMIBObjects OBJECT IDENTIFIER ::= { cwmpMIB 1 }

-- Scalar:Root Element

rootElement OBJECT-TYPE
 SYNTAX        INTEGER { device(100) , internetGatewayDevice(200) }
 MAX-ACCESS    read-write
 STATUS        current
 DESCRIPTION " Root Element

               Determines the data model used for the configuration.

                 * Device: Uses the Device data model as defined in TR-106.
                 * InternetGatewayDevice: Uses the Internet Gateway Device data
                   model as defined in TR-098.


               "
 DEFVAL        { device }
 ::= { cwmpMIBObjects 100 }

-- Scalar:Listening Port

listeningPort OBJECT-TYPE
 SYNTAX        MxAdvancedIpPort
 MAX-ACCESS    read-write
 STATUS        current
 DESCRIPTION " Listening Port

               Port on which the unit listens for incoming TR-069 connections.

               Note: If set to 0, the unit uses the default TR-069 port 7547.


               "
 DEFVAL        { 0 }
 ::= { cwmpMIBObjects 200 }

-- ****************************************************************************

-- Group:ACS

-- ****************************************************************************

acs OBJECT IDENTIFIER
 ::= { cwmpMIBObjects 1000 }
 -- Scalar:ACS URL Config Source

 acsUrlConfigSource OBJECT-TYPE
  SYNTAX        INTEGER { dhcp(100) , static(200) }
  MAX-ACCESS    read-write
  STATUS        current
  DESCRIPTION " ACS URL Config Source

                Determines the method to obtain the URL of the ACS.

                  * Dhcp: Uses the DHCP protocol to find the URL as defined in
                    TR-106 section 3.1.
                  * Static: Uses the URL defined in the AcsStaticUrl variable.


                "
  DEFVAL        { dhcp }
  ::= { acs 100 }

 -- Scalar:ACS Static URL

 acsStaticUrl OBJECT-TYPE
  SYNTAX        OCTET STRING ( SIZE(0..256) )
  MAX-ACCESS    read-write
  STATUS        current
  DESCRIPTION " ACS Static URL

                URL used by the unit to connect to the ACS using the CPE WAN
                Management Protocol if the AcsUrlConfigSource variable is set
                to 'Static'.

                This parameter must be a valid HTTP or HTTPS URL.

                Example:

                  * 'http://somewhere.com'.
                  * 'https://somewhere.secure.com'.


                "
  DEFVAL        { "" }
  ::= { acs 200 }

 -- Scalar:Username

 username OBJECT-TYPE
  SYNTAX        OCTET STRING ( SIZE(0..256) )
  MAX-ACCESS    read-write
  STATUS        current
  DESCRIPTION " Username

                Username used to authenticate the unit when making a
                connection to the ACS using the CPE WAN Management Protocol.
                "
  DEFVAL        { "" }
  ::= { acs 300 }

 -- Scalar:Password

 password OBJECT-TYPE
  SYNTAX        OCTET STRING ( SIZE(0..256) )
  MAX-ACCESS    read-write
  STATUS        current
  DESCRIPTION " Password

                Password used to authenticate the unit when making a
                connection to the ACS the CPE WAN Management Protocol.
                "
  DEFVAL        { "" }
  ::= { acs 600 }

 -- Scalar:ACS Status

 acsStatus OBJECT-TYPE
  SYNTAX        INTEGER { starting(100) , connected(200) , noUrl(300) ,
                errorCannotResolve(400) , errorNotResponding(500) ,
                errorAuthFailure(600) , errorOther(700) }
  MAX-ACCESS    read-only
  STATUS        current
  DESCRIPTION " ACS Status

                Indicates the status of the connection with the ACS.

                  * Starting: Cwmp service is starting and no connection
                    attempt have been made so far.
                  * Connected: The Cwmp service is connected to the ACS.
                  * NoUrl: The Cwmp service cannot connect with the ACS
                    because no ACS URL is configured.
                  * ErrorCannotResolve: The Cwmp service cannot connect with
                    the ACS because the FQDN cannot be resolved.
                  * ErrorNotResponding: The Cwmp service cannot connect with
                    the ACS because the ACS is not responding.
                  * ErrorAuthFailure: The Cwmp service failed authenticating
                    to the ACS.
                  * ErrorOther: The Cwmp service cannot connect to the ACS for
                    unspecified reason. See device and ACS logs.


                "
  ::= { acs 700 }

-- End of group:ACS

-- ****************************************************************************

-- Group:Periodic Inform

-- ****************************************************************************

periodicInform OBJECT IDENTIFIER
 ::= { cwmpMIBObjects 2000 }
 -- Scalar:Periodic Inform Enable

 periodicInformEnable OBJECT-TYPE
  SYNTAX        MxEnableState
  MAX-ACCESS    read-write
  STATUS        current
  DESCRIPTION " Periodic Inform Enable

                Defines whether or not the unit needs to periodically send CPE
                information to the ACS using the Inform method call.

                  * Disable: The unit does not send periodic inform.
                  * Enable: The unit sends periodic inform.


                "
  DEFVAL        { disable }
  ::= { periodicInform 100 }

 -- Scalar:Periodic Inform Interval

 periodicInformInterval OBJECT-TYPE
  SYNTAX        Unsigned32 ( 1..4294967295 )
  MAX-ACCESS    read-write
  STATUS        current
  DESCRIPTION " Periodic Inform Interval

                The duration, in seconds, of the interval for which the unit
                needs to attempt to connect with the ACS and call the Inform
                method if the PeriodicInformEnable variable is set to
                'Enable'.
                "
  DEFVAL        { 3600 }
  ::= { periodicInform 200 }

 -- Scalar:Periodic Inform Time

 periodicInformTime OBJECT-TYPE
  SYNTAX        OCTET STRING ( SIZE(20..20) )
  MAX-ACCESS    read-write
  STATUS        current
  DESCRIPTION " Periodic Inform Time

                An absolute time reference in UTC format to determine when the
                unit initiates the periodic Inform method calls. Each Inform
                call MUST occur at this reference time plus or minus an
                integer multiple of the PeriodicInformInterval.

                PeriodicInformTime is used only to set the 'phase' of the
                periodic Informs. The actual value of PeriodicInformTime can
                be arbitrarily far into the past or future.

                For example, if PeriodicInformInterval is 86400 (a day) and if
                PeriodicInformTime is set to UTC midnight on some day (in the
                past, present, or future), then periodic Informs will occur
                every day at UTC midnight. These MUST begin on the very next
                midnight, even if PeriodicInformTime refers to a day in the
                future.

                The Unknown Time value indicates that no particular time
                reference is specified. That is, the unit locally chooses the
                time reference and needs only to follow the specified
                PeriodicInformInterval.

                If absolute time is not available to the unit, its periodic
                Inform behavior is the same as if the PeriodicInformTime
                parameter was set to the Unknown Time value.

                The format of the value is 'CCYY-MM-DDThh:mm:ssZ' where:

                  * CCYY: Year number.
                  * MM: Month number in the year.
                  * DD: Day number in the month.
                  * hh: Hour number in the day.
                  * mm: Minute number in the hour.
                  * ss: Second number in the minute.

                Example: 1969-07-21T02:28:00Z.

                The Unknown Time value is defined at '0001-01-01T00:00:00Z'.


                "
  DEFVAL        { "0001-01-01T00:00:00Z" }
  ::= { periodicInform 300 }

-- End of group:Periodic Inform

-- ****************************************************************************

-- Group:TR069

-- ****************************************************************************

tr069 OBJECT IDENTIFIER
 ::= { cwmpMIBObjects 2100 }
 -- Scalar:TR-069 Annex F Enable

 tr069AnnexFEnable OBJECT-TYPE
  SYNTAX        MxEnableState
  MAX-ACCESS    read-write
  STATUS        current
  DESCRIPTION " TR-069 Annex F Enable

                Enables/disables the support of variables under the TR-069
                Device.GatewayInfo tree.
                "
  DEFVAL        { disable }
  ::= { tr069 100 }

-- End of group:TR069

-- ****************************************************************************

-- Group:TR104

-- ****************************************************************************

tr104 OBJECT IDENTIFIER
 ::= { cwmpMIBObjects 2900 }
 -- Scalar:TR-104 Enable

 tr104Enable OBJECT-TYPE
  SYNTAX        MxEnableState
  MAX-ACCESS    read-write
  STATUS        current
  DESCRIPTION " TR-104 Enable

                Enables/disables the support of variables under the TR-069
                Device.Services.VoiceService tree.
                "
  DEFVAL        { disable }
  ::= { tr104 100 }

-- End of group:TR104

-- ****************************************************************************

-- Group:TR106

-- ****************************************************************************

tr106 OBJECT IDENTIFIER
 ::= { cwmpMIBObjects 3000 }
 -- Scalar:TR-106 Lan Profile Network Interface Override

 tr106LanNetworkInterface OBJECT-TYPE
  SYNTAX        OCTET STRING ( SIZE(0..256) )
  MAX-ACCESS    read-write
  STATUS        current
  DESCRIPTION " TR-106 Lan Profile Network Interface Override

                Network interface referred by the TR-106 LAN profile. If
                empty, use the network interface configured in
                Hoc.ManagementInterface. If Hoc.ManagementInterface is set to
                ?All?, use the network interface used for contacting the ACS.
                "
  DEFVAL        { "" }
  ::= { tr106 100 }

-- End of group:TR106

-- ****************************************************************************

-- Group:TR-111

-- ****************************************************************************

tr111 OBJECT IDENTIFIER
 ::= { cwmpMIBObjects 4000 }
 -- Scalar:TR-111 STUN Enable

 tr111StunEnable OBJECT-TYPE
  SYNTAX        MxEnableState
  MAX-ACCESS    read-write
  STATUS        current
  DESCRIPTION " TR-111 STUN Enable

                Enables/disables the use of STUN binding requests to discover
                the unit?s external IP address and port and to set the
                ManagementServer.UDPConnectionRequestAddress value
                accordingly. The ACS can then send UDP connection requests to
                the unit at that IP address and port.

                  * Enable: Enables the use of STUN by the unit.
                  * Disable: Disables the use of STUN by the unit.


                "
  DEFVAL        { disable }
  ::= { tr111 100 }

 -- Scalar:TR-111 NAT Detected

 tr111NatDetected OBJECT-TYPE
  SYNTAX        INTEGER { no(100) , yes(200) }
  MAX-ACCESS    read-only
  STATUS        current
  DESCRIPTION " TR-111 NAT Detected

                When Tr111StunEnable is enabled, this parameter indicates
                whether or not the unit has detected the address and/or port
                mapping in use.

                  * Yes: Tr111StunEnable is enabled and the unit has detected
                    the address and/or port mapping.
                  * No: Tr111StunEnable is disabled or the unit has not
                    detected the address and/or port mapping.


                "
  ::= { tr111 200 }

 -- Scalar:TR-111 STUN Server Host

 tr111StunServerHost OBJECT-TYPE
  SYNTAX        MxIpHostNamePort
  MAX-ACCESS    read-write
  STATUS        current
  DESCRIPTION " TR-111 STUN Server Host

                Host name or IP address of the STUN server for the unit to
                send Binding Requests if Tr111StunEnable is enabled.

                If Tr111StunServerHost is empty and Tr111StunEnable is
                enabled, the unit uses the address of the ACS extracted from
                the host portion of the ACS URL.

                If the port is not specified or set to 0, the default STUN
                port (3478) is used.


                "
  DEFVAL        { "" }
  ::= { tr111 300 }

 -- Scalar:TR-111 STUN Keep Alive Period

 tr111StunKeepAlivePeriod OBJECT-TYPE
  SYNTAX        OCTET STRING ( SIZE(0..256) )
  MAX-ACCESS    read-write
  STATUS        current
  DESCRIPTION " TR-111 STUN Keep Alive Period

                If Tr111StunEnable is enabled, this is the period range, in
                seconds, at which STUN Binding Requests must be sent by the
                unit for the purpose of maintaining the STUN connection. The
                timeouts must be entered in the format 'minimum-maximum'.

                The value must be less than or equal to 3600 seconds.

                Note: The current implementation does not allow a range. The
                minimum and maximum values must be the same.


                "
  DEFVAL        { "60-60" }
  ::= { tr111 400 }

 -- Scalar:TR-111 STUN Username

 tr111StunUsername OBJECT-TYPE
  SYNTAX        OCTET STRING ( SIZE(0..256) )
  MAX-ACCESS    read-write
  STATUS        current
  DESCRIPTION " TR-111 STUN Username

                If non-empty, the value of the STUN username attribute to be
                used in Binding Requests when Tr111StunEnable is enabled.
                "
  DEFVAL        { "" }
  ::= { tr111 500 }

 -- Scalar:TR-111 STUN Status

 tr111StunStatus OBJECT-TYPE
  SYNTAX        INTEGER { disabled(0) , starting(100) , connected(200) ,
                errorCannotResolve(400) , errorNotResponding(500) , errorOther
                (700) }
  MAX-ACCESS    read-only
  STATUS        current
  DESCRIPTION " TR-111 STUN Status

                Indicates the status of the connection with the STUN server.

                  * Disabled: TR-111 is disabled.
                  * Starting: Cwmp service is starting and no connection
                    attempt have been made so far.
                  * Connected: The Cwmp service is connected to the STUN
                    server.
                  * ErrorCannotResolve: The Cwmp service cannot connect with
                    the STUN server because the FQDN cannot be resolved.
                  * ErrorNotResponding: The Cwmp service cannot connect with
                    the STUN server because the server is not responding.
                  * ErrorOther: The Cwmp service cannot connect to the STUN
                    server for unspecified reason or because no ACS URL is
                    configured. See device and ACS logs.


                "
  ::= { tr111 600 }

-- End of group:TR-111

-- ****************************************************************************

-- Group:Data Model

-- ****************************************************************************

dataModel OBJECT IDENTIFIER
 ::= { cwmpMIBObjects 4500 }
 -- Scalar:Enable Nlm.LocalLog.Log

 nlmLocalLogLogEnable OBJECT-TYPE
  SYNTAX        MxEnableState
  MAX-ACCESS    read-write
  STATUS        current
  DESCRIPTION " Enable Nlm.LocalLog.Log


                Add the object .X_0090F8_Nlm.LocalLog.Log{i}. to the data
                model.

                This object contains the notifications stored locally on the
                device.

                Making this object accessible requires significant CPU
                resources when notifications are frequently sent to the local
                log.


                "
  DEFVAL        { disable }
  ::= { dataModel 100 }

-- End of group:Data Model

-- ****************************************************************************

-- Group:Interop Group

-- ****************************************************************************

interopGroup OBJECT IDENTIFIER
 ::= { cwmpMIBObjects 50000 }
 -- Scalar:Allow Unauthenticated UDP Connection Requests

 interopAllowUnauthenticatedUDPConnectionRequests OBJECT-TYPE
  SYNTAX        MxEnableState
  MAX-ACCESS    read-write
  STATUS        current
  DESCRIPTION " Allow Unauthenticated UDP Connection Requests

                Determines the CPE behavior when receiving a UDP connection
                request message.

                  * Enable: Allow any UDP connection request without
                    authentication. This behavior goes against the UDP
                    Connection Request described by TR-069 Amendment-2
                    specification.
                  * Disable: Force the authentication of a UDP connection
                    request.


                "
  DEFVAL        { disable }
  ::= { interopGroup 100 }

 -- Scalar:Parameter Type Validation

 interopParameterTypeValidation OBJECT-TYPE
  SYNTAX        INTEGER { tolerant(100) , strict(200) }
  MAX-ACCESS    read-write
  STATUS        current
  DESCRIPTION " Parameter Type Validation

                Defines the parameter type validation when the ACS assigns a
                value to a parameter.

                  * Tolerant: The client target type is evaluated and
                    conversion is done (if possible): i.e., string to boolean,
                    string to int, string to unsigned int, string to datetime,
                    etc.
                  * Strict: The ACS and the client must have matching xsd:type
                    otherwise the client rejects the parameter value.


                "
  DEFVAL        { tolerant }
  ::= { interopGroup 200 }

-- End of group:Interop Group

-- ****************************************************************************

-- Group:Notification Messages Configuration

-- ****************************************************************************

notificationsGroup OBJECT IDENTIFIER
 ::= { cwmpMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { cwmpMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
