-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


MX-IPSYNC-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

ipSyncMIB MODULE-IDENTITY
 LAST-UPDATED   "0908310000Z"
 ORGANIZATION " Mediatrix Telecom, Inc. "
 CONTACT-INFO " Mediatrix Telecom, Inc.
                4229, Garlock Street
                Sherbrooke (Quebec)
                Canada
                Phone: (819) 829-8749
                "
 DESCRIPTION  " IP Media Synchronization

                IP Media synchronization using clock reference signals sent
                over IP.
                "
 -- ****************************************************************************
 
 -- Revision history
 -- ****************************************************************************
 REVISION       "0908310000Z"
 DESCRIPTION  " Initial Revision "
 REVISION       "0909080000Z"
 DESCRIPTION  " Modified the StaticMasterHost variable to include usage of a
                port in the variable. "
 REVISION       "0912150000Z"
 DESCRIPTION  " Added the StaticRedundantMasterHost scalar variable. "
 REVISION       "0912220000Z"
 DESCRIPTION  " Changed the HiddenMaxNbSlave for the HiddenUnitType. "
 REVISION       "1109060000Z"
 DESCRIPTION  " Added the ResetSyncData command and updated JitterStatus
                variable description. "
 ::= { mediatrixServices 3800 }

ipSyncMIBObjects OBJECT IDENTIFIER ::= { ipSyncMIB 1 }

-- Scalar:Clock Synchronization Packets Port

port OBJECT-TYPE
 SYNTAX        MxAdvancedIpPort
 MAX-ACCESS    read-write
 STATUS        current
 DESCRIPTION " Clock Synchronization Packets Port

               Port number with which the unit sends and receives clock
               synchronization packets. This port is used on all network
               interfaces.
               "
 DEFVAL        { 5003 }
 ::= { ipSyncMIBObjects 100 }

-- Scalar:Static Master Host

staticMasterHost OBJECT-TYPE
 SYNTAX        MxIpHostNamePort
 MAX-ACCESS    read-write
 STATUS        current
 DESCRIPTION " Static Master Host

               FQDN or IP address of the Master unit on which a Slave attempts
               to synchronize. When the port is omitted, default port 5003 is
               used.

               This variable is ignored by a Master unit.


               "
 DEFVAL        { "" }
 ::= { ipSyncMIBObjects 200 }

-- Scalar:Redundant Static Master Host

redundantStaticMasterHost OBJECT-TYPE
 SYNTAX        MxIpHostNamePort
 MAX-ACCESS    read-write
 STATUS        current
 DESCRIPTION " Redundant Static Master Host

               FQDN or IP address of the redundant Master unit on which a Slave
               attempts to synchronize when the StaticMasterHost is
               unreachable. When the port is omitted, default port 5003 is
               used.

               This variable is ignored by a Master unit.


               "
 DEFVAL        { "" }
 ::= { ipSyncMIBObjects 300 }

-- Scalar:Unit Status

unitStatus OBJECT-TYPE
 SYNTAX        INTEGER { inactive(100) , master(200) , slave(300) }
 MAX-ACCESS    read-only
 STATUS        current
 DESCRIPTION " Unit Status

               Current status of the unit in regard to the Clock
               Synchronization protocol.

                 * Inactive: Clock synchronization is not in use.
                 * Master: The unit is a Master.
                 * Slave: The unit is a Slave.


               "
 DEFVAL        { inactive }
 ::= { ipSyncMIBObjects 5000 }

-- Scalar:Jitter Status

jitterStatus OBJECT-TYPE
 SYNTAX        Unsigned32
 MAX-ACCESS    read-only
 STATUS        current
 DESCRIPTION " Jitter Status

               On a Slave unit, this variable displays the maximum jitter
               observed from incoming synchronization packets over a five
               minutes period. When the unit is a Master, the value in this
               variable should not be considered.
               "
 DEFVAL        { 0 }
 ::= { ipSyncMIBObjects 5100 }

-- Scalar:TDM Bus Precision Status

tdmBusPrecisionStatus OBJECT-TYPE
 SYNTAX        Unsigned32
 MAX-ACCESS    read-only
 STATUS        current
 DESCRIPTION " TDM Bus Precision Status

               Estimate of the drift in PPB (parts per billion), of the local
               TDM clock with regards to the reference (master) clock. A value
               of 10 000 means the local clock may be off by +/- 0,00001% which
               is +/- 0.08Hz since the frame sync frequency on the TDM bus is
               8000Hz. This may result in overruns or underruns on the TDM bus
               causing an average bit error ratio up to 0,00001. When the unit
               is not currently synchronized, the value in this variable is the
               hardware clock precision. When the unit is a Master, the value
               in this variable should not be considered.
               "
 DEFVAL        { 0 }
 ::= { ipSyncMIBObjects 5200 }

-- ****************************************************************************

-- Group:Notification Messages Configuration

-- ****************************************************************************

notificationsGroup OBJECT IDENTIFIER
 ::= { ipSyncMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { ipSyncMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
