-- ****************************************************************************
-- ****************************************************************************
--
--             Copyright(c) 2003 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

MGCP44-MX-EMERGENCY-CALL-MIB
DEFINITIONS ::= BEGIN

IMPORTS
        MODULE-IDENTITY,
        OBJECT-TYPE,
        Unsigned32
    FROM SNMPv2-SMI
        MODULE-COMPLIANCE,
        OBJECT-GROUP
    FROM SNMPv2-CONF
        ifIndex
    FROM RFC1213-MIB
        MxEnableState
    FROM MX-TC
        mediatrixConfig
    FROM MX-SMI;

emergencyCallMIB MODULE-IDENTITY
    LAST-UPDATED "0303030000Z"
    ORGANIZATION "Mediatrix Telecom, Inc."
    CONTACT-INFO "Mediatrix Telecom, Inc.
                  4229, Garlock Street
                  Sherbrooke (Quebec)
                  Canada
                  Phone: (819) 829-8749
                  "
    DESCRIPTION  "This MIB is used to configure the exceptional treatment
                  of emergency calls."


    -- ************************************************************************
    -- Revision history
    -- ************************************************************************
    REVISION    "0303030000Z"
    DESCRIPTION "March 03, 2003
                    Creation
                    The following variables were moved from MX-TELEPHONY-SERVICES-MIB
                    to this MIB, (the prefix was renamed to emergencyCall):
                    
                    telephonyServicesUrgentGatewayEnable
                    telephonyServicesUrgentGatewayDigitMap
                    telephonyServicesUrgentGatewayTargetAddress"
    ::= { mediatrixConfig 75 }

emergencyCallMIBObjects OBJECT IDENTIFIER ::= { emergencyCallMIB 1 }
emergencyCallConformance OBJECT IDENTIFIER ::= { emergencyCallMIB 2 }

    -- ************************************************************************
    -- Urgent Gateway group
    -- ************************************************************************
    emergencyCallUrgentGatewayCustomization OBJECT IDENTIFIER ::= { emergencyCallMIBObjects 5 }

    emergencyCallUrgentGatewayEnable OBJECT-TYPE
        SYNTAX  MxEnableState
        MAX-ACCESS  read-write
        STATUS      current
        DESCRIPTION "Enable/Disable the urgent gateway service.

                     This service allows a user to dial a special digit map resulting in a message
                     being sent to a specified urgent gateway, bypassing any other intermediaries.

                     If enabled, whenever the user dials the specified digit map, a message will be
                     sent to the target address.

                     See emergencyCallUrgentGatewayDigitMap and
                     emergencyCallUrgentGatewayTargetAddress."
        DEFVAL      { disable }
        ::= { emergencyCallUrgentGatewayCustomization 5 }
    
    emergencyCallUrgentGatewayDigitMap OBJECT-TYPE
        SYNTAX  OCTET STRING (SIZE(0..10))
        MAX-ACCESS  read-write
        STATUS      current
        DESCRIPTION "Digit map the user must dial to initiate a call in urgent mode.

                     This digit map must follow the syntax for digit maps as declared in the digit
                     maps MIB.

                     Note that dialing this digit map will not have any effect unless the service's
                     status is 'enabled'.

                     See emergencyCallUrgentGatewayEnable."
        DEFVAL      { "" }
        ::= { emergencyCallUrgentGatewayCustomization 10 }

    emergencyCallUrgentGatewayTargetAddress OBJECT-TYPE
        SYNTAX  OCTET STRING (SIZE(0..127))
        MAX-ACCESS  read-write
        STATUS      current
        DESCRIPTION "A string that represents the address or telephone number that the user wants to
                     automatically call when dialing the emergency number.

                     This variable's semantics are different depending on protocol and/or
                     hardware platforms.
                     Please refer to the documentation shipped with your device for more details."
        DEFVAL      { "" }
        ::= { emergencyCallUrgentGatewayCustomization 15 }


    -- ************************************************************************
    -- Conformance information
    -- ************************************************************************
    emergencyCallCompliances OBJECT IDENTIFIER ::= { emergencyCallConformance 1 }

    emergencyCallComplVer1 MODULE-COMPLIANCE
        STATUS      current
        DESCRIPTION
            "List of groups required to support emergency calls."
        MODULE  -- This Module
            MANDATORY-GROUPS {
                                emergencyCallUrgentGatewayVer1
                             }
        ::= { emergencyCallCompliances 1 }

    -- ************************************************************************
    --  MIB variable grouping
    -- ************************************************************************
    emergencyCallGroups OBJECT IDENTIFIER ::= { emergencyCallConformance 5 }

    emergencyCallUrgentGatewayVer1 OBJECT-GROUP
        OBJECTS {
                    emergencyCallUrgentGatewayEnable,
                    emergencyCallUrgentGatewayDigitMap,
                    emergencyCallUrgentGatewayTargetAddress
                }
        STATUS current
        DESCRIPTION
            "A collection of objects that defines the characteristics of emergency calls."
        ::= { emergencyCallGroups 5 }

END
