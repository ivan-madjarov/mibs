-- ****************************************************************************
-- ****************************************************************************
--
--             Copyright(c) 2001-2003 Mediatrix Telecom, Inc.
--
--  NOTICE:
--   This document contains information that is confidential and proprietary
--   to Mediatrix Telecom, Inc.
--
--   Mediatrix Telecom, Inc. reserves all rights to this document as well as
--   to the Intellectual Property of the document and the technology and
--   know how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

MGCP46-NT-SIP-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        mediatrixExperimental
    FROM MX-SMI;

ntSipMIB MODULE-IDENTITY
    LAST-UPDATED "0302110000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains Nortel-specific SIP configuration objects."

    -- ************************************************************************
    -- Revision history
    -- ************************************************************************
    REVISION    "0302110000Z"
    DESCRIPTION "February 11, 2003
                   Creation"
    ::= { mediatrixExperimental 55 }

ntSipMIBObjects  OBJECT IDENTIFIER ::= { ntSipMIB 1 }
ntSipConformance OBJECT IDENTIFIER ::= { ntSipMIB 2 }

-- ************************************************************************
-- NAT
-- ************************************************************************
ntSipNat OBJECT IDENTIFIER ::= { ntSipMIBObjects 10 }

    ntSipNatPingTimeout OBJECT-TYPE
        SYNTAX      Unsigned32 (0..600)
        MAX-ACCESS  read-write
        STATUS      current
        DESCRIPTION "PING request refresh timeout in seconds. Feature used
                     under licence from Nortel Networks Inc."
        DEFVAL { 0 }
        ::=  { ntSipNat 10 }


    -- ************************************************************************
    -- Conformance information
    -- ************************************************************************
    ntSipCompliances OBJECT IDENTIFIER ::= { ntSipConformance 1 }

    ntSipBasicComplVer1 MODULE-COMPLIANCE
        STATUS      current
        DESCRIPTION "Minimal definitions for the Nortel-specific SIP group"
        MODULE -- This Module
            MANDATORY-GROUPS {
                                ntSipNatGroupVer1
                             }
        ::= { ntSipCompliances 1 }

    -- ************************************************************************
    -- MIB variable grouping
    -- ************************************************************************
    ntSipGroups OBJECT IDENTIFIER ::= { ntSipConformance 2 }

    ntSipNatGroupVer1 OBJECT-GROUP
        OBJECTS {
                    ntSipNatPingTimeout
                }
        STATUS      current
        DESCRIPTION "This group holds the objects related to the NAT traversal
                     scheme defined in draft-sen-midcom-fw-nat-00.txt. Feature
                     used under licence from Nortel Networks Inc."
        ::= { ntSipGroups 10 }

END
