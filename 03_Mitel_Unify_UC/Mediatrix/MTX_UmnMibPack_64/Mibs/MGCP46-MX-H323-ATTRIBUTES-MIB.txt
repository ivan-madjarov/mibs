-- **SDOC***********************************************************************
-- *****************************************************************************
--
--             Copyright(c) 2003 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part, in
--   any form whatsoever without written prior approval by
--   Mediatrix Telecom, Inc.
--
--   Mediatrix Telecom, Inc. reserves the right to revise this publication
--   and make changes at any time and without the obligation to notify any
--   person and/or entity of such revisions and/or changes.
--
-- *****************************************************************************
-- *****************************************************************************
--
-- Configuration of signaling and telephony attributes of a H.323 unit. Applies
-- to H.323 terminals and H.323 gateways.
--
-- A H.323 terminal is a unit with only FXS ports. A H.323 gateway is a unit
-- with only FXO ports.
--
-- *****************************************************************************
-- **EDOC***********************************************************************

MGCP46-MX-H323-ATTRIBUTES-MIB
DEFINITIONS ::= BEGIN

IMPORTS
        OBJECT-TYPE,
        MODULE-IDENTITY,
        OBJECT-IDENTITY
    FROM SNMPv2-SMI
        OBJECT-GROUP,
        NOTIFICATION-GROUP,
        MODULE-COMPLIANCE
    FROM SNMPv2-CONF
        MxEnableState,
        MxIpAddress,
        MxIpPort,
        MxIpDhcpSiteSpecificCode
    FROM MX-TC
        ifIndex
    FROM RFC1213-MIB
        h323,
        ipAddressStatusH323,
        ipAddressConfigH323Static,
        ipAddressConfigH323Dhcp
    FROM MX-H323-MIB;

h323AttributesMIB MODULE-IDENTITY
    LAST-UPDATED "0305050000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains H.323 configuration objects."

    -- *************************************************************************
    -- Revision history
    -- *************************************************************************
    REVISION    "0305050000Z"
    DESCRIPTION "May 5, 2003
                     Added h323AttributesDirectGatewayCallHost.
                     Removed h323DirectGatewayCallHost, h323DirectGatewayCallPort,
                     h323DirectGatewayCallDhcpSiteSpecificCode and
                     h323DirectGatewayCallStaticPort.
                 March 4, 2003
                   Creation"
    ::= { h323 5 }

    -- *************************************************************************
    -- General H323 signaling configuration
    -- *************************************************************************

h323AttributesMIBObjects  OBJECT IDENTIFIER ::= { h323AttributesMIB 1 }
h323AttributesConformance OBJECT IDENTIFIER ::= { h323AttributesMIB 2 }

    -- *************************************************************************
    -- H.323 Signaling attributes table
    -- *************************************************************************

    h323IfSignalingAttributesTable OBJECT-TYPE
        SYNTAX      SEQUENCE OF H323IfSignalingAttributesEntry
        MAX-ACCESS  not-accessible
        STATUS      current
        DESCRIPTION "This table holds signaling attributes of a H.323 unit. This configuration
                     applies to both terminal and gateway lines.

                     Each row is used to configure the signaling attributes of one line."
        ::= { h323AttributesMIBObjects 5 }

        h323IfSignalingAttributesEntry OBJECT-TYPE
            SYNTAX      H323IfSignalingAttributesEntry
            MAX-ACCESS  not-accessible
            STATUS      current
            DESCRIPTION "Each row is used to configure the signaling attributes of one line."
            INDEX       { ifIndex }
            ::= { h323IfSignalingAttributesTable 1 }

            H323IfSignalingAttributesEntry ::= SEQUENCE
                {
                    h323AttributesEarlyH245Enable         MxEnableState,
                    h323AttributesH245TunnelingEnable     MxEnableState,
                    h323AttributesFastConnectEnable       MxEnableState
                }

        h323AttributesEarlyH245Enable OBJECT-TYPE
            SYNTAX      MxEnableState
            MAX-ACCESS  read-write
            STATUS      current
            DESCRIPTION "With the early H.245 procedure, the line includes its H.245 address in the SETUP
                         message (when making a call) or in the CONNECT message (when receiving a call).
                         This H.245 address may be used by the remote endpoint to open a H.245
                         connection. The H.245 connection may be opened before the call is connected,
                         thus the qualification of 'early' H.245.

                         disable : the line does not use the early H.245 procedure.

                         enable  : the line uses the early H.245 procedure."
            DEFVAL { enable }
            ::=  {  h323IfSignalingAttributesEntry 5 }

        h323AttributesH245TunnelingEnable OBJECT-TYPE
            SYNTAX      MxEnableState
            MAX-ACCESS  read-write
            STATUS      current
            DESCRIPTION "When tunneling is enabled, the line sends H.245 messages within Q.931 messages.

                         When H.245 is enabled and the line is the calling endpoint:

                            - The line offers the use of H.245 tunneling by setting the h245Tunneling
                              field to true in the SETUP message.

                            - If the called endpoint accepts the use of H.245 tunneling, the line sets
                              the h245Tunneling field to true in every subsequent Q.931 messages.

                            - If the called endpoint refuses the use of H.245 tunneling, the line stops
                              using H.245 tunneling. The line considers the H.245 messages sent in the
                              SETUP message as ignored by the called endpoint.

                         When H.245 is disabled and the line is the calling endpoint:

                            - The line does not offer the use of H.245 tunneling. The line sets the
                              h245Tunneling field to false in every Q.931 messages.

                         When H.245 is enabled and the line is the called endpoint:

                            - When offered, the line accepts the use of H.245 tunneling. The line sets
                              the h245Tunneling field to true in the first Q.931 message sent as
                              response to the SETUP message. The line sets the h245Tunneling field to
                              true in every subsequent Q.931 messages.

                         When H.245 is disabled and the line is the called endpoint:

                            - When offered, the line refuses the use of H.245 tunneling. The line sets
                              the h245Tunneling field to false in every Q.931 messages.

                         When the line is the called endpoint, it does not use H.245 tunneling if it was
                         not offered by the calling endpoint.

                         disable : the line does not use H.245 tunneling.

                         enable  : the line uses H.245 tunneling."
            DEFVAL { disable }
            ::=  {  h323IfSignalingAttributesEntry 10 }

        h323AttributesFastConnectEnable OBJECT-TYPE
            SYNTAX      MxEnableState
            MAX-ACCESS  read-write
            STATUS      current
            DESCRIPTION "The Fast Connect procedure allows two H.323 endpoints to establish a call with
                         as few as one round-trip message exchange, enabling immediate media stream
                         delivery upon call connection.

                         When making a call, the line includes the fastStart element in the SETUP
                         message.

                         When receiving a call, the line includes the fastStart element in the ALERTING
                         message.

                         The fastStart element contains the voice and data capabilities supported by the
                         line.

                         disable : the line does not use the Fast Connect procedure.

                         enable  : the line uses the Fast Connect procedure."
            DEFVAL { enable }
            ::=  {  h323IfSignalingAttributesEntry 15 }

    -- *************************************************************************
    -- H.323 telephony attributes table
    -- *************************************************************************

    h323IfTelephonyAttributesTable OBJECT-TYPE
        SYNTAX      SEQUENCE OF H323IfTelephonyAttributesEntry
        MAX-ACCESS  not-accessible
        STATUS      current
        DESCRIPTION "This table holds telephony attributes of a H.323 unit. This configuration
                     applies to both terminal and gateway lines.

                     Each row is used to configure the telephony attributes of one line."
        ::= { h323AttributesMIBObjects 10 }

        h323IfTelephonyAttributesEntry OBJECT-TYPE
            SYNTAX      H323IfTelephonyAttributesEntry
            MAX-ACCESS  not-accessible
            STATUS      current
            DESCRIPTION "Each row is used to configure the telephony attributes of one line."
            INDEX       { ifIndex }
            ::= { h323IfTelephonyAttributesTable 1 }

            H323IfTelephonyAttributesEntry ::= SEQUENCE
                {
                    h323AttributesDirectGatewayCallEnable MxEnableState,
                    h323AttributesDirectGatewayCallHost MxIpAddress
                }

        h323AttributesDirectGatewayCallEnable OBJECT-TYPE
            SYNTAX      MxEnableState
            MAX-ACCESS  read-write
            STATUS      current
            DESCRIPTION "The 'Direct Gateway Call' is a Mediatrix proprietary procedure. The line is
                         configured with the IP address of a gateway.

                         This procedure applies only to lines that are not configured to register:

                            - The unit is configured with the multiple registration method and the
                              registration for the line is disabled.

                            OR

                            - The unit is configured with the none registration method.

                         This procedure allows the use of a gateway without the presence of a
                         gatekeeper. The user simply dials a telephone number. The new outgoing call
                         goes directly to the gateway. The telephone number is the call destination on
                         the SCN side. This procedure is not used if the user dials an IP address before
                         dialing a telephone number.

                         disable : the line does not use the 'Direct Gateway Call' procedure.

                         enable  : the line uses the 'Direct Gateway Call' procedure."
            DEFVAL { disable }
            ::=  {  h323IfTelephonyAttributesEntry 5 }

        h323AttributesDirectGatewayCallHost OBJECT-TYPE
        SYNTAX      MxIpAddress
        MAX-ACCESS  read-write
        STATUS      current
        DESCRIPTION "The IP address of the gateway used in the 'Direct Gateway Call' procedure.

                     The 'Direct Gateway Call' is a Mediatrix proprietary procedure. It allows the
                     use of a gateway without the presence of a gatekeeper. The user simply dials a
                     telephone number. The new outgoing call goes directly to the gateway. The
                     telephone number is the call destination on the SCN side. This procedure is not
                     used if the user dials an IP address before dialing a telephone number.

                     This procedure applies only to lines with the following configuration:

                        - Multiple registration method

                        - Registration disabled"
        DEFVAL { "" }
            ::=  {  h323IfTelephonyAttributesEntry 10 }

    -- *************************************************************************
    -- Conformance information
    -- *************************************************************************

    h323AttributesCompliances OBJECT IDENTIFIER ::= { h323AttributesConformance 1 }

        h323AttributesBasicComplVer1 MODULE-COMPLIANCE
            STATUS      current
            DESCRIPTION "This is a list of conformance groups. These conformance groups contain the name
                         of objects necessary to adequately configure a H.323 unit."
            MODULE      -- MGCP46-MX-H323-ATTRIBUTES-MIB
            MANDATORY-GROUPS {
                               h323AttributesSignalingGroupVer1,
                               h323AttributesTelephonyGroupVer1
                             }
            ::= { h323AttributesCompliances 5 }

    -- *************************************************************************
    -- MIB variable grouping
    -- *************************************************************************

    h323AttributesGroups OBJECT IDENTIFIER ::= { h323AttributesConformance 2 }

        h323AttributesSignalingGroupVer1 OBJECT-GROUP
            OBJECTS {
                        h323AttributesEarlyH245Enable,
                        h323AttributesH245TunnelingEnable,
                        h323AttributesFastConnectEnable
                    }
            STATUS      current
            DESCRIPTION "A list of objects used to configure some call signaling features of a H.323
                         unit."
            ::= { h323AttributesGroups 5 }

        h323AttributesTelephonyGroupVer1 OBJECT-GROUP
            OBJECTS {
                       h323AttributesDirectGatewayCallEnable,
                       h323AttributesDirectGatewayCallHost
                    }
            STATUS      current
            DESCRIPTION "A list of objects used to configure the 'Direct Gateway Call' procedure for a
                         H.323 unit."
            ::= { h323AttributesGroups 10 }

END
