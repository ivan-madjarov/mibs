-- ****************************************************************************
-- ****************************************************************************
--
--             Copyright(c) 2001-2002 Mediatrix Telecom, Inc. 
--
--  NOTICE:
--   This document contains information that is confidential and proprietary
--   to Mediatrix Telecom, Inc. 
--
--   Mediatrix Telecom, Inc. reserves all rights to this document as well as
--   to the Intellectual Property of the document and the technology and
--   know how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

MGCP44-MX-DEBUG-MIB
DEFINITIONS ::= BEGIN

IMPORTS
        MODULE-IDENTITY,
        OBJECT-TYPE
    FROM SNMPv2-SMI
        MODULE-COMPLIANCE,
        OBJECT-GROUP
    FROM SNMPv2-CONF
        MxIpHostName,
        MxIpPort
    FROM MX-TC
        mediatrixExperimental
    FROM MX-SMI;

mxDebugMIB MODULE-IDENTITY
    LAST-UPDATED "0207050000Z"
    ORGANIZATION "Mediatrix Telecom, Inc."
    CONTACT-INFO "Mediatrix Telecom, Inc. 
                  4229, Garlock Street
                  Sherbrooke (Quebec)
                  Canada
                  Phone: (819) 829-8749
                  "
    DESCRIPTION "This MIB contains debug-related objects for Mediatrix products."

    -- ************************************************************************
    -- Revision history
    -- ************************************************************************
    REVISION    "0207050000Z"
    DESCRIPTION "July 5, 2002
                    Renamed signalingLog        to mxDebugSignalingLog
                            signalingLogEnable  to mxDebugSignalingLogEnable
                            signalingLogHost    to mxDebugSignalingLogHost
                            signalingLogPort    to mxDebugSignalingLogPort
                    to align with the coding guidelines
                 June 26, 2002
                    Added the OBJECT IDENTIFIERs:
                        - mxDebugFax
                    Added the MIB variables:
                        - mxDebugT38OutgoingToSyslog
                        - mxDebugT38IncomingToSyslog
                        - mxDebugFaxRelayForDspToSyslog
                        - mxDebugFaxRelayFromDspToSyslog
                    Added Conformance and OBJECT-GROUPs
                 August 03, 2001
                    Creation"
    ::= { mediatrixExperimental 5 }

mxDebugMIBObjects  OBJECT IDENTIFIER ::= { mxDebugMIB 1 }
mxDebugConformance OBJECT IDENTIFIER ::= { mxDebugMIB 2 }

mxDebugSignalingLog             OBJECT IDENTIFIER  ::= { mxDebugMIBObjects  5 }

    mxDebugSignalingLogEnable OBJECT-TYPE
        SYNTAX      INTEGER {
                              disable(0),
                              enable(1)
                            }
        MAX-ACCESS  read-write
        STATUS      current
        DESCRIPTION "Enable the logging client debugging tool for IP telephony 
                     signaling."
        DEFVAL      { disable }
        ::=  {  mxDebugSignalingLog  1  }

    mxDebugSignalingLogHost OBJECT-TYPE
        SYNTAX      MxIpHostName
        MAX-ACCESS  read-write
        STATUS      current
        DESCRIPTION "Logging client IP address or domain name."
        DEFVAL { "192.168.0.10" }
        ::=  {  mxDebugSignalingLog  2 }

    mxDebugSignalingLogPort OBJECT-TYPE
        SYNTAX      MxIpPort
        MAX-ACCESS  read-write
        STATUS      current
        DESCRIPTION "Logging client IP port number."
        DEFVAL      { 6000 }
        ::=  {  mxDebugSignalingLog  3  }

    -- ********************************************************************
    -- Fax debugging
    -- ********************************************************************
mxDebugFax              OBJECT IDENTIFIER  ::= { mxDebugMIBObjects  10 }

    -- ********************************************************************
    -- T.38 debugging using syslog
    -- ********************************************************************
    mxDebugT38OutgoingToSyslog OBJECT-TYPE
        SYNTAX      INTEGER {
                              disable(0),
                              enable(1)
                            }
        MAX-ACCESS  read-write
        STATUS      current
        DESCRIPTION "Syslog T.38 outgoing data"
        DEFVAL      { disable }
        ::=  {  mxDebugFax  5  }

    mxDebugT38IncomingToSyslog OBJECT-TYPE
        SYNTAX      INTEGER {
                              disable(0),
                              enable(1)
                            }
        MAX-ACCESS  read-write
        STATUS      current
        DESCRIPTION "Syslog T.38 incoming data"
        DEFVAL { disable }
        ::=  {  mxDebugFax  6 }

    -- ********************************************************************
    -- Fax relay debugging using syslog
    -- ********************************************************************
    mxDebugFaxRelayForDspToSyslog OBJECT-TYPE
        SYNTAX      INTEGER {
                              disable(0),
                              enable(1)
                            }
        MAX-ACCESS  read-write
        STATUS      current
        DESCRIPTION "Syslog fax relay data sent to DSPs"
        DEFVAL      { disable }
        ::=  {  mxDebugFax  15 }

    mxDebugFaxRelayFromDspToSyslog OBJECT-TYPE
        SYNTAX      INTEGER {
                              disable(0),
                              enable(1)
                            }
        MAX-ACCESS  read-write
        STATUS      current
        DESCRIPTION "Syslog fax relay data received from DSPs"
        DEFVAL      { disable }
        ::=  {  mxDebugFax  16 }

    -- ************************************************************************
    -- Conformance information
    -- ************************************************************************
    mxDebugCompliances OBJECT IDENTIFIER ::= { mxDebugConformance 1 }

    mxDebugComplVer1 MODULE-COMPLIANCE
        STATUS      current
        DESCRIPTION     
            "List of groups required to support debug parameters."
        MODULE -- This Module
            MANDATORY-GROUPS { 
                                 mxDebugSignalingLogGroupVer1,
                                 mxDebugFaxGroupVer1
                             }
        ::= { mxDebugCompliances 10 }

    -- ************************************************************************
    -- MIB variable grouping
    -- ************************************************************************
    mxDebugGroups OBJECT IDENTIFIER ::= { mxDebugConformance 2 }

    mxDebugSignalingLogGroupVer1 OBJECT-GROUP
        OBJECTS {
                    mxDebugSignalingLogEnable,
                    mxDebugSignalingLogHost,
                    mxDebugSignalingLogPort
                }
        STATUS current
        DESCRIPTION
            "A collection of objects that defines a list related to signaling log."
        ::= { mxDebugGroups 10 }
        
    mxDebugFaxGroupVer1 OBJECT-GROUP
        OBJECTS {        
                    mxDebugT38OutgoingToSyslog,
                    mxDebugT38IncomingToSyslog,
                    mxDebugFaxRelayForDspToSyslog,
                    mxDebugFaxRelayFromDspToSyslog
                }
        STATUS current
        DESCRIPTION
            "A collection of objects that defines the T.38 syslog activation"
        ::= { mxDebugGroups 20 }

END
