-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************

DGW20-MX-CROUT-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

cRoutMIB MODULE-IDENTITY
 LAST-UPDATED   "1905090000Z"
 ORGANIZATION " Mediatrix Telecom, Inc. "
 CONTACT-INFO " Mediatrix Telecom, Inc.
                4229, Garlock Street
                Sherbrooke (Quebec)
                Canada
                Phone: (819) 829-8749
                "
 DESCRIPTION  " Call Routing

                The Call Routing (CRout) service transforms properties and
                routes calls between telephony interfaces and SIP endpoints.
                "
 ::= { mediatrixServices 1750 }

cRoutMIBObjects OBJECT IDENTIFIER ::= { cRoutMIB 1 }

-- ****************************************************************************

-- Group:Status Group

-- ****************************************************************************

statusGroup OBJECT IDENTIFIER
 ::= { cRoutMIBObjects 100 }
 -- Scalar:Configuration Modified Status

 configModifiedStatus OBJECT-TYPE
  SYNTAX        INTEGER { yes(100) , no(200) }
  MAX-ACCESS    read-only
  STATUS        current
  DESCRIPTION " Configuration Modified Status

                Indicates if the call routing configuration has been modified
                without being applied.

                 1. Yes: The configuration has been modified but has not been
                    applied.
                 2. No: The call routing service uses the most recent call
                    routing configuration.

                Use the ApplyConfig command to apply the configuration.

                "
  ::= { statusGroup 100 }

 -- ***************************************************************************
 
 -- Table:Available Interfaces

 -- ***************************************************************************
 
 interfaceStatusTable OBJECT-TYPE
  SYNTAX        SEQUENCE OF InterfaceStatusEntry
  MAX-ACCESS    not-accessible
  STATUS        current
  DESCRIPTION " Available Interfaces

                This table shows the SIP and ISDN interfaces currently
                available.
                "
  ::= { statusGroup 200 }
  interfaceStatusEntry OBJECT-TYPE
   SYNTAX        InterfaceStatusEntry
   MAX-ACCESS    not-accessible
   STATUS        current
   DESCRIPTION " A row in table Available Interfaces. "
   INDEX         {
                   interfaceStatusIndex
                 }

   ::= { interfaceStatusTable 1 }

  InterfaceStatusEntry ::= SEQUENCE
  {
    interfaceStatusIndex Unsigned32,
    interfaceStatusName  OCTET STRING
  }

  -- Index:Row Index

  interfaceStatusIndex OBJECT-TYPE
   SYNTAX        Unsigned32
   MAX-ACCESS    read-only
   STATUS        current
   DESCRIPTION " Row Index

                 Unique identifier of the row in the table.
                 "
   ::= { interfaceStatusEntry 100 }

  -- Columnar:Name

  interfaceStatusName OBJECT-TYPE
   SYNTAX        OCTET STRING
   MAX-ACCESS    read-only
   STATUS        current
   DESCRIPTION " Name

                 Name of the interface.

                 The name may have the following format:

                   * sip-'name': SIP interface with the name 'name'
                   * isdn-'name': ISDN interface with the name 'name'
                   * r2-'name': R2 interface with the name 'name'
                   * e&m-'name': E&M interface with the name 'name'
                   * fxs-'name': FXS interface with the name 'name'
                   * fxo-'name': FXO interface with the name 'name'

                 "
   ::= { interfaceStatusEntry 200 }

 -- End of table:Available Interfaces

 -- ***************************************************************************
 
 -- Table:Routes

 -- ***************************************************************************
 
 routeStatusTable OBJECT-TYPE
  SYNTAX            SEQUENCE OF RouteStatusEntry
  MAX-ACCESS        not-accessible
  STATUS            current
  DESCRIPTION     " Routes

                    This table shows the actual route used by the call routing
                    service.
                    "
  ::= { statusGroup 300 }
  routeStatusEntry OBJECT-TYPE
   SYNTAX        RouteStatusEntry
   MAX-ACCESS    not-accessible
   STATUS        current
   DESCRIPTION " A row in table Routes. "
   INDEX         {
                   routeStatusIndex
                 }

   ::= { routeStatusTable 1 }

  RouteStatusEntry ::= SEQUENCE
  {
    routeStatusIndex               Unsigned32,
    routeStatusType                INTEGER,
    routeStatusSourceCriteria      OCTET STRING,
    routeStatusPropertiesCriteria  INTEGER,
    routeStatusExpressionCriteria  OCTET STRING,
    routeStatusDestination         OCTET STRING,
    routeStatusMappings            OCTET STRING,
    routeStatusSignalingProperties OCTET STRING
  }

  -- Index:Index

  routeStatusIndex OBJECT-TYPE
   SYNTAX        Unsigned32
   MAX-ACCESS    read-only
   STATUS        current
   DESCRIPTION " Index

                 Unique identifier of the row in the table.
                 "
   ::= { routeStatusEntry 100 }

  -- Columnar:Type

  routeStatusType OBJECT-TYPE
   SYNTAX        INTEGER { user(100) , auto(200) }
   MAX-ACCESS    read-only
   STATUS        current
   DESCRIPTION " Type

                 Displays the type of route based on their origin:

                   * user: The route is manually defined and entered by a
                     user.
                   * auto: The route is automatically generated following the
                     activation of the auto-routing feature (see the
                     autoRoutingEnable parameter).

                 "
   ::= { routeStatusEntry 150 }

  -- Columnar:Sources

  routeStatusSourceCriteria OBJECT-TYPE
   SYNTAX        OCTET STRING
   MAX-ACCESS    read-only
   STATUS        current
   DESCRIPTION " Sources

                 The source compared against the criteria property to
                 determine if the route can be used.

                 The source of the call can be:

                   * route-'name': the route 'name'
                   * sip-'name': the SIP interface 'name'
                   * isdn-'name': the ISDN interface 'name'
                   * r2-'name': the R2 interface 'name'
                   * e&m-'name': the E&M interface 'name'
                   * fxs-'name': the FXS interface 'name'
                   * fxo-'name': the FXO interface 'name'

                 "
   ::= { routeStatusEntry 200 }

  -- Columnar:Criteria Property

  routeStatusPropertiesCriteria OBJECT-TYPE
   SYNTAX        INTEGER { none(100) , calledE164(200) , callingE164(300) ,
                 calledName(400) , callingName(500) , calledTon(600) ,
                 callingTon(700) , calledNpi(800) , callingNpi(900) ,
                 calledHost(1000) , callingHost(1100) , callingPi(1200) ,
                 callingSi(1300) , callingItc(1400) , calledUri(1500) ,
                 callingUri(1600) , dateTime(1700) , calledPhoneContext(1800)
                 , callingPhoneContext(1900) , calledSipUsername(2000) ,
                 callingSipUsername(2100) , calledBearerChannel(2200) ,
                 callingBearerChannel(2300) , callingSipPrivacy(2400) }
   MAX-ACCESS    read-only
   STATUS        current
   DESCRIPTION " Criteria Property

                 The call property part of the criteria used to determine if
                 the route can be applied or not. The other part of the
                 criteria is the expression defined in the
                 RouteStatus.ExpressionCriteria parameter.

                 The Call Property on which the route matching criteria is
                 based on:

                   * CalledE164: the called party E.164 properties
                   * CallingE164: the calling party E.164 properties
                   * CalledName: the called party name properties
                   * CallingName: the calling party name properties
                   * CalledTon: the called party type of number properties
                   * CallingTon: the calling party type of number properties
                   * CalledNpi: the called party numbering plan indicator
                     properties
                   * CallingNpi: the calling party numbering plan indicator
                     properties
                   * CalledHost: the calling host properties
                   * CallingHost: the called host properties
                   * CallingPi: the calling party presentation indicator.
                   * CallingSi: the calling party screening indicator
                   * CallingItc: the calling party information transfer
                     capability
                   * CalledUri: the called party SIP URI
                   * CallingUri: the calling party SIP URI
                   * DateTime: the date and/or time the call arrived at the
                     call router
                   * CalledPhoneContext: the called party phone context
                   * CallingPhoneContext: the calling party phone context
                   * CalledSipUsername: the called SIP username
                   * CallingSipUsername: the calling SIP username
                   * CalledBearerChannel: the called bearer channel properties
                   * CallingBearerChannel: the calling bearer channel
                     properties
                   * CallingSipPrivacy: the calling SIP privacy properties

                 See RouteStatus.ExpressionCriteria.

                 "
   ::= { routeStatusEntry 300 }

  -- Columnar:Criteria Rule

  routeStatusExpressionCriteria OBJECT-TYPE
   SYNTAX        OCTET STRING
   MAX-ACCESS    read-only
   STATUS        current
   DESCRIPTION " Criteria Rule

                 The expression part of the criteria used to determine if the
                 route can be applied or not. The other part of the criteria
                 is the call property defined in the
                 RouteStatus.PropertiesCriteria parameter.

                 The expression syntax is related to the selected criteria
                 properties or can be a special tag:

                   * CalledE164: Regular expression
                   * CallingE164: Regular expression
                   * CalledName: Regular expression
                   * CallingName: Regular expression
                   * CalledTon: 'unknown', 'international', 'national',
                     'network', 'subscriber', or 'abbreviated'
                   * CallingTon: 'unknown', 'international', 'national',
                     'network', 'subscriber', or 'abbreviated'
                   * CalledNpi: 'unknown', 'isdn', 'data', 'telex',
                     'national', or 'private'
                   * CallingNpi: 'unknown', 'isdn', 'data', 'telex',
                     'national', or 'private'
                   * CalledHost: Regular expression. The format is 'Fqdn
                     [:port]'. If the '[:port]' is not present, the table uses
                     the well-known port of the signaling protocol.
                   * CallingHost: Regular expression. The format is 'Fqdn
                     [:port]'. If the '[:port]' is not present, the table uses
                     the well-known port of the signaling protocol.
                   * CallingPi: 'allowed', 'restricted', or 'interworking'
                   * CallingSi: 'not-screened', 'passed', 'failed', or
                     'network'
                   * CallingItc: 'speech', 'unrestricted', 'restricted',
                     '3.1Khz', 'udi-ta', or 'video'
                   * CalledUri: Regular expression
                   * CallingUri: Regular expression
                   * DateTime: Day of week and time period and/or date and
                     time period
                   * CalledPhoneContext: Regular expression
                   * CallingPhoneContext: Regular expression
                   * CalledSipUsername: Regular expression
                   * CallingSipUsername: Regular expression
                   * CalledBearerChannel: Regular expression
                   * CallingBearerChannel: Regular expression
                   * CallingSipPrivacy: 'disabled', 'none', or 'id'

                 Special tags:

                   * <undefined>: Matches if the property is not defined for
                     the call.
                   * <default>: Always matches. Generally used to set a
                     default route if the previous criteria did not match.

                 Accepted DateTime formats:

                 Date/Time Period format:

                   * 'DD.MM.YYYY/HH:MM:SS-DD.MM.YYYY/HH:MM:SS'
                   * 'DD.MM.YYYY/HH:MM:SS-HH:MM:SS'
                   * 'DD.MM.YYYY-DD.MM.YYYY'
                   * 'DD.MM.YYYY'
                   * 'HH:MM:SS-HH:MM:SS'

                 Week Day/Time period format:

                   * 'DDD'
                   * 'DDD,DDD...'
                   * 'DDD/HH:MM:SS-HH:MM:SS'
                   * 'DDD,DDD.../HH:MM:SS-HH:MM:SS'

                 where DDD must be one of: SUN, MON, TUE, WED, THU, FRI, or
                 SAT.

                 Several of the previous formats can be concatenated to form
                 one expression. They must be separated by |. Example:
                 25.12.2006 | SUN

                 Note: Whitespace at the end of a regular expression is
                 ignored.

                 See RouteStatus.PropertiesCriteria.

                 "
   ::= { routeStatusEntry 400 }

  -- Columnar:Destination

  routeStatusDestination OBJECT-TYPE
   SYNTAX        OCTET STRING
   MAX-ACCESS    read-only
   STATUS        current
   DESCRIPTION " Destination

                 Destination to apply to the call if it matches the criteria.

                 The destination can be set to:

                   * route-'name': the route 'name'
                   * hunt-'name': the hunt 'name'
                   * sip-'name': the SIP interface 'name'
                   * isdn-'name': the ISDN interface 'name'
                   * r2-'name': the R2 interface 'name'
                   * e&m-'name': the E&M interface 'name'
                   * fxs-'name': the FXS interface 'name'
                   * fxo-'name': the FXO interface 'name'
                   * SipRedirect-'name': When the Route source is a SIP
                     interface, incoming SIP Invites are replied with a 302
                     'Moved Temporarily' SIP response.

                 "
   ::= { routeStatusEntry 500 }

  -- Columnar:Transformations

  routeStatusMappings OBJECT-TYPE
   SYNTAX        OCTET STRING
   MAX-ACCESS    read-only
   STATUS        current
   DESCRIPTION " Transformations

                 Name of the transformations to apply to the call if the
                 criteria matches. The transformations are executed before
                 sending the call to the new destination.

                 More than one transformation can be specified. In this case,
                 the transformations are separated with ',' and are executed
                 in sequential order.

                 "
   ::= { routeStatusEntry 600 }

  -- Columnar:Signaling Properties

  routeStatusSignalingProperties OBJECT-TYPE
   SYNTAX        OCTET STRING
   MAX-ACCESS    read-only
   STATUS        current
   DESCRIPTION " Signaling Properties

                 Name of the signaling properties to apply to the call.
                 "
   ::= { routeStatusEntry 700 }

 -- End of table:Routes

 -- ***************************************************************************
 
 -- Table:Transformations

 -- ***************************************************************************
 
 mappingTypeStatusTable OBJECT-TYPE
  SYNTAX        SEQUENCE OF MappingTypeStatusEntry
  MAX-ACCESS    not-accessible
  STATUS        current
  DESCRIPTION " Transformations

                This table shows which Call Properties are involved in the
                transformations currently in use by the call routing service.
                The Transformation Rules (MappingExpressionStatus) table shows
                the detailed rules related to each transformation.

                "
  ::= { statusGroup 400 }
  mappingTypeStatusEntry OBJECT-TYPE
   SYNTAX        MappingTypeStatusEntry
   MAX-ACCESS    not-accessible
   STATUS        current
   DESCRIPTION " A row in table Transformations. "
   INDEX         {
                   mappingTypeStatusIndex
                 }

   ::= { mappingTypeStatusTable 1 }

  MappingTypeStatusEntry ::= SEQUENCE
  {
    mappingTypeStatusIndex          Unsigned32,
    mappingTypeStatusName           OCTET STRING,
    mappingTypeStatusCriteria       INTEGER,
    mappingTypeStatusTransformation INTEGER
  }

  -- Index:Index

  mappingTypeStatusIndex OBJECT-TYPE
   SYNTAX        Unsigned32
   MAX-ACCESS    read-only
   STATUS        current
   DESCRIPTION " Index

                 Unique identifier of the row in the table.
                 "
   ::= { mappingTypeStatusEntry 100 }

  -- Columnar:Name

  mappingTypeStatusName OBJECT-TYPE
   SYNTAX        OCTET STRING
   MAX-ACCESS    read-only
   STATUS        current
   DESCRIPTION " Name

                 Name of the call property transformations defined by this
                 row.

                 The name of the call property transformation is unique in the
                 table.

                 See RouteStatus.Mapping

                 "
   ::= { mappingTypeStatusEntry 200 }

  -- Columnar:Criteria Property

  mappingTypeStatusCriteria OBJECT-TYPE
   SYNTAX        INTEGER { none(100) , e164(200) , calledE164(300) ,
                 callingE164(400) , name(500) , calledName(600) , callingName
                 (700) , ton(800) , calledTon(900) , callingTon(1000) , npi
                 (1100) , calledNpi(1200) , callingNpi(1300) , host(1400) ,
                 calledHost(1500) , callingHost(1600) , callingPi(1700) ,
                 callingSi(1800) , callingItc(1900) , uri(2000) , calledUri
                 (2100) , callingUri(2200) , dateTime(2300) , phoneContext
                 (2400) , calledPhoneContext(2500) , callingPhoneContext(2600)
                 , sipUsername(2700) , calledSipUsername(2800) ,
                 callingSipUsername(2900) , lastDivertingReason(3000) ,
                 lastDivertingE164(3100) , lastDivertingPartyNumberType(3110)
                 , lastDivertingPublicTypeOfNumber(3120) ,
                 lastDivertingPrivateTypeOfNumber(3130) ,
                 lastDivertingNumberPresentation(3140) ,
                 originalDivertingReason(3200) , originalDivertingE164(3300) ,
                 originalDivertingPartyNumberType(3400) ,
                 originalDivertingPublicTypeOfNumber(3500) ,
                 originalDivertingPrivateTypeOfNumber(3600) ,
                 originalDivertingNumberPresentation(3700) ,
                 calledBearerChannel(3800) , callingBearerChannel(3900) ,
                 callingSipPrivacy(4000) }
   MAX-ACCESS    read-only
   STATUS        current
   DESCRIPTION " Criteria Property

                 The call property part of the criteria used to determine if
                 the transformation can be applied or not. The other part of
                 the criteria is the expression defined in the
                 MappingExpressionStatus.Criteria parameter.

                 The call properties can be:

                   * E164: called or calling E.164 properties
                   * CalledE164: called E.164 properties
                   * CallingE164: calling E.164 properties
                   * Name: called or calling name properties.
                   * CalledName: called name properties
                   * CallingName: calling name properties
                   * Ton: called or calling type of number properties
                   * CalledTon: called type of number properties
                   * CallingTon: calling type of number properties
                   * Npi: called or calling numbering plan indicator
                     properties
                   * CalledNpi: called numbering plan indicator properties
                   * CallingNpi: calling numbering plan indicator properties
                   * Host: calling or called host properties
                   * CalledHost: calling host properties
                   * CallingHost: called host properties
                   * CallingPi: calling presentation indicator
                   * CallingSi: calling screening indicator
                   * CallingItc: calling information transfer capability
                   * Uri: calling or called SIP URI properties
                   * CalledUri: called SIP URI properties
                   * CallingUri: calling SIP URI properties
                   * DateTime: route calls based on the date and/or time the
                     call arrived at the call router
                   * PhoneContext: called or calling phone context properties
                   * CalledPhoneContext: called phone context properties
                   * CallingPhoneContext: calling phone context properties
                   * SipUsername: called or calling SIP username properties
                   * CalledSipUsername: called SIP username properties
                   * CallingSipUsername: calling SIP username properties
                   * LastDivertingReason: last diverting reason properties
                   * LastDivertingE164: last diverting E.164 properties
                   * LastDivertingPartyNumberType: party number type of the
                     last diverting number properties
                   * LastDivertingPublicTypeOfNumber: public type of number of
                     the last diverting number properties
                   * LastDivertingPrivateTypeOfNumber: private type of number
                     of the last diverting number properties
                   * LastDivertingNumberPresentation: presentation of the last
                     diverting number properties
                   * OriginalDivertingReason: original diverting reason
                     properties
                   * OriginalDivertingE164: original diverting E.164
                     properties
                   * OriginalDivertingPartyNumberType: party number type of
                     the original diverting number properties
                   * OriginalDivertingPublicTypeOfNumber: public type of
                     number of the original diverting number properties
                   * OriginalDivertingPrivateTypeOfNumber: private type of
                     number of the original diverting number properties
                   * OriginalDivertingNumberPresentation: presentation of the
                     original diverting number properties
                   * CalledBearerChannel: called bearer channel properties
                   * CallingBearerChannel: calling bearer channel properties
                   * CallingSipPrivacy: calling SIP privacy properties

                 See MappingExpressionStatus.Criteria.

                 "
   ::= { mappingTypeStatusEntry 300 }

  -- Columnar:Properties to Transform

  mappingTypeStatusTransformation OBJECT-TYPE
   SYNTAX        INTEGER { none(100) , e164(200) , calledE164(300) ,
                 callingE164(400) , name(500) , calledName(600) , callingName
                 (700) , ton(800) , calledTon(900) , callingTon(1000) , npi
                 (1100) , calledNpi(1200) , callingNpi(1300) , host(1400) ,
                 calledHost(1500) , callingHost(1600) , callingPi(1700) ,
                 callingSi(1800) , callingItc(1900) , uri(2000) , calledUri
                 (2100) , callingUri(2200) , phoneContext(2300) ,
                 calledPhoneContext(2400) , callingPhoneContext(2500) ,
                 sipUsername(2600) , calledSipUsername(2700) ,
                 callingSipUsername(2800) , lastDivertingReason(2900) ,
                 lastDivertingE164(3000) , lastDivertingPartyNumberType(3010)
                 , lastDivertingPublicTypeOfNumber(3020) ,
                 lastDivertingPrivateTypeOfNumber(3030) ,
                 lastDivertingNumberPresentation(3040) ,
                 originalDivertingReason(3100) , originalDivertingE164(3200) ,
                 originalDivertingPartyNumberType(3300) ,
                 originalDivertingPublicTypeOfNumber(3400) ,
                 originalDivertingPrivateTypeOfNumber(3500) ,
                 originalDivertingNumberPresentation(3600) ,
                 calledBearerChannel(3700) , callingBearerChannel(3800) ,
                 debug(60000) }
   MAX-ACCESS    read-only
   STATUS        current
   DESCRIPTION " Properties to Transform

                 Call properties to transform. The transformation is defined
                 in the MappingExpressionStatus.Transformation parameter.

                 The call properties can be:

                   * E164: called or calling E.164 properties
                   * CalledE164: called E.164 properties
                   * CallingE164: calling E.164 properties
                   * Name: called or calling name properties
                   * CalledName: called name properties
                   * CallingName: calling name properties
                   * Ton: called or calling type of number properties
                   * CalledTon: called type of number properties
                   * CallingTon: calling type of number properties
                   * Npi: called or calling numbering plan indicator
                     properties
                   * CalledNpi: called numbering plan indicator properties
                   * CallingNpi: calling numbering plan indicator properties
                   * Host: calling or called host properties
                   * CalledHost: calling host properties
                   * CallingHost: called host properties
                   * CallingPi: calling presentation indicator
                   * CallingSi: calling screening indicator
                   * CallingItc: calling information transfer capability
                   * Uri: calling or called SIP URI properties
                   * CalledUri: called SIP URI properties
                   * CallingUri: calling SIP URI properties
                   * PhoneContext: calling or called phone context properties
                   * CalledPhoneContext: called phone context properties
                   * CallingPhoneContext: calling phone context properties
                   * SipUsername: calling or called SIP username properties
                   * CalledSipUsername: called phone SIP username properties
                   * CallingSipUsername: calling phone SIP username properties
                   * LastDivertingReason: last diverting reason properties
                   * LastDivertingE164: last diverting E.164 properties
                   * LastDivertingPartyNumberType: party number type of the
                     last diverting number properties
                   * LastDivertingPublicTypeOfNumber: public type of number of
                     the last diverting number properties
                   * LastDivertingPrivateTypeOfNumber: private type of number
                     of the last diverting number properties
                   * LastDivertingNumberPresentation: presentation of the last
                     diverting number properties
                   * OriginalDivertingReason: original diverting reason
                     properties
                   * OriginalDivertingE164: original diverting E.164
                     properties
                   * OriginalDivertingPartyNumberType: party number type of
                     the original diverting number properties
                   * OriginalDivertingPublicTypeOfNumber: public type of
                     number of the original diverting number properties
                   * OriginalDivertingPrivateTypeOfNumber: private type of
                     number of the original diverting number properties
                   * OriginalDivertingNumberPresentation: presentation of the
                     original diverting number properties
                   * CalledBearerChannel: called bearer channel properties
                   * CallingBearerChannel: calling bearer channel properties
                   * Debug: reserved for debug configuration

                 See MappingExpressionStatus.Transformation.

                 "
   ::= { mappingTypeStatusEntry 400 }

 -- End of table:Transformations

 -- ***************************************************************************
 
 -- Table:Transformations

 -- ***************************************************************************
 
 mappingExpressionStatusTable OBJECT-TYPE
  SYNTAX        SEQUENCE OF MappingExpressionStatusEntry
  MAX-ACCESS    not-accessible
  STATUS        current
  DESCRIPTION " Transformations

                This table shows the definition of the actual transformations
                used by the call routing services.
                "
  ::= { statusGroup 500 }
  mappingExpressionStatusEntry OBJECT-TYPE
   SYNTAX        MappingExpressionStatusEntry
   MAX-ACCESS    not-accessible
   STATUS        current
   DESCRIPTION " A row in table Transformations. "
   INDEX         {
                   mappingExpressionStatusIndex
                 }

   ::= { mappingExpressionStatusTable 1 }

  MappingExpressionStatusEntry ::= SEQUENCE
  {
    mappingExpressionStatusIndex          Unsigned32,
    mappingExpressionStatusName           OCTET STRING,
    mappingExpressionStatusCriteria       OCTET STRING,
    mappingExpressionStatusTransformation OCTET STRING,
    mappingExpressionStatusSubMappings    OCTET STRING
  }

  -- Index:Row Index

  mappingExpressionStatusIndex OBJECT-TYPE
   SYNTAX        Unsigned32
   MAX-ACCESS    read-only
   STATUS        current
   DESCRIPTION " Row Index

                 Unique identifier of the row in the table.
                 "
   ::= { mappingExpressionStatusEntry 100 }

  -- Columnar:Name

  mappingExpressionStatusName OBJECT-TYPE
   SYNTAX        OCTET STRING
   MAX-ACCESS    read-only
   STATUS        current
   DESCRIPTION " Name

                 Name of the transformation defined by this row.

                 More than one row can have the same name. In this case, the
                 first row matching the call will be used. The rows are used
                 in ascending order.

                 See RouteStatus.Mapping.

                 "
   ::= { mappingExpressionStatusEntry 200 }

  -- Columnar:Criteria

  mappingExpressionStatusCriteria OBJECT-TYPE
   SYNTAX        OCTET STRING
   MAX-ACCESS    read-only
   STATUS        current
   DESCRIPTION " Criteria

                 The expression part of the criteria used to determine if the
                 transformation can be applied or not. The other part of the
                 criteria is the call property defined in the
                 MappingTypeStatus.Criteria parameter.

                 The expression syntax is related to the selected Criteria
                 call property or can be a special tag:

                   * E164: regular expression
                   * CalledE164: regular expression
                   * CallingE164: regular expression
                   * Name: regular expression
                   * CalledName: regular expression
                   * CallingName: regular expression
                   * Ton: 'unknown', 'international', 'national', 'network',
                     'subscriber', or 'abbreviated'
                   * CalledTon: 'unknown', 'international', 'national',
                     'network', 'subscriber', or 'abbreviated'
                   * CallingTon: 'unknown', 'international', 'national',
                     'network', 'subscriber', or 'abbreviated'
                   * Npi: 'unknown', 'isdn', 'data', 'telex', 'national', or
                     'private'
                   * CalledNpi: 'unknown', 'isdn', 'data', 'telex',
                     'national', or 'private'
                   * CallingNpi: 'unknown', 'isdn', 'data', 'telex',
                     'national', or 'private'
                   * Host: Regular expression. The call property format is
                     'Fqdn[:port]'. If the '[:port]' is not present, the table
                     uses the well-known port of the signaling protocol.
                   * CalledHost: Regular expression. The call property format
                     is 'Fqdn[:port]'. If the '[:port]' is not present, the
                     table uses the well-known port of the signaling protocol.
                   * CallingHost: Regular expression. The call property format
                     is 'Fqdn[:port]'. If the '[:port]' is not present, the
                     table uses the well-known port of the signaling protocol.
                   * CallingPi: 'allowed', 'restricted', or 'interworking'
                   * CallingSi: 'not-screened', 'passed', 'failed', or
                     'network'
                   * CallingItc: 'speech', 'unrestricted', 'restricted',
                     '3.1Khz', 'udi-ta', or 'video'
                   * Uri: regular expression
                   * CalledUri: regular expression
                   * CallingUri: regular expression
                   * DateTime: day of week and time period and/or date and
                     time period
                   * PhoneContext: regular expression
                   * CalledPhoneContext: regular expression
                   * CallingPhoneContext: regular expression
                   * SipUsername: regular expression
                   * CalledSipUsername: regular expression
                   * CallingSipUsername: regular expression
                   * LastDivertingReason: 'cfu', 'cfb', 'cfnr', or 'unknown'
                   * LastDivertingE164: Regular expression
                   * LastDivertingPartyNumberType: 'unknown', 'public', or
                     'private'
                   * LastDivertingPublicTypeOfNumber: 'unknown',
                     'international', 'national', 'network-specific', 'local',
                     or 'abbreviated'
                   * LastDivertingPrivateTypeOfNumber: 'unknown', 'leg2-reg',
                     'leg1-reg', 'pisn-specific', 'subscriber', or
                     'abbreviated'
                   * LastDivertingNumberPresentation: 'allowed', 'restricted',
                     'interworking', or 'restricted-address'
                   * OriginalDivertingReason: 'cfu', 'cfb', 'cfnr', or
                     'unknown'
                   * OriginalDivertingE164: Regular expression
                   * OriginalDivertingPartyNumberType: 'unknown', 'public', or
                     'private'
                   * OriginalDivertingPublicTypeOfNumber: 'unknown',
                     'international', 'national', 'network-specific', 'local',
                     or 'abbreviated'
                   * OriginalDivertingPrivateTypeOfNumber: 'unknown',
                     'leg2-reg', 'leg1-reg', 'pisn-specific', 'subscriber', or
                     'abbreviated'
                   * OriginalDivertingNumberPresentation: 'allowed',
                     'restricted', 'interworking', or 'restricted-address'
                   * CalledBearerChannel: regular expression
                   * CallingBearerChannel: regular expression
                   * CallingSipPrivacy: 'disabled', 'none', or 'id'

                 Special tags:

                   * <undefined>: Matches if the property is not defined for
                     the call.
                   * <default>: Always matches. Generally used to set a
                     default transformation if the previous criteria did not
                     match.

                 Accepted DateTime formats:

                 Date/Time Period format:

                   * 'DD.MM.YYYY/HH:MM:SS-DD.MM.YYYY/HH:MM:SS'
                   * 'DD.MM.YYYY/HH:MM:SS-HH:MM:SS'
                   * 'DD.MM.YYYY-DD.MM.YYYY'
                   * 'DD.MM.YYYY'
                   * 'HH:MM:SS-HH:MM:SS'

                 Week Day/Time Period format:

                   * 'DDD'
                   * 'DDD,DDD...'
                   * 'DDD/HH:MM:SS-HH:MM:SS'
                   * 'DDD,DDD.../HH:MM:SS-HH:MM:SS'

                 where DDD must be one of: SUN, MON, TUE, WED, THU, FRI, or
                 SAT

                 Several of the previous formats can be concatenated to form
                 one expression. They must be separated by |. Example:
                 25.12.2006 | SUN

                 Note: Whitespace at the end of a regular expression is
                 ignored.

                 See MappingTypeStatus.Criteria.

                 "
   ::= { mappingExpressionStatusEntry 300 }

  -- Columnar:Transformation

  mappingExpressionStatusTransformation OBJECT-TYPE
   SYNTAX        OCTET STRING
   MAX-ACCESS    read-only
   STATUS        current
   DESCRIPTION " Transformation

                 Transformation to apply to the call properties. It is applied
                 on the call properties defined in the
                 MappingTypeStatus.Transformation parameter.

                 The transformation syntax is related to the selected
                 properties to transform:

                   * Ton: 'unknown', 'international', 'national', 'network',
                     'subscriber', or 'abbreviated'
                   * CalledTon: 'unknown', 'international', 'national',
                     'network', 'subscriber', or 'abbreviated'
                   * CallingTon: 'unknown', 'international', 'national',
                     'network', 'subscriber', or 'abbreviated'
                   * Npi: 'unknown', 'isdn', 'data', 'telex', 'national', or
                     'private'
                   * CalledNpi: 'unknown', 'isdn', 'data', 'telex',
                     'national', or 'private'
                   * CallingNpi: 'unknown', 'isdn', 'data', 'telex',
                     'national', or 'private'
                   * CallingPi: 'allowed', 'restricted', or 'interworking'
                   * CallingSi: 'not-screened', 'passed', 'failed', or
                     'network'
                   * CallingItc: 'speech', 'unrestricted', 'restricted',
                     '3.1Khz', 'udi-ta', or 'video'
                   * LastDivertingReason: 'cfu', 'cfb', 'cfnr', or 'unknown'
                   * LastDivertingPartyNumberType: 'unknown', 'public', or
                     'private'
                   * LastDivertingPublicTypeOfNumber: 'unknown',
                     'international', 'national', 'network-specific', 'local',
                     or 'abbreviated'
                   * LastDivertingPrivateTypeOfNumber: 'unknown', 'leg2-reg',
                     'leg1-reg', 'pisn-specific', 'subscriber', or
                     'abbreviated'
                   * LastDivertingNumberPresentation: 'allowed', 'restricted',
                     'interworking', or 'restricted-address'
                   * OriginalDivertingReason: 'cfu', 'cfb', 'cfnr', or
                     'unknown'
                   * OriginalDivertingPartyNumberType: 'unknown', 'public', or
                     'private'
                   * OriginalDivertingPublicTypeOfNumber: 'unknown',
                     'international', 'national', 'network-specific', 'local',
                     or 'abbreviated'
                   * OriginalDivertingPrivateTypeOfNumber: 'unknown',
                     'leg2-reg', 'leg1-reg', 'pisn-specific', 'subscriber', or
                     'abbreviated'
                   * OriginalDivertingNumberPresentation: 'allowed',
                     'restricted', 'interworking', or 'restricted-address'
                   * All others: string where '\0' to '\9' is replaced by the
                     corresponding group in the regular expression set in the
                     criteria rule (see MappingStatus.ExpressionCriteria). The
                     value can be set to the '<local_ip_port>' macro to
                     replace the properties by the local IP address and port
                     of the listening socket of the SIP gateway used to send
                     the INVITE.

                 See MappingTypeStatus.Transformation

                 "
   ::= { mappingExpressionStatusEntry 400 }

  -- Columnar:Next Transformation

  mappingExpressionStatusSubMappings OBJECT-TYPE
   SYNTAX        OCTET STRING
   MAX-ACCESS    read-only
   STATUS        current
   DESCRIPTION " Next Transformation

                 Name of the next transformation to be executed.

                 More than one transformation can be specified. In this case,
                 the transformations are separated with ',' and are executed
                 in an sequential order.

                 "
   ::= { mappingExpressionStatusEntry 500 }

 -- End of table:Transformations

 -- ***************************************************************************
 
 -- Table:Hunt Status

 -- ***************************************************************************
 
 huntStatusTable OBJECT-TYPE
  SYNTAX        SEQUENCE OF HuntStatusEntry
  MAX-ACCESS    not-accessible
  STATUS        current
  DESCRIPTION " Hunt Status

                This table shows the actual hunt used by the call routing
                services.
                "
  ::= { statusGroup 600 }
  huntStatusEntry OBJECT-TYPE
   SYNTAX        HuntStatusEntry
   MAX-ACCESS    not-accessible
   STATUS        current
   DESCRIPTION " A row in table Hunt Status. "
   INDEX         {
                   huntStatusIndex
                 }

   ::= { huntStatusTable 1 }

  HuntStatusEntry ::= SEQUENCE
  {
    huntStatusIndex              Unsigned32,
    huntStatusName               OCTET STRING,
    huntStatusDestinations       OCTET STRING,
    huntStatusSelectionAlgorithm INTEGER,
    huntStatusTimeout            Unsigned32,
    huntStatusCauses             OCTET STRING
  }

  -- Index:Index

  huntStatusIndex OBJECT-TYPE
   SYNTAX        Unsigned32
   MAX-ACCESS    read-only
   STATUS        current
   DESCRIPTION " Index

                 Unique identifier of the row in the table.
                 "
   ::= { huntStatusEntry 100 }

  -- Columnar:Name

  huntStatusName OBJECT-TYPE
   SYNTAX        OCTET STRING
   MAX-ACCESS    read-only
   STATUS        current
   DESCRIPTION " Name

                 Name of the hunt defined by this row. It must be unique in
                 the table.
                 "
   ::= { huntStatusEntry 200 }

  -- Columnar:Destinations

  huntStatusDestinations OBJECT-TYPE
   SYNTAX        OCTET STRING
   MAX-ACCESS    read-only
   STATUS        current
   DESCRIPTION " Destinations

                 List of hunt destinations separated by commas.

                 The call destination can be:

                   * route-'name': the route 'name'
                   * hunt-'name': the hunt 'name'
                   * sip-'name': the SIP interface 'name'
                   * isdn-'name': the ISDN interface 'name'
                   * r2-'name': the R2 interface 'name'
                   * e&m-'name': the E&M interface 'name'
                   * fxs-'name': the FXS interface 'name'
                   * fxo-'name': the FXO interface 'name'

                 Note: Only FXS interfaces are supported if 'Simultaneous' is
                 selected for the Selection Algorithm parameter.

                 Example: 'isdn-Slot2/Bri1, route-something'

                 "
   ::= { huntStatusEntry 300 }

  -- Columnar:Selection Algorithm

  huntStatusSelectionAlgorithm OBJECT-TYPE
   SYNTAX        INTEGER { sequential(100) , cyclic(200) , simultaneous(300) }
   MAX-ACCESS    read-only
   STATUS        current
   DESCRIPTION " Selection Algorithm

                 Algorithm used to select the destination order.

                 The destination order can be:

                   * Sequential: The hunt tries the destination in the same
                     order as listed. The first destination hunted is the
                     first listed.
                   * Cyclic: The hunt starts from the destination that follows
                     the destination used for the last hunt. Subsequent calls
                     try another first destination in a round-robin method.
                   * Simultaneous: The hunt tries every available destination
                     at the same time. The first destination to pick up has
                     the call. Other destinations stop ringing. This method
                     can only have FXS endpoints as destinations.

                 Example of cyclic selection: If the destination is set to
                 'x,y,z', the destination the hunt tries is in the following
                 order:

                  1. x,y,z
                  2. y,z,x
                  3. z,x,y
                  4. x,y,z

                 "
   ::= { huntStatusEntry 400 }

  -- Columnar:Timeout

  huntStatusTimeout OBJECT-TYPE
   SYNTAX        Unsigned32
   MAX-ACCESS    read-only
   STATUS        current
   DESCRIPTION " Timeout

                 Maximal time allowed to the destination to handle the call.

                 A value of '0' disables the timeout.

                 This value is expressed in seconds (s).

                 Note: Not applicable if 'Simultaneous' was selected for the
                 Selection Algorithm parameter.

                 "
   ::= { huntStatusEntry 500 }

  -- Columnar:Causes

  huntStatusCauses OBJECT-TYPE
   SYNTAX        OCTET STRING
   MAX-ACCESS    read-only
   STATUS        current
   DESCRIPTION " Causes

                 Lists call rejection causes to continue the hunt. The causes
                 are separated by commas. The available hunt causes are:

                 Normal event:

                   * 1: Unassigned (unallocated) number
                   * 2: No route to specified transit network
                   * 3: No route to destination
                   * 6: Channel unacceptable.
                   * 7: Call awarded and being delivered in an established
                     channel
                   * 17: User busy
                   * 18: No user responding
                   * 19: User alerting, no answer
                   * 21: Call rejected
                   * 22: Number changed
                   * 26: Non-selected user clearing
                   * 27: Destination out of order
                   * 28: Invalid number format (incomplete number)
                   * 29: Facility rejected
                   * 30: Response to STATUS ENQUIRY
                   * 31: Normal, unspecified

                 Unavailable resource:

                   * 34: No circuit/channel available
                   * 38: Network out of order
                   * 41: Temporary failure
                   * 42: Switching equipment congestion
                   * 43: Access information discarded
                   * 44: Requested circuit/channel not available
                   * 47: Resource unavailable, unspecified

                 Service or option not available:

                   * 57: Bearer capability not authorised
                   * 58: Bearer capability not presently available
                   * 63: Service or option not available, unspecified

                 Service or option not implemented:

                   * 65: Bearer capability not implemented
                   * 66: Channel type not implemented
                   * 69: Requested facility not implemented
                   * 70: Only restricted digital information bearer capability
                     is available
                   * 79: Service or option not implemented, unspecified

                 Invalid message:

                   * 81: Invalid call reference value
                   * 82: Identified channel does not exist
                   * 83: A suspended call exists, but this call identity does
                     not exist
                   * 84: Call identity in use
                   * 85: No call suspended
                   * 86: Call having the requested call identity has been
                     cleared
                   * 88: Incompatible destination
                   * 91: Invalid transit network selection
                   * 95: Invalid message, unspecified

                 Protocol error:

                   * 96: Mandatory information element missing
                   * 97: Message type non-existent or not implemented
                   * 98: Message not compatible with call state or message
                     type non-existent or not implemented
                   * 99: Information element non-existent or not implemented
                   * 100: Invalid information element contents
                   * 101: Message not compatible with call state
                   * 102: Recovery on time expiry
                   * 111: Protocol error, unspecified

                 Interworking:

                   * 127: Interworking, unspecified.

                 Note: Not applicable if 'Simultaneous' was selected for the
                 Selection Algorithm parameter.

                 "
   ::= { huntStatusEntry 600 }

 -- End of table:Hunt Status

 -- ***************************************************************************
 
 -- Table:Signaling Properties

 -- ***************************************************************************
 
 signalingPropertiesStatusTable OBJECT-TYPE
  SYNTAX        SEQUENCE OF SignalingPropertiesStatusEntry
  MAX-ACCESS    not-accessible
  STATUS        current
  DESCRIPTION " Signaling Properties

                This table shows the actual signaling properties used by the
                call routing services.
                "
  ::= { statusGroup 700 }
  signalingPropertiesStatusEntry OBJECT-TYPE
   SYNTAX        SignalingPropertiesStatusEntry
   MAX-ACCESS    not-accessible
   STATUS        current
   DESCRIPTION " A row in table Signaling Properties. "
   INDEX         {
                   signalingPropertiesStatusIndex
                 }

   ::= { signalingPropertiesStatusTable 1 }

  SignalingPropertiesStatusEntry ::= SEQUENCE
  {
    signalingPropertiesStatusIndex                     Unsigned32,
    signalingPropertiesStatusName                      OCTET STRING,
    signalingPropertiesStatusEarlyConnect              MxEnableState,
    signalingPropertiesStatusEarlyDisconnect           MxEnableState,
    signalingPropertiesStatusDestinationHost           OCTET STRING,
    signalingPropertiesStatusAllow180Sdp               MxEnableState,
    signalingPropertiesStatusAllow183NoSdp             MxEnableState,
    signalingPropertiesStatusPrivacy                   INTEGER,
    signalingPropertiesStatusCallPropertiesTranslation OCTET STRING,
    signalingPropertiesStatusSipHeadersTranslation     OCTET STRING
  }

  -- Index:Row Index

  signalingPropertiesStatusIndex OBJECT-TYPE
   SYNTAX        Unsigned32
   MAX-ACCESS    read-only
   STATUS        current
   DESCRIPTION " Row Index

                 Unique identifier of the row in the table.
                 "
   ::= { signalingPropertiesStatusEntry 100 }

  -- Columnar:SIP Header Translation Overrides

  signalingPropertiesStatusSipHeadersTranslation OBJECT-TYPE
   SYNTAX        OCTET STRING
   MAX-ACCESS    read-only
   STATUS        current
   DESCRIPTION " SIP Header Translation Overrides

                 Name of the SIP header translation to apply to the call.

                 The translation modifies the SIP headers before the call is
                 sent to its destination.

                 More than one translation can be specified. In this case, the
                 translations are separated with ',' and are executed in
                 sequential order.

                 "
   ::= { signalingPropertiesStatusEntry 1000 }

  -- Columnar:Name

  signalingPropertiesStatusName OBJECT-TYPE
   SYNTAX        OCTET STRING
   MAX-ACCESS    read-only
   STATUS        current
   DESCRIPTION " Name

                 Name of the Signaling properties defined by this row. It must
                 be unique in the table.
                 "
   ::= { signalingPropertiesStatusEntry 200 }

  -- Columnar:Early Connect

  signalingPropertiesStatusEarlyConnect OBJECT-TYPE
   SYNTAX        MxEnableState
   MAX-ACCESS    read-only
   STATUS        current
   DESCRIPTION " Early Connect

                 Enable/Disable the early connect feature.

                 When early connect is enabled, the SIP call is connected by
                 sending a 200 OK message instead of a 183 Session Progress
                 message with early media.

                 "
   ::= { signalingPropertiesStatusEntry 300 }

  -- Columnar:Early Disconnect

  signalingPropertiesStatusEarlyDisconnect OBJECT-TYPE
   SYNTAX        MxEnableState
   MAX-ACCESS    read-only
   STATUS        current
   DESCRIPTION " Early Disconnect

                 Enable/Disable the early disconnect feature.

                 When early disconnect is enabled, the SIP BYE message is sent
                 upon ISDN 'Disconnect' signal reception.

                 When early disconnect is disabled, the SIP BYE message is
                 sent upon ISDN 'Call release' signal reception.

                 If early disconnect is enabled but no ISDN 'Disconnect'
                 message is received, the SIP BYE message will be sent upon
                 receiving an ISDN 'Call release' as if the early disconnect
                 was disabled.

                 "
   ::= { signalingPropertiesStatusEntry 400 }

  -- Columnar:Destination Host

  signalingPropertiesStatusDestinationHost OBJECT-TYPE
   SYNTAX        OCTET STRING
   MAX-ACCESS    read-only
   STATUS        current
   DESCRIPTION " Destination Host

                 SIP message destination.

                 The value can be set to the '<local_ip_port>' macro to
                 replace the properties by the local IP address and port of
                 the listening socket of the SIP gateway used to send the
                 INVITE.

                 "
   ::= { signalingPropertiesStatusEntry 500 }

  -- Columnar:Allow 180 with SDP

  signalingPropertiesStatusAllow180Sdp OBJECT-TYPE
   SYNTAX        MxEnableState
   MAX-ACCESS    read-only
   STATUS        current
   DESCRIPTION " Allow 180 with SDP

                 Enable/Disable the 180 with SDP allowed.

                 When disabled, a SIP 183 with SDP is sent instead of a 180
                 with SDP.

                 This does not affect the 180 without SDP.

                 "
   ::= { signalingPropertiesStatusEntry 600 }

  -- Columnar:Allow 183 without SDP

  signalingPropertiesStatusAllow183NoSdp OBJECT-TYPE
   SYNTAX        MxEnableState
   MAX-ACCESS    read-only
   STATUS        current
   DESCRIPTION " Allow 183 without SDP

                 Enable/Disable the 183 without SDP allowed.

                 When disabled, a 183 without SDP is not sent.

                 This does not affect the 183 with SDP.

                 "
   ::= { signalingPropertiesStatusEntry 700 }

  -- Columnar:Privacy

  signalingPropertiesStatusPrivacy OBJECT-TYPE
   SYNTAX        INTEGER { disable(100) , none(200) , id(300) , rpid(400) }
   MAX-ACCESS    read-only
   STATUS        current
   DESCRIPTION " Privacy

                 Indicates the privacy level of the call.

                   * Disable: No privacy is used.
                   * None: Use P-Asserted Identity privacy.
                   * Id: Use P-Preferred Identity privacy.
                   * Rpid: Use Remote-Party-ID privacy.

                 "
   ::= { signalingPropertiesStatusEntry 800 }

  -- Columnar:Call Property Translations Override

  signalingPropertiesStatusCallPropertiesTranslation OBJECT-TYPE
   SYNTAX        OCTET STRING
   MAX-ACCESS    read-only
   STATUS        current
   DESCRIPTION " Call Property Translations Override

                 Name of the call property translation to apply to the call.

                 The translation modifies the call properties before the call
                 is sent to its destination.

                 More than one translation can be specified. In that case, the
                 translations are separated with ',' and are executed in
                 sequential order.

                 "
   ::= { signalingPropertiesStatusEntry 900 }

 -- End of table:Signaling Properties

 -- ***************************************************************************
 
 -- Table:SIP Header Translation Overrides

 -- ***************************************************************************
 
 sipHeadersTranslationStatusTable OBJECT-TYPE
  SYNTAX        SEQUENCE OF SipHeadersTranslationStatusEntry
  MAX-ACCESS    not-accessible
  STATUS        current
  DESCRIPTION " SIP Header Translation Overrides

                This table shows the configured SIP header translations to be
                used by the call routing service. The configuration is not
                used until the ApplyConfig command is executed.

                "
  ::= { statusGroup 800 }
  sipHeadersTranslationStatusEntry OBJECT-TYPE
   SYNTAX        SipHeadersTranslationStatusEntry
   MAX-ACCESS    not-accessible
   STATUS        current
   DESCRIPTION " A row in table SIP Header Translation Overrides. "
   INDEX         {
                   sipHeadersTranslationStatusIndex
                 }

   ::= { sipHeadersTranslationStatusTable 1 }

  SipHeadersTranslationStatusEntry ::= SEQUENCE
  {
    sipHeadersTranslationStatusIndex     Unsigned32,
    sipHeadersTranslationStatusName      OCTET STRING,
    sipHeadersTranslationStatusSipHeader INTEGER,
    sipHeadersTranslationStatusBuiltFrom INTEGER,
    sipHeadersTranslationStatusFixValue  OCTET STRING
  }

  -- Index:Index

  sipHeadersTranslationStatusIndex OBJECT-TYPE
   SYNTAX        Unsigned32
   MAX-ACCESS    read-only
   STATUS        current
   DESCRIPTION " Index

                 Unique identifier of the row in the table.
                 "
   ::= { sipHeadersTranslationStatusEntry 100 }

  -- Columnar:Name

  sipHeadersTranslationStatusName OBJECT-TYPE
   SYNTAX        OCTET STRING ( SIZE(0..64) )
   MAX-ACCESS    read-only
   STATUS        current
   DESCRIPTION " Name

                 Name of the SIP header translation defined in this row.
                 "
   ::= { sipHeadersTranslationStatusEntry 200 }

  -- Columnar:SIP Header

  sipHeadersTranslationStatusSipHeader OBJECT-TYPE
   SYNTAX        INTEGER { fromHeaderHostPart(100) , fromHeaderUserPart(200) ,
                 identityHeaderHostPart(300) , identityHeaderUserPart(400) ,
                 identityHeaderPhoneNumber(500) , identityHeaderFriendlyName
                 (550) , requestLineHostPart(600) , requestLineUserPart(700) ,
                 toHeaderHostPart(800) , toHeaderUserPart(900) }
   MAX-ACCESS    read-only
   STATUS        current
   DESCRIPTION " SIP Header

                 Sets which SIP header is modified by this translation.

                 The SIP headers can be:

                   * FromHeaderHostPart: host part of the From header URI
                   * FromHeaderUserPart: user part of the From header URI
                   * IdentityHeaderHostPart: host part of the Identity header
                     URI
                   * IdentityHeaderUserPart: user part of the Identity header
                     URI
                   * IdentityHeaderPhoneNumber: phone number in the Identity
                     header tel URI
                   * IdentityHeaderFriendlyName: friendly name in the Identity
                     header URI
                   * RequestLineHostPart: host part of the Request line URI
                   * RequestLineUserPart: user part of the Request line URI
                   * ToHeaderHostPart: host part of the To header URI
                   * ToHeaderUserPart: user part of the To header URI

                 "
   ::= { sipHeadersTranslationStatusEntry 300 }

  -- Columnar:Based On

  sipHeadersTranslationStatusBuiltFrom OBJECT-TYPE
   SYNTAX        INTEGER { calledE164(100) , destinationHost(200) , domain
                 (300) , fixValue(400) , hostName(500) , localIp(600) ,
                 callingBearerChannel(700) , sipEndpointUsername(800) ,
                 callingName(900) , callingE164(1000) }
   MAX-ACCESS    read-only
   STATUS        current
   DESCRIPTION " Based On

                 Sets what information is used to build the selected SIP
                 header.

                 The information can be retrieved from:

                   * CalledE164: Use the called party E.164 property.
                   * DestinationHost: Use the destination host configured in
                     the signaling properties of which this translation is
                     part of.
                   * Domain: Use the domain name configured in the unit.
                   * FixValue: Use a fixed value (see
                     SipHeadersTranslation.FixValue).
                   * HostName: Use the host name configured on the unit.
                   * LocalIp: Use the local IP address.
                   * CallingBearerChannel: Use the calling bearer channel.
                   * SipEndpointUsername: Use the SIP username associated with
                     the endpoint.
                   * CallingName: Use the calling party name property.
                   * CallingE164: Use the calling party E.164 property.

                 "
   ::= { sipHeadersTranslationStatusEntry 400 }

  -- Columnar:Fixed Value

  sipHeadersTranslationStatusFixValue OBJECT-TYPE
   SYNTAX        OCTET STRING ( SIZE(0..255) )
   MAX-ACCESS    read-only
   STATUS        current
   DESCRIPTION " Fixed Value

                 Fixed value to be inserted in the SIP header when the
                 SipHeadersTranslation.BuiltFrom parameter is set to
                 'FixValue'.

                 "
   DEFVAL        { "" }
   ::= { sipHeadersTranslationStatusEntry 500 }

 -- End of table:SIP Header Translation Overrides

 -- ***************************************************************************
 
 -- Table:Call Property Translation Overrides

 -- ***************************************************************************
 
 callPropertiesTranslationStatusTable OBJECT-TYPE
  SYNTAX        SEQUENCE OF CallPropertiesTranslationStatusEntry
  MAX-ACCESS    not-accessible
  STATUS        current
  DESCRIPTION " Call Property Translation Overrides

                This table shows the configured call property translations to
                be used by the call routing service. The configuration is not
                used until the ApplyConfig command is executed.

                "
  ::= { statusGroup 900 }
  callPropertiesTranslationStatusEntry OBJECT-TYPE
   SYNTAX        CallPropertiesTranslationStatusEntry
   MAX-ACCESS    not-accessible
   STATUS        current
   DESCRIPTION " A row in table Call Property Translation Overrides. "
   INDEX         {
                   callPropertiesTranslationStatusIndex
                 }

   ::= { callPropertiesTranslationStatusTable 1 }

  CallPropertiesTranslationStatusEntry ::= SEQUENCE
  {
    callPropertiesTranslationStatusIndex        Unsigned32,
    callPropertiesTranslationStatusName         OCTET STRING,
    callPropertiesTranslationStatusCallProperty INTEGER,
    callPropertiesTranslationStatusBuiltFrom    INTEGER,
    callPropertiesTranslationStatusFixValue     OCTET STRING
  }

  -- Index:Index

  callPropertiesTranslationStatusIndex OBJECT-TYPE
   SYNTAX        Unsigned32
   MAX-ACCESS    read-only
   STATUS        current
   DESCRIPTION " Index

                 Unique identifier of the row in the table.
                 "
   ::= { callPropertiesTranslationStatusEntry 100 }

  -- Columnar:Name

  callPropertiesTranslationStatusName OBJECT-TYPE
   SYNTAX        OCTET STRING ( SIZE(0..64) )
   MAX-ACCESS    read-only
   STATUS        current
   DESCRIPTION " Name

                 Name of the call property translation defined by this row.
                 "
   ::= { callPropertiesTranslationStatusEntry 200 }

  -- Columnar:Call Property

  callPropertiesTranslationStatusCallProperty OBJECT-TYPE
   SYNTAX        INTEGER { calledE164(100) , callingE164(200) , calledName
                 (300) , callingName(400) , calledUri(500) , callingUri(600) ,
                 calledBearerChannel(700) }
   MAX-ACCESS    read-only
   STATUS        current
   DESCRIPTION " Call Property

                 Sets which call property is modified by this translation.

                 The call properties can be:

                   * CalledE164: called party E.164 property
                   * CallingE164: calling party E.164 property
                   * CalledName: called party name property
                   * CallingName: calling party name property
                   * CalledUri: called URI name property
                   * CallingUri: calling URI name property
                   * CalledBearerChannel: called bearer channel property

                 "
   ::= { callPropertiesTranslationStatusEntry 300 }

  -- Columnar:Based On

  callPropertiesTranslationStatusBuiltFrom OBJECT-TYPE
   SYNTAX        INTEGER { domain(100) , fixValue(200) , fromHeaderUri(300) ,
                 fromHeaderFriendlyName(400) , fromHeaderUserPart(500) ,
                 identityHeaderUri(600) , identityHeaderUserPart(700) ,
                 identityHeaderPhoneNumber(800) , identityHeaderFriendlyName
                 (850) , localIp(900) , requestLineUri(1000) ,
                 requestLineUserPart(1100) , toHeaderUri(1200) ,
                 toHeaderFriendlyName(1300) , toHeaderUserPart(1400) }
   MAX-ACCESS    read-only
   STATUS        current
   DESCRIPTION " Based On

                 Sets what information is used to build the selected call
                 property.

                 The information can be retrieved from:

                   * Domain: Use the domain name configured in the unit.
                   * FixValue: Use a fixed value (see
                     CallPropertiesTranslation.FixValue).
                   * FromHeaderUri: Use the From header URI.
                   * FromHeaderFriendlyName: Use the friendly name part of the
                     From header.
                   * FromHeaderUserPart: Use the user part of the From header
                     URI.
                   * IdentityHeaderUri: Use the Identity header URI.
                   * IdentityHeaderUserPart: Use the user part of the Identity
                     header URI.
                   * IdentityHeaderPhoneNumber: Use the phone number in the
                     Identity header tel URL.
                   * IdentityHeaderFriendlyName: Use the friendly name in the
                     Identity header URI.
                   * LocalIp: Use the local IP address.
                   * RequestLineUri: Use the Request line URI.
                   * RequestLineUserPart: Use the user part of the Request
                     line URI.
                   * ToHeaderUri: Use the To header URI.
                   * ToHeaderFriendlyName: Use the friendly name part of the
                     To header.
                   * ToHeaderUserPart: Use the user part of the To header URI.

                 "
   ::= { callPropertiesTranslationStatusEntry 400 }

  -- Columnar:Fixed Value

  callPropertiesTranslationStatusFixValue OBJECT-TYPE
   SYNTAX        OCTET STRING ( SIZE(0..255) )
   MAX-ACCESS    read-only
   STATUS        current
   DESCRIPTION " Fixed Value

                 Fixed value to be inserted in the call property when the
                 CallPropertiesTranslation.BuiltFrom parameter is set to
                 'FixValue'.
                 "
   ::= { callPropertiesTranslationStatusEntry 500 }

 -- End of table:Call Property Translation Overrides

 -- ***************************************************************************
 
 -- Table:SIP Redirects

 -- ***************************************************************************
 
 sipRedirectStatusTable OBJECT-TYPE
  SYNTAX        SEQUENCE OF SipRedirectStatusEntry
  MAX-ACCESS    not-accessible
  STATUS        current
  DESCRIPTION " SIP Redirects

                This table shows the actual Redirect entry used by the call
                routing service.
                "
  ::= { statusGroup 1000 }
  sipRedirectStatusEntry OBJECT-TYPE
   SYNTAX        SipRedirectStatusEntry
   MAX-ACCESS    not-accessible
   STATUS        current
   DESCRIPTION " A row in table SIP Redirects. "
   INDEX         {
                   sipRedirectStatusIndex
                 }

   ::= { sipRedirectStatusTable 1 }

  SipRedirectStatusEntry ::= SEQUENCE
  {
    sipRedirectStatusIndex           Unsigned32,
    sipRedirectStatusName            OCTET STRING,
    sipRedirectStatusDestinationHost OCTET STRING
  }

  -- Index:Index

  sipRedirectStatusIndex OBJECT-TYPE
   SYNTAX        Unsigned32
   MAX-ACCESS    read-only
   STATUS        current
   DESCRIPTION " Index

                 Unique identifier of the row in the table.
                 "
   ::= { sipRedirectStatusEntry 100 }

  -- Columnar:Name

  sipRedirectStatusName OBJECT-TYPE
   SYNTAX        OCTET STRING ( SIZE(0..64) )
   MAX-ACCESS    read-only
   STATUS        current
   DESCRIPTION " Name

                 Name of the SIP Redirect defined by this row.

                 The name must be unique in the table.

                 "
   ::= { sipRedirectStatusEntry 200 }

  -- Columnar:Destination Host

  sipRedirectStatusDestinationHost OBJECT-TYPE
   SYNTAX        OCTET STRING
   MAX-ACCESS    read-only
   STATUS        current
   DESCRIPTION " Destination Host

                 Host address inserted in the Moved Temporarily response.
                 "
   DEFVAL        { "" }
   ::= { sipRedirectStatusEntry 300 }

 -- End of table:SIP Redirects

-- End of group:Status Group

-- Scalar:Auto-Routing

autoRoutingEnable OBJECT-TYPE
 SYNTAX        MxEnableState
 MAX-ACCESS    read-write
 STATUS        current
 DESCRIPTION " Auto-Routing

               Enable/Disable the automatic insertion of default routes for
               selected endpoints.

               When enabled, routes are automatically added to the Route Table
               in order to connect the endpoints marked as eligible for
               auto-routing and the designated SIP gateway (see the
               Autoroutable and the AutoroutingGateway parameters). These
               automatic routes are displayed in the Routes Table of the Status
               page but do not show up in the configuration.

               "
 DEFVAL        { disable }
 ::= { cRoutMIBObjects 200 }

-- *****************************************************************************

-- Table:Routes

-- *****************************************************************************

routeTable OBJECT-TYPE
 SYNTAX        SEQUENCE OF RouteEntry
 MAX-ACCESS    not-accessible
 STATUS        current
 DESCRIPTION " Routes

               This table shows the configured route to be used by the call
               routing service. The configuration is not used until the
               ApplyConfig command is executed.

               "
 ::= { cRoutMIBObjects 300 }
 routeEntry OBJECT-TYPE
  SYNTAX        RouteEntry
  MAX-ACCESS    not-accessible
  STATUS        current
  DESCRIPTION " A row in table Routes. "
  INDEX         {
                  routeIndex
                }

  ::= { routeTable 1 }

 RouteEntry ::= SEQUENCE
 {
   routeIndex               Unsigned32,
   routeSourceCriteria      OCTET STRING,
   routePropertiesCriteria  INTEGER,
   routeExpressionCriteria  OCTET STRING,
   routeDestination         OCTET STRING,
   routeMappings            OCTET STRING,
   routeSignalingProperties OCTET STRING,
   routeConfigStatus        OCTET STRING,
   routeUp                  INTEGER,
   routeDown                INTEGER,
   routeInsert              INTEGER,
   routeDelete              INTEGER
 }

 -- Index:Index

 routeIndex OBJECT-TYPE
  SYNTAX        Unsigned32
  MAX-ACCESS    read-only
  STATUS        current
  DESCRIPTION " Index

                Unique identifier of the row in the table.
                "
  ::= { routeEntry 100 }

 -- Row command:Insert

 routeInsert OBJECT-TYPE
  SYNTAX        INTEGER { noOp(0), insert(10) }
  MAX-ACCESS    read-write
  STATUS        current
  DESCRIPTION " Insert

                Inserts a new row before this row.
                "
  DEFVAL        { noOp }
  ::= { routeEntry 1000 }

 -- Row command:Delete

 routeDelete OBJECT-TYPE
  SYNTAX        INTEGER { noOp(0), delete(10) }
  MAX-ACCESS    read-write
  STATUS        current
  DESCRIPTION " Delete

                Deletes this row.
                "
  DEFVAL        { noOp }
  ::= { routeEntry 1100 }

 -- Columnar:Sources

 routeSourceCriteria OBJECT-TYPE
  SYNTAX        OCTET STRING ( SIZE(0..2048) )
  MAX-ACCESS    read-write
  STATUS        current
  DESCRIPTION " Sources

                One or many sources the service compares and matches the call
                to, in order to apply the route.

                The source the call comes from can be:

                  * route-'name': the route 'name'
                  * sip-'name': the SIP interface 'name'
                  * isdn-'name': the ISDN interface 'name'
                  * r2-'name': the R2 interface 'name'
                  * e&m-'name': Tthe E&M interface 'name'
                  * fxs-'name': the FXS interface 'name'
                  * fxo-'name': the FXO interface 'name'

                Multiple sources must be separated by commas.

                "
  DEFVAL        { "" }
  ::= { routeEntry 200 }

 -- Columnar:Criteria Property

 routePropertiesCriteria OBJECT-TYPE
  SYNTAX        INTEGER { none(100) , calledE164(200) , callingE164(300) ,
                calledName(400) , callingName(500) , calledTon(600) ,
                callingTon(700) , calledNpi(800) , callingNpi(900) , calledHost
                (1000) , callingHost(1100) , callingPi(1200) , callingSi(1300)
                , callingItc(1400) , calledUri(1500) , callingUri(1600) ,
                dateTime(1700) , calledPhoneContext(1800) , callingPhoneContext
                (1900) , calledSipUsername(2000) , callingSipUsername(2100) ,
                calledBearerChannel(2200) , callingBearerChannel(2300) ,
                callingSipPrivacy(2400) }
  MAX-ACCESS    read-write
  STATUS        current
  DESCRIPTION " Criteria Property

                The call property part of the criteria used to determine if the
                route can be applied or not. The other part of the criteria is
                the expression defined in the RouteStatus.ExpressionCriteria
                parameter.

                Calls can be routed based on the following Call Properties:

                  * CalledE164: the called party E.164 properties
                  * CallingE164: the calling party E.164 properties
                  * CalledName: the called party name properties
                  * CallingName: the calling party name properties
                  * CalledTon: the called party type of number properties
                  * CallingTon: the calling party type of number properties
                  * CalledNpi: the called party numbering plan indicator
                    properties
                  * CallingNpi: the calling party numbering plan indicator
                    properties
                  * CalledHost: the calling host properties
                  * CallingHost: the called host properties
                  * CallingPi: the calling party presentation indicator
                  * CallingSi: the calling party screening indicator
                  * CallingItc: the calling party information transfer
                    capability
                  * CalledUri: the called party SIP URI
                  * CallingUri: the calling party SIP URI
                  * DateTime: the date and/or time the call arrived at the call
                    router
                  * CalledPhoneContext: the called party phone context
                    properties
                  * CallingPhoneContext: the calling party phone context
                    properties
                  * CalledSipUsername: the called party SIP username properties
                  * CallingSipUsername: the calling party SIP username
                    properties
                  * CalledBeareChannel: the called bearer channel properties
                  * CallingBeareChannel: the calling bearer channel properties
                  * CallingSipPrivacy: the calling SIP privacy properties

                See RouteStatus.ExpressionCriteria.

                "
  DEFVAL        { none }
  ::= { routeEntry 300 }

 -- Columnar:Criteria Rule

 routeExpressionCriteria OBJECT-TYPE
  SYNTAX        OCTET STRING ( SIZE(0..256) )
  MAX-ACCESS    read-write
  STATUS        current
  DESCRIPTION " Criteria Rule

                The call property part of the criteria rule used to determine
                if the route can be applied or not. The other part of the
                criteria is the expression defined in the
                RouteStatus.PropertiesCriteria parameter.

                The criteria rule syntax is related to the selected criteria
                properties or can be a special tag:

                  * CalledE164: regular expression
                  * CallingE164: regular expression
                  * CalledName: regular expression
                  * CallingName: regular expression
                  * CalledTon: 'unknown', 'international', 'national',
                    'network', 'subscriber', or 'abbreviated'
                  * CallingTon: 'unknown', 'international', 'national',
                    'network', 'subscriber', or 'abbreviated'
                  * CalledNpi: 'unknown', 'isdn', 'data', 'telex', 'national',
                    or 'private'
                  * CallingNpi: 'unknown', 'isdn', 'data', 'telex', 'national',
                    or 'private'
                  * CalledHost: Regular expression. The call properties format
                    is 'Fqdn[:port]'. If the '[:port]' is not present, the
                    table uses the well-known port of the signaling protocol.
                  * CallingHost: Regular expression. The call properties format
                    is 'Fqdn[:port]'. If the '[:port]' is not present, the
                    table uses the well-known port of the signaling protocol.
                  * CallingPi: 'allowed', 'restricted', or 'interworking'
                  * CallingSi: 'not-screened', 'passed', 'failed', or 'network'
                  * CallingItc: 'speech', 'unrestricted', 'restricted',
                    '3.1Khz', 'udi-ta', or 'video'
                  * CalledUri: regular expression
                  * CallingUri: regular expression
                  * DateTime: day of week and time period and/or date and time
                    period
                  * CalledPhoneContext: regular expression
                  * CallingPhoneContext: regular expression
                  * CalledSipUsername: regular expression
                  * CallingSipUsername: regular expression
                  * CalledBearerChannel: regular expression
                  * CallingBearerChannel: regular expression
                  * CallingSipPrivacy: 'disabled', 'none', or 'id'

                Special tags:

                  * <undefined>: Matches if the property is not defined for the
                    call.
                  * <default>: Always matches. Generally used to set a default
                    route if the previous criteria did not match.

                Accepted DateTime formats:

                Date/Time Period format:

                  * 'DD.MM.YYYY/HH:MM:SS-DD.MM.YYYY/HH:MM:SS'
                  * 'DD.MM.YYYY/HH:MM:SS-HH:MM:SS'
                  * 'DD.MM.YYYY-DD.MM.YYYY'
                  * 'DD.MM.YYYY'
                  * 'HH:MM:SS-HH:MM:SS'

                Week Day/Time Period format:

                  * 'DDD'
                  * 'DDD,DDD...'
                  * 'DDD/HH:MM:SS-HH:MM:SS'
                  * 'DDD,DDD.../HH:MM:SS-HH:MM:SS'

                where DDD must be one of: SUN, MON, TUE, WED, THU, FRI,or SAT

                Several of the previous formats can be concatenated to form one
                expression. They must be separated by |. Example: 25.12.2006 |
                SUN

                Note: Whitespace at the end of a regular expression is ignored.

                See RouteStatus.PropertiesCriteria.

                "
  DEFVAL        { "" }
  ::= { routeEntry 400 }

 -- Columnar:Destination

 routeDestination OBJECT-TYPE
  SYNTAX        OCTET STRING ( SIZE(0..64) )
  MAX-ACCESS    read-write
  STATUS        current
  DESCRIPTION " Destination

                Destination to apply to the call if it matches the criteria.

                The call destination can be set to:

                  * route-'name': the route 'name'
                  * hunt-'name': the hunt 'name'
                  * sip-'name': the SIP interface 'name'
                  * isdn-'name': the ISDN interface 'name'
                  * r2-'name': the R2 interface 'name'
                  * e&m-'name': the E&M interface 'name'
                  * fxs-'name': the FXS interface 'name'
                  * fxo-'name': the FXO interface 'name'
                  * SipRedirect-'name': When the Route source is a SIP
                    interface, incoming SIP Invites are replied with a 302
                    'Moved Temporarily' SIP response.

                "
  DEFVAL        { "" }
  ::= { routeEntry 500 }

 -- Columnar:Transformations

 routeMappings OBJECT-TYPE
  SYNTAX        OCTET STRING ( SIZE(0..512) )
  MAX-ACCESS    read-write
  STATUS        current
  DESCRIPTION " Transformations

                Name of the transformations to apply to the call if the
                criteria match. The transformations are executed before sending
                the call to the new destination.

                More than one transformation can be specified. In that case,
                the transformations are separated with ',' and are executed in
                sequential order.

                "
  DEFVAL        { "" }
  ::= { routeEntry 600 }

 -- Columnar:Signaling Properties

 routeSignalingProperties OBJECT-TYPE
  SYNTAX        OCTET STRING ( SIZE(0..512) )
  MAX-ACCESS    read-write
  STATUS        current
  DESCRIPTION " Signaling Properties

                Name of the signaling properties to apply to the call.
                "
  DEFVAL        { "" }
  ::= { routeEntry 650 }

 -- Columnar:Config Status

 routeConfigStatus OBJECT-TYPE
  SYNTAX        OCTET STRING
  MAX-ACCESS    read-only
  STATUS        current
  DESCRIPTION " Config Status

                Configuration status of the row.

                It indicates if the configuration of the row is valid.

                "
  ::= { routeEntry 700 }

 -- Row command:Up

 routeUp OBJECT-TYPE
  SYNTAX        INTEGER { noOp(0), up(10) }
  MAX-ACCESS    read-write
  STATUS        current
  DESCRIPTION " Up

                Moves the current row upwards.
                "
  DEFVAL        { noOp }
  ::= { routeEntry 800 }

 -- Row command:Down

 routeDown OBJECT-TYPE
  SYNTAX        INTEGER { noOp(0), down(10) }
  MAX-ACCESS    read-write
  STATUS        current
  DESCRIPTION " Down

                Moves the current row downwards.
                "
  DEFVAL        { noOp }
  ::= { routeEntry 900 }

-- End of table:Routes

-- *****************************************************************************

-- Table:Transformations

-- *****************************************************************************

mappingTypeTable OBJECT-TYPE
 SYNTAX        SEQUENCE OF MappingTypeEntry
 MAX-ACCESS    not-accessible
 STATUS        current
 DESCRIPTION " Transformations

               This table defines which Call Properties are used in the
               transformations configured in the call routing service. The
               Transformation Rules (MappingExpression) table contains the
               detailed rules related to each transformation. The configuration
               is not used until the ApplyConfig command is executed.

               "
 ::= { cRoutMIBObjects 500 }
 mappingTypeEntry OBJECT-TYPE
  SYNTAX        MappingTypeEntry
  MAX-ACCESS    not-accessible
  STATUS        current
  DESCRIPTION " A row in table Transformations. "
  INDEX         {
                  mappingTypeIndex
                }

  ::= { mappingTypeTable 1 }

 MappingTypeEntry ::= SEQUENCE
 {
   mappingTypeIndex          Unsigned32,
   mappingTypeName           OCTET STRING,
   mappingTypeCriteria       INTEGER,
   mappingTypeTransformation INTEGER,
   mappingTypeConfigStatus   OCTET STRING,
   mappingTypeUp             INTEGER,
   mappingTypeDown           INTEGER,
   mappingTypeInsert         INTEGER,
   mappingTypeDelete         INTEGER
 }

 -- Index:Index

 mappingTypeIndex OBJECT-TYPE
  SYNTAX        Unsigned32
  MAX-ACCESS    read-only
  STATUS        current
  DESCRIPTION " Index

                Unique identifier of the row in the table.
                "
  ::= { mappingTypeEntry 100 }

 -- Columnar:Name

 mappingTypeName OBJECT-TYPE
  SYNTAX        OCTET STRING ( SIZE(0..64) )
  MAX-ACCESS    read-write
  STATUS        current
  DESCRIPTION " Name

                Name of the property transformations defined by this row.

                The name must be unique in the table.

                See Route.Mapping parameter.

                "
  DEFVAL        { "" }
  ::= { mappingTypeEntry 200 }

 -- Columnar:Criteria Based On

 mappingTypeCriteria OBJECT-TYPE
  SYNTAX        INTEGER { none(100) , e164(200) , calledE164(300) , callingE164
                (400) , name(500) , calledName(600) , callingName(700) , ton
                (800) , calledTon(900) , callingTon(1000) , npi(1100) ,
                calledNpi(1200) , callingNpi(1300) , host(1400) , calledHost
                (1500) , callingHost(1600) , callingPi(1700) , callingSi(1800)
                , callingItc(1900) , uri(2000) , calledUri(2100) , callingUri
                (2200) , dateTime(2300) , phoneContext(2400) ,
                calledPhoneContext(2500) , callingPhoneContext(2600) ,
                sipUsername(2700) , calledSipUsername(2800) ,
                callingSipUsername(2900) , lastDivertingReason(3000) ,
                lastDivertingE164(3100) , lastDivertingPartyNumberType(3110) ,
                lastDivertingPublicTypeOfNumber(3120) ,
                lastDivertingPrivateTypeOfNumber(3130) ,
                lastDivertingNumberPresentation(3140) , originalDivertingReason
                (3200) , originalDivertingE164(3300) ,
                originalDivertingPartyNumberType(3400) ,
                originalDivertingPublicTypeOfNumber(3500) ,
                originalDivertingPrivateTypeOfNumber(3600) ,
                originalDivertingNumberPresentation(3700) , calledBearerChannel
                (3800) , callingBearerChannel(3900) , callingSipPrivacy(4000) }
  MAX-ACCESS    read-write
  STATUS        current
  DESCRIPTION " Criteria Based On

                The call property part of the criteria used to determine if the
                transformation rule can be applied or not. The other part of
                the criteria is the expression defined in the
                MappingExpression.Criteria.

                The expression syntax is related to the criteria property:

                  * E164: called or calling E.164 properties
                  * CalledE164: called E.164 properties
                  * CallingE164: calling E.164 properties
                  * Name: called or calling name properties
                  * CalledName: called name properties
                  * CallingName: calling name properties
                  * Ton: called or calling type of number properties
                  * CalledTon: called type of number properties
                  * CallingTon: calling type of number properties
                  * Npi: called or calling numbering plan indicator properties
                  * CalledNpi: called numbering plan indicator properties
                  * CallingNpi: calling numbering plan indicator properties
                  * Host: calling or called host properties
                  * CalledHost: calling host properties
                  * CallingHost: called host properties
                  * CallingPi: calling presentation indicator
                  * CallingSi: calling screening indicator
                  * CallingItc: calling information transfer capability
                  * Uri: calling or called SIP URI properties
                  * CalledUri: called SIP URI properties
                  * CallingUri: calling SIP URI properties
                  * DateTime: routes calls based on the date and/or time the
                    call arrived at the call router
                  * PhoneContext: called or calling phone context properties
                  * CalledPhoneContext: called phone context properties
                  * CallingPhoneContext: calling phone context properties
                  * SipUsername: called or calling SIP username properties
                  * CalledSipUsername: called SIP username properties
                  * CallingSipUsername: calling SIP username properties
                  * LastDivertingReason: last diverting reason properties
                  * LastDivertingE164: last diverting E.164 properties
                  * LastDivertingPartyNumberType: party number type of the last
                    diverting number properties
                  * LastDivertingPublicTypeOfNumber: public type of number of
                    the last diverting number properties
                  * LastDivertingPrivateTypeOfNumber: private type of number of
                    the last diverting number properties
                  * LastDivertingNumberPresentation: presentation of the last
                    diverting number properties
                  * OriginalDivertingReason: original diverting reason
                    properties
                  * OriginalDivertingE164: original diverting E.164 properties
                  * OriginalDivertingPartyNumberType: party number type of the
                    original diverting number properties
                  * OriginalDivertingPublicTypeOfNumber: public type of number
                    of the original diverting number properties
                  * OriginalDivertingPrivateTypeOfNumber: private type of
                    number of the original diverting number properties
                  * OriginalDivertingNumberPresentation: presentation of the
                    original diverting number properties
                  * CalledBearerChannel: called bearer channel properties
                  * CallingBearerChannel: calling bearer channel properties
                  * CallingSipPrivacy: calling SIP privacy properties

                See MappingStatus.ExpressionCriteria.

                "
  DEFVAL        { none }
  ::= { mappingTypeEntry 300 }

 -- Columnar:Transformation Applies to

 mappingTypeTransformation OBJECT-TYPE
  SYNTAX        INTEGER { none(100) , e164(200) , calledE164(300) , callingE164
                (400) , name(500) , calledName(600) , callingName(700) , ton
                (800) , calledTon(900) , callingTon(1000) , npi(1100) ,
                calledNpi(1200) , callingNpi(1300) , host(1400) , calledHost
                (1500) , callingHost(1600) , callingPi(1700) , callingSi(1800)
                , callingItc(1900) , uri(2000) , calledUri(2100) , callingUri
                (2200) , phoneContext(2300) , calledPhoneContext(2400) ,
                callingPhoneContext(2500) , sipUsername(2600) ,
                calledSipUsername(2700) , callingSipUsername(2800) ,
                lastDivertingReason(2900) , lastDivertingE164(3000) ,
                lastDivertingPartyNumberType(3010) ,
                lastDivertingPublicTypeOfNumber(3020) ,
                lastDivertingPrivateTypeOfNumber(3030) ,
                lastDivertingNumberPresentation(3040) , originalDivertingReason
                (3100) , originalDivertingE164(3200) ,
                originalDivertingPartyNumberType(3300) ,
                originalDivertingPublicTypeOfNumber(3400) ,
                originalDivertingPrivateTypeOfNumber(3500) ,
                originalDivertingNumberPresentation(3600) , calledBearerChannel
                (3700) , callingBearerChannel(3800) , debug(60000) }
  MAX-ACCESS    read-write
  STATUS        current
  DESCRIPTION " Transformation Applies to

                Call properties to transform. The transformation is defined in
                the MappingExpression.Transformation parameter.

                The call properties can be:

                  * E164: called or calling E.164 properties.
                  * CalledE164: called E.164 properties.
                  * CallingE164: calling E.164 properties.
                  * Name: called or calling name properties.
                  * CalledName: called name properties.
                  * CallingName: calling name properties.
                  * Ton: called or calling type of number properties.
                  * CalledTon: called type of number properties.
                  * CallingTon: calling type of number properties.
                  * Npi: called or calling numbering plan indicator properties.
                  * CalledNpi: called numbering plan indicator properties.
                  * CallingNpi: calling numbering plan indicator properties.
                  * Host: calling or called host properties.
                  * CalledHost: calling host properties.
                  * CallingHost: called host properties.
                  * CallingPi: calling presentation indicator.
                  * CallingSi: calling screening indicator.
                  * CallingItc: calling information transfer capability.
                  * Uri: calling or called SIP URI properties.
                  * CalledUri: called SIP URI properties.
                  * CallingUri: calling SIP URI properties.
                  * PhoneContext: calling or called phone context properties.
                  * CalledPhoneContext: called phone context properties.
                  * CallingPhoneContext: calling phone context properties.
                  * SipUsername: calling or called SIP username properties.
                  * CalledSipUsername: called SIP username properties.
                  * CallingSipUsername: calling SIP username properties.
                  * LastDivertingReason: last diverting reason properties.
                  * LastDivertingE164: last diverting E.164 properties.
                  * LastDivertingPartyNumberType: party number type of the last
                    diverting number properties.
                  * LastDivertingPublicTypeOfNumber: public type of number of
                    the last diverting number properties.
                  * LastDivertingPrivateTypeOfNumber: private type of number of
                    the last diverting number properties.
                  * LastDivertingNumberPresentation: presentation of the last
                    diverting number properties.
                  * OriginalDivertingReason: original diverting reason
                    properties.
                  * OriginalDivertingE164: original diverting E.164 properties.
                  * OriginalDivertingPartyNumberType: party number type of the
                    original diverting number properties.
                  * OriginalDivertingPublicTypeOfNumber: public type of number
                    of the original diverting number properties.
                  * OriginalDivertingPrivateTypeOfNumber: private type of
                    number of the original diverting number properties.
                  * OriginalDivertingNumberPresentation: presentation of the
                    original diverting number properties.
                  * CalledBearerChannel: called bearer channel properties.
                  * CallingBearerChannel: calling bearer channel properties.
                  * Debug: reserved for debug configuration.

                See MappingStatus.Transformation parameter.

                "
  DEFVAL        { none }
  ::= { mappingTypeEntry 400 }

 -- Columnar:Config Status

 mappingTypeConfigStatus OBJECT-TYPE
  SYNTAX        OCTET STRING
  MAX-ACCESS    read-only
  STATUS        current
  DESCRIPTION " Config Status

                Configuration status of the row.

                Indicates if the configuration of the row is valid.

                "
  ::= { mappingTypeEntry 500 }

 -- Row command:Up

 mappingTypeUp OBJECT-TYPE
  SYNTAX        INTEGER { noOp(0), up(10) }
  MAX-ACCESS    read-write
  STATUS        current
  DESCRIPTION " Up

                Moves the current row upwards.
                "
  DEFVAL        { noOp }
  ::= { mappingTypeEntry 600 }

 -- Row command:Down

 mappingTypeDown OBJECT-TYPE
  SYNTAX        INTEGER { noOp(0), down(10) }
  MAX-ACCESS    read-write
  STATUS        current
  DESCRIPTION " Down

                Moves the current row downwards.
                "
  DEFVAL        { noOp }
  ::= { mappingTypeEntry 700 }

 -- Row command:Insert

 mappingTypeInsert OBJECT-TYPE
  SYNTAX        INTEGER { noOp(0), insert(10) }
  MAX-ACCESS    read-write
  STATUS        current
  DESCRIPTION " Insert

                Inserts a new row before this row.
                "
  DEFVAL        { noOp }
  ::= { mappingTypeEntry 800 }

 -- Row command:Delete

 mappingTypeDelete OBJECT-TYPE
  SYNTAX        INTEGER { noOp(0), delete(10) }
  MAX-ACCESS    read-write
  STATUS        current
  DESCRIPTION " Delete

                Deletes this row.
                "
  DEFVAL        { noOp }
  ::= { mappingTypeEntry 900 }

-- End of table:Transformations

-- *****************************************************************************

-- Table:Transformation Rules

-- *****************************************************************************

mappingExpressionTable OBJECT-TYPE
 SYNTAX        SEQUENCE OF MappingExpressionEntry
 MAX-ACCESS    not-accessible
 STATUS        current
 DESCRIPTION " Transformation Rules

               This table shows the transformation rules used by the call
               routing service. The Transformations (MappingType) table
               contains the transformation related to this rule. The
               configuration is not used until the ApplyConfig command is
               executed.

               "
 ::= { cRoutMIBObjects 700 }
 mappingExpressionEntry OBJECT-TYPE
  SYNTAX        MappingExpressionEntry
  MAX-ACCESS    not-accessible
  STATUS        current
  DESCRIPTION " A row in table Transformation Rules. "
  INDEX         {
                  mappingExpressionIndex
                }

  ::= { mappingExpressionTable 1 }

 MappingExpressionEntry ::= SEQUENCE
 {
   mappingExpressionIndex          Unsigned32,
   mappingExpressionName           OCTET STRING,
   mappingExpressionCriteria       OCTET STRING,
   mappingExpressionTransformation OCTET STRING,
   mappingExpressionSubMappings    OCTET STRING,
   mappingExpressionConfigStatus   OCTET STRING,
   mappingExpressionUp             INTEGER,
   mappingExpressionDown           INTEGER,
   mappingExpressionInsert         INTEGER,
   mappingExpressionDelete         INTEGER
 }

 -- Index:Index

 mappingExpressionIndex OBJECT-TYPE
  SYNTAX        Unsigned32
  MAX-ACCESS    read-only
  STATUS        current
  DESCRIPTION " Index

                Unique identifier of the row in the table.
                "
  ::= { mappingExpressionEntry 100 }

 -- Row command:Delete

 mappingExpressionDelete OBJECT-TYPE
  SYNTAX        INTEGER { noOp(0), delete(10) }
  MAX-ACCESS    read-write
  STATUS        current
  DESCRIPTION " Delete

                Deletes this row.
                "
  DEFVAL        { noOp }
  ::= { mappingExpressionEntry 1000 }

 -- Columnar:Name

 mappingExpressionName OBJECT-TYPE
  SYNTAX        OCTET STRING ( SIZE(0..64) )
  MAX-ACCESS    read-write
  STATUS        current
  DESCRIPTION " Name

                Name of the transformation rule defined by this row. It must
                match the name of a row in the Transformations (MappingType)
                table.

                More than one row can have the same name. In that case, the
                first row matching the call will be used. The row are used in
                ascending order.

                See MappingType.Name.

                "
  DEFVAL        { "" }
  ::= { mappingExpressionEntry 200 }

 -- Columnar:Criteria Rule

 mappingExpressionCriteria OBJECT-TYPE
  SYNTAX        OCTET STRING ( SIZE(0..256) )
  MAX-ACCESS    read-write
  STATUS        current
  DESCRIPTION " Criteria Rule

                The call property part of the criteria used to determine if the
                transformation rule can be applied or not. The other part of
                the criteria is the expression defined in the
                MappingType.Criteria parameter.

                The expression syntax is related to the selected criteria
                properties or can be a special tag:

                  * E164: regular expression
                  * CalledE164: regular expression
                  * CallingE164: regular expression
                  * Name: regular expression
                  * CalledName: regular expression
                  * CallingName: regular expression
                  * Ton: 'unknown', 'international', 'national', 'network',
                    'subscriber', or 'abbreviated'
                  * CalledTon: 'unknown', 'international', 'national',
                    'network', 'subscriber', or 'abbreviated'
                  * CallingTon: 'unknown', 'international', 'national',
                    'network', 'subscriber', or 'abbreviated'
                  * Npi: 'unknown', 'isdn', 'data', 'telex', 'national', or
                    'private'
                  * CalledNpi: 'unknown', 'isdn', 'data', 'telex', 'national',
                    or 'private'.
                  * CallingNpi: 'unknown', 'isdn', 'data', 'telex', 'national',
                    or 'private'.
                  * Host: Regular expression. The call property format is 'Fqdn
                    [:port]'. If the '[:port]' is not present, the table uses
                    the well-known port of the signaling protocol.
                  * CalledHost: Regular expression. The call property format is
                    'Fqdn[:port]'. If the '[:port]' is not present, the table
                    uses the well-known port of the signaling protocol.
                  * CallingHost: Regular expression. The call property format
                    is 'Fqdn[:port]'. If the '[:port]' is not present, the
                    table uses the well-known port of the signaling protocol.
                  * CallingPi: 'allowed', 'restricted', or 'interworking'
                  * CallingSi: 'not-screened', 'passed', 'failed', or 'network'
                  * CallingItc: 'speech', 'unrestricted', 'restricted',
                    '3.1Khz', 'udi-ta', or 'video'
                  * DateTime: day of week and time period and/or date and time
                    period
                  * PhoneContext: regular expression
                  * CalledPhoneContext: regular expression
                  * CallingPhoneContext: regular expression
                  * SipUsername: regular expression
                  * CalledSipUsername: regular expression
                  * CallingSipUsername: regular expression
                  * LastDivertingReason: 'cfu', 'cfb', 'cfnr', or 'unknown'
                  * LastDivertingE164: regular expression
                  * LastDivertingPartyNumberType: 'unknown', 'public', or
                    'private'
                  * LastDivertingPublicTypeOfNumber: 'unknown',
                    'international', 'national', 'network-specific', 'local',
                    or 'abbreviated'.
                  * LastDivertingPrivateTypeOfNumber: 'unknown', 'leg2-reg',
                    'leg1-reg', 'pisn-specific', 'subscriber', or
                    'abbreviated'.
                  * LastDivertingNumberPresentation: 'allowed', 'restricted',
                    'interworking', or 'restricted-address'
                  * OriginalDivertingReason: 'cfu', 'cfb', 'cfnr', or 'unknown'
                  * OriginalDivertingE164: regular expression
                  * OriginalDivertingPartyNumberType: 'unknown', 'public', or
                    'private'
                  * OriginalDivertingPublicTypeOfNumber: 'unknown',
                    'international', 'national', 'network-specific', 'local',
                    or 'abbreviated'
                  * OriginalDivertingPrivateTypeOfNumber: 'unknown',
                    'leg2-reg', 'leg1-reg', 'pisn-specific', 'subscriber', or
                    'abbreviated'
                  * OriginalDivertingNumberPresentation: 'allowed',
                    'restricted', 'interworking', or 'restricted-address'
                  * CalledBearerChannel: regular expression
                  * CallingBearerChannel: regular expression
                  * CallingSipPrivacy: 'disabled', 'none', or 'id'

                Special tags:

                  * <undefined>: Matches if the property is not defined for the
                    call.
                  * <default>: Always matches. Generally used to set a default
                    transformation if the previous transformation does not
                    match.

                Accepted DateTime formats:

                Date/Time Period format:

                  * 'DD.MM.YYYY/HH:MM:SS-DD.MM.YYYY/HH:MM:SS'
                  * 'DD.MM.YYYY/HH:MM:SS-HH:MM:SS'
                  * 'DD.MM.YYYY-DD.MM.YYYY'
                  * 'DD.MM.YYYY'
                  * 'HH:MM:SS-HH:MM:SS'

                Week Day/Time Period format:

                  * 'DDD'
                  * 'DDD,DDD...'
                  * 'DDD/HH:MM:SS-HH:MM:SS'
                  * 'DDD,DDD.../HH:MM:SS-HH:MM:SS'

                where DDD must be one of: SUN, MON, TUE, WED, THU, FRI, or SAT.

                Several of the previous formats can be concatenated to form one
                expression. They must be separated by |. Example: 25.12.2006 |
                SUN

                Note: Whitespace at the end of a regular expression is ignored.

                See MappingStatus.PropertiesCriteria.

                "
  DEFVAL        { "" }
  ::= { mappingExpressionEntry 300 }

 -- Columnar:Transformation Rule

 mappingExpressionTransformation OBJECT-TYPE
  SYNTAX        OCTET STRING ( SIZE(0..64) )
  MAX-ACCESS    read-write
  STATUS        current
  DESCRIPTION " Transformation Rule

                Transformation rule to apply to the call properties. The rule
                is applied on the call properties defined in the
                MappingType.Transformation parameter.

                The transformation rule syntax is related to the selected
                properties to transform:

                  * Ton: 'unknown', 'international', 'national', 'network',
                    'subscriber', or 'abbreviated'
                  * CalledTon: 'unknown', 'international', 'national',
                    'network', 'subscriber', or 'abbreviated'
                  * CallingTon: 'unknown', 'international', 'national',
                    'network', 'subscriber', or 'abbreviated'
                  * Npi: 'unknown', 'isdn', 'data', 'telex', 'national', or
                    'private'
                  * CalledNpi: 'unknown', 'isdn', 'data', 'telex', 'national',
                    or 'private'
                  * CallingNpi: 'unknown', 'isdn', 'data', 'telex', 'national',
                    or 'private'
                  * CallingPi: 'allowed', 'restricted', or 'interworking'
                  * CallingSi: 'not-screened', 'passed', 'failed', or 'network'
                  * CallingItc: 'speech', 'unrestricted', 'restricted',
                    '3.1Khz', 'udi-ta', or 'video'
                  * LastDivertingReason: 'cfu', 'cfb', 'cfnr', or 'unknown'
                  * LastDivertingPartyNumberType: 'unknown', 'public', or
                    'private'
                  * LastDivertingPublicTypeOfNumber: 'unknown',
                    'international', 'national', 'network-specific', 'local',
                    or 'abbreviated'
                  * LastDivertingPrivateTypeOfNumber: 'unknown', 'leg2-reg',
                    'leg1-reg', 'pisn-specific', 'subscriber', or 'abbreviated'
                  * LastDivertingNumberPresentation: 'allowed', 'restricted',
                    'interworking', or 'restricted-address'
                  * OriginalDivertingReason: 'cfu', 'cfb', 'cfnr', or 'unknown'
                  * OriginalDivertingPartyNumberType: 'unknown', 'public', or
                    'private'
                  * OriginalDivertingPublicTypeOfNumber: 'unknown',
                    'international', 'national', 'network-specific', 'local' or
                    'abbreviated'
                  * OriginalDivertingPrivateTypeOfNumber: 'unknown',
                    'leg2-reg', 'leg1-reg', 'pisn-specific', 'subscriber', or
                    'abbreviated'
                  * OriginalDivertingNumberPresentation: 'allowed',
                    'restricted', 'interworking', or 'restricted-address'
                  * All others: string where '\0' to '\9' is replaced by the
                    corresponding group in the regular expresion set in the
                    criteria rule (see MappingStatus.ExpressionCriteria). The
                    value can be set to the '<local_ip_port>' macro to replace
                    the properties by the local IP address and port of the
                    listening socket of the SIP gateway used to send the
                    INVITE.

                See MappingStatus.PropertiesToTransform.

                "
  DEFVAL        { "" }
  ::= { mappingExpressionEntry 400 }

 -- Columnar:Next Transformation

 mappingExpressionSubMappings OBJECT-TYPE
  SYNTAX        OCTET STRING ( SIZE(0..512) )
  MAX-ACCESS    read-write
  STATUS        current
  DESCRIPTION " Next Transformation

                Name of a next transformation to execute.

                More than one transformation can be specified. In that case,
                the transformations are separated with ',' and are executed in
                sequential order.

                "
  DEFVAL        { "" }
  ::= { mappingExpressionEntry 500 }

 -- Columnar:Config Status

 mappingExpressionConfigStatus OBJECT-TYPE
  SYNTAX        OCTET STRING
  MAX-ACCESS    read-only
  STATUS        current
  DESCRIPTION " Config Status

                Configuration status of the row.

                It indicates if the configuration of the row is valid.

                "
  ::= { mappingExpressionEntry 600 }

 -- Row command:Up

 mappingExpressionUp OBJECT-TYPE
  SYNTAX        INTEGER { noOp(0), up(10) }
  MAX-ACCESS    read-write
  STATUS        current
  DESCRIPTION " Up

                Moves the current row upwards.
                "
  DEFVAL        { noOp }
  ::= { mappingExpressionEntry 700 }

 -- Row command:Down

 mappingExpressionDown OBJECT-TYPE
  SYNTAX        INTEGER { noOp(0), down(10) }
  MAX-ACCESS    read-write
  STATUS        current
  DESCRIPTION " Down

                Moves the current row downwards.
                "
  DEFVAL        { noOp }
  ::= { mappingExpressionEntry 800 }

 -- Row command:Insert

 mappingExpressionInsert OBJECT-TYPE
  SYNTAX        INTEGER { noOp(0), insert(10) }
  MAX-ACCESS    read-write
  STATUS        current
  DESCRIPTION " Insert

                Inserts a new row before this row.
                "
  DEFVAL        { noOp }
  ::= { mappingExpressionEntry 900 }

-- End of table:Transformation Rules

-- *****************************************************************************

-- Table:Hunt

-- *****************************************************************************

huntTable OBJECT-TYPE
 SYNTAX        SEQUENCE OF HuntEntry
 MAX-ACCESS    not-accessible
 STATUS        current
 DESCRIPTION " Hunt

               This table shows the configured hunt to be used by the call
               routing service. The configuration is not used until the
               ApplyConfig command is executed.

               "
 ::= { cRoutMIBObjects 900 }
 huntEntry OBJECT-TYPE
  SYNTAX        HuntEntry
  MAX-ACCESS    not-accessible
  STATUS        current
  DESCRIPTION " A row in table Hunt. "
  INDEX         {
                  huntIndex
                }

  ::= { huntTable 1 }

 HuntEntry ::= SEQUENCE
 {
   huntIndex              Unsigned32,
   huntName               OCTET STRING,
   huntDestinations       OCTET STRING,
   huntSelectionAlgorithm INTEGER,
   huntTimeout            Unsigned32,
   huntCauses             OCTET STRING,
   huntConfigStatus       OCTET STRING,
   huntUp                 INTEGER,
   huntDown               INTEGER,
   huntInsert             INTEGER,
   huntDelete             INTEGER
 }

 -- Index:Index

 huntIndex OBJECT-TYPE
  SYNTAX        Unsigned32
  MAX-ACCESS    read-only
  STATUS        current
  DESCRIPTION " Index

                Unique identifier of the row in the table.
                "
  ::= { huntEntry 100 }

 -- Row command:Insert

 huntInsert OBJECT-TYPE
  SYNTAX        INTEGER { noOp(0), insert(10) }
  MAX-ACCESS    read-write
  STATUS        current
  DESCRIPTION " Insert

                Inserts a new row before this row.
                "
  DEFVAL        { noOp }
  ::= { huntEntry 1000 }

 -- Row command:Delete

 huntDelete OBJECT-TYPE
  SYNTAX        INTEGER { noOp(0), delete(10) }
  MAX-ACCESS    read-write
  STATUS        current
  DESCRIPTION " Delete

                Deletes this row.
                "
  DEFVAL        { noOp }
  ::= { huntEntry 1100 }

 -- Columnar:Name

 huntName OBJECT-TYPE
  SYNTAX        OCTET STRING ( SIZE(0..64) )
  MAX-ACCESS    read-write
  STATUS        current
  DESCRIPTION " Name

                Name of the hunt defined by this row. It must be unique in the
                table.
                "
  DEFVAL        { "" }
  ::= { huntEntry 200 }

 -- Columnar:Destinations

 huntDestinations OBJECT-TYPE
  SYNTAX        OCTET STRING
  MAX-ACCESS    read-write
  STATUS        current
  DESCRIPTION " Destinations

                List of hunt destinations separated by commas.

                The call destination can be:

                  * route-'name': the route 'name'
                  * hunt-'name': the hunt 'name'
                  * sip-'name':the SIP interface 'name'
                  * isdn-'name': the ISDN interface 'name'
                  * r2-'name': the R2 interface 'name'
                  * e&m-'name': the E&M interface 'name'
                  * fxs-'name': the FXS interface 'name'
                  * fxo-'name': the FXO interface 'name'

                Note: Only FXS interfaces are supported if 'Simultaneous' is
                selected for the Selection Algorithm parameter.

                Example: 'isdn-Slot2/Bri1, route-something'

                "
  DEFVAL        { "" }
  ::= { huntEntry 300 }

 -- Columnar:Selection Algorithm

 huntSelectionAlgorithm OBJECT-TYPE
  SYNTAX        INTEGER { sequential(100) , cyclic(200) , simultaneous(300) }
  MAX-ACCESS    read-write
  STATUS        current
  DESCRIPTION " Selection Algorithm

                Algorithm used to select the destination order.

                The destination order can be:

                  * Sequential: The hunt tries the destination in the same
                    order as listed. The first destination hunted is the first
                    listed.
                  * Cyclic: The hunt starts from the destination that follows
                    the destination used for the last hunt. Subsequent calls
                    try another first destination in a round-robin method.
                  * Simultaneous: The hunt tries every available destination at
                    the same time. The first destination to pick up has the
                    call. Other destinations stop ringing. This method can only
                    have FXS endpoints as destinations.

                Example of cyclic selection: If the destination is set to
                'x,y,z', the destination the hunt group tries is in the
                following order:

                 1. x,y,z
                 2. y,z,x
                 3. z,x,y
                 4. x,y,z

                "
  DEFVAL        { sequential }
  ::= { huntEntry 400 }

 -- Columnar:Timeout

 huntTimeout OBJECT-TYPE
  SYNTAX        Unsigned32 ( 0..100 )
  MAX-ACCESS    read-write
  STATUS        current
  DESCRIPTION " Timeout

                Maximal time allowed to the destination to handle the call.

                A value of '0' disables the timeout.

                This value is expressed in seconds (s).

                Note: Not applicable if 'Simultaneous' is used for the
                Selection Algorithm parameter.

                "
  DEFVAL        { 0 }
  ::= { huntEntry 500 }

 -- Columnar:Causes

 huntCauses OBJECT-TYPE
  SYNTAX        OCTET STRING ( SIZE(0..255) )
  MAX-ACCESS    read-write
  STATUS        current
  DESCRIPTION " Causes

                Lists the call rejection causes to continue the hunt. The
                causes are separated by commas. The available hunt causes are:

                Normal event:

                  * 1: unassigned (unallocated) number
                  * 2: no route to specified transit network
                  * 3: no route to destination
                  * 6: channel unacceptable
                  * 7: call awarded and being delivered in an established
                    channel
                  * 16: normal call clearing
                  * 17: user busy
                  * 18: no user responding
                  * 19: user alerting, no answer
                  * 21: call rejected
                  * 22: number changed
                  * 26: non-selected user clearing
                  * 27: destination out of order
                  * 28: invalid number format (incomplete number)
                  * 29: facility rejected
                  * 30: response to STATUS ENQUIRY
                  * 31: normal, unspecified

                Resource unavailable:

                  * 34: no circuit/channel available
                  * 38: network out of order
                  * 41: temporary failure
                  * 42: switching equipment congestion
                  * 43: access information discarded
                  * 44: requested circuit/channel not available
                  * 47: resource unavailable, unspecified

                Service or option not available:

                  * 57: bearer capability not authorised
                  * 58: bearer capability not presently available
                  * 63: service or option not available, unspecified

                Service or option not implemented:

                  * 65: bearer capability not implemented
                  * 66: channel type not implemented
                  * 69: requested facility not implemented
                  * 70: only restricted digital information bearer capability
                    is available
                  * 79: service or option not implemented, unspecified

                Invalid message:

                  * 81: invalid call reference value
                  * 82: identified channel does not exist
                  * 83: a suspended call exists, but this call identity does
                    not
                  * 84: call identity in use
                  * 85: no call suspended
                  * 86: call having the requested call identity has been
                    cleared
                  * 88: incompatible destination
                  * 91: invalid transit network selection
                  * 95: invalid message, unspecified

                Protocol error:

                  * 96: mandatory information element is missing
                  * 97: message type non-existent or not implemented
                  * 98: message not compatible with call state or message type
                    non-existent or not implemented
                  * 99: information element non-existent or not implemented
                  * 100: invalid information element contents
                  * 101: message not compatible with call state
                  * 102: recovery on time expiry
                  * 111: Protocol error, unspecified

                Interworking:

                  * 127: Interworking, unspecified

                Note: Not applicable if 'Simultaneous' is used for the
                Selection Algorithm parameter.

                "
  DEFVAL        { "31, 34, 38, 41, 42, 43, 44, 47" }
  ::= { huntEntry 600 }

 -- Columnar:Config Status

 huntConfigStatus OBJECT-TYPE
  SYNTAX        OCTET STRING
  MAX-ACCESS    read-only
  STATUS        current
  DESCRIPTION " Config Status

                Configuration status of the row.

                It indicates if the configuration of the row is valid.

                "
  ::= { huntEntry 700 }

 -- Row command:Up

 huntUp OBJECT-TYPE
  SYNTAX        INTEGER { noOp(0), up(10) }
  MAX-ACCESS    read-write
  STATUS        current
  DESCRIPTION " Up

                Moves the current row upwards.
                "
  DEFVAL        { noOp }
  ::= { huntEntry 800 }

 -- Row command:Down

 huntDown OBJECT-TYPE
  SYNTAX        INTEGER { noOp(0), down(10) }
  MAX-ACCESS    read-write
  STATUS        current
  DESCRIPTION " Down

                Moves the current row downwards.
                "
  DEFVAL        { noOp }
  ::= { huntEntry 900 }

-- End of table:Hunt

-- *****************************************************************************

-- Table:Signaling Properties

-- *****************************************************************************

signalingPropertiesTable OBJECT-TYPE
 SYNTAX        SEQUENCE OF SignalingPropertiesEntry
 MAX-ACCESS    not-accessible
 STATUS        current
 DESCRIPTION " Signaling Properties

               This table shows the configured signaling properties to be used
               by the call routing service. The configuration is not used until
               the ApplyConfig command is executed.

               "
 ::= { cRoutMIBObjects 1200 }
 signalingPropertiesEntry OBJECT-TYPE
  SYNTAX        SignalingPropertiesEntry
  MAX-ACCESS    not-accessible
  STATUS        current
  DESCRIPTION " A row in table Signaling Properties. "
  INDEX         {
                  signalingPropertiesIndex
                }

  ::= { signalingPropertiesTable 1 }

 SignalingPropertiesEntry ::= SEQUENCE
 {
   signalingPropertiesIndex                     Unsigned32,
   signalingPropertiesName                      OCTET STRING,
   signalingPropertiesEarlyConnect              MxEnableState,
   signalingPropertiesEarlyDisconnect           MxEnableState,
   signalingPropertiesDestinationHost           OCTET STRING,
   signalingPropertiesAllow180Sdp               MxEnableState,
   signalingPropertiesAllow183NoSdp             MxEnableState,
   signalingPropertiesPrivacy                   INTEGER,
   signalingPropertiesCallPropertiesTranslation OCTET STRING,
   signalingPropertiesSipHeadersTranslation     OCTET STRING,
   signalingPropertiesConfigStatus              OCTET STRING,
   signalingPropertiesUp                        INTEGER,
   signalingPropertiesDown                      INTEGER,
   signalingPropertiesInsert                    INTEGER,
   signalingPropertiesDelete                    INTEGER
 }

 -- Index:Index

 signalingPropertiesIndex OBJECT-TYPE
  SYNTAX        Unsigned32
  MAX-ACCESS    read-only
  STATUS        current
  DESCRIPTION " Index

                Unique identifier of the row in the table.
                "
  ::= { signalingPropertiesEntry 100 }

 -- Row command:Delete

 signalingPropertiesDelete OBJECT-TYPE
  SYNTAX        INTEGER { noOp(0), delete(10) }
  MAX-ACCESS    read-write
  STATUS        current
  DESCRIPTION " Delete

                Deletes this row.
                "
  DEFVAL        { noOp }
  ::= { signalingPropertiesEntry 1000 }

 -- Columnar:Name

 signalingPropertiesName OBJECT-TYPE
  SYNTAX        OCTET STRING ( SIZE(0..64) )
  MAX-ACCESS    read-write
  STATUS        current
  DESCRIPTION " Name

                Name of the signaling properties defined by this row. It must
                be unique in the table.
                "
  DEFVAL        { "" }
  ::= { signalingPropertiesEntry 200 }

 -- Columnar:Early Connect

 signalingPropertiesEarlyConnect OBJECT-TYPE
  SYNTAX        MxEnableState
  MAX-ACCESS    read-write
  STATUS        current
  DESCRIPTION " Early Connect

                Enable/Disable the early connect feature.

                When early connect is enabled, the SIP call is connected by
                sending a 200 OK message instead of a 183 Session Progress
                message with early media.

                "
  DEFVAL        { disable }
  ::= { signalingPropertiesEntry 300 }

 -- Columnar:Early Disconnect

 signalingPropertiesEarlyDisconnect OBJECT-TYPE
  SYNTAX        MxEnableState
  MAX-ACCESS    read-write
  STATUS        current
  DESCRIPTION " Early Disconnect

                Enable/Disable the early disconnect feature.

                When early disconnect is enabled, the SIP BYE message is sent
                upon ISDN 'Disconnect' signal reception.

                When early disconnect is disabled, the SIP BYE message is sent
                upon ISDN 'Call release' signal reception.

                If early disconnect is enabled but no ISDN 'Disconnect' message
                is received, the SIP BYE message will be sent upon receiving an
                ISDN 'Call release' as if the early disconnect was disabled.

                "
  DEFVAL        { disable }
  ::= { signalingPropertiesEntry 400 }

 -- Columnar:Destination Host

 signalingPropertiesDestinationHost OBJECT-TYPE
  SYNTAX        OCTET STRING ( SIZE(0..255) )
  MAX-ACCESS    read-write
  STATUS        current
  DESCRIPTION " Destination Host

                SIP message destination.

                The value can be set to the '<local_ip_port>' macro to replace
                the properties by the local IP address and port of the
                listening socket of the SIP gateway used to send the INVITE.

                "
  DEFVAL        { "" }
  ::= { signalingPropertiesEntry 500 }

 -- Columnar:Allow 180 SDP

 signalingPropertiesAllow180Sdp OBJECT-TYPE
  SYNTAX        MxEnableState
  MAX-ACCESS    read-write
  STATUS        current
  DESCRIPTION " Allow 180 SDP

                Enable/Disable the 180 with SDP allowed.

                When disabled, a SIP 183 with SDP is sent instead of a 180 with
                SDP.

                This does not affect the 180 without SDP.

                "
  DEFVAL        { enable }
  ::= { signalingPropertiesEntry 550 }

 -- Columnar:Allow 183 without SDP

 signalingPropertiesAllow183NoSdp OBJECT-TYPE
  SYNTAX        MxEnableState
  MAX-ACCESS    read-write
  STATUS        current
  DESCRIPTION " Allow 183 without SDP

                Enable/Disable the 183 without SDP allowed.

                When disabled, a 183 without SDP is not sent.

                This does not affect the 183 with SDP.

                "
  DEFVAL        { enable }
  ::= { signalingPropertiesEntry 560 }

 -- Columnar:Privacy

 signalingPropertiesPrivacy OBJECT-TYPE
  SYNTAX        INTEGER { disable(100) , none(200) , id(300) , rpid(400) }
  MAX-ACCESS    read-write
  STATUS        current
  DESCRIPTION " Privacy

                Sets the privacy level of the call.

                  * Disable: No privacy is used.
                  * None: Use P-Asserted Identity privacy.
                  * Id: Use P-Preferred Identity privacy.
                  * Rpid: Use Remote-Party-ID privacy.

                "
  DEFVAL        { disable }
  ::= { signalingPropertiesEntry 570 }

 -- Columnar:Call Property Translation Overrides

 signalingPropertiesCallPropertiesTranslation OBJECT-TYPE
  SYNTAX        OCTET STRING ( SIZE(0..512) )
  MAX-ACCESS    read-write
  STATUS        current
  DESCRIPTION " Call Property Translation Overrides

                Name of the call property translation to apply to the call.

                The translation modifies the call properties before the call is
                sent to its destination.

                More than one translation can be specified. In this case, the
                translations are separated with ',' and are executed in
                sequential order.

                "
  DEFVAL        { "" }
  ::= { signalingPropertiesEntry 580 }

 -- Columnar:SIP Headers Translation Overrides

 signalingPropertiesSipHeadersTranslation OBJECT-TYPE
  SYNTAX        OCTET STRING ( SIZE(0..512) )
  MAX-ACCESS    read-write
  STATUS        current
  DESCRIPTION " SIP Headers Translation Overrides

                Name of the SIP header translations to apply to the call.

                The translation modifies the SIP headers before the call is
                sent to its destination.

                More than one translation can be specified. In that case, the
                translations are separated with ',' and are executed in
                sequential order.

                "
  DEFVAL        { "" }
  ::= { signalingPropertiesEntry 590 }

 -- Columnar:Config Status

 signalingPropertiesConfigStatus OBJECT-TYPE
  SYNTAX        OCTET STRING
  MAX-ACCESS    read-only
  STATUS        current
  DESCRIPTION " Config Status

                Configuration status of the row.

                It indicates if the configuration of the row is valid.

                "
  ::= { signalingPropertiesEntry 600 }

 -- Row command:Up

 signalingPropertiesUp OBJECT-TYPE
  SYNTAX        INTEGER { noOp(0), up(10) }
  MAX-ACCESS    read-write
  STATUS        current
  DESCRIPTION " Up

                Moves the current row upwards.
                "
  DEFVAL        { noOp }
  ::= { signalingPropertiesEntry 700 }

 -- Row command:Down

 signalingPropertiesDown OBJECT-TYPE
  SYNTAX        INTEGER { noOp(0), down(10) }
  MAX-ACCESS    read-write
  STATUS        current
  DESCRIPTION " Down

                Moves the current row downwards.
                "
  DEFVAL        { noOp }
  ::= { signalingPropertiesEntry 800 }

 -- Row command:Insert

 signalingPropertiesInsert OBJECT-TYPE
  SYNTAX        INTEGER { noOp(0), insert(10) }
  MAX-ACCESS    read-write
  STATUS        current
  DESCRIPTION " Insert

                Inserts a new row before this row.
                "
  DEFVAL        { noOp }
  ::= { signalingPropertiesEntry 900 }

-- End of table:Signaling Properties

-- *****************************************************************************

-- Table:SIP Header Translation Overrides

-- *****************************************************************************

sipHeadersTranslationTable OBJECT-TYPE
 SYNTAX        SEQUENCE OF SipHeadersTranslationEntry
 MAX-ACCESS    not-accessible
 STATUS        current
 DESCRIPTION " SIP Header Translation Overrides

               This table shows the configured SIP header translations to be
               used by the call routing service. The configuration is not used
               until the ApplyConfig command is executed.

               "
 ::= { cRoutMIBObjects 1400 }
 sipHeadersTranslationEntry OBJECT-TYPE
  SYNTAX        SipHeadersTranslationEntry
  MAX-ACCESS    not-accessible
  STATUS        current
  DESCRIPTION " A row in table SIP Header Translation Overrides. "
  INDEX         {
                  sipHeadersTranslationIndex
                }

  ::= { sipHeadersTranslationTable 1 }

 SipHeadersTranslationEntry ::= SEQUENCE
 {
   sipHeadersTranslationIndex        Unsigned32,
   sipHeadersTranslationName         OCTET STRING,
   sipHeadersTranslationSipHeader    INTEGER,
   sipHeadersTranslationBuiltFrom    INTEGER,
   sipHeadersTranslationFixValue     OCTET STRING,
   sipHeadersTranslationConfigStatus OCTET STRING,
   sipHeadersTranslationUp           INTEGER,
   sipHeadersTranslationDown         INTEGER,
   sipHeadersTranslationInsert       INTEGER,
   sipHeadersTranslationDelete       INTEGER
 }

 -- Index:Index

 sipHeadersTranslationIndex OBJECT-TYPE
  SYNTAX        Unsigned32
  MAX-ACCESS    read-only
  STATUS        current
  DESCRIPTION " Index

                Unique identifier of the row in the table.
                "
  ::= { sipHeadersTranslationEntry 100 }

 -- Row command:Delete

 sipHeadersTranslationDelete OBJECT-TYPE
  SYNTAX        INTEGER { noOp(0), delete(10) }
  MAX-ACCESS    read-write
  STATUS        current
  DESCRIPTION " Delete

                Deletes this row.
                "
  DEFVAL        { noOp }
  ::= { sipHeadersTranslationEntry 1000 }

 -- Columnar:Name

 sipHeadersTranslationName OBJECT-TYPE
  SYNTAX        OCTET STRING ( SIZE(0..64) )
  MAX-ACCESS    read-write
  STATUS        current
  DESCRIPTION " Name

                Name of the SIP header translation defined by this row.
                "
  DEFVAL        { "" }
  ::= { sipHeadersTranslationEntry 200 }

 -- Columnar:SIP Header

 sipHeadersTranslationSipHeader OBJECT-TYPE
  SYNTAX        INTEGER { fromHeaderHostPart(100) , fromHeaderUserPart(200) ,
                identityHeaderHostPart(300) , identityHeaderUserPart(400) ,
                identityHeaderPhoneNumber(500) , identityHeaderFriendlyName
                (550) , requestLineHostPart(600) , requestLineUserPart(700) ,
                toHeaderHostPart(800) , toHeaderUserPart(900) }
  MAX-ACCESS    read-write
  STATUS        current
  DESCRIPTION " SIP Header

                Sets which SIP header is modified by this translation.

                The SIP headers can be:

                  * FromHeaderHostPart: host part of the From header URI
                  * FromHeaderUserPart: user part of the From header URI
                  * IdentityHeaderHostPart: host part of the Identity header
                    URI
                  * IdentityHeaderUserPart: user part of the Identity header
                    URI
                  * IdentityHeaderPhoneNumber: phone number in the Identity
                    header tel URL
                  * IdentityHeaderFriendlyName: friendly name in the Identity
                    header URI
                  * RequestLineHostPart: host part of the Request line URI
                  * RequestLineUserPart: user part of the Request line URI
                  * ToHeaderHostPart: host part of the To header URI
                  * ToHeaderUserPart: user part of the To header URI

                "
  DEFVAL        { fromHeaderHostPart }
  ::= { sipHeadersTranslationEntry 300 }

 -- Columnar:Based On

 sipHeadersTranslationBuiltFrom OBJECT-TYPE
  SYNTAX        INTEGER { calledE164(100) , destinationHost(200) , domain(300)
                , fixValue(400) , hostName(500) , localIp(600) ,
                callingBearerChannel(700) , sipEndpointUsername(800) ,
                callingName(900) , callingE164(1000) }
  MAX-ACCESS    read-write
  STATUS        current
  DESCRIPTION " Based On

                Sets what information is used to build the selected SIP header.

                The information can be retrieved from:

                  * CalledE164: the called party E.164 property
                  * DestinationHost:the destination host configured in the
                    signaling properties of which this translation is part
                  * Domain: the domain name configured in the unit
                  * FixValue: a fixed value (see SipHeadersTranslation.FixValue
                    )
                  * HostName: the host name configured on the unit
                  * LocalIp: the local IP address
                  * CallingBearerChannel: the calling bearer channel
                  * SipEndpointUsername: the SIP username associated with the
                    endpoint
                  * CallingName: the calling party name property
                  * CallingE164: the calling party E.164 property

                "
  DEFVAL        { fixValue }
  ::= { sipHeadersTranslationEntry 400 }

 -- Columnar:Fixed Value

 sipHeadersTranslationFixValue OBJECT-TYPE
  SYNTAX        OCTET STRING ( SIZE(0..255) )
  MAX-ACCESS    read-write
  STATUS        current
  DESCRIPTION " Fixed Value

                Fixed value to be inserted in the SIP header when the
                SipHeadersTranslation.BuiltFrom parameter is set to 'FixValue'.

                "
  DEFVAL        { "" }
  ::= { sipHeadersTranslationEntry 500 }

 -- Columnar:Config Status

 sipHeadersTranslationConfigStatus OBJECT-TYPE
  SYNTAX        OCTET STRING
  MAX-ACCESS    read-only
  STATUS        current
  DESCRIPTION " Config Status

                Configuration status of the row.

                It indicates if the configuration of the row is valid.

                "
  ::= { sipHeadersTranslationEntry 600 }

 -- Row command:Up

 sipHeadersTranslationUp OBJECT-TYPE
  SYNTAX        INTEGER { noOp(0), up(10) }
  MAX-ACCESS    read-write
  STATUS        current
  DESCRIPTION " Up

                Moves the current row upwards.
                "
  DEFVAL        { noOp }
  ::= { sipHeadersTranslationEntry 700 }

 -- Row command:Down

 sipHeadersTranslationDown OBJECT-TYPE
  SYNTAX        INTEGER { noOp(0), down(10) }
  MAX-ACCESS    read-write
  STATUS        current
  DESCRIPTION " Down

                Moves the current row downwards.
                "
  DEFVAL        { noOp }
  ::= { sipHeadersTranslationEntry 800 }

 -- Row command:Insert

 sipHeadersTranslationInsert OBJECT-TYPE
  SYNTAX        INTEGER { noOp(0), insert(10) }
  MAX-ACCESS    read-write
  STATUS        current
  DESCRIPTION " Insert

                Inserts a new row before this row.
                "
  DEFVAL        { noOp }
  ::= { sipHeadersTranslationEntry 900 }

-- End of table:SIP Header Translation Overrides

-- *****************************************************************************

-- Table:Call Property Translation Overrides

-- *****************************************************************************

callPropertiesTranslationTable OBJECT-TYPE
 SYNTAX        SEQUENCE OF CallPropertiesTranslationEntry
 MAX-ACCESS    not-accessible
 STATUS        current
 DESCRIPTION " Call Property Translation Overrides

               This table shows the configured call properties translations to
               be used by the call routing service. The configuration is not
               used until the ApplyConfig command is executed.

               "
 ::= { cRoutMIBObjects 1600 }
 callPropertiesTranslationEntry OBJECT-TYPE
  SYNTAX        CallPropertiesTranslationEntry
  MAX-ACCESS    not-accessible
  STATUS        current
  DESCRIPTION " A row in table Call Property Translation Overrides. "
  INDEX         {
                  callPropertiesTranslationIndex
                }

  ::= { callPropertiesTranslationTable 1 }

 CallPropertiesTranslationEntry ::= SEQUENCE
 {
   callPropertiesTranslationIndex        Unsigned32,
   callPropertiesTranslationName         OCTET STRING,
   callPropertiesTranslationCallProperty INTEGER,
   callPropertiesTranslationBuiltFrom    INTEGER,
   callPropertiesTranslationFixValue     OCTET STRING,
   callPropertiesTranslationConfigStatus OCTET STRING,
   callPropertiesTranslationUp           INTEGER,
   callPropertiesTranslationDown         INTEGER,
   callPropertiesTranslationInsert       INTEGER,
   callPropertiesTranslationDelete       INTEGER
 }

 -- Index:Index

 callPropertiesTranslationIndex OBJECT-TYPE
  SYNTAX        Unsigned32
  MAX-ACCESS    read-only
  STATUS        current
  DESCRIPTION " Index

                Unique identifier of the row in the table.
                "
  ::= { callPropertiesTranslationEntry 100 }

 -- Row command:Delete

 callPropertiesTranslationDelete OBJECT-TYPE
  SYNTAX        INTEGER { noOp(0), delete(10) }
  MAX-ACCESS    read-write
  STATUS        current
  DESCRIPTION " Delete

                Deletes this row.
                "
  DEFVAL        { noOp }
  ::= { callPropertiesTranslationEntry 1000 }

 -- Columnar:Name

 callPropertiesTranslationName OBJECT-TYPE
  SYNTAX        OCTET STRING ( SIZE(0..64) )
  MAX-ACCESS    read-write
  STATUS        current
  DESCRIPTION " Name

                Name of the call property translation defined by this row.
                "
  DEFVAL        { "" }
  ::= { callPropertiesTranslationEntry 200 }

 -- Columnar:Call Property

 callPropertiesTranslationCallProperty OBJECT-TYPE
  SYNTAX        INTEGER { calledE164(100) , callingE164(200) , calledName(300)
                , callingName(400) , calledUri(500) , callingUri(600) ,
                calledBearerChannel(700) }
  MAX-ACCESS    read-write
  STATUS        current
  DESCRIPTION " Call Property

                Sets which call property is modified by this translation.

                The call properties can be:

                  * CalledE164: called party E.164 property
                  * CallingE164: calling party E.164 property
                  * CalledName: called party name property
                  * CallingName: calling party name property
                  * CalledUri: called URI name property
                  * CallingUri: calling URI name property
                  * CalledBearerChannel: called bearer channel property

                "
  DEFVAL        { calledE164 }
  ::= { callPropertiesTranslationEntry 300 }

 -- Columnar:Based On

 callPropertiesTranslationBuiltFrom OBJECT-TYPE
  SYNTAX        INTEGER { domain(100) , fixValue(200) , fromHeaderUri(300) ,
                fromHeaderFriendlyName(400) , fromHeaderUserPart(500) ,
                identityHeaderUri(600) , identityHeaderUserPart(700) ,
                identityHeaderPhoneNumber(800) , identityHeaderFriendlyName
                (850) , localIp(900) , requestLineUri(1000) ,
                requestLineUserPart(1100) , toHeaderUri(1200) ,
                toHeaderFriendlyName(1300) , toHeaderUserPart(1400) }
  MAX-ACCESS    read-write
  STATUS        current
  DESCRIPTION " Based On

                Sets what information is used to build the selected call
                property.

                The information can be retrieved from:

                  * Domain: the domain name configured in the unit.
                  * FixValue: a fixed value (see
                    CallPropertiesTranslation.FixValue)
                  * FromHeaderUri: the From header URI
                  * FromHeaderFriendlyName: the friendly name part of the From
                    header
                  * FromHeaderUserPart: the user part of the From header URI
                  * IdentityHeaderUri: the Identity header URI
                  * IdentityHeaderUserPart: the user part of the Identity
                    header URI
                  * IdentityHeaderPhoneNumber: the phone number in the Identity
                    header tel URL
                  * IdentityHeaderFriendlyName: the friendly name in the
                    Identity header URI
                  * LocalIp: the local IP address
                  * RequestLineUri: the Request line URI
                  * RequestLineUserPart: the user part of the Request line URI
                  * ToHeaderUri: the To header URI
                  * ToHeaderFriendlyName: Uthe friendly name part of the To
                    header
                  * ToHeaderUserPart: the user part of the To header URI

                "
  DEFVAL        { fixValue }
  ::= { callPropertiesTranslationEntry 400 }

 -- Columnar:Fixed Value

 callPropertiesTranslationFixValue OBJECT-TYPE
  SYNTAX        OCTET STRING ( SIZE(0..255) )
  MAX-ACCESS    read-write
  STATUS        current
  DESCRIPTION " Fixed Value

                Fixed value to be inserted in the call property when the
                CallPropertiesTranslation.BuiltFrom parameter is set to
                'FixValue'.

                "
  DEFVAL        { "" }
  ::= { callPropertiesTranslationEntry 500 }

 -- Columnar:Config Status

 callPropertiesTranslationConfigStatus OBJECT-TYPE
  SYNTAX        OCTET STRING
  MAX-ACCESS    read-only
  STATUS        current
  DESCRIPTION " Config Status

                Configuration status of the row.

                It indicates if the configuration of the row is valid.

                "
  ::= { callPropertiesTranslationEntry 600 }

 -- Row command:Up

 callPropertiesTranslationUp OBJECT-TYPE
  SYNTAX        INTEGER { noOp(0), up(10) }
  MAX-ACCESS    read-write
  STATUS        current
  DESCRIPTION " Up

                Moves the current row upwards.
                "
  DEFVAL        { noOp }
  ::= { callPropertiesTranslationEntry 700 }

 -- Row command:Down

 callPropertiesTranslationDown OBJECT-TYPE
  SYNTAX        INTEGER { noOp(0), down(10) }
  MAX-ACCESS    read-write
  STATUS        current
  DESCRIPTION " Down

                Moves the current row downwards.
                "
  DEFVAL        { noOp }
  ::= { callPropertiesTranslationEntry 800 }

 -- Row command:Insert

 callPropertiesTranslationInsert OBJECT-TYPE
  SYNTAX        INTEGER { noOp(0), insert(10) }
  MAX-ACCESS    read-write
  STATUS        current
  DESCRIPTION " Insert

                Inserts a new row before this row.
                "
  DEFVAL        { noOp }
  ::= { callPropertiesTranslationEntry 900 }

-- End of table:Call Property Translation Overrides

-- *****************************************************************************

-- Table:Auto-routing Config

-- *****************************************************************************

autoRoutingTable OBJECT-TYPE
 SYNTAX        SEQUENCE OF AutoRoutingEntry
 MAX-ACCESS    not-accessible
 STATUS        current
 DESCRIPTION " Auto-routing Config

               This table holds the parameters required for the configuration
               of the auto-routing feature.
               "
 ::= { cRoutMIBObjects 1900 }
 autoRoutingEntry OBJECT-TYPE
  SYNTAX        AutoRoutingEntry
  MAX-ACCESS    not-accessible
  STATUS        current
  DESCRIPTION " A row in table Auto-routing Config. "
  INDEX         {
                  autoRoutingEpId
                }

  ::= { autoRoutingTable 1 }

 AutoRoutingEntry ::= SEQUENCE
 {
   autoRoutingEpId                   OCTET STRING,
   autoRoutingAutoroutable           INTEGER,
   autoRoutingAutoRoutingGateway     OCTET STRING,
   autoRoutingAutoRoutingDestination OCTET STRING,
   autoRoutingE164                   OCTET STRING,
   autoRoutingSipUsername            OCTET STRING,
   autoRoutingName                   OCTET STRING
 }

 -- Index:Endpoint Identifier

 autoRoutingEpId OBJECT-TYPE
  SYNTAX        OCTET STRING
  MAX-ACCESS    read-only
  STATUS        current
  DESCRIPTION " Endpoint Identifier

                Character string that identifies an endpoint in other tables.
                "
  ::= { autoRoutingEntry 100 }

 -- Columnar:Auto-Routable

 autoRoutingAutoroutable OBJECT-TYPE
  SYNTAX        INTEGER { enable(100) , disable(200) , hardwareDependent(300) }
  MAX-ACCESS    read-write
  STATUS        current
  DESCRIPTION " Auto-Routable

                Determines whether or not automatic routes are generated for
                the endpoint when auto-routing is enabled (see the
                AutoRoutingEnable parameter).

                  * Enable: Automatic routes allowing incoming and outgoing
                    calls to and from the endpoint are added to the Route Table
                    when auto-routing is enabled.
                  * Disable: Automatic route generation is turned off for this
                    endpoint.
                  * HardwareDependent: Automatic routes are generated if the
                    endpoint belongs to an FXS interface.

                "
  DEFVAL        { hardwareDependent }
  ::= { autoRoutingEntry 200 }

 -- Columnar:Auto-Routing Gateway

 autoRoutingAutoRoutingGateway OBJECT-TYPE
  SYNTAX        OCTET STRING ( SIZE(0..255) )
  MAX-ACCESS    read-write
  STATUS        current
  DESCRIPTION " Auto-Routing Gateway

                The name of the SIP gateways to use as the destination of
                outgoing calls and the source of incoming calls when generating
                auto-routing rules.

                More than one SIP gateway can be defined. The SIP gateways
                names are separated by comas. Example: 'gw1,gw2,gw3'.

                When one SIP gateway is defined:

                  * A route is automatically created from the SIP gateway to
                    the telephony interface.
                  * A route is automatically created from the telephony
                    interface to the SIP gateway if the
                    AutoRouting.AutoRoutingDestination parameter is empty.
                    Otherwise, the destination of the route is the destination
                    defined in the AutoRouting.AutoRoutingDestination
                    parameter.

                When more than one SIP gateway is defined:

                  * Routes are automatically created from each defined SIP
                    gateway to the telephony interface.
                  * A route is automatically created from the telephony
                    interface to the hunt defined in the
                    AutoRouting.AutoRoutingDestination parameter.

                "
  DEFVAL        { "" }
  ::= { autoRoutingEntry 300 }

 -- Columnar:Auto-Routing Destination

 autoRoutingAutoRoutingDestination OBJECT-TYPE
  SYNTAX        OCTET STRING ( SIZE(0..255) )
  MAX-ACCESS    read-write
  STATUS        current
  DESCRIPTION " Auto-Routing Destination

                The destination to use for the routes from the telephony
                interface.

                The destination can be set to:

                  * route-'name': the route 'name'
                  * hunt-'name': the hunt 'name'
                  * sip-'name': the SIP interface 'name'
                  * isdn-'name': the ISDN interface 'name'
                  * r2-'name': the R2 interface 'name'
                  * e&m-'name': the E&M interface 'name'
                  * fxs-'name': the FXS interface 'name'
                  * fxo-'name': the FXO interface 'name'

                See the AutoRouting.AutoRoutingGateway parameter.

                "
  DEFVAL        { "" }
  ::= { autoRoutingEntry 350 }

 -- Columnar:E.164

 autoRoutingE164 OBJECT-TYPE
  SYNTAX        OCTET STRING ( SIZE(0..255) )
  MAX-ACCESS    read-only
  STATUS        current
  DESCRIPTION " E.164

                The telephone number associated with this endpoint, if any.
                This reflects the Username configured in the UserAgent table of
                the SIP Endpoint (SipEp) service as long as the name follows
                the E.164 syntax.

                "
  ::= { autoRoutingEntry 400 }

 -- Columnar:SIP Username

 autoRoutingSipUsername OBJECT-TYPE
  SYNTAX        OCTET STRING ( SIZE(0..255) )
  MAX-ACCESS    read-only
  STATUS        current
  DESCRIPTION " SIP Username

                The SIP username associated with this endpoint, if any. This
                simply reflects the Username configured in the UserAgent table
                of the SIP Endpoint (SipEp) service without the Username
                parameter.

                For example: If the SipEp.UserAgent.Username parameter is set
                to '123456_test', the SIP username field will display
                '123456_test'.

                "
  ::= { autoRoutingEntry 450 }

 -- Columnar:Name

 autoRoutingName OBJECT-TYPE
  SYNTAX        OCTET STRING ( SIZE(0..255) )
  MAX-ACCESS    read-only
  STATUS        current
  DESCRIPTION " Name

                The FriendlyName associated with this endpoint, if any. This
                reflects the FriendlyName configured in the UserAgent table of
                the SIP Endpoint (SipEp) service.

                "
  ::= { autoRoutingEntry 500 }

-- End of table:Auto-routing Config

-- Scalar:Criteria Type

autoRoutingCriteriaType OBJECT-TYPE
 SYNTAX        INTEGER { e164(100) , sipUsername(200) }
 MAX-ACCESS    read-write
 STATUS        current
 DESCRIPTION " Criteria Type

               Determines the type of criteria to use to create an automatic
               rule from SIP to the telephony endpoints.

                 * E164: The E164 associated with the endpoint is used as the
                   criteria. (See AutoRouting.E164).
                 * SipUsername: The SIP username associated with the endpoint
                   is used as the criteria. (See AutoRouting.SipUsername).

               "
 DEFVAL        { e164 }
 ::= { cRoutMIBObjects 2000 }

-- Scalar:Incoming Transformations

autoRoutingIncomingMappings OBJECT-TYPE
 SYNTAX        OCTET STRING ( SIZE(0..512) )
 MAX-ACCESS    read-write
 STATUS        current
 DESCRIPTION " Incoming Transformations

               Name of the transformations associated with the route from the
               SIP gateway to the endpoint.

               More than one transformation can be specified. In that case, the
               transformations are separated with ',' and are executed in an
               sequential order.

               See also Route.Mappings.

               "
 DEFVAL        { "" }
 ::= { cRoutMIBObjects 2100 }

-- Scalar:Outgoing Transformations

autoRoutingOutgoingMappings OBJECT-TYPE
 SYNTAX        OCTET STRING ( SIZE(0..512) )
 MAX-ACCESS    read-write
 STATUS        current
 DESCRIPTION " Outgoing Transformations

               Name of the transformations associated with the route from the
               endpoint to the SIP gateway.

               More than one transformation can be specified. In this case, the
               transformations are separated with ',' and are executed in
               sequential order.

               See also Route.Mappings

               "
 DEFVAL        { "" }
 ::= { cRoutMIBObjects 2200 }

-- Scalar:Incoming Signaling Properties

autoRoutingIncomingSignalingProperties OBJECT-TYPE
 SYNTAX        OCTET STRING ( SIZE(0..512) )
 MAX-ACCESS    read-write
 STATUS        current
 DESCRIPTION " Incoming Signaling Properties

               Name of the signaling properties associated with the route from
               the SIP gateway to the endpoint.

               See also Route.SignalingProperties

               "
 DEFVAL        { "" }
 ::= { cRoutMIBObjects 2300 }

-- Scalar:Outgoing Signaling Properties

autoRoutingOutgoingSignalingProperties OBJECT-TYPE
 SYNTAX        OCTET STRING ( SIZE(0..512) )
 MAX-ACCESS    read-write
 STATUS        current
 DESCRIPTION " Outgoing Signaling Properties

               Name of the signaling properties associated with the route from
               the endpoint to the SIP gateway.

               See also Route.SignalingProperties

               "
 DEFVAL        { "" }
 ::= { cRoutMIBObjects 2400 }

-- *****************************************************************************

-- Table:SIP Redirects

-- *****************************************************************************

sipRedirectTable OBJECT-TYPE
 SYNTAX        SEQUENCE OF SipRedirectEntry
 MAX-ACCESS    not-accessible
 STATUS        current
 DESCRIPTION " SIP Redirects

               This table allows the configuration of SIP redirections that can
               be used as Route destinations. When the Route source is a SIP
               interface, incoming SIP Invites are replied with a 302 'Moved
               Temporarily' SIP response.
               "
 ::= { cRoutMIBObjects 2500 }
 sipRedirectEntry OBJECT-TYPE
  SYNTAX        SipRedirectEntry
  MAX-ACCESS    not-accessible
  STATUS        current
  DESCRIPTION " A row in table SIP Redirects. "
  INDEX         {
                  sipRedirectIndex
                }

  ::= { sipRedirectTable 1 }

 SipRedirectEntry ::= SEQUENCE
 {
   sipRedirectIndex           Unsigned32,
   sipRedirectName            OCTET STRING,
   sipRedirectDestinationHost OCTET STRING,
   sipRedirectConfigStatus    OCTET STRING,
   sipRedirectUp              INTEGER,
   sipRedirectDown            INTEGER,
   sipRedirectInsert          INTEGER,
   sipRedirectDelete          INTEGER
 }

 -- Index:Index

 sipRedirectIndex OBJECT-TYPE
  SYNTAX        Unsigned32
  MAX-ACCESS    read-only
  STATUS        current
  DESCRIPTION " Index

                Unique identifier of the row in the table.
                "
  ::= { sipRedirectEntry 100 }

 -- Columnar:Name

 sipRedirectName OBJECT-TYPE
  SYNTAX        OCTET STRING ( SIZE(0..64) )
  MAX-ACCESS    read-write
  STATUS        current
  DESCRIPTION " Name

                Name of the SIP Redirect defined by this row. It must be unique
                in the table.
                "
  DEFVAL        { "" }
  ::= { sipRedirectEntry 200 }

 -- Columnar:Destination Host

 sipRedirectDestinationHost OBJECT-TYPE
  SYNTAX        OCTET STRING ( SIZE(0..255) )
  MAX-ACCESS    read-write
  STATUS        current
  DESCRIPTION " Destination Host

                Host address to be inserted in the 'Moved Temporarily'
                response.
                "
  DEFVAL        { "" }
  ::= { sipRedirectEntry 300 }

 -- Columnar:Config Status

 sipRedirectConfigStatus OBJECT-TYPE
  SYNTAX        OCTET STRING
  MAX-ACCESS    read-only
  STATUS        current
  DESCRIPTION " Config Status

                Configuration status of the row.

                Indicates if the configuration of the row is valid.

                "
  ::= { sipRedirectEntry 400 }

 -- Row command:Up

 sipRedirectUp OBJECT-TYPE
  SYNTAX        INTEGER { noOp(0), up(10) }
  MAX-ACCESS    read-write
  STATUS        current
  DESCRIPTION " Up

                Moves the current row upwards.
                "
  DEFVAL        { noOp }
  ::= { sipRedirectEntry 500 }

 -- Row command:Down

 sipRedirectDown OBJECT-TYPE
  SYNTAX        INTEGER { noOp(0), down(10) }
  MAX-ACCESS    read-write
  STATUS        current
  DESCRIPTION " Down

                Moves the current row downwards.
                "
  DEFVAL        { noOp }
  ::= { sipRedirectEntry 600 }

 -- Row command:Insert

 sipRedirectInsert OBJECT-TYPE
  SYNTAX        INTEGER { noOp(0), insert(10) }
  MAX-ACCESS    read-write
  STATUS        current
  DESCRIPTION " Insert

                Inserts a new row before this row.
                "
  DEFVAL        { noOp }
  ::= { sipRedirectEntry 700 }

 -- Row command:Delete

 sipRedirectDelete OBJECT-TYPE
  SYNTAX        INTEGER { noOp(0), delete(10) }
  MAX-ACCESS    read-write
  STATUS        current
  DESCRIPTION " Delete

                Deletes this row.
                "
  DEFVAL        { noOp }
  ::= { sipRedirectEntry 800 }

-- End of table:SIP Redirects

-- ****************************************************************************

-- Group:Notification Messages Configuration

-- ****************************************************************************

notificationsGroup OBJECT IDENTIFIER
 ::= { cRoutMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with a 'Informational' and
                    higher severity are issued.
                  * Warning: Notification messages with a 'Warning' and higher
                    severity are issued.
                  * Error: Notification messages with an 'Error' and higher
                    severity are issued.
                  * Critical: Notification messages with a 'Critical' severity
                    are issued.

                "
  DEFVAL        { warning }
  ::= { notificationsGroup 100 }

-- End of group:Notification Messages Configuration

-- ****************************************************************************

-- Group:Configuration Settings

-- ****************************************************************************

configurationGroup OBJECT IDENTIFIER
 ::= { cRoutMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for the
                configuration to fully take effect.

                  * Yes: Service needs to be restarted.
                  * No: Service does not need to be restarted.

                Services can be restarted by using the
                Scm.ServiceCommands.Restart command.

                "
  ::= { configurationGroup 100 }

-- End of group:Configuration Settings

END
