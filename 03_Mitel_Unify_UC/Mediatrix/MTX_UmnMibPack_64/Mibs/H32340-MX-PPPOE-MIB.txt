-- **SDOC***********************************************************************
-- *****************************************************************************
--
--             Copyright(c) 2003 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- *****************************************************************************
-- **EDOC***********************************************************************

H32340-MX-PPPOE-MIB
DEFINITIONS ::= BEGIN

IMPORTS
        MODULE-IDENTITY,
        OBJECT-TYPE
    FROM SNMPv2-SMI
        MODULE-COMPLIANCE,
        OBJECT-GROUP
    FROM SNMPv2-CONF
        mediatrixConfig
    FROM MX-SMI
        MxEnableState
    FROM MX-TC;

pppoeMIB MODULE-IDENTITY
    LAST-UPDATED "0307090000Z"
    ORGANIZATION "Mediatrix Telecom, Inc."
    CONTACT-INFO "Mediatrix Telecom, Inc.
                  4229, Garlock Street
                  Sherbrooke (Quebec)
                  Canada, J1L 2C8
                  Phone: (819) 829-8749
                  http://www.mediatrix.com"
    DESCRIPTION  "This MIB is used to customize properties of the PPPoE service."


    -- *************************************************************************
    -- Revision history
    -- *************************************************************************
    REVISION    "0307090000Z"
    DESCRIPTION "July 9, 2003
                    Creation."
    ::= { mediatrixConfig 105 }

pppoeMIBObjects OBJECT IDENTIFIER ::= { pppoeMIB 1 }
pppoeConformance OBJECT IDENTIFIER ::= { pppoeMIB 5 }


    -- *************************************************************************
    -- pppoeMIBObjects.
    -- *************************************************************************
    pppoeEnable OBJECT-TYPE
        SYNTAX      MxEnableState
        MAX-ACCESS  read-write
        STATUS      current
        DESCRIPTION "Enable/disable the PPPoE service.

                     enable :  The PPPoE service is enabled. The unit tries to establish a PPPoE
                               connection to the access concentrator (AC) and service specified in
                               pppoeAcName and pppoeServiceName.

                     disable : The PPPoE service is disabled.

                     Changes to this setting require a reboot to take effect.
                     
                     This variable's semantics are different depending on protocol and/or
                     hardware platforms.
                     Please refer to the documentation shipped with your device for more details."
        DEFVAL      { disable }
        ::= { pppoeMIBObjects  5 }

    pppoeAcName OBJECT-TYPE
        SYNTAX      OCTET STRING (SIZE (0..255))
        MAX-ACCESS  read-write
        STATUS      current
        DESCRIPTION "The name of the access concentrator (AC) to connect to on the next PPPoE
                     connection establishment.

                     This name is matched against the AC-Name field of the PADO packet sent by the
                     access concentrators. See RFC2516 section 5.2 for details.

                     If empty, the unit accepts the first offer that it receives.
                     
                     This variable's semantics are different depending on protocol and/or
                     hardware platforms.
                     Please refer to the documentation shipped with your device for more details."
        DEFVAL { "" }
        ::=  {  pppoeMIBObjects 10 }

    pppoeServiceName OBJECT-TYPE
        SYNTAX      OCTET STRING (SIZE (0..255))
        MAX-ACCESS  read-write
        STATUS      current
        DESCRIPTION "The name of the service requested to the access concentrator (AC) on the next
                     PPPoE connection establishment.

                     This string is used as the Service-Name field of the PADI packet broadcasted
                     to the access concentrators. See RFC2516 section 5.1 for details.

                     If empty, the unit sends a null Service-Name field meaning that any service is
                     acceptable.
                     
                     This variable's semantics are different depending on protocol and/or
                     hardware platforms.
                     Please refer to the documentation shipped with your device for more details."
        DEFVAL { "" }
        ::=  {  pppoeMIBObjects 15 }

    -- *************************************************************************
    -- Conformance information
    -- *************************************************************************
    pppoeCompliances OBJECT IDENTIFIER ::= { pppoeConformance 1 }

    pppoeComplVer1 MODULE-COMPLIANCE
        STATUS      current
        DESCRIPTION
            "List of groups required to support PPPoE service."
        MODULE  -- This Module
            MANDATORY-GROUPS {
                                pppoeConnectionCustomizationVer1
                             }
        ::= { pppoeCompliances 1 }

    -- *************************************************************************
    --  MIB variable grouping
    -- *************************************************************************
    pppoeGroups OBJECT IDENTIFIER ::= { pppoeConformance 5 }

    pppoeConnectionCustomizationVer1 OBJECT-GROUP
        OBJECTS {
                    pppoeEnable,
                    pppoeAcName,
                    pppoeServiceName
                }
        STATUS current
        DESCRIPTION "A collection of objects that defines the characteristics of a PPPoE connection."
        ::= { pppoeGroups 10 }

END
