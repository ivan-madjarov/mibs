-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************

DGW20-MX-ISDN-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

isdnMIB MODULE-IDENTITY
 LAST-UPDATED   "1905090000Z"
 ORGANIZATION " Mediatrix Telecom, Inc. "
 CONTACT-INFO " Mediatrix Telecom, Inc.
                4229, Garlock Street
                Sherbrooke (Quebec)
                Canada
                Phone: (819) 829-8749
                "
 DESCRIPTION  " Integrated Services Digital Network

                The Integrated Services Digital Network (ISDN) service manages
                the ISDN parameters for BRI and PRI telephony interfaces.
                "
 ::= { mediatrixServices 1850 }

isdnMIBObjects OBJECT IDENTIFIER ::= { isdnMIB 1 }

-- *****************************************************************************

-- Group:Primary Rate Interface Configuration

-- *****************************************************************************

primaryRateInterfaceGroup OBJECT IDENTIFIER
 ::= { isdnMIBObjects 200 }
 -- *****************************************************************************
 
 -- Table:Primary Rate Interface

 -- *****************************************************************************
 
 primaryRateInterfaceTable OBJECT-TYPE
  SYNTAX        SEQUENCE OF PrimaryRateInterfaceEntry
  MAX-ACCESS    not-accessible
  STATUS        current
  DESCRIPTION " Primary Rate Interface

                Configuration parameters related to the Primary Rate interfaces
                on this managed device.
                "
  ::= { primaryRateInterfaceGroup 100 }
  primaryRateInterfaceEntry OBJECT-TYPE
   SYNTAX        PrimaryRateInterfaceEntry
   MAX-ACCESS    not-accessible
   STATUS        current
   DESCRIPTION " A row in table Primary Rate Interface. "
   INDEX         {
                   primaryRateInterfaceName
                 }

   ::= { primaryRateInterfaceTable 1 }

  PrimaryRateInterfaceEntry ::= SEQUENCE
  {
    primaryRateInterfaceName                             OCTET STRING,
    primaryRateInterfaceEndpointType                     INTEGER,
    primaryRateInterfacePortPinout                       INTEGER,
    primaryRateInterfaceLineCoding                       INTEGER,
    primaryRateInterfaceLineFraming                      INTEGER,
    primaryRateInterfaceNetworkLocation                  INTEGER,
    primaryRateInterfacePreferredEncodingScheme          INTEGER,
    primaryRateInterfaceFallbackEncodingScheme           INTEGER,
    primaryRateInterfaceChannelRange                     OCTET STRING,
    primaryRateInterfaceIncomingChannelRange             OCTET STRING,
    primaryRateInterfaceOutgoingChannelRange             OCTET STRING,
    primaryRateInterfaceChannelAllocationStrategy        INTEGER,
    primaryRateInterfaceMaxActiveCalls                   Unsigned32,
    primaryRateInterfaceSignalInformationElementEnable   MxEnableState,
    primaryRateInterfaceInbandToneGenerationEnable       MxEnableState,
    primaryRateInterfaceInbandDtmfDialingEnable          MxEnableState,
    primaryRateInterfaceOverlapDialingEnable             MxEnableState,
    primaryRateInterfaceCallingNameMaxLength             Unsigned32,
    primaryRateInterfaceExclusiveBChannelSelectionEnable MxEnableState,
    primaryRateInterfaceSendingCompleteEnable            MxEnableState,
    primaryRateInterfaceClipEnable                       INTEGER,
    primaryRateInterfaceClirEnable                       MxEnableState,
    primaryRateInterfaceClirOverrideEnable               MxEnableState,
    primaryRateInterfaceSendRestartOnStartupEnable       MxEnableState
  }

  -- Index:Name

  primaryRateInterfaceName OBJECT-TYPE
   SYNTAX        OCTET STRING
   MAX-ACCESS    read-only
   STATUS        current
   DESCRIPTION " Name

                 Name that identifies the interface.
                 "
   ::= { primaryRateInterfaceEntry 100 }

  -- Columnar:Maximum Active Calls

  primaryRateInterfaceMaxActiveCalls OBJECT-TYPE
   SYNTAX        Unsigned32 ( 0..30 )
   MAX-ACCESS    read-write
   STATUS        current
   DESCRIPTION " Maximum Active Calls

                 Defines the maximum number of active calls on the interface.

                 Note: The special value 0 indicates no maximum number of active
                 calls.

                 "
   DEFVAL        { 0 }
   ::= { primaryRateInterfaceEntry 1000 }

  -- Columnar:Signal Information Element Enable

  primaryRateInterfaceSignalInformationElementEnable OBJECT-TYPE
   SYNTAX        MxEnableState
   MAX-ACCESS    read-write
   STATUS        current
   DESCRIPTION " Signal Information Element Enable

                 Defines whether the signal information element is enabled on
                 the interface. When activated at the Network UNI-side (
                 PrimaryRateInterfaceEndpointType parameter set to Nt), the
                 signal information element is sent to the User UNI-side. When
                 activated at the User UNI-side (
                 PrimaryRateInterfaceEndpointType parameter set to Te), the tone
                 indicated in the signal information element is played in the IP
                 direction.

                 "
   DEFVAL        { disable }
   ::= { primaryRateInterfaceEntry 1050 }

  -- Columnar:Inband Tone Generation Enable

  primaryRateInterfaceInbandToneGenerationEnable OBJECT-TYPE
   SYNTAX        MxEnableState
   MAX-ACCESS    read-write
   STATUS        current
   DESCRIPTION " Inband Tone Generation Enable

                 Defines whether inband tone generation is enabled on the
                 interface.

                 When activated at the User UNI-side (
                 PrimaryRateInterfaceEndpointType parameter set to Te), only the
                 ringback tone is generated.

                 When the SignalingChannel.Protocol parameter is set to 'QSIG'
                 and this parameter is activated, the incoming side of the call
                 plays the tones inband.

                 "
   DEFVAL        { enable }
   ::= { primaryRateInterfaceEntry 1100 }

  -- Columnar:Inband DTMF Dialing Enable

  primaryRateInterfaceInbandDtmfDialingEnable OBJECT-TYPE
   SYNTAX        MxEnableState
   MAX-ACCESS    read-write
   STATUS        current
   DESCRIPTION " Inband DTMF Dialing Enable

                 Defines whether inband DTMF dialing is enabled.
                 "
   DEFVAL        { enable }
   ::= { primaryRateInterfaceEntry 1200 }

  -- Columnar:Overlap Dialing Enable

  primaryRateInterfaceOverlapDialingEnable OBJECT-TYPE
   SYNTAX        MxEnableState
   MAX-ACCESS    read-write
   STATUS        current
   DESCRIPTION " Overlap Dialing Enable

                 Defines whether overlap dialing is enabled on the interface.
                 "
   DEFVAL        { enable }
   ::= { primaryRateInterfaceEntry 1300 }

  -- Columnar:Calling Name Maximum Length

  primaryRateInterfaceCallingNameMaxLength OBJECT-TYPE
   SYNTAX        Unsigned32 ( 0..82 )
   MAX-ACCESS    read-write
   STATUS        current
   DESCRIPTION " Calling Name Maximum Length

                 Defines the maximum length of the calling party name for calls
                 from SIP to ISDN on the interface.
                 "
   DEFVAL        { 34 }
   ::= { primaryRateInterfaceEntry 1400 }

  -- Columnar:Exclusive Bearer Channel Selection Enable

  primaryRateInterfaceExclusiveBChannelSelectionEnable OBJECT-TYPE
   SYNTAX        MxEnableState
   MAX-ACCESS    read-write
   STATUS        current
   DESCRIPTION " Exclusive Bearer Channel Selection Enable

                 Defines whether exclusive B-Channel selection is enabled for
                 calls from SIP to ISDN on the interface.
                 "
   DEFVAL        { disable }
   ::= { primaryRateInterfaceEntry 1500 }

  -- Columnar:Sending Complete Enable

  primaryRateInterfaceSendingCompleteEnable OBJECT-TYPE
   SYNTAX        MxEnableState
   MAX-ACCESS    read-write
   STATUS        current
   DESCRIPTION " Sending Complete Enable

                 Defines whether the Sending Complete information element in
                 SETUP messages is enabled for calls from SIP to ISDN on the
                 interface.
                 "
   DEFVAL        { enable }
   ::= { primaryRateInterfaceEntry 1600 }

  -- Columnar:Calling Line Information Presentation Enable

  primaryRateInterfaceClipEnable OBJECT-TYPE
   SYNTAX        INTEGER { userOnly(0) , enable(1) , disable(2) }
   MAX-ACCESS    read-write
   STATUS        current
   DESCRIPTION " Calling Line Information Presentation Enable

                 Enables the CLIP service, which is offered to the called party
                 to see the calling party's ISDN number. CLIP is complemented by
                 privacy rules controlled by the ClirEnable and
                 ClirOverrideEnable parameters. The ClipEnable parameter has the
                 following effect:

                   * UserOnly: Sends a Calling Number IE which contains the
                     calling number digits when acting as the User UNI-side (
                     PrimaryRateInterfaceEndpointType parameter set to Te)
                     otherwise the Calling Number IE is not sent.
                   * Enable: Sends a Calling Number IE which contains the
                     calling number digits.
                   * Disable: The Calling Number IE is never sent.

                 "
   DEFVAL        { userOnly }
   ::= { primaryRateInterfaceEntry 1700 }

  -- Columnar:Calling Line Information Restriction Enable

  primaryRateInterfaceClirEnable OBJECT-TYPE
   SYNTAX        MxEnableState
   MAX-ACCESS    read-write
   STATUS        current
   DESCRIPTION " Calling Line Information Restriction Enable

                 Enables the CLIR service, which is offered to the calling party
                 to restrict presentation of the calling party's ISDN number to
                 the called party.

                 Setting this parameter to 'Disable' disables the CLIR service.

                 Setting this parameter to 'Enable' enables the CLIR service.
                 This has the following effects:

                 For all ISDN signaling protocols except QSIG:

                   * On a TE interface at the originating network side, when
                     sending a SETUP message with a Calling Party Number (CPN)
                     IE, the Presentation Indicator (PI) is set to 'Restricted'.
                     The calling party number itself is included in the CPN IE
                     if available.
                   * On a NT interface at the originating network side, when
                     receiving a SETUP message with a CPN IE, the PI is set to
                     'Restricted'. The calling party number itself is forwarded.

                 For the QSIG signaling protocol:

                   * Sending a SETUP message: The PI is set to 'Restricted' in
                     the CPN IE inserted in the SETUP message sent to the ISDN,
                     unless the CLIR override option is set. However, even if PI
                     is set to 'Restricted', the calling number is included in
                     the CPN IE.
                   * Receiving a SETUP message: If PI is set in the received
                     message, the calling party number is removed, unless the
                     CLIR override option is set.

                 "
   DEFVAL        { disable }
   ::= { primaryRateInterfaceEntry 1725 }

  -- Columnar:Calling Line Information Restriction Override Enable

  primaryRateInterfaceClirOverrideEnable OBJECT-TYPE
   SYNTAX        MxEnableState
   MAX-ACCESS    read-write
   STATUS        current
   DESCRIPTION " Calling Line Information Restriction Override Enable

                 Enables the CLIR override option. This option allows the
                 calling party number to be presented to the destination party
                 even when the Calling Party Number (CPN) IE's Presentation
                 Indicator (PI) is set to 'Restricted'. This option is typically
                 used for police or emergency services.

                 Setting this parameter to 'Disable' disables the CLIR Override
                 option.

                 Setting this parameter to 'Enable' enables the CLIR Override
                 option. This has the following effects:

                 For all ISDN signaling protocols except QSIG:

                   * The override option acts on the NT interface of the
                     destination network side. It prevents the number to be
                     removed from the CPN IE inserted in the SETUP message sent
                     to the destination TE.

                 For the QSIG signaling protocol:

                   * The override option prevents the calling name to be removed
                     from the CPN IE in a received SETUP message.

                 "
   DEFVAL        { disable }
   ::= { primaryRateInterfaceEntry 1750 }

  -- Columnar:Send Restart On Startup Enable

  primaryRateInterfaceSendRestartOnStartupEnable OBJECT-TYPE
   SYNTAX        MxEnableState
   MAX-ACCESS    read-write
   STATUS        current
   DESCRIPTION " Send Restart On Startup Enable

                 Defines whether the RESTART message is sent upon a signaling
                 channel 'UP' event
                 "
   DEFVAL        { enable }
   ::= { primaryRateInterfaceEntry 1800 }

  -- Columnar:Endpoint Type

  primaryRateInterfaceEndpointType OBJECT-TYPE
   SYNTAX        INTEGER { te(100) , nt(200) }
   MAX-ACCESS    read-write
   STATUS        current
   DESCRIPTION " Endpoint Type

                 Defines the endpoint type:

                   * Te: Terminal Equipment
                   * Nt: Network Termination

                 When the SignalingChannel.Protocol parameter is set to QSIG,
                 the endpoint type will only be used in the second layer (LAPD)
                 since it is a concept that does not exist within QSIG.

                 "
   DEFVAL        { te }
   ::= { primaryRateInterfaceEntry 200 }

  -- Columnar:Port Pinout

  primaryRateInterfacePortPinout OBJECT-TYPE
   SYNTAX        INTEGER { auto(100) , te(200) , nt(300) }
   MAX-ACCESS    read-write
   STATUS        current
   DESCRIPTION " Port Pinout

                 Defines the port pinout:

                   * Auto: The pinout is set according to the endpoint type.
                   * Te: Force the pinout to TE regardless of the endpoint type.
                   * Nt: Force the pinout to NT regardless of the endpoint type.

                 See PrimaryRateInterface.EndpointType parameter for a
                 description of the endpoint type.

                 "
   DEFVAL        { auto }
   ::= { primaryRateInterfaceEntry 250 }

  -- Columnar:Line Coding

  primaryRateInterfaceLineCoding OBJECT-TYPE
   SYNTAX        INTEGER { b8zs(100) , hdb3(200) , ami(300) }
   MAX-ACCESS    read-write
   STATUS        current
   DESCRIPTION " Line Coding

                 Defines the transmission encoding of bits:

                   * B8ZS: Bipolar with 8-Zeros Substitution (T1 lines)
                   * HDB3: High-Density Bipolar with 3-zeros (E1 lines)
                   * AMI: Alternate Mark Inversion (E1 and T1 lines)

                 For further information, see ITU-T Recommendation G.703.

                 "
   DEFVAL        { hdb3 }
   ::= { primaryRateInterfaceEntry 400 }

  -- Columnar:Line Framing

  primaryRateInterfaceLineFraming OBJECT-TYPE
   SYNTAX        INTEGER { sf(100) , esf(200) , crc4(300) , noCrc4(400) }
   MAX-ACCESS    read-write
   STATUS        current
   DESCRIPTION " Line Framing

                 Defines the frame format:

                   * SF: Super frame. Sometimes known as D4 (T1 lines)
                   * ESF: Extended super frame (T1 lines)
                   * CRC4: Cyclic redundancy check 4 (E1 lines)
                   * NO-CRC4: No Cyclic redundancy check 4 (E1 lines)

                 For further information, see ITU-T Recommendation G.704.

                 "
   DEFVAL        { crc4 }
   ::= { primaryRateInterfaceEntry 500 }

  -- Columnar:Network Location

  primaryRateInterfaceNetworkLocation OBJECT-TYPE
   SYNTAX        INTEGER { user(100) , private(200) , public(300) , transit(400)
                 , international(500) }
   MAX-ACCESS    read-write
   STATUS        current
   DESCRIPTION " Network Location

                 Defines the value of the network location in the progress
                 indicator messages sent by the unit.
                 "
   DEFVAL        { user }
   ::= { primaryRateInterfaceEntry 600 }

  -- Columnar:Preferred Encoding Scheme

  primaryRateInterfacePreferredEncodingScheme OBJECT-TYPE
   SYNTAX        INTEGER { g711alaw(100) , g711ulaw(200) }
   MAX-ACCESS    read-write
   STATUS        current
   DESCRIPTION " Preferred Encoding Scheme

                 Defines the preferred data encoding scheme in the bearer
                 capabilities (user information layer 1 protocol). This encoding
                 scheme is used when initiating a call on the ISDN side.
                 "
   DEFVAL        { g711alaw }
   ::= { primaryRateInterfaceEntry 700 }

  -- Columnar:Fallback Encoding Scheme

  primaryRateInterfaceFallbackEncodingScheme OBJECT-TYPE
   SYNTAX        INTEGER { g711alaw(100) , g711ulaw(200) }
   MAX-ACCESS    read-write
   STATUS        current
   DESCRIPTION " Fallback Encoding Scheme

                 Defines the fallback data encoding scheme in the bearer
                 capabilities (user information layer 1 protocol).
                 "
   DEFVAL        { g711ulaw }
   ::= { primaryRateInterfaceEntry 750 }

  -- Columnar:Channel Range

  primaryRateInterfaceChannelRange OBJECT-TYPE
   SYNTAX        OCTET STRING ( SIZE(1..10) )
   MAX-ACCESS    read-write
   STATUS        current
   DESCRIPTION " Channel Range

                 Defines the range of active bearer channels.
                 "
   DEFVAL        { "1-30" }
   ::= { primaryRateInterfaceEntry 800 }

  -- Columnar:Channel Range Reserved for Incoming Calls

  primaryRateInterfaceIncomingChannelRange OBJECT-TYPE
   SYNTAX        OCTET STRING ( SIZE(0..255) )
   MAX-ACCESS    read-write
   STATUS        current
   DESCRIPTION " Channel Range Reserved for Incoming Calls

                 Bearer channels are by default usable for both incoming and
                 outgoing calls. Use this range to reserve channels for incoming
                 calls.

                 NOTE: Channels outside of the range defined by ChannelRange are
                 ignored.

                 NOTE: Channels reserved in both IncomingChannelRange and
                 OutgoingChannelRange parameters are considered usable for both
                 incoming and outgoing calls.

                 The string has the following syntax:

                   * ',': Separator between non-consecutive lists of channels or
                     single channel.
                   * 'n': A single channel, where n is the channel number.
                   * 'm-n': List of channels where m is the start channel number
                     and n is the end channel number.

                 NOTE: The space character is ignored and duplication is not
                 allowed. Channels must be specified in low to high order.

                 Example: '1,12-15': The accepted channels are 1, 12, 13, 14 and
                 15.

                 "
   DEFVAL        { "" }
   ::= { primaryRateInterfaceEntry 830 }

  -- Columnar:Channel Range Reserved for Outgoing Calls

  primaryRateInterfaceOutgoingChannelRange OBJECT-TYPE
   SYNTAX        OCTET STRING ( SIZE(0..255) )
   MAX-ACCESS    read-write
   STATUS        current
   DESCRIPTION " Channel Range Reserved for Outgoing Calls

                 Bearer channels are by default usable for both incoming and
                 outgoing calls. Use this range to reserve channels for outgoing
                 calls.

                 NOTE: Channels outside of the range defined by ChannelRange are
                 ignored.

                 NOTE: Channels reserved in both IncomingChannelRange and
                 OutgoingChannelRange parameters are considered usable for both
                 incoming and outgoing calls.

                 The string has the following syntax:

                   * ',': Separator between non-consecutive lists of channels or
                     single channel.
                   * 'n': A single channel, where n is the channel number.
                   * 'm-n': List of channels where m is the start channel number
                     and n is the end channel number.

                 NOTE: The space character is ignored and duplication is not
                 allowed. Channels must be specified in low to high order.

                 Example: '1,12-15': The accepted channels are 1, 12, 13, 14 and
                 15.

                 "
   DEFVAL        { "" }
   ::= { primaryRateInterfaceEntry 860 }

  -- Columnar:Channel Allocation Strategy

  primaryRateInterfaceChannelAllocationStrategy OBJECT-TYPE
   SYNTAX        INTEGER { ascending(100) , descending(200) ,
                 roundRobinAscending(300) , roundRobinDescending(400) }
   MAX-ACCESS    read-write
   STATUS        current
   DESCRIPTION " Channel Allocation Strategy

                 Defines the strategy for selecting bearer channels. Available
                 strategies are:

                   * Ascending: select the lowest-numbered non-busy bearer
                     channel
                   * Descending: select the highest-numbered non-busy bearer
                     channel
                   * RoundRobinAscending: use a cyclic round-robin search;
                     starting from the bearer channel that follows the bearer
                     channel used for the last call, select the lowest-numbered
                     non-busy bearer channel
                   * RoundRobinDescending: use a cyclic round-robin search;
                     starting from the bearer channel that precedes the bearer
                     channel used for the last call, select the highest-numbered
                     non-busy bearer channel

                 "
   DEFVAL        { ascending }
   ::= { primaryRateInterfaceEntry 900 }

 -- End of table:Primary Rate Interface

 -- *****************************************************************************
 
 -- Group:Primary Rate Interface Configuration

 -- *****************************************************************************
 
 primaryRateInterfaceInteropGroup OBJECT IDENTIFIER
  ::= { primaryRateInterfaceGroup 50000 }
  -- *****************************************************************************
  
  -- Table:Primary Rate Interface Interop

  -- *****************************************************************************
  
  primaryRateInterfaceInteropTable OBJECT-TYPE
   SYNTAX        SEQUENCE OF PrimaryRateInterfaceInteropEntry
   MAX-ACCESS    not-accessible
   STATUS        current
   DESCRIPTION " Primary Rate Interface Interop

                 Interop configuration parameters related to the Primary Rate interfaces on
                 this managed device.
                 "
   ::= { primaryRateInterfaceInteropGroup 100 }
   primaryRateInterfaceInteropEntry OBJECT-TYPE
    SYNTAX        PrimaryRateInterfaceInteropEntry
    MAX-ACCESS    not-accessible
    STATUS        current
    DESCRIPTION " A row in table Primary Rate Interface Interop. "
    INDEX         {
                    primaryRateInterfaceInteropName
                  }

    ::= { primaryRateInterfaceInteropTable 1 }

   PrimaryRateInterfaceInteropEntry ::= SEQUENCE
   {
     primaryRateInterfaceInteropName                                          OCTET STRING,
     primaryRateInterfaceInteropProgressIndicatorInSetupEnable                MxEnableState,
     primaryRateInterfaceInteropProgressIndicatorInSetupAckEnable             MxEnableState,
     primaryRateInterfaceInteropProgressIndicatorInCallProgressForSetupEnable MxEnableState,
     primaryRateInterfaceInteropProgressIndicatorInProgressEnable             MxEnableState,
     primaryRateInterfaceInteropProgressIndicatorInAlertingEnable             MxEnableState,
     primaryRateInterfaceInteropProgressIndicatorInConnectEnable              MxEnableState,
     primaryRateInterfaceInteropMaximumFacilityWaitingDelay                   Unsigned32,
     primaryRateInterfaceInteropUseImplicitInbandInfoEnable                   MxEnableState
   }

   -- Index:Name

   primaryRateInterfaceInteropName OBJECT-TYPE
    SYNTAX        OCTET STRING
    MAX-ACCESS    read-only
    STATUS        current
    DESCRIPTION " Name

                  Name that identifies the interface.
                  "
    ::= { primaryRateInterfaceInteropEntry 100 }

   -- Columnar:Progress Indicator In Setup

   primaryRateInterfaceInteropProgressIndicatorInSetupEnable OBJECT-TYPE
    SYNTAX        MxEnableState
    MAX-ACCESS    read-write
    STATUS        current
    DESCRIPTION " Progress Indicator In Setup

                  Defines whether or not the Progress Indicator information
                  element is allowed in the SETUP message when acting as the
                  originating side.

                  See the SignalingChannel.SendProgressIndicatorIE parameter for
                  other conditions for sending Progress Indicator IE.

                  "
    DEFVAL        { enable }
    ::= { primaryRateInterfaceInteropEntry 200 }

   -- Columnar:Progress Indicator In Setup Ack

   primaryRateInterfaceInteropProgressIndicatorInSetupAckEnable OBJECT-TYPE
    SYNTAX        MxEnableState
    MAX-ACCESS    read-write
    STATUS        current
    DESCRIPTION " Progress Indicator In Setup Ack

                  Defines whether or not the Progress Indicator information
                  element is allowed in the SETUP ACK when acting as the
                  terminating side.

                  See the SignalingChannel.SendProgressIndicatorIE parameter for
                  other conditions for sending Progress Indicator IE.

                  "
    DEFVAL        { enable }
    ::= { primaryRateInterfaceInteropEntry 300 }

   -- Columnar:Progress Indicator In Call Progress For Setup

   primaryRateInterfaceInteropProgressIndicatorInCallProgressForSetupEnable
   OBJECT-TYPE
    SYNTAX        MxEnableState
    MAX-ACCESS    read-write
    STATUS        current
    DESCRIPTION " Progress Indicator In Call Progress For Setup

                  Defines whether or not the Progress Indicator information
                  element is allowed in the CALL PROCEEDING message in response to
                  a SETUP message when acting as the terminating side.

                  See the SignalingChannel.SendProgressIndicatorIE parameter for
                  other conditions for sending Progress Indicator IE.

                  "
    DEFVAL        { enable }
    ::= { primaryRateInterfaceInteropEntry 400 }

   -- Columnar:Progress Indicator In Progress

   primaryRateInterfaceInteropProgressIndicatorInProgressEnable OBJECT-TYPE
    SYNTAX        MxEnableState
    MAX-ACCESS    read-write
    STATUS        current
    DESCRIPTION " Progress Indicator In Progress

                  Defines whether or not the Progress Indicator information
                  element is allowed in the PROGRESS message in response to a
                  SETUP message when acting as the terminating side.

                  See the SignalingChannel.SendProgressIndicatorIE parameter for
                  other conditions for sending Progress Indicator IE.

                  "
    DEFVAL        { enable }
    ::= { primaryRateInterfaceInteropEntry 450 }

   -- Columnar:Progress Indicator In Alerting

   primaryRateInterfaceInteropProgressIndicatorInAlertingEnable OBJECT-TYPE
    SYNTAX        MxEnableState
    MAX-ACCESS    read-write
    STATUS        current
    DESCRIPTION " Progress Indicator In Alerting

                  Defines whether or not the Progress Indicator information
                  element is allowed in the ALERTING message.

                  See the SignalingChannel.SendProgressIndicatorIE parameter for
                  other conditions for sending Progress Indicator IE.

                  "
    DEFVAL        { enable }
    ::= { primaryRateInterfaceInteropEntry 500 }

   -- Columnar:Progress Indicator In Connect

   primaryRateInterfaceInteropProgressIndicatorInConnectEnable OBJECT-TYPE
    SYNTAX        MxEnableState
    MAX-ACCESS    read-write
    STATUS        current
    DESCRIPTION " Progress Indicator In Connect

                  Defines whether or not the Progress Indicator information
                  element is allowed in the CONNECT message.

                  See the SignalingChannel.SendProgressIndicatorIE parameter for
                  other conditions for sending Progress Indicator IE.

                  "
    DEFVAL        { enable }
    ::= { primaryRateInterfaceInteropEntry 600 }

   -- Columnar:Maximum FACILITY Waiting Delay

   primaryRateInterfaceInteropMaximumFacilityWaitingDelay OBJECT-TYPE
    SYNTAX        Unsigned32 ( 0..1500 )
    MAX-ACCESS    read-write
    STATUS        current
    DESCRIPTION " Maximum FACILITY Waiting Delay

                  Defines the maximum amount of time to wait for a FACILITY
                  message, after receiving a SETUP message, before going on with
                  normal call processing.

                  After receiving a SETUP message, the system waits for this
                  amount of time for a FACILITY message. As soon as it receives a
                  FACILITY message or the delay expires, it goes on with normal
                  call processing.

                  A FACILITY message can contain useful information for the call.
                  For example, it can contain a Calling Name.

                  In order for this to be effective, the
                  SignalingChannel.FacilityServicesEnable parameter must be
                  enabled.

                  The value 0 deactivates this waiting delay.

                  This value is expressed in milliseconds (ms).

                  "
    DEFVAL        { 0 }
    ::= { primaryRateInterfaceInteropEntry 700 }

   -- Columnar:Use Implicit Inband Information

   primaryRateInterfaceInteropUseImplicitInbandInfoEnable OBJECT-TYPE
    SYNTAX        MxEnableState
    MAX-ACCESS    read-write
    STATUS        current
    DESCRIPTION " Use Implicit Inband Information

                  Defines if a message with progress indicator No. 1 (the call is
                  not end-to-end ISDN; further call progress information may be
                  available in-band) MUST be considered as offering inband
                  information available. If so, the network shall activate the
                  B-channel connection.
                  "
    DEFVAL        { enable }
    ::= { primaryRateInterfaceInteropEntry 800 }

  -- End of table:Primary Rate Interface Interop

 -- End of group:Primary Rate Interface Configuration

-- End of group:Primary Rate Interface Configuration

-- *****************************************************************************

-- Group:Basic Rate Interface Configuration

-- *****************************************************************************

basicRateInterfaceGroup OBJECT IDENTIFIER
 ::= { isdnMIBObjects 300 }
 -- *****************************************************************************
 
 -- Table:Basic Rate Interface

 -- *****************************************************************************
 
 basicRateInterfaceTable OBJECT-TYPE
  SYNTAX        SEQUENCE OF BasicRateInterfaceEntry
  MAX-ACCESS    not-accessible
  STATUS        current
  DESCRIPTION " Basic Rate Interface

                Configuration and operational parameters for all physical Basic
                Rate interfaces on this managed device.
                "
  ::= { basicRateInterfaceGroup 100 }
  basicRateInterfaceEntry OBJECT-TYPE
   SYNTAX        BasicRateInterfaceEntry
   MAX-ACCESS    not-accessible
   STATUS        current
   DESCRIPTION " A row in table Basic Rate Interface. "
   INDEX         {
                   basicRateInterfaceName
                 }

   ::= { basicRateInterfaceTable 1 }

  BasicRateInterfaceEntry ::= SEQUENCE
  {
    basicRateInterfaceName                             OCTET STRING,
    basicRateInterfaceEndpointType                     INTEGER,
    basicRateInterfaceConnectionType                   INTEGER,
    basicRateInterfaceNetworkLocation                  INTEGER,
    basicRateInterfacePreferredEncodingScheme          INTEGER,
    basicRateInterfaceFallbackEncodingScheme           INTEGER,
    basicRateInterfaceChannelAllocationStrategy        INTEGER,
    basicRateInterfaceMaxActiveCalls                   Unsigned32,
    basicRateInterfaceSignalInformationElementEnable   MxEnableState,
    basicRateInterfaceInbandToneGenerationEnable       MxEnableState,
    basicRateInterfaceInbandDtmfDialingEnable          MxEnableState,
    basicRateInterfaceOverlapDialingEnable             MxEnableState,
    basicRateInterfaceCallingNameMaxLength             Unsigned32,
    basicRateInterfaceExclusiveBChannelSelectionEnable MxEnableState,
    basicRateInterfaceSendingCompleteEnable            MxEnableState,
    basicRateInterfaceClipEnable                       INTEGER,
    basicRateInterfaceClirEnable                       MxEnableState,
    basicRateInterfaceClirOverrideEnable               MxEnableState,
    basicRateInterfaceSendRestartOnStartupEnable       MxEnableState,
    basicRateInterfaceHookFlashKeypad                  OCTET STRING,
    basicRateInterfaceKeypadReceptionTimeout           Unsigned32,
    basicRateInterfaceMsn                              OCTET STRING,
    basicRateInterfaceMsn2                             OCTET STRING,
    basicRateInterfaceMsn3                             OCTET STRING,
    basicRateInterfaceTeiNegotiation                   INTEGER
  }

  -- Index:Name

  basicRateInterfaceName OBJECT-TYPE
   SYNTAX        OCTET STRING
   MAX-ACCESS    read-only
   STATUS        current
   DESCRIPTION " Name

                 The physical interface name.
                 "
   ::= { basicRateInterfaceEntry 100 }

  -- Columnar:Maximum Active Calls

  basicRateInterfaceMaxActiveCalls OBJECT-TYPE
   SYNTAX        Unsigned32 ( 0..2 )
   MAX-ACCESS    read-write
   STATUS        current
   DESCRIPTION " Maximum Active Calls

                 Defines the maximum number of active calls on the interface.

                 Note: The special value 0 indicates no maximum number of active
                 calls.

                 "
   DEFVAL        { 0 }
   ::= { basicRateInterfaceEntry 1000 }

  -- Columnar:Signal Information Element Enable

  basicRateInterfaceSignalInformationElementEnable OBJECT-TYPE
   SYNTAX        MxEnableState
   MAX-ACCESS    read-write
   STATUS        current
   DESCRIPTION " Signal Information Element Enable

                 Defines whether the signal information element is enabled on
                 the interface. When activated at the Network UNI-side (
                 BasicRateInterfaceEndpointType parameter set to Nt), the signal
                 information element is sent to the User UNI-side. When
                 activated at the User UNI-side (BasicRateInterfaceEndpointType
                 parameter set to Te), the tone indicated in the signal
                 information element is played in the IP direction.

                 "
   DEFVAL        { disable }
   ::= { basicRateInterfaceEntry 1050 }

  -- Columnar:Inband Tone Generation Enable

  basicRateInterfaceInbandToneGenerationEnable OBJECT-TYPE
   SYNTAX        MxEnableState
   MAX-ACCESS    read-write
   STATUS        current
   DESCRIPTION " Inband Tone Generation Enable

                 Defines whether inband tone generation is enabled on the
                 interface. When activated at the User UNI-side (
                 BasicRateInterfaceEndpointType parameter set to Te), only the
                 ringback tone is generated.

                 When the SignalingChannel.Protocol parameter is set to 'QSIG'
                 and this parameter is activated, the incoming side of the call
                 plays the tones inband.

                 "
   DEFVAL        { enable }
   ::= { basicRateInterfaceEntry 1100 }

  -- Columnar:Inband DTMF Dialing Enable

  basicRateInterfaceInbandDtmfDialingEnable OBJECT-TYPE
   SYNTAX        MxEnableState
   MAX-ACCESS    read-write
   STATUS        current
   DESCRIPTION " Inband DTMF Dialing Enable

                 Defines whether inband DTMF dialing is enabled.
                 "
   DEFVAL        { enable }
   ::= { basicRateInterfaceEntry 1200 }

  -- Columnar:Overlap Dialing Enable

  basicRateInterfaceOverlapDialingEnable OBJECT-TYPE
   SYNTAX        MxEnableState
   MAX-ACCESS    read-write
   STATUS        current
   DESCRIPTION " Overlap Dialing Enable

                 Defines whether overlap dialing is enabled on the interface.
                 "
   DEFVAL        { enable }
   ::= { basicRateInterfaceEntry 1300 }

  -- Columnar:Calling Name Maximum Length

  basicRateInterfaceCallingNameMaxLength OBJECT-TYPE
   SYNTAX        Unsigned32 ( 0..82 )
   MAX-ACCESS    read-write
   STATUS        current
   DESCRIPTION " Calling Name Maximum Length

                 Defines the maximum length of the calling party name for calls
                 from SIP to ISDN on the interface.
                 "
   DEFVAL        { 34 }
   ::= { basicRateInterfaceEntry 1400 }

  -- Columnar:Exclusive Bearer Channel Selection Enable

  basicRateInterfaceExclusiveBChannelSelectionEnable OBJECT-TYPE
   SYNTAX        MxEnableState
   MAX-ACCESS    read-write
   STATUS        current
   DESCRIPTION " Exclusive Bearer Channel Selection Enable

                 Defines whether exclusive B-Channel selection is enabled for
                 calls from SIP to ISDN on the interface.
                 "
   DEFVAL        { disable }
   ::= { basicRateInterfaceEntry 1500 }

  -- Columnar:Sending Complete Enable

  basicRateInterfaceSendingCompleteEnable OBJECT-TYPE
   SYNTAX        MxEnableState
   MAX-ACCESS    read-write
   STATUS        current
   DESCRIPTION " Sending Complete Enable

                 Defines whether the Sending Complete information element in
                 SETUP messages is enabled for calls from SIP to ISDN on the
                 interface.
                 "
   DEFVAL        { enable }
   ::= { basicRateInterfaceEntry 1600 }

  -- Columnar:Calling Line Information Presentation Enable

  basicRateInterfaceClipEnable OBJECT-TYPE
   SYNTAX        INTEGER { userOnly(0) , enable(1) , disable(2) }
   MAX-ACCESS    read-write
   STATUS        current
   DESCRIPTION " Calling Line Information Presentation Enable

                 Enables the CLIP service, which is offered to the called party
                 to see the calling party's ISDN number. CLIP is complemented by
                 privacy rules controlled by the ClirEnable and
                 ClirOverrideEnable parameters. The ClipEnable parameter has the
                 following effect:

                   * UserOnly: Sends a Calling Number IE which contains the
                     calling number digits when acting as the User UNI-side (
                     PrimaryRateInterfaceEndpointType parameter set to Te)
                     otherwise the Calling Number IE is not sent.
                   * Enable: Sends a Calling Number IE which contains the
                     calling number digits.
                   * Disable: The Calling Number IE is never sent.

                 "
   DEFVAL        { userOnly }
   ::= { basicRateInterfaceEntry 1700 }

  -- Columnar:Calling Line Information Restriction Enable

  basicRateInterfaceClirEnable OBJECT-TYPE
   SYNTAX        MxEnableState
   MAX-ACCESS    read-write
   STATUS        current
   DESCRIPTION " Calling Line Information Restriction Enable

                 Enables the CLIR service, which is offered to the calling party
                 to restrict presentation of the calling party's ISDN number to
                 the called party.

                 Setting this parameter to 'Disable' disables the CLIR service.

                 Setting this parameter to 'Enable' enables the CLIR service.
                 This has the following effects:

                 For all ISDN signaling protocols except QSIG:

                   * On a TE interface at the originating network side, when
                     sending a SETUP message with a Calling Party Number (CPN)
                     IE, the Presentation Indicator (PI) is set to 'Restricted'.
                     The calling party number itself is included in the CPN IE
                     if available.
                   * On a NT interface at the originating network side, when
                     receiving a SETUP message with a CPN IE, the PI is set to
                     'Restricted'. The calling party number itself is forwarded.

                 For the QSIG signaling protocol:

                   * Sending a SETUP message: The PI is set to 'Restricted' in
                     the CPN IE inserted in the SETUP message sent to the ISDN,
                     unless the CLIR override option is set. However, even if PI
                     is set to 'Restricted', the calling number is included in
                     the CPN IE.
                   * Receiving a SETUP message: If PI is set in the received
                     message, the calling party number is removed, unless the
                     CLIR override option is set.

                 "
   DEFVAL        { disable }
   ::= { basicRateInterfaceEntry 1725 }

  -- Columnar:Calling Line Information Restriction Override Enable

  basicRateInterfaceClirOverrideEnable OBJECT-TYPE
   SYNTAX        MxEnableState
   MAX-ACCESS    read-write
   STATUS        current
   DESCRIPTION " Calling Line Information Restriction Override Enable

                 Enables the CLIR override option. This option allows the
                 calling party number to be presented to the destination party
                 even when the Calling Party Number (CPN) IE's Presentation
                 Indicator (PI) is set to 'Restricted'. This option is typically
                 used for police or emergency services.

                 Setting this parameter to 'Disable' disables the CLIR Override
                 option.

                 Setting this parameter to 'Enable' enables the CLIR Override
                 option. This has the following effects:

                 For all ISDN signaling protocols except QSIG:

                   * The override option acts on the NT interface of the
                     destination network side. It prevents the number to be
                     removed from the CPN IE inserted in the SETUP message sent
                     to the destination TE.

                 For the QSIG signaling protocol:

                   * The override option prevents the calling name to be removed
                     from the CPN IE in a received SETUP message.

                 "
   DEFVAL        { disable }
   ::= { basicRateInterfaceEntry 1750 }

  -- Columnar:Send Restart On Startup Enable

  basicRateInterfaceSendRestartOnStartupEnable OBJECT-TYPE
   SYNTAX        MxEnableState
   MAX-ACCESS    read-write
   STATUS        current
   DESCRIPTION " Send Restart On Startup Enable

                 Defines whether the RESTART message is sent upon a signaling
                 channel 'UP' event
                 "
   DEFVAL        { enable }
   ::= { basicRateInterfaceEntry 1800 }

  -- Columnar:Hook-Flash Keypad

  basicRateInterfaceHookFlashKeypad OBJECT-TYPE
   SYNTAX        OCTET STRING ( SIZE(0..32) )
   MAX-ACCESS    read-write
   STATUS        current
   DESCRIPTION " Hook-Flash Keypad

                 The actual keypad string that is to be considered as a
                 hook-flash.

                 Setting this parameter to an empty string disables the
                 hook-flash detection.

                 The permitted keypad must be made up of IA5 characters. See
                 ITU-T Recommendation T.50.

                 "
   DEFVAL        { "" }
   ::= { basicRateInterfaceEntry 1900 }

  -- Columnar:Endpoint Type

  basicRateInterfaceEndpointType OBJECT-TYPE
   SYNTAX        INTEGER { te(100) , nt(200) }
   MAX-ACCESS    read-write
   STATUS        current
   DESCRIPTION " Endpoint Type

                 Defines the endpoint type:

                   * Te: Terminal Equipment
                   * Nt: Network Termination

                 When the SignalingChannel.Protocol parameter is set to QSIG,
                 the endpoint type will only be used in the second layer (LAPD)
                 since it is a concept that does not exist within QSIG.

                 "
   DEFVAL        { te }
   ::= { basicRateInterfaceEntry 200 }

  -- Columnar:Keypad Reception Timeout

  basicRateInterfaceKeypadReceptionTimeout OBJECT-TYPE
   SYNTAX        Unsigned32 ( 0..4 )
   MAX-ACCESS    read-write
   STATUS        current
   DESCRIPTION " Keypad Reception Timeout

                 The actual time to wait before considering the keypad reception
                 over.

                 The value is expressed in seconds.

                 Setting this parameter to 0 disables the timeout, thus assuming
                 that all keypads will be received in a single Information
                 message.

                 "
   DEFVAL        { 2 }
   ::= { basicRateInterfaceEntry 2000 }

  -- Columnar:MSN

  basicRateInterfaceMsn OBJECT-TYPE
   SYNTAX        OCTET STRING ( SIZE(0..255) )
   MAX-ACCESS    read-write
   STATUS        current
   DESCRIPTION " MSN

                 This enables the MSN supplementary service with a comma
                 separated list of numbers.

                 The MSN supplementary service shall enable each individual
                 terminal on one access to have one or more identities.

                 If the Called E.164 received from a call does not match any MSN
                 numbers, the call is silently discarded.

                 This service is available only for a BRI interface configured
                 in TE Point To Multipoint. This service is also disabled when
                 all fields are blank. This field must contain numeric values.

                 The comma separated list must use the following syntax: 777,
                 888, 999, 555, 444

                 "
   DEFVAL        { "" }
   ::= { basicRateInterfaceEntry 2200 }

  -- Columnar:MSN 2

  basicRateInterfaceMsn2 OBJECT-TYPE
   SYNTAX        OCTET STRING ( SIZE(0..32) )
   MAX-ACCESS    read-write
   STATUS        deprecated
   DESCRIPTION " MSN 2

                 Deprecated: Use Isdn.BasicRateInterface.Msn instead. This
                 enables the MSN supplementary service with these numbers.

                 The MSN supplementary service shall enable each individual
                 terminal on one access to have one or more identities.

                 If the Called E.164 received from a call does not match any MSN
                 numbers, the call is silently discarded.

                 This service is available only for a BRI interface configured
                 in TE Point To Multipoint. This service is also disabled when
                 all fields are blank. This field must contain numeric values.

                 "
   DEFVAL        { "" }
   ::= { basicRateInterfaceEntry 2300 }

  -- Columnar:MSN 3

  basicRateInterfaceMsn3 OBJECT-TYPE
   SYNTAX        OCTET STRING ( SIZE(0..32) )
   MAX-ACCESS    read-write
   STATUS        deprecated
   DESCRIPTION " MSN 3

                 Deprecated: Use Isdn.BasicRateInterface.Msn instead. This
                 enables the MSN supplementary service with these numbers.

                 The MSN supplementary service shall enable each individual
                 terminal on one access to have one or more identities.

                 If the Called E.164 received from a call does not match any MSN
                 numbers, the call is silently discarded.

                 This service is available only for a BRI interface configured
                 in TE Point To Multipoint. This service is also disabled when
                 all fields are blank. This field must contain numeric values.

                 "
   DEFVAL        { "" }
   ::= { basicRateInterfaceEntry 2400 }

  -- Columnar:TEI Negotiation

  basicRateInterfaceTeiNegotiation OBJECT-TYPE
   SYNTAX        INTEGER { linkUp(100) , powerUp(200) , signalingUp(300) }
   MAX-ACCESS    read-write
   STATUS        current
   DESCRIPTION " TEI Negotiation

                 Sets the Terminal Endpoint Identifier (TEI) negotiation
                 strategy.

                   * LinkUp: Each time the physical link comes up, the unit
                     renegotiates the TEI value.
                   * PowerUp: When the physical link comes up, the unit does not
                     renegotiate the TEI value. The value obtained at power-up
                     is reused.
                   * SignalingUp: Each time the signaling link comes up, the
                     unit renegotiates the TEI value.

                 NOTE: only applies on Point To Multipoint connections.

                 "
   DEFVAL        { linkUp }
   ::= { basicRateInterfaceEntry 2500 }

  -- Columnar:Connection Type

  basicRateInterfaceConnectionType OBJECT-TYPE
   SYNTAX        INTEGER { pointToPoint(100) , pointToMultiPoint(200) }
   MAX-ACCESS    read-write
   STATUS        current
   DESCRIPTION " Connection Type

                 Defines the connection type:

                   * PointToPoint: Can only attach one device (for instance a
                     PABX or PSTN)
                   * PointToMultiPoint: Can attach more than one device

                 PointToMultiPoint configuration is not available in QSIG.

                 "
   DEFVAL        { pointToMultiPoint }
   ::= { basicRateInterfaceEntry 300 }

  -- Columnar:Network Location

  basicRateInterfaceNetworkLocation OBJECT-TYPE
   SYNTAX        INTEGER { user(100) , private(200) , public(300) , transit(400)
                 , international(500) }
   MAX-ACCESS    read-write
   STATUS        current
   DESCRIPTION " Network Location

                 Defines the value of the network location in the progress
                 indicator messages sent by the unit.
                 "
   DEFVAL        { user }
   ::= { basicRateInterfaceEntry 600 }

  -- Columnar:Preferred Encoding Scheme

  basicRateInterfacePreferredEncodingScheme OBJECT-TYPE
   SYNTAX        INTEGER { g711alaw(100) , g711ulaw(200) }
   MAX-ACCESS    read-write
   STATUS        current
   DESCRIPTION " Preferred Encoding Scheme

                 Defines the preferred data encoding scheme in the bearer
                 capabilities (user information layer 1 protocol). This encoding
                 scheme is used when initiating a call on the ISDN side.
                 "
   DEFVAL        { g711alaw }
   ::= { basicRateInterfaceEntry 700 }

  -- Columnar:Fallback Encoding Scheme

  basicRateInterfaceFallbackEncodingScheme OBJECT-TYPE
   SYNTAX        INTEGER { g711alaw(100) , g711ulaw(200) }
   MAX-ACCESS    read-write
   STATUS        current
   DESCRIPTION " Fallback Encoding Scheme

                 Defines the fallback data encoding scheme in the bearer
                 capabilities (user information layer 1 protocol).
                 "
   DEFVAL        { g711ulaw }
   ::= { basicRateInterfaceEntry 750 }

  -- Columnar:Channel Allocation Strategy

  basicRateInterfaceChannelAllocationStrategy OBJECT-TYPE
   SYNTAX        INTEGER { ascending(100) , descending(200) ,
                 roundRobinAscending(300) , roundRobinDescending(400) }
   MAX-ACCESS    read-write
   STATUS        current
   DESCRIPTION " Channel Allocation Strategy

                 Defines the strategy for selecting bearer channels. Available
                 strategies are:

                   * Ascending: select the lowest-numbered non-busy bearer
                     channel
                   * Descending: select the highest-numbered non-busy bearer
                     channel
                   * RoundRobinAscending: use a cyclic round-robin search;
                     starting from the bearer channel that follows the bearer
                     channel used for the last call, select the lowest-numbered
                     non-busy bearer channel
                   * RoundRobinDescending: use a cyclic round-robin search;
                     starting from the bearer channel that precedes the bearer
                     channel used for the last call, select the highest-numbered
                     non-busy bearer channel

                 "
   DEFVAL        { ascending }
   ::= { basicRateInterfaceEntry 900 }

 -- End of table:Basic Rate Interface

 -- *****************************************************************************
 
 -- Group:Basic Rate Interface Configuration

 -- *****************************************************************************
 
 basicRateInterfaceInteropGroup OBJECT IDENTIFIER
  ::= { basicRateInterfaceGroup 50000 }
  -- *****************************************************************************
  
  -- Table:Basic Rate Interface Interop

  -- *****************************************************************************
  
  basicRateInterfaceInteropTable OBJECT-TYPE
   SYNTAX        SEQUENCE OF BasicRateInterfaceInteropEntry
   MAX-ACCESS    not-accessible
   STATUS        current
   DESCRIPTION " Basic Rate Interface Interop

                 Interop configuration parameters related to the Basic Rate interfaces on
                 this managed device.
                 "
   ::= { basicRateInterfaceInteropGroup 100 }
   basicRateInterfaceInteropEntry OBJECT-TYPE
    SYNTAX        BasicRateInterfaceInteropEntry
    MAX-ACCESS    not-accessible
    STATUS        current
    DESCRIPTION " A row in table Basic Rate Interface Interop. "
    INDEX         {
                    basicRateInterfaceInteropName
                  }

    ::= { basicRateInterfaceInteropTable 1 }

   BasicRateInterfaceInteropEntry ::= SEQUENCE
   {
     basicRateInterfaceInteropName                                          OCTET STRING,
     basicRateInterfaceInteropProgressIndicatorInSetupEnable                MxEnableState,
     basicRateInterfaceInteropProgressIndicatorInSetupAckEnable             MxEnableState,
     basicRateInterfaceInteropProgressIndicatorInCallProgressForSetupEnable MxEnableState,
     basicRateInterfaceInteropProgressIndicatorInProgressEnable             MxEnableState,
     basicRateInterfaceInteropProgressIndicatorInAlertingEnable             MxEnableState,
     basicRateInterfaceInteropProgressIndicatorInConnectEnable              MxEnableState,
     basicRateInterfaceInteropMaximumFacilityWaitingDelay                   Unsigned32,
     basicRateInterfaceInteropUseImplicitInbandInfoEnable                   MxEnableState,
     basicRateInterfaceInteropAllowTeiBroadcastInPtpEnable                  MxEnableState
   }

   -- Index:Name

   basicRateInterfaceInteropName OBJECT-TYPE
    SYNTAX        OCTET STRING
    MAX-ACCESS    read-only
    STATUS        current
    DESCRIPTION " Name

                  Name that identifies the interface.
                  "
    ::= { basicRateInterfaceInteropEntry 100 }

   -- Columnar:Progress Indicator In Setup

   basicRateInterfaceInteropProgressIndicatorInSetupEnable OBJECT-TYPE
    SYNTAX        MxEnableState
    MAX-ACCESS    read-write
    STATUS        current
    DESCRIPTION " Progress Indicator In Setup

                  Defines whether or not the Progress Indicator information
                  element is allowed in the SETUP message when acting as the
                  originating side.

                  See the SignalingChannel.SendProgressIndicatorIE parameter for
                  other conditions for sending Progress Indicator IE.

                  "
    DEFVAL        { enable }
    ::= { basicRateInterfaceInteropEntry 200 }

   -- Columnar:Progress Indicator In Setup Ack

   basicRateInterfaceInteropProgressIndicatorInSetupAckEnable OBJECT-TYPE
    SYNTAX        MxEnableState
    MAX-ACCESS    read-write
    STATUS        current
    DESCRIPTION " Progress Indicator In Setup Ack

                  Defines whether or not the Progress Indicator information
                  element is allowed in the SETUP ACK when acting as the
                  terminating side.

                  See the SignalingChannel.SendProgressIndicatorIE parameter for
                  other conditions for sending Progress Indicator IE.

                  "
    DEFVAL        { enable }
    ::= { basicRateInterfaceInteropEntry 300 }

   -- Columnar:Progress Indicator In Call Progress For Setup

   basicRateInterfaceInteropProgressIndicatorInCallProgressForSetupEnable
   OBJECT-TYPE
    SYNTAX        MxEnableState
    MAX-ACCESS    read-write
    STATUS        current
    DESCRIPTION " Progress Indicator In Call Progress For Setup

                  Defines whether or not the Progress Indicator information
                  element is allowed in the CALL PROCEEDING message in response to
                  a SETUP message when acting as the terminating side.

                  See the SignalingChannel.SendProgressIndicatorIE parameter for
                  other conditions for sending Progress Indicator IE.

                  "
    DEFVAL        { enable }
    ::= { basicRateInterfaceInteropEntry 400 }

   -- Columnar:Progress Indicator In Progress

   basicRateInterfaceInteropProgressIndicatorInProgressEnable OBJECT-TYPE
    SYNTAX        MxEnableState
    MAX-ACCESS    read-write
    STATUS        current
    DESCRIPTION " Progress Indicator In Progress

                  Defines whether or not the Progress Indicator information
                  element is allowed in the PROGRESS message in response to a
                  SETUP message when acting as the terminating side.

                  See the SignalingChannel.SendProgressIndicatorIE parameter for
                  other conditions for sending Progress Indicator IE.

                  "
    DEFVAL        { enable }
    ::= { basicRateInterfaceInteropEntry 450 }

   -- Columnar:Progress Indicator In Alerting

   basicRateInterfaceInteropProgressIndicatorInAlertingEnable OBJECT-TYPE
    SYNTAX        MxEnableState
    MAX-ACCESS    read-write
    STATUS        current
    DESCRIPTION " Progress Indicator In Alerting

                  Defines whether or not the Progress Indicator information
                  element is allowed in the ALERTING message.

                  See the SignalingChannel.SendProgressIndicatorIE parameter for
                  other conditions for sending Progress Indicator IE.

                  "
    DEFVAL        { enable }
    ::= { basicRateInterfaceInteropEntry 500 }

   -- Columnar:Progress Indicator In Connect

   basicRateInterfaceInteropProgressIndicatorInConnectEnable OBJECT-TYPE
    SYNTAX        MxEnableState
    MAX-ACCESS    read-write
    STATUS        current
    DESCRIPTION " Progress Indicator In Connect

                  Defines whether or not the Progress Indicator information
                  element is allowed in the CONNECT message.

                  See the SignalingChannel.SendProgressIndicatorIE parameter for
                  other conditions for sending Progress Indicator IE.

                  "
    DEFVAL        { enable }
    ::= { basicRateInterfaceInteropEntry 600 }

   -- Columnar:Maximum FACILITY Waiting Delay

   basicRateInterfaceInteropMaximumFacilityWaitingDelay OBJECT-TYPE
    SYNTAX        Unsigned32 ( 0..1500 )
    MAX-ACCESS    read-write
    STATUS        current
    DESCRIPTION " Maximum FACILITY Waiting Delay

                  Defines the maximum amount of time to wait for a FACILITY
                  message, after receiving a SETUP message, before going on with
                  normal call processing.

                  After receiving a SETUP message, the system waits for this
                  amount of time for a FACILITY message. As soon as it receives a
                  FACILITY message or the delay expires, it goes on with normal
                  call processing.

                  A FACILITY message can contain useful information for the call.
                  For example, it can contain a Calling Name.

                  In order for this to be effective, the
                  SignalingChannel.FacilityServicesEnable parameter must be
                  enabled.

                  The value 0 deactivates this waiting delay.

                  This value is expressed in milliseconds (ms).

                  "
    DEFVAL        { 0 }
    ::= { basicRateInterfaceInteropEntry 700 }

   -- Columnar:Use Implicit Inband Information

   basicRateInterfaceInteropUseImplicitInbandInfoEnable OBJECT-TYPE
    SYNTAX        MxEnableState
    MAX-ACCESS    read-write
    STATUS        current
    DESCRIPTION " Use Implicit Inband Information

                  Defines if a message with progress indicator No. 1 (the call is
                  not end-to-end ISDN; further call progress information may be
                  available in-band) MUST be considered as offering inband
                  information available. If so, the network shall activate the
                  B-channel connection.
                  "
    DEFVAL        { enable }
    ::= { basicRateInterfaceInteropEntry 800 }

   -- Columnar:Allow TEI Broadcast in Point-to-Point

   basicRateInterfaceInteropAllowTeiBroadcastInPtpEnable OBJECT-TYPE
    SYNTAX        MxEnableState
    MAX-ACCESS    read-write
    STATUS        current
    DESCRIPTION " Allow TEI Broadcast in Point-to-Point

                  Defines whether or not an ISDN message with a TEI broadcast
                  needs to be interpreted as a TEI 0 when the connection type is
                  'PointToPoint' (see BasicRateInterfaceGroup.ConnectionType
                  parameter).

                  "
    DEFVAL        { enable }
    ::= { basicRateInterfaceInteropEntry 900 }

  -- End of table:Basic Rate Interface Interop

 -- End of group:Basic Rate Interface Configuration

-- End of group:Basic Rate Interface Configuration

-- ****************************************************************************

-- Group:Bearer Channel Configuration

-- ****************************************************************************

bearerChannelGroup OBJECT IDENTIFIER
 ::= { isdnMIBObjects 400 }
 -- ***************************************************************************
 
 -- Table:Bearer Channel Info

 -- ***************************************************************************
 
 bearerChannelInfoTable OBJECT-TYPE
  SYNTAX        SEQUENCE OF BearerChannelInfoEntry
  MAX-ACCESS    not-accessible
  STATUS        current
  DESCRIPTION " Bearer Channel Info

                Port-specific operational, statistics, and active call data
                for ISDN B channels.
                "
  ::= { bearerChannelGroup 100 }
  bearerChannelInfoEntry OBJECT-TYPE
   SYNTAX        BearerChannelInfoEntry
   MAX-ACCESS    not-accessible
   STATUS        current
   DESCRIPTION " A row in table Bearer Channel Info. "
   INDEX         {
                   bearerChannelInfoIndex
                 }

   ::= { bearerChannelInfoTable 1 }

  BearerChannelInfoEntry ::= SEQUENCE
  {
    bearerChannelInfoIndex OCTET STRING,
    bearerChannelInfoState INTEGER
  }

  -- Index:Index

  bearerChannelInfoIndex OBJECT-TYPE
   SYNTAX        OCTET STRING
   MAX-ACCESS    read-only
   STATUS        current
   DESCRIPTION " Index

                 Identifies the Bearer Channel..
                 "
   ::= { bearerChannelInfoEntry 100 }

  -- Columnar:State

  bearerChannelInfoState OBJECT-TYPE
   SYNTAX        INTEGER { idle(100) , inUse(200) , maintenance(300) , error
                 (400) , disabled(500) }
   MAX-ACCESS    read-only
   STATUS        current
   DESCRIPTION " State

                 The current call control state for this channel:

                   * Idle: The channel is available
                   * InUse: The channel is currently used
                   * Maintenance: Maintenance state, temporarily unavailable
                   * Error: Error on this channel
                   * Disabled: The channel is disabled

                 "
   ::= { bearerChannelInfoEntry 200 }

 -- End of table:Bearer Channel Info

-- End of group:Bearer Channel Configuration

-- *****************************************************************************

-- Group:Signaling Channel Configuration

-- *****************************************************************************

signalingChannelGroup OBJECT IDENTIFIER
 ::= { isdnMIBObjects 500 }
 -- *****************************************************************************
 
 -- Table:Signaling

 -- *****************************************************************************
 
 signalingChannelTable OBJECT-TYPE
  SYNTAX        SEQUENCE OF SignalingChannelEntry
  MAX-ACCESS    not-accessible
  STATUS        current
  DESCRIPTION " Signaling

                ISDN signaling table containing configuration and operational
                parameters for all ISDN signaling channels on this managed
                device.
                "
  ::= { signalingChannelGroup 100 }
  signalingChannelEntry OBJECT-TYPE
   SYNTAX        SignalingChannelEntry
   MAX-ACCESS    not-accessible
   STATUS        current
   DESCRIPTION " A row in table Signaling. "
   INDEX         {
                   signalingChannelInterfaceName
                 }

   ::= { signalingChannelTable 1 }

  SignalingChannelEntry ::= SEQUENCE
  {
    signalingChannelInterfaceName                     OCTET STRING,
    signalingChannelProtocol                          INTEGER,
    signalingChannelFacilityServicesEnable            MxEnableState,
    signalingChannelColpEnable                        MxEnableState,
    signalingChannelColrEnable                        MxEnableState,
    signalingChannelColrOverrideEnable                MxEnableState,
    signalingChannelConpEnable                        MxEnableState,
    signalingChannelOutgoingNotifyEnable              MxEnableState,
    signalingChannelAcceptedProgressCauses            OCTET STRING,
    signalingChannelAutoCancelTimeout                 Unsigned32,
    signalingChannelDateTimeIeSupport                 INTEGER,
    signalingChannelMaintenanceServiceCallTermination INTEGER,
    signalingChannelLinkEstablishment                 INTEGER,
    signalingChannelLinkEstablishmentTimer            Unsigned32,
    signalingChannelAcceptedStatusCauses              OCTET STRING,
    signalingChannelSendIsdnProgress                  INTEGER,
    signalingChannelSendProgressIndicatorIE           INTEGER,
    signalingChannelAocESupport                       INTEGER,
    signalingChannelAocDSupport                       INTEGER,
    signalingChannelCallReroutingBehavior             INTEGER,
    signalingChannelDefaultCallingTon                 INTEGER,
    signalingChannelDefaultCallingNpi                 INTEGER,
    signalingChannelDefaultCallingPi                  INTEGER,
    signalingChannelDefaultCallingSi                  INTEGER,
    signalingChannelDefaultCalledTon                  INTEGER,
    signalingChannelDefaultCalledNpi                  INTEGER,
    signalingChannelUserSuspendedHandling             INTEGER,
    signalingChannelStrictHandlingErrorConditions     MxEnableState,
    signalingChannelMcidEnable                        MxEnableState
  }

  -- Index:Interface Name

  signalingChannelInterfaceName OBJECT-TYPE
   SYNTAX        OCTET STRING
   MAX-ACCESS    read-only
   STATUS        current
   DESCRIPTION " Interface Name

                 Identifies the interface.
                 "
   ::= { signalingChannelEntry 100 }

  -- Columnar:Maintenance Service Call Termination

  signalingChannelMaintenanceServiceCallTermination OBJECT-TYPE
   SYNTAX        INTEGER { graceful(100) , abrupt(200) }
   MAX-ACCESS    read-write
   STATUS        current
   DESCRIPTION " Maintenance Service Call Termination

                 Describes the call termination strategy after reception of a
                 service message requesting a maintenance on the associated
                 bearer channel.

                   * Graceful: The call proceeds normally until the user clears
                     the call. The associated bearer is then set to maintenance.
                   * Abrupt: The call is terminated immediately and set to
                     maintenance.

                 "
   DEFVAL        { graceful }
   ::= { signalingChannelEntry 10000 }

  -- Columnar:Link Establishment

  signalingChannelLinkEstablishment OBJECT-TYPE
   SYNTAX        INTEGER { onDemand(100) , permanent(200) }
   MAX-ACCESS    read-write
   STATUS        current
   DESCRIPTION " Link Establishment

                 Sets the link establishment strategy.

                   * OnDemand: When the data link is shut down, the unit
                     establishes a new link only when required.
                   * Permanent: When the data link is shut down, the unit
                     attempts to establish a new link.

                 "
   DEFVAL        { onDemand }
   ::= { signalingChannelEntry 10100 }

  -- Columnar:Link Establishment Timer

  signalingChannelLinkEstablishmentTimer OBJECT-TYPE
   SYNTAX        Unsigned32 ( 0..30000 )
   MAX-ACCESS    read-write
   STATUS        current
   DESCRIPTION " Link Establishment Timer

                 Sets the link establishment timer.

                 This parameter has no effect if the LinkEstablishment parameter
                 is set to 'OnDemand'.

                 "
   DEFVAL        { 100 }
   ::= { signalingChannelEntry 10110 }

  -- Columnar:Accepted STATUS Causes

  signalingChannelAcceptedStatusCauses OBJECT-TYPE
   SYNTAX        OCTET STRING ( SIZE(0..255) )
   MAX-ACCESS    read-write
   STATUS        current
   DESCRIPTION " Accepted STATUS Causes

                 Sets the STATUS causes that can be received without
                 automatically clearing the call.

                 The default action is to clear the call upon the receipt of a
                 STATUS message. If a STATUS message is received indicating a
                 compatible call state and containing the supplied STATUS
                 causes, the clearing of the call is prevented

                 The string has the following syntax:

                   * ',': Separator between non-consecutive lists of causes or
                     single cause.
                   * 'n': A single cause, where n is the cause number.
                   * 'm-n': List of causes where m is the start cause number and
                     n is the end cause number.

                 NOTE: The space character are ignored and cause duplication is
                 not allowed. Causes must be specified in low to high order.

                 Example: '1,124-127': The accepted causes are 1, 124, 125, 126
                 and 127.

                 "
   DEFVAL        { "" }
   ::= { signalingChannelEntry 10200 }

  -- Columnar:Send ISDN Progress message

  signalingChannelSendIsdnProgress OBJECT-TYPE
   SYNTAX        INTEGER { sendAll(100) , sendInband(200) , sendAlerting(300) }
   MAX-ACCESS    read-write
   STATUS        current
   DESCRIPTION " Send ISDN Progress message

                 Sets the strategy for sending ISDN Progress messages.

                   * SendAll: Send an ISDN Progress message in all situations
                     where call progression is signaled.
                   * SendInband: Send an ISDN Progress message only when call
                     progression contains an indication of in-band information.
                   * SendAlerting: Send an ISDN Alerting message only when call
                     progression contains an indication of in-band information.

                 The strategy for sending Progress messages should be adapted to
                 the configuration of the peer ISDN switch. Some switches may
                 terminate calls when receiving one or many ISDN progress
                 messages.

                 "
   DEFVAL        { sendAll }
   ::= { signalingChannelEntry 10300 }

  -- Columnar:Send ISDN Progress Indicator Information Element

  signalingChannelSendProgressIndicatorIE OBJECT-TYPE
   SYNTAX        INTEGER { sendAll(100) , sendInbandOnly(200) }
   MAX-ACCESS    read-write
   STATUS        current
   DESCRIPTION " Send ISDN Progress Indicator Information Element

                 Sets the strategy for sending the Progress Indicator
                 Information Element.

                   * SendAll: Send the Progress Indicator IE in all situations.
                   * SendInbandOnly: Send the Progress Indicator only when the
                     Progress Description contains an indication of in-band
                     information.

                 The strategy for the Progress Indicator IE should be adapted to
                 the configuration of the peer ISDN switch.

                 This parameter controls sending of a Progress Indicator IE in
                 ISDN messages where Progress Indicators are allowed. See the
                 parameters in the BasicRateInterfaceInterop and
                 PrimaryRateInterfaceInterop tables for a control over which
                 ISDN messages allow Progress Indicators.

                 "
   DEFVAL        { sendAll }
   ::= { signalingChannelEntry 10400 }

  -- Columnar:Advice of Charge AOC-E Support

  signalingChannelAocESupport OBJECT-TYPE
   SYNTAX        INTEGER { no(100) , transparent(200) , automatic(300) ,
                 explicit(400) }
   MAX-ACCESS    read-write
   STATUS        current
   DESCRIPTION " Advice of Charge AOC-E Support

                 Send the total charge at the (E)nd of the call in AOC-E
                 messages.

                   * no: The AOC-E support is disabled. No information is
                     forwarded to the peer interface.
                   * transparent: On an NT interface, the information is sent as
                     received from the network. No information is sent if the
                     network does not provide information. On a TE interface,
                     the information is forwarded to the peer interface if AOC
                     messages are received from the network.
                   * automatic: On an NT interface, always send the information.
                     If the network does not provide information,
                     'noChargeAvailable' is sent. On a TE interface, the
                     information is forwarded to the peer interface if AOC
                     messages are received from the network.
                   * explicit: On an NT interface, always send the information
                     if the phone requests AOC on a per-call basis.
                     'noChargeAvailable' is sent if the network does not provide
                     information. If the phone does not request AOC on a
                     per-call basis, no information is sent. On a TE interface,
                     send an AOC request to the network. If the network rejects
                     the request, no information is forwarded to the peer
                     interface. Otherwise, the information is forwarded to the
                     peer interface if AOC messages are received from the
                     network.

                 "
   DEFVAL        { no }
   ::= { signalingChannelEntry 10600 }

  -- Columnar:Advice of Charge AOC-D Support

  signalingChannelAocDSupport OBJECT-TYPE
   SYNTAX        INTEGER { no(100) , transparent(200) , automatic(300) ,
                 explicit(400) }
   MAX-ACCESS    read-write
   STATUS        current
   DESCRIPTION " Advice of Charge AOC-D Support

                 Send the current charge (D)uring the call in AOC-D messages.

                   * no: The AOC-D support is disabled. No information is
                     forwarded to the peer interface.
                   * transparent: On an NT interface, the information is sent as
                     received from the network. No information is sent if the
                     network does not provide information. On a TE interface,
                     the information is forwarded to the peer interface if AOC
                     messages are received from the network.
                   * automatic: On an NT interface, always send the information.
                     If the network does not provide information,
                     'noChargeAvailable' is sent. On a TE interface, the
                     information is forwarded to the peer interface if AOC
                     messages are received from the network.
                   * explicit: On an NT interface, always send the information
                     if the phone requests AOC on a per-call basis.
                     'noChargeAvailable' is sent if the network does not provide
                     information. If the phone does not request AOC on a
                     per-call basis, no information is sent. On a TE interface,
                     send an AOC request to the network. If the network rejects
                     the request, no information is forwarded to the peer
                     interface. Otherwise, the information is forwarded to the
                     peer interface if AOC messages are received from the
                     network.

                 "
   DEFVAL        { no }
   ::= { signalingChannelEntry 10620 }

  -- Columnar:Call Rerouting Behavior

  signalingChannelCallReroutingBehavior OBJECT-TYPE
   SYNTAX        INTEGER { unsupported(100) , relayReroute(200) , processLocally
                 (300) }
   MAX-ACCESS    read-write
   STATUS        current
   DESCRIPTION " Call Rerouting Behavior

                 Defines how the call rerouting request received from the
                 private network side is supported. Rerouting requests are
                 received in a Facility IE.

                   * Unsupported: Rerouting requests received are rejected. A
                     reject answer is sent to the private network.
                   * RelayReroute: Rerouting requests are relayed as received to
                     the public network side. If the peer rejects or does not
                     support the reroute request, the ISDN service may initiate
                     a new call to process the rerouting request locally.
                   * ProcessLocally: Received Rerouting requests are not relayed
                     to the public network side. The ISDN service attempts to
                     connect to the rerouted address by initiating a new call.

                 "
   DEFVAL        { unsupported }
   ::= { signalingChannelEntry 10700 }

  -- Columnar:Default Type of Number for Calling Party Number IE

  signalingChannelDefaultCallingTon OBJECT-TYPE
   SYNTAX        INTEGER { unknown(100) , international(200) , national(300) ,
                 networkSpecific(400) , subscriber(500) , abbreviated(600) }
   MAX-ACCESS    read-write
   STATUS        current
   DESCRIPTION " Default Type of Number for Calling Party Number IE

                 Default value to insert in the 'Type of Number' parameter of
                 the 'Calling Party Number' IE when 'Type of Number' is not
                 already defined in the call properties. A call property set by
                 the 'Properties Manipulation' feature of the Call Router has
                 precedence over this default value. This parameter applies to
                 the outgoing ISDN calls.

                 Possible values are:

                   * Unknown: Default value of Type of Number is set to Unknown.
                   * International: Default value of Type of Number is set to
                     International.
                   * National: Default value of Type of Number is set to
                     National.
                   * NetworkSpecific: Default value of Type of Number is set to
                     Network-Specific.
                   * Subscriber: Default value of Type of Number is set to
                     Subscriber.
                   * Abbreviated: Default value of Type of Number is set to
                     Abbreviated.

                 "
   DEFVAL        { unknown }
   ::= { signalingChannelEntry 10800 }

  -- Columnar:Default Numbering Plan Identification for Calling Party Number IE

  signalingChannelDefaultCallingNpi OBJECT-TYPE
   SYNTAX        INTEGER { unknown(100) , isdnTelephony(200) , data(300) , telex
                 (400) , nationalStandard(500) , private(600) }
   MAX-ACCESS    read-write
   STATUS        current
   DESCRIPTION " Default Numbering Plan Identification for Calling Party Number
                 IE

                 Default value to insert in the 'Numbering Plan Identification'
                 parameter of the 'Calling Party Number' IE when 'Numbering Plan
                 Identification' is not already defined in the call properties.
                 A call property set by the 'Properties Manipulation' feature of
                 the Call Router has precedence over this default value. This
                 parameter applies to the outgoing ISDN calls.

                 Possible values are:

                   * Unknown: Default value of Numbering Plan Identification is
                     set to Unknown.
                   * IsdnTelephony: Default value of Numbering Plan
                     Identification is set to ISDN Telephony.
                   * Data: Default value of Numbering Plan Identification is set
                     to Data.
                   * Telex: Default value of Numbering Plan Identification is
                     set to Telex.
                   * NationalStandard: Default value of Numbering Plan
                     Identification is set to National Standard.
                   * Private: Default value of Numbering Plan Identification is
                     set to Private.

                 "
   DEFVAL        { unknown }
   ::= { signalingChannelEntry 10900 }

  -- Columnar:Default Presentation Indicator for Calling Party Number IE

  signalingChannelDefaultCallingPi OBJECT-TYPE
   SYNTAX        INTEGER { presentationAllowed(100) , presentationRestricted
                 (200) , notAvailable(300) }
   MAX-ACCESS    read-write
   STATUS        current
   DESCRIPTION " Default Presentation Indicator for Calling Party Number IE

                 Default value to insert in the 'Presentation Indicator'
                 parameter of the 'Calling Party Number' IE when 'Presentation
                 Indicator' is not already defined in the call properties. A
                 call property set by the 'Properties Manipulation' feature of
                 the Call Router has precedence over this default value. If
                 'Presentation Indicator' is not provided by the call
                 properties, its value is determined by the following two steps.
                 First, it is set to the default value defined by
                 'DefaultCallingPi'. Second, the 'Presentation Indicator' can be
                 overridden by the CLIP and CLIR services: the value can be set
                 to 'Restricted' by the CLIR service and the value can be set to
                 'NotAvailable' if there is no number to forward. This parameter
                 applies to the outgoing ISDN calls.

                 Possible values are:

                   * PresentationAllowed: Default value of Presentation
                     Indicator is set to Presentation Allowed.
                   * PresentationRestricted: Default value of Presentation
                     Indicator is set to Presentation Restricted.
                   * NotAvailable: Default value of Presentation Indicator is
                     set to Not Available.

                 "
   DEFVAL        { presentationAllowed }
   ::= { signalingChannelEntry 11000 }

  -- Columnar:Default Screening Indicator for Calling Party Number IE

  signalingChannelDefaultCallingSi OBJECT-TYPE
   SYNTAX        INTEGER { userProvidedNotScreened(100) ,
                 userProvidedVerifiedAndPassed(200) ,
                 userProvidedVerifiedAndFailed(300) , networkProvided(400) ,
                 contextDependent(500) }
   MAX-ACCESS    read-write
   STATUS        current
   DESCRIPTION " Default Screening Indicator for Calling Party Number IE

                 Default value to insert in the 'Screening Indicator' parameter
                 of the 'Calling Party Number' IE when 'Screening Indicator' is
                 not already defined in the call properties. A call property set
                 by the 'Properties Manipulation' feature of the Call Router has
                 precedence over this default value. This parameter applies to
                 the outgoing ISDN calls.

                 Possible values are:

                   * UserProvidedNotScreened: Default value of Screening
                     Indicator is set to User Provided Not Screened.
                   * UserProvidedVerifiedAndPassed: Default value of Screening
                     Indicator is set to User Provided Verified And Passed.
                   * UserProvidedVerifiedAndFailed: Default value of Screening
                     Indicator is set to User Provided Verified And Failed.
                   * NetworkProvided: Default value of Screening Indicator is
                     set to Network Provided.
                   * ContextDependent: Screening Indicator is set to the value
                     that makes the most sense according to run-time context.

                 "
   DEFVAL        { contextDependent }
   ::= { signalingChannelEntry 11100 }

  -- Columnar:Default Type of Number for Called Party Number IE

  signalingChannelDefaultCalledTon OBJECT-TYPE
   SYNTAX        INTEGER { unknown(100) , international(200) , national(300) ,
                 networkSpecific(400) , subscriber(500) , abbreviated(600) }
   MAX-ACCESS    read-write
   STATUS        current
   DESCRIPTION " Default Type of Number for Called Party Number IE

                 Default value to insert in the 'Type of Number' parameter of
                 the 'Called Party Number' IE when 'Type of Number' is not
                 already defined in the call properties. A call property set by
                 the 'Properties Manipulation' feature of the Call Router has
                 precedence over this default value. This parameter applies to
                 the outgoing ISDN calls.

                 Possible values are:

                   * Unknown: Default value of Type of Number is set to Unknown.
                   * International: Default value of Type of Number is set to
                     International.
                   * National: Default value of Type of Number is set to
                     National.
                   * NetworkSpecific: Default value of Type of Number is set to
                     Network-Specific.
                   * Subscriber: Default value of Type of Number is set to
                     Subscriber.
                   * Abbreviated: Default value of Type of Number is set to
                     Abbreviated.

                 "
   DEFVAL        { unknown }
   ::= { signalingChannelEntry 11200 }

  -- Columnar:Default Numbering Plan Identification for Called Party Number IE

  signalingChannelDefaultCalledNpi OBJECT-TYPE
   SYNTAX        INTEGER { unknown(100) , isdnTelephony(200) , data(300) , telex
                 (400) , nationalStandard(500) , private(600) }
   MAX-ACCESS    read-write
   STATUS        current
   DESCRIPTION " Default Numbering Plan Identification for Called Party Number
                 IE

                 Default value to insert in the 'Numbering Plan Identification'
                 parameter of the 'Called Party Number' IE when 'Numbering Plan
                 Identification' is not already defined in the call properties.
                 A call property set by the 'Properties Manipulation' feature of
                 the Call Router has precedence over this default value. This
                 parameter applies to the outgoing ISDN calls.

                 Possible values are:

                   * Unknown: Default value of Numbering Plan Identification is
                     set to Unknown.
                   * IsdnTelephony: Default value of Numbering Plan
                     Identification is set to ISDN Telephony.
                   * Data: Default value of Numbering Plan Identification is set
                     to Data.
                   * Telex: Default value of Numbering Plan Identification is
                     set to Telex.
                   * NationalStandard: Default value of Numbering Plan
                     Identification is set to National Standard.
                   * Private: Default value of Numbering Plan Identification is
                     set to Private.

                 "
   DEFVAL        { unknown }
   ::= { signalingChannelEntry 11300 }

  -- Columnar:User Suspended Handling

  signalingChannelUserSuspendedHandling OBJECT-TYPE
   SYNTAX        INTEGER { ignore(100) , disconnect(200) }
   MAX-ACCESS    read-write
   STATUS        current
   DESCRIPTION " User Suspended Handling

                 Defines the unit's behaviour when it receives a Notification
                 Indicator IE with the description set to User suspended.

                 Possible values are:

                   * Ignore: Ignore the Notification Indicator IE with
                     description set to User suspended.
                   * Disconnect: Disconnect the call on Notification Indicator
                     IE with description set to User suspended.

                 "
   DEFVAL        { ignore }
   ::= { signalingChannelEntry 11400 }

  -- Columnar:Strict handling of error conditions

  signalingChannelStrictHandlingErrorConditions OBJECT-TYPE
   SYNTAX        MxEnableState
   MAX-ACCESS    read-write
   STATUS        current
   DESCRIPTION " Strict handling of error conditions

                 When activated, validation of Information Elements is applied
                 to every received messages.

                 Detailed error handling procedures are protocol dependent and
                 may vary from network-to-network. The handling of error
                 conditions follows procedures described in ITU-T Q.931
                 subclause 5.8.

                 "
   DEFVAL        { disable }
   ::= { signalingChannelEntry 11500 }

  -- Columnar:Malicious Call Identification Enable

  signalingChannelMcidEnable OBJECT-TYPE
   SYNTAX        MxEnableState
   MAX-ACCESS    read-write
   STATUS        current
   DESCRIPTION " Malicious Call Identification Enable

                 Defines if the Malicious Call Identification (MCID) request
                 sent from the user or network side is supported. Malicious Call
                 Identification (MCID) requests are sent in a Facility IE.

                 The MCID request is triggered by the reception of a SIP INFO
                 message with a proprietary header indicating the malicious
                 nature of the call.

                 This parameter only applies to the DSS1 signaling protocol.

                   * Enable: MCID requests are sent.
                   * Disable: MCID requests are never sent.

                 "
   DEFVAL        { disable }
   ::= { signalingChannelEntry 11600 }

  -- Columnar:Protocol

  signalingChannelProtocol OBJECT-TYPE
   SYNTAX        INTEGER { dss1(100) , dms100(200) , ni2(300) , ess5(400) , qSig
                 (500) }
   MAX-ACCESS    read-write
   STATUS        current
   DESCRIPTION " Protocol

                 Defines the protocol to use for the signaling channel:

                   * DSS1: Digital Subscriber Signaling System No.1
                   * DMS100: Digital Multiplex System 100
                   * NI2: National ISDN No.2
                   * ESS5: 5 Electronic Switching System (5ESS)
                   * QSIG: ECMA's protocol for Private Integrated Services
                     Networks

                 "
   DEFVAL        { dss1 }
   ::= { signalingChannelEntry 200 }

  -- Columnar:Facility Services Enable

  signalingChannelFacilityServicesEnable OBJECT-TYPE
   SYNTAX        MxEnableState
   MAX-ACCESS    read-write
   STATUS        current
   DESCRIPTION " Facility Services Enable

                 Defines whether or not supplementary services FACILITY messages
                 and FACILITY information elements should be enabled on the ISDN
                 interface.

                 Disable: Facility information elements are disabled in both
                 directions (send and receive). No Facility information element
                 can be inserted in sent messages. When receiving a FACILITY
                 message containing supplementary services information, reply
                 with a STATUS message saying the FACILITY is not supported.

                 Enable: Facility information elements are enabled in both
                 directions (send and receive). Facility information elements
                 can be inserted in sent messages. When receiving a FACILITY
                 message containing supplementary services information, accept
                 and interpret the message, processing supported supplementary
                 service messages and silently discarding unsupported
                 supplementary service messages.

                 Generic procedures for the control of ISDN supplementary
                 services are defined in the recommendation ITU-T Q.932.

                 "
   DEFVAL        { disable }
   ::= { signalingChannelEntry 250 }

  -- Columnar:Connected Line Identification Presentation Enable

  signalingChannelColpEnable OBJECT-TYPE
   SYNTAX        MxEnableState
   MAX-ACCESS    read-write
   STATUS        current
   DESCRIPTION " Connected Line Identification Presentation Enable

                 Defines the Connected Number Information Element at the
                 originating ISDN side:

                   * Enable: Sends a Connected Number IE within the CONNECT
                     message, which contains the connected number digits once
                     the transformation of the routing table has been applied.
                   * Disable: The Connected Number IE is never sent.

                 "
   DEFVAL        { disable }
   ::= { signalingChannelEntry 300 }

  -- Columnar:Connected Line Identification Restriction Enable

  signalingChannelColrEnable OBJECT-TYPE
   SYNTAX        MxEnableState
   MAX-ACCESS    read-write
   STATUS        current
   DESCRIPTION " Connected Line Identification Restriction Enable

                 Defines the Connected Number Information Element restriction at
                 the destination ISDN side:

                   * enable: When activated at the User UNI-side (Te), marks the
                     Connected Number IE with a 'restricted' Presentation
                     Indicator, which keeps privacy over the connected number
                     digits. This option has no effect when activated at the
                     Network UNI-side (Nt).
                   * disable: No restriction is applied.

                 When the SignalingChannel.Protocol parameter is set to 'QSIG',
                 the effect of this parameter does not depend on the
                 PrimaryRateInterface.EndpointType parameter (Nt or Te).

                   * Enable: The Presentation Indicator of the Connected Number
                     IE is set to 'restricted' in replies to incoming calls.
                   * Disable: There is no restriction on the connected user
                     number.

                 "
   DEFVAL        { disable }
   ::= { signalingChannelEntry 400 }

  -- Columnar:Connected Line Identification Restriction Override Enable

  signalingChannelColrOverrideEnable OBJECT-TYPE
   SYNTAX        MxEnableState
   MAX-ACCESS    read-write
   STATUS        current
   DESCRIPTION " Connected Line Identification Restriction Override Enable

                 Defines the Connected Number Information Element restriction
                 override at the originating ISDN side:

                   * enable: When activated at the Network UNI-side (Nt), the
                     connected number digits are delivered even if the
                     Presentation Indicator is set to 'restricted'. This option
                     has no effect when activated at the User UNI-side (Te).
                     This is a national option designed for emergency services.
                   * disable: The restriction is not overridden.

                 When the SignalingChannel.Protocol parameter is set to 'QSIG',
                 the effect of this parameter does not depend on the
                 PrimaryRateInterface.EndpointType parameter (Nt or Te).

                   * enable: When the Presentation Indicator of the Connected
                     Number IE is set to 'restricted', the restriction is
                     overridden and the connected user number is presented to
                     the calling user.
                   * disable: The restriction is not overridden.

                 "
   DEFVAL        { disable }
   ::= { signalingChannelEntry 500 }

  -- Columnar:Connected Name Identification Presentation Enable

  signalingChannelConpEnable OBJECT-TYPE
   SYNTAX        MxEnableState
   MAX-ACCESS    read-write
   STATUS        current
   DESCRIPTION " Connected Name Identification Presentation Enable

                 Connected Name identification Presentation (CONP) is a
                 supplementary service which provides the name of the answering
                 or alerting user to the calling user.

                   * Enable: When acting as the terminating side, sends the name
                     of the user who has answered the call in a FACILITY IE
                     within the CONNECT message or the name of the alerted user
                     within the ALERTING or PROGRESS message. The called name
                     and connected name will be set from the P-Asserted-Identity
                     SIP header value. If the name of the user is not available,
                     the NameNotAvailable value is sent in the FACILITY IE. When
                     acting as the originating side, sets the value used to
                     build the P-Asserted-Identity SIP header from the name of
                     the user who has answered the call in the received FACILITY
                     IE within the CONNECT message or the name of the alerted
                     user received from the ALERTING or PROGRESS message.
                   * Disable: No answered or alerted user name information is
                     provided.

                 When acting as the originating side, the user name will be
                 provided to the requesting network even if the presentation
                 indicator in the name presentation argument of the CONP service
                 is set to restricted.

                 CONP is only available for QSIG and NI-2 protocols.

                 "
   DEFVAL        { disable }
   ::= { signalingChannelEntry 510 }

  -- Columnar:Outgoing Notify Enable

  signalingChannelOutgoingNotifyEnable OBJECT-TYPE
   SYNTAX        MxEnableState
   MAX-ACCESS    read-write
   STATUS        current
   DESCRIPTION " Outgoing Notify Enable

                 Defines if NOTIFY messages can be sent.

                   * Enable: NOTIFY messages can be sent.
                   * Disable: NOTIFY messages are never sent.

                 The following NOTIFY messages are supported:

                   * REMOTE HOLD: Sent when the remote peer holds the call.
                   * REMOTE RETRIEVAL: Sent when the remote peer retrieves the
                     call.

                 "
   DEFVAL        { disable }
   ::= { signalingChannelEntry 600 }

  -- Columnar:Accepted PROGRESS Causes

  signalingChannelAcceptedProgressCauses OBJECT-TYPE
   SYNTAX        OCTET STRING ( SIZE(0..255) )
   MAX-ACCESS    read-write
   STATUS        current
   DESCRIPTION " Accepted PROGRESS Causes

                 Sets the range of PROGRESS causes accepted by the unit. Causes
                 excluded from this range trigger call disconnections.

                 The string has the following syntax:

                   * ',': Separator between non-consecutive lists of causes or
                     single cause.
                   * 'n': A single cause, where n is the cause number.
                   * 'm-n': List of causes where m is the start cause number and
                     n is the end cause number.

                 NOTE: The space character are ignored and cause duplication is
                 not allowed. Causes must be specified in low to high order.

                 Example: '1,124-127': The accepted causes are 1, 124, 125, 126
                 and 127.

                 "
   DEFVAL        { "1-127" }
   ::= { signalingChannelEntry 700 }

  -- Columnar:Auto Cancel Timeout

  signalingChannelAutoCancelTimeout OBJECT-TYPE
   SYNTAX        Unsigned32 ( 0..180 )
   MAX-ACCESS    read-write
   STATUS        current
   DESCRIPTION " Auto Cancel Timeout

                 Time, in seconds, the endpoint rings before the call is
                 automatically cancelled.

                 Setting this parameter to 0 disables the timeout. Calls will
                 not be automatically cancelled.

                 "
   DEFVAL        { 0 }
   ::= { signalingChannelEntry 800 }

  -- Columnar:Date/Time IE

  signalingChannelDateTimeIeSupport OBJECT-TYPE
   SYNTAX        INTEGER { none(100) , localTime(200) , utc(300) }
   MAX-ACCESS    read-write
   STATUS        current
   DESCRIPTION " Date/Time IE

                 Defines if the optional Date/Time Information Element (IE) can
                 be sent into the CONNECT and SETUP messages issued over BRI and
                 PRI.

                   * None: Date/Time IE is not sent.
                   * LocalTime: Date/Time IE is sent, containing the local time
                     according to the configured time zone in HOC.
                   * Utc: Date/Time IE is sent, containing the Coordinated
                     Universal Time (UTC).

                 Refer to the HOC service for time zones and time server
                 configuration. Without an SNTP synchronized connection, Date/
                 Time IE is not sent.

                 "
   DEFVAL        { none }
   ::= { signalingChannelEntry 900 }

 -- End of table:Signaling

 -- *****************************************************************************
 
 -- Table:Signaling Channel Info

 -- *****************************************************************************
 
 signalingChannelInfoTable OBJECT-TYPE
  SYNTAX        SEQUENCE OF SignalingChannelInfoEntry
  MAX-ACCESS    not-accessible
  STATUS        current
  DESCRIPTION " Signaling Channel Info

                ISDN signaling table containing configuration and operational
                parameters for all ISDN signaling channels on this managed
                device.
                "
  ::= { signalingChannelGroup 200 }
  signalingChannelInfoEntry OBJECT-TYPE
   SYNTAX        SignalingChannelInfoEntry
   MAX-ACCESS    not-accessible
   STATUS        current
   DESCRIPTION " A row in table Signaling Channel Info. "
   INDEX         {
                   signalingChannelInfoInterfaceName
                 }

   ::= { signalingChannelInfoTable 1 }

  SignalingChannelInfoEntry ::= SEQUENCE
  {
    signalingChannelInfoInterfaceName OCTET STRING,
    signalingChannelInfoState         INTEGER
  }

  -- Index:Interface Name

  signalingChannelInfoInterfaceName OBJECT-TYPE
   SYNTAX         OCTET STRING
   MAX-ACCESS     read-only
   STATUS         current
   DESCRIPTION  " Interface Name

                  Identifies the interface.
                  "
   ::= { signalingChannelInfoEntry 100 }

  -- Columnar:State

  signalingChannelInfoState OBJECT-TYPE
   SYNTAX        INTEGER { up(100) , down(200) }
   MAX-ACCESS    read-only
   STATUS        current
   DESCRIPTION " State

                 The current call control state for this channel:

                   * Up:
                   * Down:

                 "
   ::= { signalingChannelInfoEntry 200 }

 -- End of table:Signaling Channel Info

 -- *****************************************************************************
 
 -- Group:Signaling Channel Interop Configuration

 -- *****************************************************************************
 
 signalingChannelInteropGroup OBJECT IDENTIFIER
  ::= { signalingChannelGroup 50000 }
  -- *****************************************************************************
  
  -- Table:Signaling Channel Interop

  -- *****************************************************************************
  
  signalingChannelInteropTable OBJECT-TYPE
   SYNTAX        SEQUENCE OF SignalingChannelInteropEntry
   MAX-ACCESS    not-accessible
   STATUS        current
   DESCRIPTION " Signaling Channel Interop

                 Interop configuration parameters related to the Signaling Channel
                 on this managed device.
                 "
   ::= { signalingChannelInteropGroup 100 }
   signalingChannelInteropEntry OBJECT-TYPE
    SYNTAX        SignalingChannelInteropEntry
    MAX-ACCESS    not-accessible
    STATUS        current
    DESCRIPTION " A row in table Signaling Channel Interop. "
    INDEX         {
                    signalingChannelInteropInterfaceName
                  }

    ::= { signalingChannelInteropTable 1 }

   SignalingChannelInteropEntry ::= SEQUENCE
   {
     signalingChannelInteropInterfaceName                             OCTET STRING,
     signalingChannelInteropCallProceedingDelay                       Unsigned32,
     signalingChannelInteropCallingNameDelivery                       INTEGER,
     signalingChannelInteropInteropPlayLocalRingbackWhenNoMediaStream MxEnableState,
     signalingChannelInteropInteropConsecutiveChannelIndicator        MxEnableState,
     signalingChannelInteropInteropAddReleaseSecondCauseOnExpiry      MxEnableState
   }

   -- Index:Name

   signalingChannelInteropInterfaceName OBJECT-TYPE
    SYNTAX        OCTET STRING
    MAX-ACCESS    read-only
    STATUS        current
    DESCRIPTION " Name

                  Name that identifies the interface.
                  "
    ::= { signalingChannelInteropEntry 100 }

   -- Columnar:CallProceeding Delay

   signalingChannelInteropCallProceedingDelay OBJECT-TYPE
    SYNTAX        Unsigned32 ( 0..4000 )
    MAX-ACCESS    read-write
    STATUS        current
    DESCRIPTION " CallProceeding Delay

                  Defines the maximum time to wait after receiving a SETUP message
                  before sending a CALL PROCEEDING message and going on with
                  normal call processing.

                  After receiving a SETUP message, the system waits for a message
                  from the called party. If the message maps to a User Busy cause,
                  a DISCONNECT message is sent instead of the CALL PROCEEDING
                  otherwise it goes on with normal call processing.

                  The value 0 deactivates this feature.

                  This value is expressed in milliseconds (ms).

                  "
    DEFVAL        { 0 }
    ::= { signalingChannelInteropEntry 200 }

   -- Columnar:Calling Name delivery method.

   signalingChannelInteropCallingNameDelivery OBJECT-TYPE
    SYNTAX        INTEGER { facilityIe(100) , displayIe(200) , userUserIe(300) ,
                  signalingProtocol(400) }
    MAX-ACCESS    read-write
    STATUS        current
    DESCRIPTION " Calling Name delivery method.

                  Defines how the Calling Name is delivered.

                    * FacilityIe: Use a Facility Information Element for
                      delivering the Calling Name.
                    * DisplayIe: Use a Display Information Element for delivering
                      the Calling Name.
                    * UserUserIe: Use a User-User Information Element for
                      delivering the Calling Name.
                    * SignalingProtocol: Use the delivery method defined by the
                      signaling protocol.

                  "
    DEFVAL        { signalingProtocol }
    ::= { signalingChannelInteropEntry 300 }

   -- Columnar:Play Local Ringback when no media stream.

   signalingChannelInteropInteropPlayLocalRingbackWhenNoMediaStream OBJECT-TYPE
    SYNTAX        MxEnableState
    MAX-ACCESS    read-write
    STATUS        current
    DESCRIPTION " Play Local Ringback when no media stream.

                  Forces local ringback generation when early-media is enabled but
                  no media stream has been received yet.

                    * Enable: The local ringback is played after sending an
                      ALERTING and no media stream has been received yet from the
                      outgoing interface.
                    * Disable: Do not play local ringback when doing early-media.

                  Note that this parameter only applies to 180 SIP responses when
                  early-media is enabled.

                  Note that this parameter only affects incoming call on the ISDN
                  interface.

                  "
    DEFVAL        { disable }
    ::= { signalingChannelInteropEntry 500 }

   -- Columnar:Consecutive Channel mode for channel indicator

   signalingChannelInteropInteropConsecutiveChannelIndicator OBJECT-TYPE
    SYNTAX        MxEnableState
    MAX-ACCESS    read-write
    STATUS        current
    DESCRIPTION " Consecutive Channel mode for channel indicator

                  To choose which numbering is used in the channel indicator.

                    * Enable: Channel indicator use logical numbering (1-30).
                    * Disable: Channel indicator use physical time slot number as
                      defined in ISDN (1-15, 17-31).

                  Note that when enabling this parameter, the ISDN standard is no
                  longer followed. This parameter applies only for a PRI interface
                  in E1.

                  "
    DEFVAL        { disable }
    ::= { signalingChannelInteropEntry 600 }

   -- Columnar:Add Release Second Cause On Expiry

   signalingChannelInteropInteropAddReleaseSecondCauseOnExpiry OBJECT-TYPE
    SYNTAX        MxEnableState
    MAX-ACCESS    read-write
    STATUS        current
    DESCRIPTION " Add Release Second Cause On Expiry

                  Specifies if an optional second cause information element with
                  cause No. 102 (recovery on timer expiry) should be sent in the
                  Release message with the original Disconnect cause number.

                    * Enable: The unit will send a RELEASE message with the cause
                      number originally contained in the DISCONNECT message and
                      indicate a second Cause information element with cause No.
                      102 (recovery on timer expiry).
                    * Disable: The cause No. 102 (recovery on timer expiry) is not
                      sent with the original Disconnect cause.

                  This parameter only applies to timers T305, T306, and T308, for
                  endpoint type TE or NT.

                  Some implementations compliant to TBR-3 require this parameter
                  to be disabled.

                  "
    DEFVAL        { enable }
    ::= { signalingChannelInteropEntry 700 }

  -- End of table:Signaling Channel Interop

 -- End of group:Signaling Channel Interop Configuration

-- End of group:Signaling Channel Configuration

-- ****************************************************************************

-- Group:Signaling Channel Configuration

-- ****************************************************************************

physicalGroup OBJECT IDENTIFIER
 ::= { isdnMIBObjects 600 }
 -- ***************************************************************************
 
 -- Table:Physical Link Information

 -- ***************************************************************************
 
 physicalLinkInfoTable OBJECT-TYPE
  SYNTAX        SEQUENCE OF PhysicalLinkInfoEntry
  MAX-ACCESS    not-accessible
  STATUS        current
  DESCRIPTION " Physical Link Information

                The ISDN physical link information table contains status
                information for all ISDN interfaces on this managed device.
                "
  ::= { physicalGroup 100 }
  physicalLinkInfoEntry OBJECT-TYPE
   SYNTAX        PhysicalLinkInfoEntry
   MAX-ACCESS    not-accessible
   STATUS        current
   DESCRIPTION " A row in table Physical Link Information. "
   INDEX         {
                   physicalLinkInfoInterfaceName
                 }

   ::= { physicalLinkInfoTable 1 }

  PhysicalLinkInfoEntry ::= SEQUENCE
  {
    physicalLinkInfoInterfaceName OCTET STRING,
    physicalLinkInfoState         INTEGER
  }

  -- Index:Interface Name

  physicalLinkInfoInterfaceName OBJECT-TYPE
   SYNTAX        OCTET STRING
   MAX-ACCESS    read-only
   STATUS        current
   DESCRIPTION " Interface Name

                 Identifies the interface.
                 "
   ::= { physicalLinkInfoEntry 100 }

  -- Columnar:State

  physicalLinkInfoState OBJECT-TYPE
   SYNTAX        INTEGER { up(100) , down(200) }
   MAX-ACCESS    read-only
   STATUS        current
   DESCRIPTION " State

                 The layer 1 state for this interface:

                   * Up: Layer 1 connectivity.
                   * Down: No layer 1 connectivity. The interface might be in
                     this state because no cable is plugged in or a pinout
                     problem is detected.

                 "
   ::= { physicalLinkInfoEntry 200 }

 -- End of table:Physical Link Information

 -- ***************************************************************************
 
 -- Table:Physical Link

 -- ***************************************************************************
 
 physicalLinkTable OBJECT-TYPE
  SYNTAX        SEQUENCE OF PhysicalLinkEntry
  MAX-ACCESS    not-accessible
  STATUS        current
  DESCRIPTION " Physical Link

                The ISDN physical link table containing configuration and
                operational parameters for all ISDN interfaces on this managed
                device.
                "
  ::= { physicalGroup 200 }
  physicalLinkEntry OBJECT-TYPE
   SYNTAX        PhysicalLinkEntry
   MAX-ACCESS    not-accessible
   STATUS        current
   DESCRIPTION " A row in table Physical Link. "
   INDEX         {
                   physicalLinkInterfaceName
                 }

   ::= { physicalLinkTable 1 }

  PhysicalLinkEntry ::= SEQUENCE
  {
    physicalLinkInterfaceName          OCTET STRING,
    physicalLinkL1TimerT3              Unsigned32,
    physicalLinkClockMode              INTEGER,
    physicalLinkMonitorLinkStateEnable MxEnableState
  }

  -- Index:Interface Name

  physicalLinkInterfaceName OBJECT-TYPE
   SYNTAX        OCTET STRING
   MAX-ACCESS    read-only
   STATUS        current
   DESCRIPTION " Interface Name

                 Identifies the interface.
                 "
   ::= { physicalLinkEntry 100 }

  -- Columnar:Layer 1 Timer T3 Value

  physicalLinkL1TimerT3 OBJECT-TYPE
   SYNTAX        Unsigned32 ( 0..30000 )
   MAX-ACCESS    read-write
   STATUS        current
   DESCRIPTION " Layer 1 Timer T3 Value

                 Timer 3 (T3) is a supervisory timer that has to take into
                 account the overall time to activate. This time includes the
                 time it takes to activate both the TE-NT and the NT-TE
                 portion of the customer access.

                 The expiry of Timer T3 is intended to provide an indication
                 that the network side cannot complete the activation
                 procedure, probably due to a failure condition or the
                 terminal cannot detect INFO 4.

                 This value is expressed in milliseconds (ms).

                 "
   DEFVAL        { 3000 }
   ::= { physicalLinkEntry 200 }

  -- Columnar:Clock Mode

  physicalLinkClockMode OBJECT-TYPE
   SYNTAX        INTEGER { auto(100) , master(200) , slave(300) }
   MAX-ACCESS    read-write
   STATUS        current
   DESCRIPTION " Clock Mode

                 An ISDN port can either generate the clocking for the line or
                 accept the clock from the line. The options master or slave
                 determine the clocking method:

                   * Auto: Derived from the endpoint type (NT: clock master,
                     TE: clock slave)
                   * Master: Generates clock
                   * Slave: Accepts clock

                 Note: For BRI interfaces with the endpoint type configured in
                 TE the clock mode is always slave (even if configuration is
                 set to master).

                 "
   DEFVAL        { auto }
   ::= { physicalLinkEntry 300 }

  -- Columnar:Monitor Link State Enable

  physicalLinkMonitorLinkStateEnable OBJECT-TYPE
   SYNTAX        MxEnableState
   MAX-ACCESS    read-write
   STATUS        current
   DESCRIPTION " Monitor Link State Enable

                 Monitors the physical link state of an ISDN interface.

                 Enable: An ISDN endpoint's operational state is affected by
                 its interface physical link state. When the link state of an
                 ISDN interface is down, the operational state of its matching
                 endpoint becomes 'disable'.

                 Disable: An ISDN endpoint's operational state is not affected
                 by its interface physical link state.

                 "
   DEFVAL        { enable }
   ::= { physicalLinkEntry 400 }

 -- End of table:Physical Link

-- End of group:Signaling Channel Configuration

-- ****************************************************************************

-- Group:Automatic Configuration

-- ****************************************************************************

autoConfigure OBJECT IDENTIFIER
 ::= { isdnMIBObjects 700 }
 -- Scalar:Auto Configure Status

 autoConfigureStatus OBJECT-TYPE
  SYNTAX        INTEGER { idle(100) , sensing(200) }
  MAX-ACCESS    read-only
  STATUS        current
  DESCRIPTION " Auto Configure Status

                Indicates the current status of the ISDN automatic
                configuration mechanism.

                  * Idle: The automatic configuration mechanism is ready to be
                    started.
                  * Sensing: The automatic configuration mechanism is
                    currently started and is testing different ISDN
                    configurations to obtain a link up.

                "
  ::= { autoConfigure 100 }

 -- Scalar:Last Auto Configure Result

 lastAutoConfigureResult OBJECT-TYPE
  SYNTAX        INTEGER { none(100) , success(200) , fail(300) , aborted(400)
                }
  MAX-ACCESS    read-only
  STATUS        current
  DESCRIPTION " Last Auto Configure Result

                Result of the last ISDN automatic configuration.

                  * None: No result is available.
                  * Success: The last automatic configuration succeeded.
                  * Fail: The last automatic configuration failed.
                  * Aborted: The last automatic configuration has been
                    cancelled by the user.

                "
  ::= { autoConfigure 200 }

-- End of group:Automatic Configuration

-- ****************************************************************************

-- Group:Notification Messages Configuration

-- ****************************************************************************

notificationsGroup OBJECT IDENTIFIER
 ::= { isdnMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with a 'Informational' and
                    higher severity are issued.
                  * Warning: Notification messages with a 'Warning' and higher
                    severity are issued.
                  * Error: Notification messages with an 'Error' and higher
                    severity are issued.
                  * Critical: Notification messages with a 'Critical' severity
                    are issued.

                "
  DEFVAL        { warning }
  ::= { notificationsGroup 100 }

-- End of group:Notification Messages Configuration

-- ****************************************************************************

-- Group:Configuration Settings

-- ****************************************************************************

configurationGroup OBJECT IDENTIFIER
 ::= { isdnMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for the
                configuration to fully take effect.

                  * Yes: Service needs to be restarted.
                  * No: Service does not need to be restarted.

                Services can be restarted by using the
                Scm.ServiceCommands.Restart command.

                "
  ::= { configurationGroup 100 }

-- End of group:Configuration Settings

END
