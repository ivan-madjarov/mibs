-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


DGW11-MX-TELIF-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

telIfMIB MODULE-IDENTITY
 LAST-UPDATED   "0603290000Z"
 ORGANIZATION " Mediatrix Telecom, Inc. "
 CONTACT-INFO " Mediatrix Telecom, Inc.
                4229, Garlock Street
                Sherbrooke (Quebec)
                Canada
                Phone: (819) 829-8749
                "
 DESCRIPTION  " Basic Telephony Interface

                The Telephony Interface service allows to configure the basic
                specification of each telephony interface.
                "
 -- ****************************************************************************
 
 -- Revision history
 -- ****************************************************************************
 REVISION       "0603290000Z"
 DESCRIPTION  " Initial Revision "
 REVISION       "0709240000Z"
 DESCRIPTION  " Added MusicOnHoldStreamingEnable variable "
 REVISION       "0711280000Z"
 DESCRIPTION  " Added support for Brazil1 and UK1. "
 REVISION       "0805230000Z"
 DESCRIPTION  " Added CountryToneStatus status table "
 REVISION       "0808170000Z"
 DESCRIPTION  " Added Interop group "
 ::= { mediatrixServices 1775 }

telIfMIBObjects OBJECT IDENTIFIER ::= { telIfMIB 1 }

-- Scalar:Country Selection

countrySelection OBJECT-TYPE
 SYNTAX        INTEGER { austria1(2000) , brazil1(3000) , czechRepublic1(4500)
               , france1(6000) , germany1(7000) , germany2(7100) , italy1
               (11000) , northAmerica1(17000) , spain1(19000) , switzerland1
               (21000) , uk1(24000) }
 MAX-ACCESS    read-write
 STATUS        current
 DESCRIPTION " Country Selection

               The country selection allows to select predefined country
               settings for the tone profiles, ring patterns, and other
               parameters such as input and output gains.
               "
 DEFVAL        { northAmerica1 }
 ::= { telIfMIBObjects 100 }

-- ****************************************************************************

-- Group:Country Customization

-- ****************************************************************************

countryCustomizationGroup OBJECT IDENTIFIER
 ::= { telIfMIBObjects 200 }
 -- ***************************************************************************
 
 -- Group:Users Gain

 -- ***************************************************************************
 
 countryCustomizationUserGainGroup OBJECT IDENTIFIER
  ::= { countryCustomizationGroup 100 }
  -- Scalar:Default User Output Gain Offset

  defaultCountryCustomizationUserGainOutputOffset OBJECT-TYPE
   SYNTAX        Integer32 ( -12..12 )
   MAX-ACCESS    read-write
   STATUS        current
   DESCRIPTION " Default User Output Gain Offset

                 The user output gain offset is added to the base output gain
                 to compute the total output gain. The user output gain is in
                 dB. Valid output gain range is between -12 dB and +12 dB.

                 If a specific configuration is set in the
                 SpecificCountryCustomizationUserGain.OutputOffset variable and
                 the SpecificCountryCustomizationUserGain.EnableConfig variable
                 is set to 'Enable', then it overrides the current default
                 configuration.


                 "
   DEFVAL        { 0 }
   ::= { countryCustomizationUserGainGroup 200 }

  -- ***************************************************************************
  
  -- Table:Specific User Gain

  -- ***************************************************************************
  
  specificCountryCustomizationUserGainTable OBJECT-TYPE
   SYNTAX        SEQUENCE OF SpecificCountryCustomizationUserGainEntry
   MAX-ACCESS    not-accessible
   STATUS        current
   DESCRIPTION " Specific User Gain

                 This table allows to configure the user gain for a specific
                 interface. All interfaces have the default configuration
                 unless 'EnableConfig' is enabled.
                 "
   ::= { countryCustomizationUserGainGroup 300 }
   specificCountryCustomizationUserGainEntry OBJECT-TYPE
    SYNTAX        SpecificCountryCustomizationUserGainEntry
    MAX-ACCESS    not-accessible
    STATUS        current
    DESCRIPTION " A row in table Specific User Gain. "
    INDEX         {
                    specificCountryCustomizationUserGainInterfaceId
                  }

    ::= { specificCountryCustomizationUserGainTable 1 }

   SpecificCountryCustomizationUserGainEntry ::= SEQUENCE
   {
     specificCountryCustomizationUserGainInterfaceId  OCTET STRING,
     specificCountryCustomizationUserGainEnableConfig MxEnableState,
     specificCountryCustomizationUserGainOutputOffset Integer32
   }

   -- Index:Interface Identifier

   specificCountryCustomizationUserGainInterfaceId OBJECT-TYPE
    SYNTAX        OCTET STRING
    MAX-ACCESS    read-only
    STATUS        current
    DESCRIPTION " Interface Identifier

                  String that identifies a interface in other tables.
                  "
    ::= { specificCountryCustomizationUserGainEntry 100 }

   -- Columnar:Enable Configuration

   specificCountryCustomizationUserGainEnableConfig OBJECT-TYPE
    SYNTAX        MxEnableState
    MAX-ACCESS    read-write
    STATUS        current
    DESCRIPTION " Enable Configuration

                  Defines the configuration to use for a specific interface.

                    * Disable: The interface uses the default configuration as
                      defined in the
                      DefaultCountryCustomizationUserGainInputOffset and
                      DefaultCountryCustomizationUserGainOutputOffset
                      variables.
                    * Enable: The interface uses the specific configuration as
                      defined in the
                      SpecificCountryCustomizationUserGain.InputOffset and
                      SpecificCountryCustomizationUserGain.OutputOffset
                      variables.


                  "
    DEFVAL        { disable }
    ::= { specificCountryCustomizationUserGainEntry 200 }

   -- Columnar:Specific User Output Gain Offset

   specificCountryCustomizationUserGainOutputOffset OBJECT-TYPE
    SYNTAX        Integer32 ( -12..12 )
    MAX-ACCESS    read-write
    STATUS        current
    DESCRIPTION " Specific User Output Gain Offset

                  The user output gain offset is added to the base output gain
                  to compute the total output gain. The user output gain is in
                  dB. Valid output gain range is between -12 dB and +12 dB.

                  This configuration overrides the default configuration set in
                  the DefaultCountryCustomizationUserGainOutputOffset variable
                  if the SpecificCountryCustomizationUserGain.EnableConfig
                  variable is set to 'Enable'.


                  "
    DEFVAL        { 0 }
    ::= { specificCountryCustomizationUserGainEntry 400 }


  -- End of table:Specific User Gain

 -- End of group:Users Gain

 -- ***************************************************************************
 
 -- Group:Country Override Dialing

 -- ***************************************************************************
 
 countryCustomizationDialingGroup OBJECT IDENTIFIER
  ::= { countryCustomizationGroup 400 }
  -- Scalar:Default Override Dialing Country Configuration

  defaultCountryCustomizationDialingOverride OBJECT-TYPE
   SYNTAX        MxEnableState
   MAX-ACCESS    read-write
   STATUS        current
   DESCRIPTION " Default Override Dialing Country Configuration

                 Allows to override the default country dialing setting.

                   * Disable: The interface uses the default country dialing
                     setting.
                   * Enable: The interface uses the dialing country setting as
                     defined in the
                     DefaultCountryCustomizationDialingInterDtmfDialDelay and
                     DefaultCountryCustomizationDialingDtmfDuration variables.

                 If a specific configuration is set in the
                 SpecificCountryCustomizationDialing.Override variable and the
                 SpecificCountryCustomizationDialing.EnableConfig variable is
                 set to 'Enable', then it overrides the current default
                 configuration.


                 "
   DEFVAL        { disable }
   ::= { countryCustomizationDialingGroup 100 }

  -- Scalar:Default Country Override Delay Between Dialed DTMF

  defaultCountryCustomizationDialingInterDtmfDialDelay OBJECT-TYPE
   SYNTAX        Unsigned32 ( 50..600 )
   MAX-ACCESS    read-write
   STATUS        current
   DESCRIPTION " Default Country Override Delay Between Dialed DTMF

                 The delay between two DTMFs when dialing on the interface.

                 This value is expressed in milliseconds (ms).

                 This configuration is used only if the variable
                 DefaultCountryCustomizationDialingOverride is set to 'Enable'.

                 If a specific configuration is set in the
                 SpecificCountryCustomizationDialing.InterDtmfDialDelay
                 variable and the
                 SpecificCountryCustomizationDialing.EnableConfig variable is
                 set to 'Enable', then it overrides the current default
                 configuration.


                 "
   DEFVAL        { 100 }
   ::= { countryCustomizationDialingGroup 200 }

  -- Scalar:Default Country Override Dialed DTMF Duration

  defaultCountryCustomizationDialingDtmfDuration OBJECT-TYPE
   SYNTAX        Unsigned32 ( 50..600 )
   MAX-ACCESS    read-write
   STATUS        current
   DESCRIPTION " Default Country Override Dialed DTMF Duration

                 The duration of a DTMF when dialing on the interface.

                 This value is expressed in milliseconds (ms).

                 This configuration is used only if the variable
                 DefaultCountryCustomizationDialingOverride is set to 'Enable'.

                 If a specific configuration is set in the
                 SpecificCountryCustomizationDialing.DtmfDuration variable and
                 the SpecificCountryCustomizationDialing.EnableConfig variable
                 is set to 'Enable', then it overrides the current default
                 configuration.


                 "
   DEFVAL        { 100 }
   ::= { countryCustomizationDialingGroup 300 }

  -- ***************************************************************************
  
  -- Table:Specific Country Override Dialing.

  -- ***************************************************************************
  
  specificCountryCustomizationDialingTable OBJECT-TYPE
   SYNTAX        SEQUENCE OF SpecificCountryCustomizationDialingEntry
   MAX-ACCESS    not-accessible
   STATUS        current
   DESCRIPTION " Specific Country Override Dialing.

                 This table allows to override the default country dialing
                 configuration for a specific interface. All interfaces have
                 the default configuration unless 'EnableConfig' is enabled.
                 "
   ::= { countryCustomizationDialingGroup 400 }
   specificCountryCustomizationDialingEntry OBJECT-TYPE
    SYNTAX        SpecificCountryCustomizationDialingEntry
    MAX-ACCESS    not-accessible
    STATUS        current
    DESCRIPTION " A row in table Specific Country Override Dialing.. "
    INDEX         {
                    specificCountryCustomizationDialingInterfaceId
                  }

    ::= { specificCountryCustomizationDialingTable 1 }

   SpecificCountryCustomizationDialingEntry ::= SEQUENCE
   {
     specificCountryCustomizationDialingInterfaceId        OCTET STRING,
     specificCountryCustomizationDialingEnableConfig       MxEnableState,
     specificCountryCustomizationDialingOverride           MxEnableState,
     specificCountryCustomizationDialingInterDtmfDialDelay Unsigned32,
     specificCountryCustomizationDialingDtmfDuration       Unsigned32
   }

   -- Index:Interface Identifier

   specificCountryCustomizationDialingInterfaceId OBJECT-TYPE
    SYNTAX        OCTET STRING
    MAX-ACCESS    read-only
    STATUS        current
    DESCRIPTION " Interface Identifier

                  String that identifies a Interface in other tables.
                  "
    ::= { specificCountryCustomizationDialingEntry 100 }

   -- Columnar:Enable Configuration

   specificCountryCustomizationDialingEnableConfig OBJECT-TYPE
    SYNTAX        MxEnableState
    MAX-ACCESS    read-write
    STATUS        current
    DESCRIPTION " Enable Configuration

                  Defines the configuration to use for a specific interface.

                    * Disable: The interface uses the default configuration as
                      defined in the
                      DefaultCountryCustomizationDialingOverride,
                      DefaultCountryCustomizationDialingInterDtmfDialDelay and
                      DefaultCountryCustomizationDialingDtmfDuration variables.
                    * Enable: The interface uses the specific configuration as
                      defined in the
                      SpecificCountryCustomizationDialing.Override,
                      SpecificCountryCustomizationDialing.InterDtmfDialDelay
                      and SpecificCountryCustomizationDialing.DtmfDuration
                      variables.


                  "
    DEFVAL        { disable }
    ::= { specificCountryCustomizationDialingEntry 200 }

   -- Columnar:Specific Override Dialing Country Configuration

   specificCountryCustomizationDialingOverride OBJECT-TYPE
    SYNTAX        MxEnableState
    MAX-ACCESS    read-write
    STATUS        current
    DESCRIPTION " Specific Override Dialing Country Configuration

                  Allows to override the default country dialing setting.

                    * Disable: The interface uses the default country dialing
                      setting.
                    * Enable: The interface uses the specific dialing
                      configuration as defined in the InterDtmfDialDelay and
                      DtmfDuration variables.

                  This configuration overrides the default configuration set in
                  the DefaultCountryCustomizationDialingOverride variable if
                  the SpecificCountryCustomizationDialing.EnableConfig variable
                  is set to 'Enable'.


                  "
    DEFVAL        { disable }
    ::= { specificCountryCustomizationDialingEntry 300 }

   -- Columnar:Specific Delay Between Dialed DTMF

   specificCountryCustomizationDialingInterDtmfDialDelay OBJECT-TYPE
    SYNTAX        Unsigned32 ( 50..600 )
    MAX-ACCESS    read-write
    STATUS        current
    DESCRIPTION " Specific Delay Between Dialed DTMF

                  The delay between two DTMFs when dialing on the interface.

                  This value is expressed in milliseconds (ms).

                  This configuration is used only if the variable Override is
                  set to 'Enable'.

                  This configuration overrides the default configuration set in
                  the DefaultCountryCustomizationDialingInterDtmfDialDelay
                  variable if the
                  SpecificCountryCustomizationDialing.EnableConfig variable is
                  set to 'Enable'.


                  "
    DEFVAL        { 100 }
    ::= { specificCountryCustomizationDialingEntry 400 }

   -- Columnar:Specific Dialed DTMF Duration

   specificCountryCustomizationDialingDtmfDuration OBJECT-TYPE
    SYNTAX        Unsigned32 ( 50..600 )
    MAX-ACCESS    read-write
    STATUS        current
    DESCRIPTION " Specific Dialed DTMF Duration

                  The duration of a DTMF when dialing on the interface.

                  This value is expressed in milliseconds (ms).

                  This configuration is used only if the variable Override is
                  set to 'Enable'.

                  This configuration overrides the default configuration set in
                  the DefaultCountryCustomizationDialingDtmfDuration variable
                  if the SpecificCountryCustomizationDialing.EnableConfig
                  variable is set to 'Enable'.


                  "
    DEFVAL        { 100 }
    ::= { specificCountryCustomizationDialingEntry 500 }


  -- End of table:Specific Country Override Dialing.

 -- End of group:Country Override Dialing

 -- ***************************************************************************
 
 -- Group:Country Customization Tone

 -- ***************************************************************************
 
 countryCustomizationToneGroup OBJECT IDENTIFIER
  ::= { countryCustomizationGroup 500 }
  -- ***************************************************************************
  
  -- Table:Country Tone Status

  -- ***************************************************************************
  
  countryToneStatusTable OBJECT-TYPE
   SYNTAX        SEQUENCE OF CountryToneStatusEntry
   MAX-ACCESS    not-accessible
   STATUS        current
   DESCRIPTION " Country Tone Status

                 This table displays the current tone pattern used (depends on
                 the CountrySelection variable and the CountryCustomizationTone
                 table). The configuration applies to all interfaces.
                 "
   ::= { countryCustomizationToneGroup 100 }
   countryToneStatusEntry OBJECT-TYPE
    SYNTAX        CountryToneStatusEntry
    MAX-ACCESS    not-accessible
    STATUS        current
    DESCRIPTION " A row in table Country Tone Status. "
    INDEX         {
                    countryToneStatusTone
                  }

    ::= { countryToneStatusTable 1 }

   CountryToneStatusEntry ::= SEQUENCE
   {
     countryToneStatusTone    INTEGER,
     countryToneStatusPattern OCTET STRING
   }

   -- Index:Tone

   countryToneStatusTone OBJECT-TYPE
    SYNTAX        INTEGER { busy (100) , confirmation (200) , congestion(300) ,
                  dial(400) , hold(500) , intercept(600) , messageWaiting (700)
                  , preemption(800) , reorder(900) , ringback (1000) , roh
                  (1100) , sit(1200) , stutter(1300) }
    MAX-ACCESS    read-only
    STATUS        current
    DESCRIPTION " Tone

                  Tone.
                  "
    ::= { countryToneStatusEntry 100 }

   -- Columnar:Pattern

   countryToneStatusPattern OBJECT-TYPE
    SYNTAX        OCTET STRING ( SIZE(0..512) )
    MAX-ACCESS    read-only
    STATUS        current
    DESCRIPTION " Pattern

                  Pattern description of the currently used tone.

                  See the documentation for a description of the syntax.


                  "
    DEFVAL        { "" }
    ::= { countryToneStatusEntry 300 }


  -- End of table:Country Tone Status

  -- ***************************************************************************
  
  -- Table:Country Customization Tone

  -- ***************************************************************************
  
  countryCustomizationToneTable OBJECT-TYPE
   SYNTAX        SEQUENCE OF CountryCustomizationToneEntry
   MAX-ACCESS    not-accessible
   STATUS        current
   DESCRIPTION " Country Customization Tone

                 This table allows to override the default country tone
                 configuration. The configuration applies to all interfaces.
                 "
   ::= { countryCustomizationToneGroup 200 }
   countryCustomizationToneEntry OBJECT-TYPE
    SYNTAX        CountryCustomizationToneEntry
    MAX-ACCESS    not-accessible
    STATUS        current
    DESCRIPTION " A row in table Country Customization Tone. "
    INDEX         {
                    countryCustomizationToneTone
                  }

    ::= { countryCustomizationToneTable 1 }

   CountryCustomizationToneEntry ::= SEQUENCE
   {
     countryCustomizationToneTone     INTEGER,
     countryCustomizationToneOverride MxEnableState,
     countryCustomizationTonePattern  OCTET STRING
   }

   -- Index:Tone

   countryCustomizationToneTone OBJECT-TYPE
    SYNTAX        INTEGER { busy (100) , confirmation (200) , congestion(300) ,
                  dial(400) , hold(500) , intercept(600) , messageWaiting (700)
                  , preemption(800) , reorder(900) , ringback (1000) , roh
                  (1100) , sit(1200) , stutter(1300) }
    MAX-ACCESS    read-only
    STATUS        current
    DESCRIPTION " Tone

                  Tone to customize.
                  "
    ::= { countryCustomizationToneEntry 100 }

   -- Columnar:Override Tone Country Configuration

   countryCustomizationToneOverride OBJECT-TYPE
    SYNTAX        MxEnableState
    MAX-ACCESS    read-write
    STATUS        current
    DESCRIPTION " Override Tone Country Configuration

                  Allows to override the default country tone setting.

                    * Disable: The unit uses the default country dialing
                      setting.
                    * Enable: The unit uses the tone configuration as defined
                      in the Pattern variables.


                  "
    DEFVAL        { disable }
    ::= { countryCustomizationToneEntry 200 }

   -- Columnar:Pattern

   countryCustomizationTonePattern OBJECT-TYPE
    SYNTAX        OCTET STRING ( SIZE(0..512) )
    MAX-ACCESS    read-write
    STATUS        current
    DESCRIPTION " Pattern

                  Pattern description of the custom tone. Used only if the
                  variable Override is set to 'Enable'.

                  See the documentation for a description of the syntax.


                  "
    DEFVAL        { "" }
    ::= { countryCustomizationToneEntry 300 }


  -- End of table:Country Customization Tone

 -- End of group:Country Customization Tone

-- End of group:Country Customization

-- ****************************************************************************

-- Group:Machine Detection

-- ****************************************************************************

machineDetectionGroup OBJECT IDENTIFIER
 ::= { telIfMIBObjects 300 }
 -- Scalar:Default Enable/Disable CNG Tone Detection

 defaultMachineDetectionCngToneDetection OBJECT-TYPE
  SYNTAX        MxEnableState
  MAX-ACCESS    read-write
  STATUS        current
  DESCRIPTION " Default Enable/Disable CNG Tone Detection

                Enables fax calling tone (CNG tone) detection.

                  * Enable: Upon recognition of the CNG tone, the unit
                    switches the communication from voice mode to fax mode and
                    the CNG is transferred by using the preferred fax codec.
                    NOTE: This option allows for quicker fax detection, but it
                    also increases the risk of falsedetection.
                  * Disable: The CNG tone does not trigger a transition from
                    voice to data and the CNG is transferred in the voice
                    channel. NOTE: With this option, faxes are detected later,
                    but the risk of false detection is reduced.

                If a specific configuration is set in the
                SpecificMachineDetection.CngToneDetection variable and the
                SpecificMachineDetection.EnableConfig variable is set to
                'Enable', then it overrides the current default configuration.


                "
  DEFVAL        { enable }
  ::= { machineDetectionGroup 100 }

 -- ***************************************************************************
 
 -- Table:Specific Voice Codec Configuration

 -- ***************************************************************************
 
 specificMachineDetectionTable OBJECT-TYPE
  SYNTAX                SEQUENCE OF SpecificMachineDetectionEntry
  MAX-ACCESS            not-accessible
  STATUS                current
  DESCRIPTION         " Specific Voice Codec Configuration

                        specific configuration.
                        "
  ::= { machineDetectionGroup 200 }
  specificMachineDetectionEntry OBJECT-TYPE
   SYNTAX        SpecificMachineDetectionEntry
   MAX-ACCESS    not-accessible
   STATUS        current
   DESCRIPTION " A row in table Specific Voice Codec Configuration . "
   INDEX         {
                   specificMachineDetectionInterfaceId
                 }

   ::= { specificMachineDetectionTable 1 }

  SpecificMachineDetectionEntry ::= SEQUENCE
  {
    specificMachineDetectionInterfaceId      OCTET STRING,
    specificMachineDetectionEnableConfig     MxEnableState,
    specificMachineDetectionCngToneDetection MxEnableState
  }

  -- Index:Interface Identifier

  specificMachineDetectionInterfaceId OBJECT-TYPE
   SYNTAX        OCTET STRING
   MAX-ACCESS    read-only
   STATUS        current
   DESCRIPTION " Interface Identifier

                 String that identifies a interface in other tables.
                 "
   ::= { specificMachineDetectionEntry 100 }

  -- Columnar:Enable Configuration

  specificMachineDetectionEnableConfig OBJECT-TYPE
   SYNTAX        MxEnableState
   MAX-ACCESS    read-write
   STATUS        current
   DESCRIPTION " Enable Configuration

                 Defines the configuration to use for a specific interface.

                   * Disable: The interface uses the default configuration as
                     defined in the DefaultMachineDetectionCngToneDetection
                     variable.
                   * Enable: The interface uses the specific configuration as
                     defined in the SpecificMachineDetection.CngToneDetection
                     variable.


                 "
   DEFVAL        { disable }
   ::= { specificMachineDetectionEntry 200 }

  -- Columnar:Specific Enable/Disable CNG Tone Detection

  specificMachineDetectionCngToneDetection OBJECT-TYPE
   SYNTAX        MxEnableState
   MAX-ACCESS    read-write
   STATUS        current
   DESCRIPTION " Specific Enable/Disable CNG Tone Detection

                 Enables fax calling tone (CNG tone) detection.

                   * Enable: Upon recognition of the CNG tone, the unit
                     switches the communication from voice mode to fax mode
                     and the CNG is transferred by using the preferred fax
                     codec. NOTE: This option allows for quicker fax
                     detection, but it also increases the risk of false
                     detection.
                   * Disable: The CNG tone does not trigger a transition from
                     voice to data and the CNG is transferred in the voice
                     channel. NOTE: With this option, faxes are detected
                     later, but the risk of false detection is reduced.

                 This configuration overrides the default configuration set in
                 the DefaultMachineDetectionCngToneDetection variable if the
                 SpecificMachineDetection.EnableConfig variable is set to
                 'Enable'.


                 "
   DEFVAL        { enable }
   ::= { specificMachineDetectionEntry 300 }


 -- End of table:Specific Voice Codec Configuration

-- End of group:Machine Detection

-- ****************************************************************************

-- Group:Music On Hold Streaming

-- ****************************************************************************

musicOnHoldStreamingGroup OBJECT IDENTIFIER
 ::= { telIfMIBObjects 400 }
 -- Scalar:Music On Hold Streaming Enable

 musicOnHoldStreamingEnable OBJECT-TYPE
  SYNTAX        MxEnableState
  MAX-ACCESS    read-write
  STATUS        current
  DESCRIPTION " Music On Hold Streaming Enable

                Indicates whether or not the unit should play music when being
                put on hold.

                  * Disable: No music is played.
                  * Enable: Music is played toward the telephony side when
                    being put on hold from the network side.


                "
  DEFVAL        { disable }
  ::= { musicOnHoldStreamingGroup 100 }

-- End of group:Music On Hold Streaming

-- ****************************************************************************

-- Group:Interop Group

-- ****************************************************************************

interopGroup OBJECT IDENTIFIER
 ::= { telIfMIBObjects 50000 }
 -- ***************************************************************************
 
 -- Table:DTMF Detection Configuration

 -- ***************************************************************************
 
 interopDtmfDetectionTable OBJECT-TYPE
  SYNTAX                  SEQUENCE OF InteropDtmfDetectionEntry
  MAX-ACCESS              not-accessible
  STATUS                  current
  DESCRIPTION           " DTMF Detection Configuration

                          DTMF Detection Configuration
                          "
  ::= { interopGroup 100 }
  interopDtmfDetectionEntry OBJECT-TYPE
   SYNTAX        InteropDtmfDetectionEntry
   MAX-ACCESS    not-accessible
   STATUS        current
   DESCRIPTION " A row in table DTMF Detection Configuration. "
   INDEX         {
                   interopDtmfDetectionInterfaceId
                 }

   ::= { interopDtmfDetectionTable 1 }

  InteropDtmfDetectionEntry ::= SEQUENCE
  {
    interopDtmfDetectionInterfaceId      OCTET STRING,
    interopDtmfDetectionRiseTimeCriteria INTEGER,
    interopDtmfDetectionPositiveTwist    Unsigned32
  }

  -- Index:Interface Identifier

  interopDtmfDetectionInterfaceId OBJECT-TYPE
   SYNTAX        OCTET STRING
   MAX-ACCESS    read-only
   STATUS        current
   DESCRIPTION " Interface Identifier

                 String that identifies an interface in other tables.
                 "
   ::= { interopDtmfDetectionEntry 100 }

  -- Columnar:Rise Time Criteria

  interopDtmfDetectionRiseTimeCriteria OBJECT-TYPE
   SYNTAX        INTEGER { checkSr (100) , confirmSnr (200) }
   MAX-ACCESS    read-write
   STATUS        current
   DESCRIPTION " Rise Time Criteria

                 Defines how the Rise Time criteria should be configured for
                 DTMF detection.

                   * CheckSr: Enable the Step Rise criteria and disable the
                     Confirm DTMF SNR criteria.
                   * ConfirmSnr: Enable the Confirm DTMF SNR criteria and
                     disable the Step Rise criteria.

                 The Step Rise criteria compares the current frame energy to
                 the high frequency power of the previous frame. If the
                 current frame energy is high enough, then it passes the test,
                 further validating the DTMF.

                 Disabling the Step Rise criteria may result in deteriorated
                 talk-off performance, but increases the detection of
                 malformed DTMF.

                 The Confirm DTMF SNR criteria is an additional
                 Signal-to-noise ratio test performed before a confirmed DTMF
                 report is sent to finally validate the DTMF.


                 "
   DEFVAL        { confirmSnr }
   ::= { interopDtmfDetectionEntry 200 }

  -- Columnar:Malformed DTMF Detection Method

  interopDtmfDetectionPositiveTwist OBJECT-TYPE
   SYNTAX        Unsigned32 ( 1..10 )
   MAX-ACCESS    read-write
   STATUS        current
   DESCRIPTION " Malformed DTMF Detection Method

                 Defines the value for the Positive Twist DTMF detection
                 parameter.

                 When the high-group frequency of a DTMF is more powerful than
                 the low-group frequency, the difference between the
                 high-group frequency absolute power and the low-group
                 frequency absolute power must be smaller than or equal to the
                 value set in this variable. Otherwise, the DTMF is not
                 detected.

                 Raising this value increases the sensitivity of DTMF
                 detection. Raising this value too high may also cause false
                 detections of DTMFs.


                 "
   DEFVAL        { 6 }
   ::= { interopDtmfDetectionEntry 300 }


 -- End of table:DTMF Detection Configuration

-- End of group:Interop Group

-- ****************************************************************************

-- Group:Notification Messages Configuration

-- ****************************************************************************

notificationsGroup OBJECT IDENTIFIER
 ::= { telIfMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { telIfMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
