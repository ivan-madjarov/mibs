-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************

DGW20-MX-TELIF-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

telIfMIB MODULE-IDENTITY
 LAST-UPDATED   "1905090000Z"
 ORGANIZATION " Mediatrix Telecom, Inc. "
 CONTACT-INFO " Mediatrix Telecom, Inc.
                4229, Garlock Street
                Sherbrooke (Quebec)
                Canada
                Phone: (819) 829-8749
                "
 DESCRIPTION  " Basic Telephony Interface

                The Telephony Interface (TelIf) service manages tone generation
                and detection on the telephony interfaces.
                "
 ::= { mediatrixServices 1775 }

telIfMIBObjects OBJECT IDENTIFIER ::= { telIfMIB 1 }

-- Scalar:Country Selection

countrySelection OBJECT-TYPE
 SYNTAX        INTEGER { argentina1(900) , australia1(1000) , australia2(1100)
               , austria1(2000) , brazil1(3000) , china1(4000) , czechRepublic1
               (4500) , denmark1(5000) , france1(6000) , germany1(7000) ,
               germany2(7100) , israel2(10100) , italy1(11000) , japan2(12100)
               , mexico1(14000) , netherlands1(15000) , newZealand1(16000) ,
               northAmerica1(17000) , russia1(18000) , spain1(19000) , sweden1
               (20000) , switzerland1(21000) , uae2(23100) , uae3(23200) , uae4
               (23300) , uk1(24000) }
 MAX-ACCESS    read-write
 STATUS        current
 DESCRIPTION " Country Selection

               The country selection allows to select predefined country
               settings for the tone profiles, ring patterns, and other
               parameters such as input and output gains.
               "
 DEFVAL        { northAmerica1 }
 ::= { telIfMIBObjects 100 }

-- ****************************************************************************

-- Group:Country Customisation

-- ****************************************************************************

countryCustomizationGroup OBJECT IDENTIFIER
 ::= { telIfMIBObjects 200 }
 -- ***************************************************************************
 
 -- Group:Users Gain

 -- ***************************************************************************
 
 countryCustomizationUserGainGroup OBJECT IDENTIFIER
  ::= { countryCustomizationGroup 100 }
  -- Scalar:Default User Input Gain Offset

  defaultCountryCustomizationUserGainInputOffset OBJECT-TYPE
   SYNTAX        Integer32 ( -12..12 )
   MAX-ACCESS    read-write
   STATUS        current
   DESCRIPTION " Default User Input Gain Offset

                 The user input gain offset is added to the base input gain to
                 compute the total input gain on all telephony interfaces. The
                 user input gain is in dB.

                 Ex.: On a call involving a SIP terminal and an FXS terminal,
                 raising the input offset will raise the volume perceived on
                 the SIP terminal.

                 If a specific configuration is set in the
                 SpecificCountryCustomizationUserGain.InputOffset parameter and
                 the SpecificCountryCustomizationUserGain.EnableConfig
                 parameter is set to 'Enable', then it overrides the current
                 default configuration.

                 "
   DEFVAL        { 0 }
   ::= { countryCustomizationUserGainGroup 100 }

  -- Scalar:Default User Output Gain Offset

  defaultCountryCustomizationUserGainOutputOffset OBJECT-TYPE
   SYNTAX        Integer32 ( -12..12 )
   MAX-ACCESS    read-write
   STATUS        current
   DESCRIPTION " Default User Output Gain Offset

                 The user output gain offset is added to the base output gain
                 to compute the total output gain on all telephony interfaces.
                 The user output gain is in dB.

                 Ex.: On a call involving a SIP terminal and an FXS terminal,
                 raising the output offset will raise the volume perceived on
                 the FXS terminal.

                 If a specific configuration is set in the
                 SpecificCountryCustomizationUserGain.OutputOffset parameter
                 and the SpecificCountryCustomizationUserGain.EnableConfig
                 parameter is set to 'Enable', then it overrides the current
                 default configuration.

                 "
   DEFVAL        { 0 }
   ::= { countryCustomizationUserGainGroup 200 }

  -- ***************************************************************************
  
  -- Table:Specific User Gain

  -- ***************************************************************************
  
  specificCountryCustomizationUserGainTable OBJECT-TYPE
   SYNTAX        SEQUENCE OF SpecificCountryCustomizationUserGainEntry
   MAX-ACCESS    not-accessible
   STATUS        current
   DESCRIPTION " Specific User Gain

                 This table allows to configure the user gain for a specific
                 interface. All interfaces have the default configuration
                 unless the EnableConfig parameter is enabled.

                 "
   ::= { countryCustomizationUserGainGroup 300 }
   specificCountryCustomizationUserGainEntry OBJECT-TYPE
    SYNTAX        SpecificCountryCustomizationUserGainEntry
    MAX-ACCESS    not-accessible
    STATUS        current
    DESCRIPTION " A row in table Specific User Gain. "
    INDEX         {
                    specificCountryCustomizationUserGainInterfaceId
                  }

    ::= { specificCountryCustomizationUserGainTable 1 }

   SpecificCountryCustomizationUserGainEntry ::= SEQUENCE
   {
     specificCountryCustomizationUserGainInterfaceId  OCTET STRING,
     specificCountryCustomizationUserGainEnableConfig MxEnableState,
     specificCountryCustomizationUserGainInputOffset  Integer32,
     specificCountryCustomizationUserGainOutputOffset Integer32
   }

   -- Index:Interface Identifier

   specificCountryCustomizationUserGainInterfaceId OBJECT-TYPE
    SYNTAX        OCTET STRING
    MAX-ACCESS    read-only
    STATUS        current
    DESCRIPTION " Interface Identifier

                  String that identifies a interface in other tables.
                  "
    ::= { specificCountryCustomizationUserGainEntry 100 }

   -- Columnar:Enable Configuration

   specificCountryCustomizationUserGainEnableConfig OBJECT-TYPE
    SYNTAX        MxEnableState
    MAX-ACCESS    read-write
    STATUS        current
    DESCRIPTION " Enable Configuration

                  Defines the configuration to use for a specific interface.

                    * Disable: The interface uses the default configuration as
                      defined in the
                      DefaultCountryCustomizationUserGainInputOffset and
                      DefaultCountryCustomizationUserGainOutputOffset
                      parameters.
                    * Enable: The interface uses the specific configuration as
                      defined in the
                      SpecificCountryCustomizationUserGain.InputOffset and
                      SpecificCountryCustomizationUserGain.OutputOffset
                      parameters.

                  "
    DEFVAL        { disable }
    ::= { specificCountryCustomizationUserGainEntry 200 }

   -- Columnar:Specific User Input Gain Offset

   specificCountryCustomizationUserGainInputOffset OBJECT-TYPE
    SYNTAX        Integer32 ( -12..12 )
    MAX-ACCESS    read-write
    STATUS        current
    DESCRIPTION " Specific User Input Gain Offset

                  The user input gain offset is added to the base input gain to
                  compute the total input gain on this specific telephony
                  interface. The user input gain is in dB.

                  Ex.: On a call involving a SIP terminal and an FXS terminal,
                  raising the input offset will raise the volume perceived on
                  the SIP terminal.

                  This configuration overrides the default configuration set in
                  the DefaultCountryCustomizationUserGainInputOffset parameter
                  if the SpecificCountryCustomizationUserGain.EnableConfig
                  parameter is set to 'Enable'.

                  "
    DEFVAL        { 0 }
    ::= { specificCountryCustomizationUserGainEntry 300 }

   -- Columnar:Specific User Output Gain Offset

   specificCountryCustomizationUserGainOutputOffset OBJECT-TYPE
    SYNTAX        Integer32 ( -12..12 )
    MAX-ACCESS    read-write
    STATUS        current
    DESCRIPTION " Specific User Output Gain Offset

                  The user output gain offset is added to the base output gain
                  to compute the total output gain on this specific telephony
                  interface. The user output gain is in dB.

                  Ex.: On a call involving a SIP terminal and an FXS terminal,
                  raising the output offset will raise the volume perceived on
                  the FXS terminal.

                  This configuration overrides the default configuration set in
                  the DefaultCountryCustomizationUserGainOutputOffset parameter
                  if the SpecificCountryCustomizationUserGain.EnableConfig
                  parameter is set to 'Enable'.

                  "
    DEFVAL        { 0 }
    ::= { specificCountryCustomizationUserGainEntry 400 }

  -- End of table:Specific User Gain

 -- End of group:Users Gain

 -- ***************************************************************************
 
 -- Group:Country Override Dialing

 -- ***************************************************************************
 
 countryCustomizationDialingGroup OBJECT IDENTIFIER
  ::= { countryCustomizationGroup 400 }
  -- Scalar:Default Override Dialing Country Configuration

  defaultCountryCustomizationDialingOverride OBJECT-TYPE
   SYNTAX        MxEnableState
   MAX-ACCESS    read-write
   STATUS        current
   DESCRIPTION " Default Override Dialing Country Configuration

                 Allows to override the default country dialing setting.

                   * Disable: The interface uses the default country dialing
                     setting.
                   * Enable: The interface uses the dialing country setting as
                     defined in the
                     DefaultCountryCustomizationDialingInterMfR1DialDelay,
                     DefaultCountryCustomizationDialingMfR1Duration,
                     DefaultCountryCustomizationDialingInterDtmfDialDelay and
                     DefaultCountryCustomizationDialingDtmfDuration parameters.

                 If a specific configuration is set in the
                 SpecificCountryCustomizationDialing.Override parameter and the
                 SpecificCountryCustomizationDialing.EnableConfig parameter is
                 set to 'Enable', then it overrides the current default
                 configuration.

                 "
   DEFVAL        { disable }
   ::= { countryCustomizationDialingGroup 100 }

  -- Scalar:Default Country Override Delay Between Dialed DTMF

  defaultCountryCustomizationDialingInterDtmfDialDelay OBJECT-TYPE
   SYNTAX        Unsigned32 ( 50..600 )
   MAX-ACCESS    read-write
   STATUS        current
   DESCRIPTION " Default Country Override Delay Between Dialed DTMF

                 The delay between two DTMFs when dialing on the interface.

                 This value is expressed in milliseconds (ms).

                 This configuration is used only if the
                 DefaultCountryCustomizationDialingOverride parameter is set to
                 'Enable'.

                 If a specific configuration is set in the
                 SpecificCountryCustomizationDialing.InterDtmfDialDelay
                 parameter and the
                 SpecificCountryCustomizationDialing.EnableConfig parameter is
                 set to 'Enable', then it overrides the current default
                 configuration.

                 "
   DEFVAL        { 100 }
   ::= { countryCustomizationDialingGroup 200 }

  -- Scalar:Default Country Override Dialed DTMF Duration

  defaultCountryCustomizationDialingDtmfDuration OBJECT-TYPE
   SYNTAX        Unsigned32 ( 50..600 )
   MAX-ACCESS    read-write
   STATUS        current
   DESCRIPTION " Default Country Override Dialed DTMF Duration

                 The duration of a DTMF when dialing on the interface.

                 This value is expressed in milliseconds (ms).

                 This configuration is used only if the
                 DefaultCountryCustomizationDialingOverride parameter is set to
                 'Enable'.

                 If a specific configuration is set in the
                 SpecificCountryCustomizationDialing.DtmfDuration parameter and
                 the SpecificCountryCustomizationDialing.EnableConfig parameter
                 is set to 'Enable', then it overrides the current default
                 configuration.

                 "
   DEFVAL        { 100 }
   ::= { countryCustomizationDialingGroup 300 }

  -- Scalar:Default Country Override Delay Between Dialed MFR1

  defaultCountryCustomizationDialingInterMfR1DialDelay OBJECT-TYPE
   SYNTAX        Unsigned32 ( 50..600 )
   MAX-ACCESS    read-write
   STATUS        current
   DESCRIPTION " Default Country Override Delay Between Dialed MFR1

                 The delay between two MFR1s when dialing on the interface.

                 This value is expressed in milliseconds (ms).

                 This configuration is used only if the
                 DefaultCountryCustomizationDialingOverride parameter is set to
                 'Enable'.

                 If a specific configuration is set in the
                 SpecificCountryCustomizationDialing.InterMfR1DialDelay
                 parameter and the
                 SpecificCountryCustomizationDialing.EnableConfig parameter is
                 set to 'Enable', then it overrides the current default
                 configuration.

                 "
   DEFVAL        { 68 }
   ::= { countryCustomizationDialingGroup 340 }

  -- Scalar:Default Country Override Dialed MFR1 Duration

  defaultCountryCustomizationDialingMfR1Duration OBJECT-TYPE
   SYNTAX        Unsigned32 ( 50..600 )
   MAX-ACCESS    read-write
   STATUS        current
   DESCRIPTION " Default Country Override Dialed MFR1 Duration

                 The duration of a MFR1 when dialing on the interface.

                 This value is expressed in milliseconds (ms).

                 This configuration is used only if the
                 DefaultCountryCustomizationDialingOverride parameter is set to
                 'Enable'.

                 If a specific configuration is set in the
                 SpecificCountryCustomizationDialing.MfR1Duration parameter and
                 the SpecificCountryCustomizationDialing.EnableConfig parameter
                 is set to 'Enable', then it overrides the current default
                 configuration.

                 "
   DEFVAL        { 68 }
   ::= { countryCustomizationDialingGroup 370 }

  -- ***************************************************************************
  
  -- Table:Specific Country Override Dialing.

  -- ***************************************************************************
  
  specificCountryCustomizationDialingTable OBJECT-TYPE
   SYNTAX        SEQUENCE OF SpecificCountryCustomizationDialingEntry
   MAX-ACCESS    not-accessible
   STATUS        current
   DESCRIPTION " Specific Country Override Dialing.

                 This table allows to override the default country dialing
                 configuration for a specific interface. All interfaces have
                 the default configuration unless the EnableConfig parameter is
                 enabled.

                 "
   ::= { countryCustomizationDialingGroup 400 }
   specificCountryCustomizationDialingEntry OBJECT-TYPE
    SYNTAX        SpecificCountryCustomizationDialingEntry
    MAX-ACCESS    not-accessible
    STATUS        current
    DESCRIPTION " A row in table Specific Country Override Dialing.. "
    INDEX         {
                    specificCountryCustomizationDialingInterfaceId
                  }

    ::= { specificCountryCustomizationDialingTable 1 }

   SpecificCountryCustomizationDialingEntry ::= SEQUENCE
   {
     specificCountryCustomizationDialingInterfaceId        OCTET STRING,
     specificCountryCustomizationDialingEnableConfig       MxEnableState,
     specificCountryCustomizationDialingOverride           MxEnableState,
     specificCountryCustomizationDialingInterDtmfDialDelay Unsigned32,
     specificCountryCustomizationDialingDtmfDuration       Unsigned32,
     specificCountryCustomizationDialingInterMfR1DialDelay Unsigned32,
     specificCountryCustomizationDialingMfR1Duration       Unsigned32
   }

   -- Index:Interface Identifier

   specificCountryCustomizationDialingInterfaceId OBJECT-TYPE
    SYNTAX        OCTET STRING
    MAX-ACCESS    read-only
    STATUS        current
    DESCRIPTION " Interface Identifier

                  String that identifies a Interface in other tables.
                  "
    ::= { specificCountryCustomizationDialingEntry 100 }

   -- Columnar:Enable Configuration

   specificCountryCustomizationDialingEnableConfig OBJECT-TYPE
    SYNTAX        MxEnableState
    MAX-ACCESS    read-write
    STATUS        current
    DESCRIPTION " Enable Configuration

                  Defines the configuration to use for a specific interface.

                    * Disable: The interface uses the default configuration as
                      defined in the DefaultCountryCustomizationDialingOverride
                      , DefaultCountryCustomizationDialingInterMfR1DialDelay,
                      DefaultCountryCustomizationDialingMfR1Duration,
                      DefaultCountryCustomizationDialingInterDtmfDialDelay and
                      DefaultCountryCustomizationDialingDtmfDuration
                      parameters.
                    * Enable: The interface uses the specific configuration as
                      defined in the
                      SpecificCountryCustomizationDialing.Override,
                      SpecificCountryCustomizationDialing.InterMfR1DialDelay,
                      SpecificCountryCustomizationDialing.MfR1Duration,
                      SpecificCountryCustomizationDialing.InterDtmfDialDelay
                      and SpecificCountryCustomizationDialing.DtmfDuration
                      parameters.

                  "
    DEFVAL        { disable }
    ::= { specificCountryCustomizationDialingEntry 200 }

   -- Columnar:Specific Override Dialing Country Configuration

   specificCountryCustomizationDialingOverride OBJECT-TYPE
    SYNTAX        MxEnableState
    MAX-ACCESS    read-write
    STATUS        current
    DESCRIPTION " Specific Override Dialing Country Configuration

                  Allows to override the default country dialing setting.

                    * Disable: The interface uses the default country dialing
                      setting.
                    * Enable: The interface uses the specific dialing
                      configuration as defined in the InterDtmfDialDelay,
                      DtmfDuration, InterMfR1DialDelay and MfR1Duration
                      parameters.

                  This configuration overrides the default configuration set in
                  the DefaultCountryCustomizationDialingOverride parameter if
                  the SpecificCountryCustomizationDialing.EnableConfig
                  parameter is set to 'Enable'.

                  "
    DEFVAL        { disable }
    ::= { specificCountryCustomizationDialingEntry 300 }

   -- Columnar:Specific Delay Between Dialed DTMF

   specificCountryCustomizationDialingInterDtmfDialDelay OBJECT-TYPE
    SYNTAX        Unsigned32 ( 50..600 )
    MAX-ACCESS    read-write
    STATUS        current
    DESCRIPTION " Specific Delay Between Dialed DTMF

                  The delay between two DTMFs when dialing on the interface.

                  This value is expressed in milliseconds (ms).

                  This configuration is used only if the Override parameter is
                  set to 'Enable'.

                  This configuration overrides the default configuration set in
                  the DefaultCountryCustomizationDialingInterDtmfDialDelay
                  parameter if the
                  SpecificCountryCustomizationDialing.EnableConfig parameter is
                  set to 'Enable'.

                  "
    DEFVAL        { 100 }
    ::= { specificCountryCustomizationDialingEntry 400 }

   -- Columnar:Specific Dialed DTMF Duration

   specificCountryCustomizationDialingDtmfDuration OBJECT-TYPE
    SYNTAX        Unsigned32 ( 50..600 )
    MAX-ACCESS    read-write
    STATUS        current
    DESCRIPTION " Specific Dialed DTMF Duration

                  The duration of a DTMF when dialing on the interface.

                  This value is expressed in milliseconds (ms).

                  This configuration is used only if the Override parameter is
                  set to 'Enable'.

                  This configuration overrides the default configuration set in
                  the DefaultCountryCustomizationDialingDtmfDuration parameter
                  if the SpecificCountryCustomizationDialing.EnableConfig
                  parameter is set to 'Enable'.

                  "
    DEFVAL        { 100 }
    ::= { specificCountryCustomizationDialingEntry 500 }

   -- Columnar:Specific Delay Between Dialed MFR1

   specificCountryCustomizationDialingInterMfR1DialDelay OBJECT-TYPE
    SYNTAX        Unsigned32 ( 50..600 )
    MAX-ACCESS    read-write
    STATUS        current
    DESCRIPTION " Specific Delay Between Dialed MFR1

                  The delay between two MFR1s when dialing on the interface.

                  This value is expressed in milliseconds (ms).

                  This configuration is used only if the Override parameter is
                  set to 'Enable'.

                  This configuration overrides the default configuration set in
                  the DefaultCountryCustomizationDialingInterMfR1DialDelay
                  parameter if the
                  SpecificCountryCustomizationDialing.EnableConfig parameter is
                  set to 'Enable'.

                  "
    DEFVAL        { 68 }
    ::= { specificCountryCustomizationDialingEntry 600 }

   -- Columnar:Specific Dialed MFR1 Duration

   specificCountryCustomizationDialingMfR1Duration OBJECT-TYPE
    SYNTAX        Unsigned32 ( 50..600 )
    MAX-ACCESS    read-write
    STATUS        current
    DESCRIPTION " Specific Dialed MFR1 Duration

                  The duration of a MFR1 when dialing on the interface.

                  This value is expressed in milliseconds (ms).

                  This configuration is used only if the Override parameter is
                  set to 'Enable'.

                  This configuration overrides the default configuration set in
                  the DefaultCountryCustomizationDialingMfR1Duration parameter
                  if the SpecificCountryCustomizationDialing.EnableConfig
                  parameter is set to 'Enable'.

                  "
    DEFVAL        { 68 }
    ::= { specificCountryCustomizationDialingEntry 700 }

  -- End of table:Specific Country Override Dialing.

 -- End of group:Country Override Dialing

 -- ***************************************************************************
 
 -- Group:Country Customisation Tone

 -- ***************************************************************************
 
 countryCustomizationToneGroup OBJECT IDENTIFIER
  ::= { countryCustomizationGroup 500 }
  -- ***************************************************************************
  
  -- Table:Country Tone Status

  -- ***************************************************************************
  
  countryToneStatusTable OBJECT-TYPE
   SYNTAX        SEQUENCE OF CountryToneStatusEntry
   MAX-ACCESS    not-accessible
   STATUS        current
   DESCRIPTION " Country Tone Status

                 This table displays the current tone pattern used (depends on
                 the CountrySelection parameter and the
                 CountryCustomizationTone table). The configuration applies to
                 all interfaces.

                 "
   ::= { countryCustomizationToneGroup 100 }
   countryToneStatusEntry OBJECT-TYPE
    SYNTAX        CountryToneStatusEntry
    MAX-ACCESS    not-accessible
    STATUS        current
    DESCRIPTION " A row in table Country Tone Status. "
    INDEX         {
                    countryToneStatusTone
                  }

    ::= { countryToneStatusTable 1 }

   CountryToneStatusEntry ::= SEQUENCE
   {
     countryToneStatusTone    INTEGER,
     countryToneStatusPattern OCTET STRING
   }

   -- Index:Tone

   countryToneStatusTone OBJECT-TYPE
    SYNTAX        INTEGER { busy (100) , callWaiting(150) , confirmation (200)
                  , congestion(300) , dial(400) , hold(500) , intercept(600) ,
                  messageWaiting (700) , preemption(800) , reorder(900) ,
                  ringback (1000) , roh(1100) , sit(1200) , stutter(1300) }
    MAX-ACCESS    read-only
    STATUS        current
    DESCRIPTION " Tone

                  Tone.
                  "
    ::= { countryToneStatusEntry 100 }

   -- Columnar:Pattern

   countryToneStatusPattern OBJECT-TYPE
    SYNTAX        OCTET STRING ( SIZE(0..512) )
    MAX-ACCESS    read-only
    STATUS        current
    DESCRIPTION " Pattern

                  Pattern description of the currently used tone.

                  See the CountryCustomizationTone.Pattern parameter for a
                  description of the syntax.

                  "
    DEFVAL        { "" }
    ::= { countryToneStatusEntry 300 }

  -- End of table:Country Tone Status

  -- ***************************************************************************
  
  -- Table:Country Customisation Tone

  -- ***************************************************************************
  
  countryCustomizationToneTable OBJECT-TYPE
   SYNTAX        SEQUENCE OF CountryCustomizationToneEntry
   MAX-ACCESS    not-accessible
   STATUS        current
   DESCRIPTION " Country Customisation Tone

                 This table allows to override the default country tone
                 configuration. The configuration applies to all interfaces.
                 "
   ::= { countryCustomizationToneGroup 200 }
   countryCustomizationToneEntry OBJECT-TYPE
    SYNTAX        CountryCustomizationToneEntry
    MAX-ACCESS    not-accessible
    STATUS        current
    DESCRIPTION " A row in table Country Customisation Tone. "
    INDEX         {
                    countryCustomizationToneTone
                  }

    ::= { countryCustomizationToneTable 1 }

   CountryCustomizationToneEntry ::= SEQUENCE
   {
     countryCustomizationToneTone     INTEGER,
     countryCustomizationToneOverride MxEnableState,
     countryCustomizationTonePattern  OCTET STRING
   }

   -- Index:Tone

   countryCustomizationToneTone OBJECT-TYPE
    SYNTAX        INTEGER { busy (100) , callWaiting(150) , confirmation (200)
                  , congestion(300) , dial(400) , hold(500) , intercept(600) ,
                  messageWaiting (700) , preemption(800) , reorder(900) ,
                  ringback (1000) , roh(1100) , sit(1200) , stutter(1300) }
    MAX-ACCESS    read-only
    STATUS        current
    DESCRIPTION " Tone

                  Tone to customise.
                  "
    ::= { countryCustomizationToneEntry 100 }

   -- Columnar:Override Tone Country Configuration

   countryCustomizationToneOverride OBJECT-TYPE
    SYNTAX        MxEnableState
    MAX-ACCESS    read-write
    STATUS        current
    DESCRIPTION " Override Tone Country Configuration

                  Allows to override the default country tone setting.

                    * Disable: The unit uses the default country dialing
                      setting.
                    * Enable: The unit uses the tone configuration as defined
                      in the Pattern parameter.

                  "
    DEFVAL        { disable }
    ::= { countryCustomizationToneEntry 200 }

   -- Columnar:Pattern

   countryCustomizationTonePattern OBJECT-TYPE
    SYNTAX        OCTET STRING ( SIZE(0..512) )
    MAX-ACCESS    read-write
    STATUS        current
    DESCRIPTION " Pattern

                  Describes a tone pattern.

                  A tone description contains frequencies, states and loops. Up
                  to 4 frequencies (f1 to f4) each with a power level can be
                  defined. At least one frequency/power pair must be defined.
                  Frequency range is from 10 to 4000 Hz and Power level range
                  is from -99 to 3 dbm.

                  The syntax is: f1=<frequency>:<power>

                  Up to 8 states (s1 to s8) can be defined, each with an
                  action, a set of frequencies, a duration and a next state. At
                  least one state must be described if the tone-pattern is not
                  empty. The action can be 'on', 'off' or 'CID' (for call
                  waiting tones). The duration of the state is from 10 to 56000
                  ms. The tone is continuous if no time is specified.

                  The syntax is: s1=<action>:<frequency>:...:<frequency>:
                  <duration>:<end-of-loop-indicator>:<next state>

                  Additionally, a set of states can be enclosed in a loop. The
                  starting state of a loop is marked with a loop counter (l=),
                  the range is from 2 to 128. The ending state of a loop is
                  marked with an end-of-loop indicator (l).

                  The syntax is: l=<loop count>,<state definition>,...,<state
                  definition (with end-of-loop-indicator)>,<state
                  definition>...

                  Examples:

                    * Germany dialtone (continuous): 'f1=350:-17,f2=440:-17,s1=
                      on:f1:f2'
                    * North America Recall dialtone (3 quick tones followed by
                      a continuous tone): 'f1=350:-17,f2=440:-17,l=3,s1=
                      on:f1:f2:100:s2,s2=off:100:l:s1,s3=on:f1:f2'
                    * Australia ring back tone (on 400ms, off 200 ms, on 400 ms
                      and off 2000 ms and replay): 'f1=425:-17,f2=400:-5,f3=
                      450:-5,s1=on:f1:f2:f3:400:s2,s2=off:200:s3,s3=
                      on:f1:f2:f3:400:s4,s4=off:2000:s1'

                  Only two frequencies can be used by the Call Waiting tone.

                  "
    DEFVAL        { "" }
    ::= { countryCustomizationToneEntry 300 }

  -- End of table:Country Customisation Tone

 -- End of group:Country Customisation Tone

-- End of group:Country Customisation

-- ****************************************************************************

-- Group:Machine Detection

-- ****************************************************************************

machineDetectionGroup OBJECT IDENTIFIER
 ::= { telIfMIBObjects 300 }
 -- Scalar:Default Enable/Disable CNG Tone Detection

 defaultMachineDetectionCngToneDetection OBJECT-TYPE
  SYNTAX        MxEnableState
  MAX-ACCESS    read-write
  STATUS        current
  DESCRIPTION " Default Enable/Disable CNG Tone Detection

                Enables fax calling tone (CNG tone) detection.

                  * Enable: Upon recognition of the CNG tone, the unit
                    switches the communication from voice mode to fax mode and
                    the CNG is transferred by using the preferred fax codec.
                    NOTE: This option allows for quicker fax detection, but it
                    also increases the risk of falsedetection.
                  * Disable: The CNG tone does not trigger a transition from
                    voice to data and the CNG is transferred in the voice
                    channel. NOTE: With this option, faxes are detected later,
                    but the risk of false detection is reduced.

                If a specific configuration is set in the
                SpecificMachineDetection.CngToneDetection parameter and the
                SpecificMachineDetection.EnableConfig parameter is set to
                'Enable', then it overrides the current default configuration.

                "
  DEFVAL        { enable }
  ::= { machineDetectionGroup 100 }

 -- Scalar:Default Enable/Disable CED Tone Detection

 defaultMachineDetectionCedToneDetection OBJECT-TYPE
  SYNTAX        MxEnableState
  MAX-ACCESS    read-write
  STATUS        current
  DESCRIPTION " Default Enable/Disable CED Tone Detection

                Enables CED tone detection.

                  * Enable: Upon recognition of the CED tone, the unit behaves
                    as defined in
                    DefaultMachineDetectionBehaviorOnCedToneDetection.
                  * Disable: The CED tone does not trigger a transition to fax
                    or voiceband data mode. The CED is transferred in the
                    voice channel.

                If a specific configuration is set in the
                SpecificMachineDetection.CedToneDetection parameter and the
                SpecificMachineDetection.EnableConfig parameter is set to
                'Enable', then it overrides the current default configuration.

                "
  DEFVAL        { enable }
  ::= { machineDetectionGroup 101 }

 -- Scalar:Default Enable/Disable V.21 Modulation Detection

 defaultMachineDetectionV21ModulationDetection OBJECT-TYPE
  SYNTAX        MxEnableState
  MAX-ACCESS    read-write
  STATUS        current
  DESCRIPTION " Default Enable/Disable V.21 Modulation Detection

                Enables fax V.21 modulation detection.

                  * Enable: Upon recognition of the V.21 modulation tone, the
                    unit switches the communication from voice mode to fax
                    mode and the signal is transferred by using the preferred
                    fax codec.
                  * Disable: The V.21 modulation does not trigger a transition
                    from voice to data and the signal is transferred in the
                    voice channel.

                If a specific configuration is set in the
                SpecificMachineDetection.CedToneDetection parameter and the
                SpecificMachineDetection.EnableConfig parameter is set to
                'Enable', then it overrides the current default configuration.

                "
  DEFVAL        { enable }
  ::= { machineDetectionGroup 102 }

 -- Scalar:Behavior on Default CED Tone Detection

 defaultMachineDetectionBehaviorOnCedToneDetection OBJECT-TYPE
  SYNTAX        INTEGER { passthrough (100) , faxmode (200) }
  MAX-ACCESS    read-write
  STATUS        current
  DESCRIPTION " Behavior on Default CED Tone Detection

                Defines the behavior of the unit upon detection of a CED tone.

                  * Passthrough: In passthrough mode the CED tone triggers a
                    transition from voice to voice band data and is
                    transferred in the voice channel. Use this setting when
                    any kind of analog device (i.e.: telephone, fax or modem)
                    can be connected to this port.
                  * Faxmode: In 'fax mode', upon detection of a CED tone the
                    unit switches the communication from voice mode to fax
                    mode and the CED is transferred by using the preferred fax
                    codec. Only a fax can then be connected to this port.

                If a specific configuration is set in the
                SpecificMachineDetection.BehaviorOnCedToneDetection parameter
                and the SpecificMachineDetection.EnableConfig parameter is set
                to 'Enable', then it overrides the current default
                configuration.

                Note that this parameter has no effect if the CED tone
                detection is disabled.

                "
  DEFVAL        { passthrough }
  ::= { machineDetectionGroup 110 }

 -- ***************************************************************************
 
 -- Table:Specific Voice Codec Configuration

 -- ***************************************************************************
 
 specificMachineDetectionTable OBJECT-TYPE
  SYNTAX                SEQUENCE OF SpecificMachineDetectionEntry
  MAX-ACCESS            not-accessible
  STATUS                current
  DESCRIPTION         " Specific Voice Codec Configuration

                        specific configuration.
                        "
  ::= { machineDetectionGroup 200 }
  specificMachineDetectionEntry OBJECT-TYPE
   SYNTAX        SpecificMachineDetectionEntry
   MAX-ACCESS    not-accessible
   STATUS        current
   DESCRIPTION " A row in table Specific Voice Codec Configuration . "
   INDEX         {
                   specificMachineDetectionInterfaceId
                 }

   ::= { specificMachineDetectionTable 1 }

  SpecificMachineDetectionEntry ::= SEQUENCE
  {
    specificMachineDetectionInterfaceId                OCTET STRING,
    specificMachineDetectionEnableConfig               MxEnableState,
    specificMachineDetectionCngToneDetection           MxEnableState,
    specificMachineDetectionCedToneDetection           MxEnableState,
    specificMachineDetectionV21ModulationDetection     MxEnableState,
    specificMachineDetectionBehaviorOnCedToneDetection INTEGER
  }

  -- Index:Interface Identifier

  specificMachineDetectionInterfaceId OBJECT-TYPE
   SYNTAX        OCTET STRING
   MAX-ACCESS    read-only
   STATUS        current
   DESCRIPTION " Interface Identifier

                 String that identifies a interface in other tables.
                 "
   ::= { specificMachineDetectionEntry 100 }

  -- Columnar:Enable Configuration

  specificMachineDetectionEnableConfig OBJECT-TYPE
   SYNTAX        MxEnableState
   MAX-ACCESS    read-write
   STATUS        current
   DESCRIPTION " Enable Configuration

                 Defines the configuration to use for a specific interface.

                   * Disable: The interface uses the default configuration as
                     defined in the DefaultMachineDetectionCngToneDetection
                     and DefaultMachineDetectionBehaviorOnCedToneDetection
                     parameters.
                   * Enable: The interface uses the specific configuration as
                     defined in the SpecificMachineDetection.CngToneDetection
                     and SpecificMachineDetection.BehaviorOnCedToneDetection
                     parameters.

                 "
   DEFVAL        { disable }
   ::= { specificMachineDetectionEntry 200 }

  -- Columnar:Specific Enable/Disable CNG Tone Detection

  specificMachineDetectionCngToneDetection OBJECT-TYPE
   SYNTAX        MxEnableState
   MAX-ACCESS    read-write
   STATUS        current
   DESCRIPTION " Specific Enable/Disable CNG Tone Detection

                 Enables fax calling tone (CNG tone) detection.

                   * Enable: Upon recognition of the CNG tone, the unit
                     switches the communication from voice mode to fax mode
                     and the CNG is transferred by using the preferred fax
                     codec. NOTE: This option allows for quicker fax
                     detection, but it also increases the risk of false
                     detection.
                   * Disable: The CNG tone does not trigger a transition from
                     voice to data and the CNG is transferred in the voice
                     channel. NOTE: With this option, faxes are detected
                     later, but the risk of false detection is reduced.

                 This configuration overrides the default configuration set in
                 the DefaultMachineDetectionCngToneDetection parameter if the
                 SpecificMachineDetection.EnableConfig parameter is set to
                 'Enable'.

                 "
   DEFVAL        { enable }
   ::= { specificMachineDetectionEntry 300 }

  -- Columnar:Specific Enable/Disable CED Tone Detection

  specificMachineDetectionCedToneDetection OBJECT-TYPE
   SYNTAX        MxEnableState
   MAX-ACCESS    read-write
   STATUS        current
   DESCRIPTION " Specific Enable/Disable CED Tone Detection

                 Enables CED tone detection.

                   * Enable: Upon recognition of the CED tone, the unit
                     behaves as defined in
                     DefaultMachineDetectionBehaviorOnCedToneDetection.
                   * Disable: The CED tone does not trigger a transition to
                     fax or voiceband data mode. The CED is transferred in the
                     voice channel.

                 This configuration overrides the default configuration set in
                 the DefaultMachineDetectionCedToneDetection parameter if the
                 SpecificMachineDetection.EnableConfig parameter is set to
                 'Enable'.

                 "
   DEFVAL        { enable }
   ::= { specificMachineDetectionEntry 310 }

  -- Columnar:Specific Enable/Disable V.21 Modulation Detection

  specificMachineDetectionV21ModulationDetection OBJECT-TYPE
   SYNTAX        MxEnableState
   MAX-ACCESS    read-write
   STATUS        current
   DESCRIPTION " Specific Enable/Disable V.21 Modulation Detection

                 Enables fax V.21 modulation detection.

                   * Enable: Upon recognition of the V.21 modulation tone, the
                     unit switches the communication from voice mode to fax
                     mode and the signal is transferred by using the preferred
                     fax codec.
                   * Disable: The V.21 modulation does not trigger a
                     transition from voice to data and the signal is
                     transferred in the voice channel.

                 This configuration overrides the default configuration set in
                 the DefaultMachineDetectionV21ModulationDetection parameter
                 if the SpecificMachineDetection.EnableConfig parameter is set
                 to 'Enable'.

                 "
   DEFVAL        { enable }
   ::= { specificMachineDetectionEntry 320 }

  -- Columnar:Specific CED Tone Detection Behavior

  specificMachineDetectionBehaviorOnCedToneDetection OBJECT-TYPE
   SYNTAX        INTEGER { passthrough (100) , faxmode (200) }
   MAX-ACCESS    read-write
   STATUS        current
   DESCRIPTION " Specific CED Tone Detection Behavior

                 Defines the behavior of the unit upon detection of a CED
                 tone.

                   * Passthrough: In passthrough mode the CED tone does not
                     trigger a transition from voice to data and is
                     transferred in the voice channel. Use this setting when
                     any kind of analog device (i.e.: telephone, fax or modem)
                     can be connected to this port.
                   * Faxmode: In 'fax mode', upon detection of a CED tone the
                     unit switches the communication from voice mode to fax
                     mode and the CED is transferred by using the preferred
                     fax codec. Only a fax can then be connected to this port.

                 This configuration overrides the default configuration set in
                 the DefaultMachineDetectionBehaviorOnCedToneDetection
                 parameter if the SpecificMachineDetection.EnableConfig
                 parameter is set to 'Enable'.

                 Note that this parameter has no effect if the CED tone
                 detection is disabled.

                 "
   DEFVAL        { passthrough }
   ::= { specificMachineDetectionEntry 400 }

 -- End of table:Specific Voice Codec Configuration

-- End of group:Machine Detection

-- ****************************************************************************

-- Group:Music On Hold Streaming

-- ****************************************************************************

musicOnHoldStreamingGroup OBJECT IDENTIFIER
 ::= { telIfMIBObjects 400 }
 -- Scalar:Music On Hold Streaming Enable

 musicOnHoldStreamingEnable OBJECT-TYPE
  SYNTAX        MxEnableState
  MAX-ACCESS    read-write
  STATUS        current
  DESCRIPTION " Music On Hold Streaming Enable

                Indicates whether or not the unit should play music when being
                put on hold.

                  * Disable: No music is played.
                  * Enable: Music is played toward the telephony side when
                    being put on hold from the network side.

                "
  DEFVAL        { disable }
  ::= { musicOnHoldStreamingGroup 100 }

-- End of group:Music On Hold Streaming

-- ****************************************************************************

-- Group:Call Waiting Tone

-- ****************************************************************************

callWaitingToneGroup OBJECT IDENTIFIER
 ::= { telIfMIBObjects 500 }
 -- ***************************************************************************
 
 -- Table:Distinctive Call Waiting Tone

 -- ***************************************************************************
 
 distinctiveCallWaitingToneTable OBJECT-TYPE
  SYNTAX        SEQUENCE OF DistinctiveCallWaitingToneEntry
  MAX-ACCESS    not-accessible
  STATUS        current
  DESCRIPTION " Distinctive Call Waiting Tone

                This table allows to override the default country call waiting
                tone configuration. The configuration applies to all
                interfaces.
                "
  ::= { callWaitingToneGroup 100 }
  distinctiveCallWaitingToneEntry OBJECT-TYPE
   SYNTAX        DistinctiveCallWaitingToneEntry
   MAX-ACCESS    not-accessible
   STATUS        current
   DESCRIPTION " A row in table Distinctive Call Waiting Tone. "
   INDEX         {
                   distinctiveCallWaitingToneIndex
                 }

   ::= { distinctiveCallWaitingToneTable 1 }

  DistinctiveCallWaitingToneEntry ::= SEQUENCE
  {
    distinctiveCallWaitingToneIndex   Unsigned32,
    distinctiveCallWaitingToneToneId  OCTET STRING,
    distinctiveCallWaitingTonePattern OCTET STRING
  }

  -- Index:Row Index

  distinctiveCallWaitingToneIndex OBJECT-TYPE
   SYNTAX        Unsigned32 ( 1..4 )
   MAX-ACCESS    read-only
   STATUS        current
   DESCRIPTION " Row Index

                 Unique identifier of the row in the table.
                 "
   ::= { distinctiveCallWaitingToneEntry 100 }

  -- Columnar:Tone ID

  distinctiveCallWaitingToneToneId OBJECT-TYPE
   SYNTAX        OCTET STRING ( SIZE(0..512) )
   MAX-ACCESS    read-write
   STATUS        current
   DESCRIPTION " Tone ID

                 Identification of the distinctive call waiting tone. When the
                 ToneId parameter is defined and the incoming call property
                 'distinctive-ring' matches with it, the corresponding tone
                 pattern is used. Otherwise, the country call waiting tone is
                 used.

                 Example:

                   * A distinctive ring call-property of '//127.0.0.1/
                     Bellcore-dr2' matches with the following ToneId: '//
                     127.0.0.1/Bellcore-dr2'

                 "
   DEFVAL        { "" }
   ::= { distinctiveCallWaitingToneEntry 200 }

  -- Columnar:Pattern

  distinctiveCallWaitingTonePattern OBJECT-TYPE
   SYNTAX        OCTET STRING ( SIZE(0..512) )
   MAX-ACCESS    read-write
   STATUS        current
   DESCRIPTION " Pattern

                 Pattern description of the custom tone.

                 See the CountryCustomizationTone.Pattern parameter for syntax
                 description.

                 Note that only two frequencies can be used by the Call
                 Waiting tone.

                 "
   DEFVAL        { "" }
   ::= { distinctiveCallWaitingToneEntry 300 }

 -- End of table:Distinctive Call Waiting Tone

-- End of group:Call Waiting Tone

-- ****************************************************************************

-- Group:Interop Group

-- ****************************************************************************

interopGroup OBJECT IDENTIFIER
 ::= { telIfMIBObjects 50000 }
 -- ***************************************************************************
 
 -- Table:DTMF Detection Configuration

 -- ***************************************************************************
 
 interopDtmfDetectionTable OBJECT-TYPE
  SYNTAX                  SEQUENCE OF InteropDtmfDetectionEntry
  MAX-ACCESS              not-accessible
  STATUS                  current
  DESCRIPTION           " DTMF Detection Configuration

                          DTMF Detection Configuration
                          "
  ::= { interopGroup 100 }
  interopDtmfDetectionEntry OBJECT-TYPE
   SYNTAX        InteropDtmfDetectionEntry
   MAX-ACCESS    not-accessible
   STATUS        current
   DESCRIPTION " A row in table DTMF Detection Configuration. "
   INDEX         {
                   interopDtmfDetectionInterfaceId
                 }

   ::= { interopDtmfDetectionTable 1 }

  InteropDtmfDetectionEntry ::= SEQUENCE
  {
    interopDtmfDetectionInterfaceId         OCTET STRING,
    interopDtmfDetectionRiseTimeCriteria    INTEGER,
    interopDtmfDetectionPositiveTwist       Unsigned32,
    interopDtmfDetectionNegativeTwist       Unsigned32,
    interopDtmfDetectionMaxPowerThreshold   Integer32,
    interopDtmfDetectionMinPowerThreshold   Integer32,
    interopDtmfDetectionBreakPowerThreshold Integer32
  }

  -- Index:Interface Identifier

  interopDtmfDetectionInterfaceId OBJECT-TYPE
   SYNTAX        OCTET STRING
   MAX-ACCESS    read-only
   STATUS        current
   DESCRIPTION " Interface Identifier

                 String that identifies an interface in other tables.
                 "
   ::= { interopDtmfDetectionEntry 100 }

  -- Columnar:Rise Time Criteria

  interopDtmfDetectionRiseTimeCriteria OBJECT-TYPE
   SYNTAX        INTEGER { checkSr (100) , confirmSnr (200) }
   MAX-ACCESS    read-write
   STATUS        current
   DESCRIPTION " Rise Time Criteria

                 Defines how the Rise Time criteria should be configured for
                 DTMF detection.

                   * CheckSr: Enable the Step Rise criteria and disable the
                     Confirm DTMF SNR criteria.
                   * ConfirmSnr: Enable the Confirm DTMF SNR criteria and
                     disable the Step Rise criteria.

                 The Step Rise criteria compares the current frame energy to
                 the high frequency power of the previous frame. If the
                 current frame energy is high enough, then it passes the test,
                 further validating the DTMF.

                 Disabling the Step Rise criteria may result in deteriorated
                 talk-off performance, but increases the detection of
                 malformed DTMF.

                 The Confirm DTMF SNR criteria is an additional
                 Signal-to-noise ratio test performed before a confirmed DTMF
                 report is sent to finally validate the DTMF.

                 "
   DEFVAL        { confirmSnr }
   ::= { interopDtmfDetectionEntry 200 }

  -- Columnar:Malformed DTMF Detection Method

  interopDtmfDetectionPositiveTwist OBJECT-TYPE
   SYNTAX        Unsigned32 ( 1..14 )
   MAX-ACCESS    read-write
   STATUS        current
   DESCRIPTION " Malformed DTMF Detection Method

                 Defines the value for the Positive Twist DTMF detection
                 parameter.

                 When the high-group frequency of a DTMF is more powerful than
                 the low-group frequency, the difference between the
                 high-group frequency absolute power and the low-group
                 frequency absolute power must be smaller than or equal to the
                 value set in this parameter. Otherwise, the DTMF is not
                 detected.

                 Raising this value increases the sensitivity of DTMF
                 detection. Raising this value too high may also cause false
                 detections of DTMFs.

                 "
   DEFVAL        { 6 }
   ::= { interopDtmfDetectionEntry 300 }

  -- Columnar:Malformed DTMF Detection Method

  interopDtmfDetectionNegativeTwist OBJECT-TYPE
   SYNTAX        Unsigned32 ( 1..14 )
   MAX-ACCESS    read-write
   STATUS        current
   DESCRIPTION " Malformed DTMF Detection Method

                 Defines the value for the Negative Twist DTMF detection
                 parameter.

                 When the low-group frequency of a DTMF is more powerful than
                 the high-group frequency, the difference between the
                 low-group frequency absolute power and the high-group
                 frequency absolute power must be smaller than or equal to the
                 value set in this parameter. Otherwise, the DTMF is not
                 detected.

                 Raising this value increases the sensitivity of DTMF
                 detection. Raising this value too high may also cause false
                 detections of DTMFs.

                 "
   DEFVAL        { 9 }
   ::= { interopDtmfDetectionEntry 350 }

  -- Columnar:Maximum power for dual-tone detection

  interopDtmfDetectionMaxPowerThreshold OBJECT-TYPE
   SYNTAX        Integer32 ( -20..1 )
   MAX-ACCESS    read-write
   STATUS        current
   DESCRIPTION " Maximum power for dual-tone detection

                 The average power of a DTMF must be below the value set in
                 this parameter to be no longer detected. Raising this value
                 increases the sensitivity of the DTMF detection. Raising this
                 value too high may also cause false detections of DTMFs.

                 The value is expressed in dBm (relative to 1mW of power).

                 "
   DEFVAL        { 1 }
   ::= { interopDtmfDetectionEntry 400 }

  -- Columnar:Minimum power for dual-tone detection

  interopDtmfDetectionMinPowerThreshold OBJECT-TYPE
   SYNTAX        Integer32 ( -45..-10 )
   MAX-ACCESS    read-write
   STATUS        current
   DESCRIPTION " Minimum power for dual-tone detection

                 The average power of a DTMF must be above the value set in
                 this parameter for at least 30ms to be detected. Raising this
                 value reduces the sensitivity to DTMF detection.

                 The value is expressed in dBm (relative to 1mW of power).

                 "
   DEFVAL        { -30 }
   ::= { interopDtmfDetectionEntry 450 }

  -- Columnar:Power threshold not to be exceeded when looking for break
  -- detection

  interopDtmfDetectionBreakPowerThreshold OBJECT-TYPE
   SYNTAX        Integer32 ( -45..-12 )
   MAX-ACCESS    read-write
   STATUS        current
   DESCRIPTION " Power threshold not to be exceeded when looking for break
                 detection

                 When the average power of a DTMF falls below the value set in
                 this parameter for at least 20ms, it is considered that the
                 DTMF ended.

                 The value is expressed in dBm (relative to 1mW of power).

                 "
   DEFVAL        { -32 }
   ::= { interopDtmfDetectionEntry 500 }

 -- End of table:DTMF Detection Configuration

 -- ***************************************************************************
 
 -- Table:Start Call In VBD

 -- ***************************************************************************
 
 interopStartCallInVbdTable OBJECT-TYPE
  SYNTAX               SEQUENCE OF InteropStartCallInVbdEntry
  MAX-ACCESS           not-accessible
  STATUS               current
  DESCRIPTION       "  Start Call In VBD

                       Start Call In VBD
                       "
  ::= { interopGroup 200 }
  interopStartCallInVbdEntry OBJECT-TYPE
   SYNTAX        InteropStartCallInVbdEntry
   MAX-ACCESS    not-accessible
   STATUS        current
   DESCRIPTION " A row in table Start Call In VBD. "
   INDEX         {
                   interopStartCallInVbdInterfaceId
                 }

   ::= { interopStartCallInVbdTable 1 }

  InteropStartCallInVbdEntry ::= SEQUENCE
  {
    interopStartCallInVbdInterfaceId OCTET STRING,
    interopStartCallInVbdEnable      MxEnableState
  }

  -- Index:Interface Identifier

  interopStartCallInVbdInterfaceId OBJECT-TYPE
   SYNTAX        OCTET STRING
   MAX-ACCESS    read-only
   STATUS        current
   DESCRIPTION " Interface Identifier

                 String that identifies an interface in other tables.
                 "
   ::= { interopStartCallInVbdEntry 100 }

  -- Columnar:Enable

  interopStartCallInVbdEnable OBJECT-TYPE
   SYNTAX        MxEnableState
   MAX-ACCESS    read-write
   STATUS        current
   DESCRIPTION " Enable

                 Indicates whether or not a call should be started in
                 voiceband data mode.

                   * Disable: Call is started in voice mode. A fax/modem tone
                     detection triggers a transition from voice to voiceband
                     data according to the configuration in
                     MachineDetectionGroup.
                   * Enable: Call is started in voiceband data mode.

                 "
   DEFVAL        { disable }
   ::= { interopStartCallInVbdEntry 200 }

 -- End of table:Start Call In VBD

-- End of group:Interop Group

-- ****************************************************************************

-- Group:Notification Messages Configuration

-- ****************************************************************************

notificationsGroup OBJECT IDENTIFIER
 ::= { telIfMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with a 'Informational' and
                    higher severity are issued.
                  * Warning: Notification messages with a 'Warning' and higher
                    severity are issued.
                  * Error: Notification messages with an 'Error' and higher
                    severity are issued.
                  * Critical: Notification messages with a 'Critical' severity
                    are issued.

                "
  DEFVAL        { warning }
  ::= { notificationsGroup 100 }

-- End of group:Notification Messages Configuration

-- ****************************************************************************

-- Group:Configuration Settings

-- ****************************************************************************

configurationGroup OBJECT IDENTIFIER
 ::= { telIfMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for the
                configuration to fully take effect.

                  * Yes: Service needs to be restarted.
                  * No: Service does not need to be restarted.

                Services can be restarted by using the
                Scm.ServiceCommands.Restart command.

                "
  ::= { configurationGroup 100 }

-- End of group:Configuration Settings

END
