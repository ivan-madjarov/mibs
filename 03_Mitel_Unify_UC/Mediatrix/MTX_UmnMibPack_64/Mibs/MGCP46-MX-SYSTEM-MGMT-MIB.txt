-- ****************************************************************************
-- ****************************************************************************
--
--             Copyright(c) 2001 Mediatrix Telecom, Inc. 
--
--  NOTICE:
--   This document contains information that is confidential and proprietary
--   to Mediatrix Telecom, Inc. 
--
--   Mediatrix Telecom, Inc. reserves all rights to this document as well as
--   to the Intellectual Property of the document and the technology and
--   know-how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

MGCP46-MX-SYSTEM-MGMT-MIB
DEFINITIONS ::= BEGIN

IMPORTS
        MODULE-IDENTITY,
        OBJECT-TYPE,
        Unsigned32
    FROM SNMPv2-SMI
        MODULE-COMPLIANCE,
        OBJECT-GROUP
    FROM SNMPv2-CONF
       mediatrixMgmt
    FROM MX-SMI;

sysMgmtMIB MODULE-IDENTITY
    LAST-UPDATED "0108290000Z"
    ORGANIZATION "Mediatrix Telecom, Inc."
    CONTACT-INFO "Mediatrix Telecom, Inc.
                  4229, Garlock Street
                  Sherbrooke (Quebec)
                  Canada
                  Phone: (819) 829-8749
                  "
    DESCRIPTION  "This MIB provides General system management information."
    -- ************************************************************************
    -- Revision history
    -- ************************************************************************
    REVISION    "0108290000Z"
    DESCRIPTION "August 29, 2001
                    Creation"
    ::= { mediatrixMgmt 15 }

sysMgmtMIBObjects     OBJECT IDENTIFIER ::= { sysMgmtMIB 1 }
sysMgmtConformance    OBJECT IDENTIFIER ::= { sysMgmtMIB 2 }

       
    sysMacAddress OBJECT-TYPE
        SYNTAX      OCTET STRING (SIZE (1..50))
        MAX-ACCESS  read-only
        STATUS      current
        DESCRIPTION "Ethernet MAC address."
        DEFVAL { " " }
        ::= {  sysMgmtMIBObjects 1 }
         
    sysHardwareVersion OBJECT-TYPE
        SYNTAX      OCTET STRING (SIZE (1..255))
        MAX-ACCESS  read-only
        STATUS      current
        DESCRIPTION "Hardware version."
        DEFVAL { " " }
        ::= {  sysMgmtMIBObjects 2}   

    sysSoftwareVersion OBJECT-TYPE
        SYNTAX      OCTET STRING (SIZE (1..255))
        MAX-ACCESS  read-only
        STATUS      current
        DESCRIPTION "Software version."
        DEFVAL { " " }
        ::= {  sysMgmtMIBObjects 3 }   

    sysMibVersion OBJECT-TYPE
        SYNTAX      OCTET STRING (SIZE (1..255))
        MAX-ACCESS  read-only
        STATUS      current
        DESCRIPTION "MIB version."
        DEFVAL { " " }
        ::= {  sysMgmtMIBObjects 4 }   

-- ************************************************************************


    -- ************************************************************************
    -- Conformance information
    -- ************************************************************************
    sysMgmtCompliances OBJECT IDENTIFIER ::= { sysMgmtConformance 1 }

    sysMgmtComplVer1 MODULE-COMPLIANCE
        STATUS      current
        DESCRIPTION     
            ""
        MODULE -- This Module
            MANDATORY-GROUPS { 
                                sysMgmtGroupVer1
                             }
        ::= { sysMgmtCompliances 1 }

    -- ************************************************************************
    -- MIB variable grouping
    -- ************************************************************************
    sysMgmtGroups OBJECT IDENTIFIER ::= { sysMgmtConformance 2 }

    sysMgmtGroupVer1 OBJECT-GROUP
        OBJECTS {
                 sysMacAddress,
                 sysHardwareVersion,
                 sysSoftwareVersion,
                 sysMibVersion
                }
        STATUS current
        DESCRIPTION
            "This group holds the objects that contain system Management Information."
        ::= { sysMgmtGroups 1 }


END
