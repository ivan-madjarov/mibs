-- ****************************************************************************
-- ****************************************************************************
--
--             Copyright(c) 2001 Mediatrix Telecom, Inc. 
--
--  NOTICE:
--   This document contains information that is confidential and proprietary
--   to Mediatrix Telecom, Inc. 
--
--   Mediatrix Telecom, Inc. reserves all rights to this document as well as
--   to the Intellectual Property of the document and the technology and
--   know-how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

H32340-MX-SMI
DEFINITIONS ::= BEGIN

IMPORTS
        MODULE-IDENTITY,
        OBJECT-IDENTITY,
        enterprises
    FROM SNMPv2-SMI;
    
mediatrix MODULE-IDENTITY
    LAST-UPDATED "0108070000Z"
    ORGANIZATION "Mediatrix Telecom, Inc."
    CONTACT-INFO "Mediatrix Telecom, Inc. 
                  4229, Garlock Street
                  Sherbrooke (Quebec)
                  Canada
                  Phone: (819) 829-8749
                  Web: http://www.mediatrix.com"
    DESCRIPTION "The Mediatrix Structure of Management Information."
    -- ************************************************************************
    -- Revision history
    -- ************************************************************************
    REVISION    "0108070000Z"
    DESCRIPTION "August 07, 2001
                    Creation"
        ::= { enterprises 4935 }

    mediatrixProducts OBJECT-IDENTITY
        STATUS       current
        DESCRIPTION "Root for the OBJECT IDENTIFIER used as sysObjectID values."
        ::= { mediatrix 1 }

    mediatrixAdmin OBJECT-IDENTITY
        STATUS       current
        DESCRIPTION "Root for modules used for the administration of
                     the mediatrix products."
        ::= { mediatrix 5 }

    mediatrixMgmt OBJECT-IDENTITY
        STATUS       current
        DESCRIPTION "Root for modules used to manage the mediatrix
                     products."
        ::= { mediatrix 10 }

    mediatrixConfig OBJECT-IDENTITY
        STATUS       current
        DESCRIPTION "Root for modules used to configure the mediatrix
                     products."
        ::= { mediatrix 15 }
        
    mediatrixIpTelephonySignaling OBJECT-IDENTITY
        STATUS       current
        DESCRIPTION "Root for modules used to configure the mediatrix
                     signaling protocols."
        ::= { mediatrix 20 }

    mediatrixModules OBJECT-IDENTITY
        STATUS       current
        DESCRIPTION "Provide a root in which modules can register
                     their module entity."
        ::= { mediatrix 90}


    mediatrixExperimental OBJECT-IDENTITY
        STATUS       current
        DESCRIPTION "The experimental sub-tree is the area where objects 
                     and events in MIBs under development can be placed 
                     without fear of conflicting with other MIBs. When 
                     the items rooted under an experimental sub-tree are 
                     ready for release, all that needs to be done is to 
                     re-attach the sub-tree under a permanent branch."
        ::= { mediatrix 99 }

    -- ************************************************************************
    -- In the common MIB, the common branch repository for all IP addresses
    -- is provided.
    -- ************************************************************************

    ipAddressStatus OBJECT-IDENTITY
        STATUS current
        DESCRIPTION "This object is the root of all status
                     of IP address configurable in mediatrix products."
        ::= { mediatrixMgmt   1 }

    ipAddressConfig OBJECT-IDENTITY
        STATUS current
        DESCRIPTION "This object is the root of all IP address objects
                     that can be configured in mediatrix products."
        ::= { mediatrixConfig 1 }



END
