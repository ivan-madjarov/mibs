-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


DGW11-MX-CLI-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

cliMIB MODULE-IDENTITY
 LAST-UPDATED   "0707060000Z"
 ORGANIZATION " Mediatrix Telecom, Inc. "
 CONTACT-INFO " Mediatrix Telecom, Inc.
                4229, Garlock Street
                Sherbrooke (Quebec)
                Canada
                Phone: (819) 829-8749
                "
 DESCRIPTION  " Command Line Interface

                The Command Line Interface interprets and runs the commands of
                the unit's configuration.
                "
 -- ****************************************************************************
 
 -- Revision history
 -- ****************************************************************************
 REVISION       "0707060000Z"
 DESCRIPTION  " Initial Revision "
 ::= { mediatrixServices 2700 }

cliMIBObjects OBJECT IDENTIFIER ::= { cliMIB 1 }

-- Scalar:Inactivity Timeout Delay

inactivityTimeOut OBJECT-TYPE
 SYNTAX        Unsigned32 ( 1..90 )
 MAX-ACCESS    read-write
 STATUS        current
 DESCRIPTION " Inactivity Timeout Delay

               Inactivity expiration delay for exiting the CLI session. This
               value is expressed in minutes.
               "
 DEFVAL        { 15 }
 ::= { cliMIBObjects 100 }

-- ****************************************************************************

-- Group:Telnet Interface

-- ****************************************************************************

telnetGroup OBJECT IDENTIFIER
 ::= { cliMIBObjects 1000 }
 -- Scalar:Enable Telnet

 enableTelnet OBJECT-TYPE
  SYNTAX        MxEnableState
  MAX-ACCESS    read-write
  STATUS        current
  DESCRIPTION " Enable Telnet

                Enable/Disable access to the system by Telnet.
                "
  DEFVAL        { disable }
  ::= { telnetGroup 100 }

 -- Scalar:Listen Port

 telnetPort OBJECT-TYPE
  SYNTAX        MxIpPort
  MAX-ACCESS    read-write
  STATUS        current
  DESCRIPTION " Listen Port

                Port on which the Telnet service should listen for incoming
                Telnet requests.
                "
  DEFVAL        { 23 }
  ::= { telnetGroup 200 }

-- End of group:Telnet Interface

-- ****************************************************************************

-- Group:SSH Interface

-- ****************************************************************************

sshGroup OBJECT IDENTIFIER
 ::= { cliMIBObjects 1100 }
 -- Scalar:Enable SSH

 enableSsh OBJECT-TYPE
  SYNTAX        MxEnableState
  MAX-ACCESS    read-write
  STATUS        current
  DESCRIPTION " Enable SSH

                Enable/Disable access to the system by SSH.
                "
  DEFVAL        { enable }
  ::= { sshGroup 100 }

 -- Scalar:Listen Port

 sshPort OBJECT-TYPE
  SYNTAX        MxIpPort
  MAX-ACCESS    read-write
  STATUS        current
  DESCRIPTION " Listen Port

                Port on which the SSH service should listen for incoming SSH
                requests.
                "
  DEFVAL        { 22 }
  ::= { sshGroup 200 }

-- End of group:SSH Interface

-- ****************************************************************************

-- Group:Notification Messages Configuration

-- ****************************************************************************

notificationsGroup OBJECT IDENTIFIER
 ::= { cliMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { cliMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
