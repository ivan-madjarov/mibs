-- ****************************************************************************
-- ****************************************************************************
--
--             Copyright(c) 2001 Mediatrix Telecom, Inc. 
--
--  NOTICE:
--   This document contains information that is confidential and proprietary
--   to Mediatrix Telecom, Inc. 
--
--   Mediatrix Telecom, Inc. reserves all rights to this document as well as
--   to the Intellectual Property of the document and the technology and
--   know how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

MGCP43-MX-PRODUCTS-MIB 
DEFINITIONS ::= BEGIN

IMPORTS 
        MODULE-IDENTITY
    FROM SNMPv2-SMI
        mediatrixModules,
        mediatrixProducts
    FROM MX-SMI;
    
mxProductsMIB MODULE-IDENTITY
    LAST-UPDATED "0202120000Z"
    ORGANIZATION "Mediatrix Telecom, Inc."
    CONTACT-INFO "Mediatrix Telecom, Inc. 
                  4229, Garlock Street
                  Sherbrooke (Quebec)
                  Canada
                  Phone: (819) 829-8749
                  Web: http://www.Mediatrix.com"
    DESCRIPTION "This module contains objectID for each Mediatrix product.
                 This objectID is used in the sysObjectID to identify the product."
    REVISION    "0202120000Z"
    DESCRIPTION "February 12, 2002
                    Added the mediatrix-III-4FXS-4M product.
                 August 21, 2001
                    Creation"
        ::= { mediatrixModules 2 }

    mediatrix-III-4FXS       OBJECT IDENTIFIER ::= { mediatrixProducts 1 }
    mediatrix-III-4FXO       OBJECT IDENTIFIER ::= { mediatrixProducts 2 }
    mediatrix1102            OBJECT IDENTIFIER ::= { mediatrixProducts 3 }
    mediatrix1104            OBJECT IDENTIFIER ::= { mediatrixProducts 4 }
    mediatrix1124            OBJECT IDENTIFIER ::= { mediatrixProducts 5 }
    mediatrix-III-4FXS-4M    OBJECT IDENTIFIER ::= { mediatrixProducts 6 }

END
