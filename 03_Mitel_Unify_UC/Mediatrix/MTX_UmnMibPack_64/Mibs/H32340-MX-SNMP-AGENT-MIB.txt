-- **SDOC***********************************************************************
-- *****************************************************************************
--
--             Copyright(c) 2004-2005 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part, in
--   any form whatsoever without written prior approval by
--   Mediatrix Telecom, Inc.
--
--   Mediatrix Telecom, Inc. reserves the right to revise this publication
--   and make changes at any time and without the obligation to notify any
--   person and/or entity of such revisions and/or changes.
--
-- *****************************************************************************
-- **EDOC***********************************************************************


H32340-MX-SNMP-AGENT-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        mediatrixConfig
    FROM MX-SMI
        MxEnableState
    FROM MX-TC;


snmpAgentMIB MODULE-IDENTITY
    LAST-UPDATED "200504280000Z"
    ORGANIZATION "Mediatrix Telecom, Inc."
    CONTACT-INFO "Mediatrix Telecom, Inc.
                  4229, Garlock Street
                  Sherbrooke (Quebec)
                  Canada
                  Phone: (819) 829-8749"
    DESCRIPTION  "This MIB is used to customize the properties of the SNMP agent."


    -- *************************************************************************
    -- Revision history
    -- *************************************************************************
    REVISION    "200504280000Z"
    DESCRIPTION "Added snmpAgentEnable."
    REVISION    "200402130000Z"
    DESCRIPTION "Creation."
    ::= { mediatrixConfig 150 }

snmpAgentMIBObjects  OBJECT IDENTIFIER ::= { snmpAgentMIB 1 }
snmpAgentConformance OBJECT IDENTIFIER ::= { snmpAgentMIB 2 }

    -- *************************************************************************
    -- SNMP Agent MIB objects
    -- *************************************************************************
    snmpAgentEnable OBJECT-TYPE
        SYNTAX      MxEnableState
        MAX-ACCESS  read-write
        STATUS      current
        DESCRIPTION "Enable or disable the SNMP service agent.

                     enable: SNMP connections are allowed.
                     disable: SNMP connections are forbidden."
        DEFVAL      { enable }
        ::= { snmpAgentMIBObjects 1 }

    snmpAgentAccess  OBJECT-TYPE
        SYNTAX      INTEGER {
                             lanOnly(0),
                             wanOnly(1),
                             all(2)
                            }
        MAX-ACCESS  read-write
        STATUS      current
        DESCRIPTION "Interface from which the unit can be accessed via SNMP:

                     lanOnly: SNMP connections are only permitted on the LAN side
                     wanOnly: SNMP connections are only permitted on the WAN side
                     all    : SNMP connections are permitted on both LAN and WAN sides."
        DEFVAL      { all }

        ::= { snmpAgentMIBObjects 5 }


    -- *************************************************************************
    -- Conformance information
    -- *************************************************************************
    snmpAgentCompliances OBJECT IDENTIFIER ::= { snmpAgentConformance 1 }

        snmpAgentAccessComplVer1 MODULE-COMPLIANCE
            STATUS      current
            DESCRIPTION "List of groups required to configure the SNMP agent."
            MODULE      -- This Module
            MANDATORY-GROUPS {
                                snmpAgentAccessGroupVer1
                             }
            ::= { snmpAgentCompliances 1 }

    -- *************************************************************************
    -- MIB variable grouping
    -- *************************************************************************
    snmpAgentGroups OBJECT IDENTIFIER ::= { snmpAgentConformance 5 }

        snmpAgentAccessGroupVer1 OBJECT-GROUP
            OBJECTS {
                        snmpAgentEnable,
                        snmpAgentAccess
                    }
            STATUS      current
            DESCRIPTION "A list of objects used to configure the SNMP agent."
            ::= { snmpAgentGroups 5 }

END
