-- ****************************************************************************
-- ****************************************************************************
--
--             Copyright(c) 2003-2005 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- ****************************************************************************
-- ****************************************************************************

H32340-MX-SYSTEM-CONFIG-MIB
DEFINITIONS ::= BEGIN

IMPORTS
        MODULE-IDENTITY,
        OBJECT-TYPE,
        Unsigned32
    FROM SNMPv2-SMI
        MODULE-COMPLIANCE,
        OBJECT-GROUP
    FROM SNMPv2-CONF
        MxIpAddress,
        MxIpConfigSource,
        MxIpPort,
        MxIpSubnetMask,
        MxIpSelectConfigSource,
        MxEnableState
    FROM MX-TC
        ipAddressStatus,
        ipAddressConfig,
        mediatrixMgmt,
        mediatrixConfig
    FROM MX-SMI;

sysConfigMIB MODULE-IDENTITY
    LAST-UPDATED "200508310000Z"
    ORGANIZATION "Mediatrix Telecom, Inc."
    CONTACT-INFO "Mediatrix Telecom, Inc.
                  4229, Garlock Street
                  Sherbrooke (Quebec)
                  Canada
                  Phone: (819) 829-8749
                  "
    DESCRIPTION  "This MIB provides General system settings."
    -- ************************************************************************
    -- Revision history
    -- ************************************************************************
    REVISION    "200508310000Z"
    DESCRIPTION "New variables sysConfigDhcpWait and sysConfigDhcpWaitDelay for 
                 PCR050810 - 3 min DHCP for Spanning Tree."
    REVISION    "200505090000Z"
    DESCRIPTION "Addition of pppoa enum to localHostWanAddressConfigSource and
                 localHostWanAddressSelectConfigSource."
    REVISION    "200409200000Z"
    DESCRIPTION "Addition of sysConfigStatsBySyslogEnable."
    REVISION    "200402120000Z"
    DESCRIPTION "Updated the sysConfigDownloadConfigFile description."
    REVISION    "200311140000Z"
    DESCRIPTION "Updated the sysConfigDownloadConfigFile description."
    REVISION    "200311130000Z"
    DESCRIPTION "Added an option in sysConfigDownloadConfigFile: automaticInitiateFileDownload."
    REVISION    "200309110000Z"
    DESCRIPTION "Addition of sysConfigMaxDynamicPort and sysConfigMinDynamicPort."
    REVISION    "200307160000Z"
    DESCRIPTION "Added WAN address configuration and status objects."
    REVISION    "200304100000Z"
    DESCRIPTION "Added the protocol specific note for localHostFqdn."
    REVISION    "200304070000Z"
    DESCRIPTION "Removed reference to MGCP/NCS protocols in description of localHostFqdn."
    REVISION    "200304030000Z"
    DESCRIPTION "Added variable for the computer ethernet connection speed.
                 Renamed variable for network ethernet connection speed."
    REVISION    "200303110000Z"
    DESCRIPTION "Updated sysConfigInterfaceEthernetSpeed description."
    REVISION    "200208190000Z"
    DESCRIPTION "Updated local FQDN description."
    REVISION    "200207100000Z"
    DESCRIPTION "Changed the layout of a DESCRIPTION to ease end users
                 understanding.
                 Removed the term 'III' in a DESCRIPTION."
    REVISION    "200201100000Z"
    DESCRIPTION "Added the variables for FQDN choice."
    REVISION    "200108220000Z"
    DESCRIPTION "Creation"
    ::= { mediatrixConfig 3 }

sysConfigMIBObjects     OBJECT IDENTIFIER ::= { sysConfigMIB 1 }
sysConfigConformance    OBJECT IDENTIFIER ::= { sysConfigMIB 2 }



    sysConfigNetworkEthernetSpeed OBJECT-TYPE
        SYNTAX      INTEGER {
                             autoDetect(0),
                             at-10Mbs-HalfDuplex(1),
                             at-100Mbs-HalfDuplex(2),
                             at-10Mbs-FullDuplex(3),
                             at-100Mbs-FullDuplex(4)
                            }
        MAX-ACCESS  read-write
        STATUS      current
        DESCRIPTION "Set the network ethernet connection speed.

                     By default, autoDetect should handle most situations. In some cases however, it
                     might be required to force the speed and duplex to certain setting.

                     Whenever forcing a connection speed / duplex mode, make sure that the other
                     device has the same configuration.

                     Please refer to the documentation shipped with your device for more details."
        DEFVAL      { autoDetect }
        ::=  {  sysConfigMIBObjects  10  }

    sysConfigComputerEthernetSpeed OBJECT-TYPE
        SYNTAX      INTEGER {
                             autoDetect(0),
                             at-10Mbs-HalfDuplex(1),
                             at-100Mbs-HalfDuplex(2),
                             at-10Mbs-FullDuplex(3),
                             at-100Mbs-FullDuplex(4)
                            }
        MAX-ACCESS  read-write
        STATUS      current
        DESCRIPTION "Set the computer ethernet connection speed.

                     By default, autoDetect should handle most situations. In some cases however, it
                     might be required to force the speed and duplex to certain setting.

                     Whenever forcing a connection speed / duplex mode, make sure that the other
                     device has the same configuration.

                     Please refer to the documentation shipped with your device for more details."
        DEFVAL      { autoDetect }
        ::=  {  sysConfigMIBObjects  12  }

    sysConfigMinDynamicPort OBJECT-TYPE
        SYNTAX      Unsigned32 ( 1025..65535 )
        MAX-ACCESS  read-write
        STATUS      current
        DESCRIPTION "Lower boundary for the range of dynamic UDP and TCP ports. The smallest
                     acceptable range, between the lower and upper boundaries, is 500.

                     When needed, the TCP/IP implementation of the unit randomly selects a dynamic
                     port amongst the free ports of the range.

                     For example, the dynamic ports range is configured from 41000 to 42000. The unit
                     needs to download a new version of its software. The TCP/IP implementation of
                     the unit selects a local UDP port for the TFTP client. The port is selected in
                     the dynamic ports range so the port has a value between 41000 and 42000.

                     The UDP and TCP ports are separated in three ranges: well-known ports (0 to
                     1023), registered ports (1024 to 49151) and dynamic ports (49152 to 65535). The
                     IANA (Internet Assigned Numbers Authority, www.iana.org) assigns the well-known
                     ports. The IANA also lists the registered ports. The dynamic ports are not under
                     the authority of the IANA. Most TCP/IP implementations use the range 1025 to
                     65535 for dynamic ports instead of the range defined by the IANA.

                     This variable’s semantics are different depending on protocol and/or
                     hardware platforms.
                     Please refer to the documentation shipped with your device for more details."
        DEFVAL      { 31001 }
        ::=  { sysConfigMIBObjects 14 }

    sysConfigMaxDynamicPort OBJECT-TYPE
        SYNTAX      Unsigned32 ( 1025..65535 )
        MAX-ACCESS  read-write
        STATUS      current
        DESCRIPTION "Upper boundary for the range of dynamic UDP and TCP ports. The smallest
                     acceptable range, between the lower and upper boundaries, is 500.

                     When needed, the TCP/IP implementation of the unit randomly selects a dynamic
                     port amongst the free ports of the range.

                     For example, the dynamic ports range is configured from 41000 to 42000. The unit
                     needs to download a new version of its software. The TCP/IP implementation of
                     the unit selects a local UDP port for the TFTP client. The port is selected in
                     the dynamic ports range so the port has a value between 41000 and 42000.

                     The UDP and TCP ports are separated in three ranges: well-known ports (0 to
                     1023), registered ports (1024 to 49151) and dynamic ports (49152 to 65535). The
                     IANA (Internet Assigned Numbers Authority, www.iana.org) assigns the well-known
                     ports. The IANA also lists the registered ports. The dynamic ports are not under
                     the authority of the IANA. Most TCP/IP implementations use the range 1025 to
                     65535 for dynamic ports instead of the range defined by the IANA.

                     This variable’s semantics are different depending on protocol and/or
                     hardware platforms.
                     Please refer to the documentation shipped with your device for more details."
        DEFVAL      { 32000 }
        ::=  { sysConfigMIBObjects 16 }

    sysConfigDhcpWait OBJECT-TYPE
        SYNTAX      MxEnableState
        MAX-ACCESS  read-write
        STATUS      current
        DESCRIPTION "Determines the restart behaviour of a unit that needs to issue
                     a DHCP request to receive some options.
                     This variable has no influence on the wait behaviour in effect when the
                     unit is requesting an IP address lease from the DHCP server.
                     
                     enable: The unit waits up to 130 seconds for DHCP options
                             and then, in the absence of a response, proceeds to restart 
                             without a valid address for the requested servers.
                     
                     disable: The unit restarts, without valid server addresses, if a DHCP 
                              response has not been received after the amount of time 
                              specified in the variable sysConfigDhcpWaitDelay.

                     This variable’s semantics are different depending on protocol and/or
                     hardware platforms.
                     Please refer to the documentation shipped with your device for more details."
        DEFVAL      { enable }
        ::=  { sysConfigMIBObjects 19 }

    sysConfigDhcpWaitDelay OBJECT-TYPE
        SYNTAX      Unsigned32 ( 1..200 )
        MAX-ACCESS  read-write
        STATUS      current
        DESCRIPTION "The amount of time (in seconds) a unit will wait for DHCP options
                     before restarting without a valid address for the requested servers.
                     This variable is only effective when the variable sysConfigDhcpWait is set 
                     to disable.

                     This variable’s semantics are different depending on protocol and/or
                     hardware platforms.
                     Please refer to the documentation shipped with your device for more details."
        DEFVAL      { 10 }
        ::=  { sysConfigMIBObjects 22 }

sysConfigStats OBJECT IDENTIFIER ::= { sysConfigMIBObjects 25 }

    sysConfigStatsPeriodLength OBJECT-TYPE
        SYNTAX      Unsigned32 (1..288)
        MAX-ACCESS  read-write
        STATUS      current
        DESCRIPTION "Duration of time that statistics are collected in the
                     current statistics buffer. At expiration, the current statistics
                     are added to the cumulated statistics buffer and then reset.
                     These are units of 5 minutes.
                     1 = 5 minutes.
                     12 = 1 hour.
                     288 = 24 hours.
                     Changing this value resets all the statistics buffers."
        DEFVAL       { 1 }
        ::=  {  sysConfigStats  1  }

    sysConfigStatsNumberPeriods OBJECT-TYPE
        SYNTAX      Unsigned32 (0..24)
        MAX-ACCESS  read-write
        STATUS      current
        DESCRIPTION "Number of statistics period used for cumulating statistics.
                     Changing this value resets all the statistics buffers.
                     0 = Disable cumulated statistics."
        DEFVAL       { 0 }
        ::= { sysConfigStats 2 }

    sysConfigStatsBySyslogEnable OBJECT-TYPE
        SYNTAX      MxEnableState
        MAX-ACCESS  read-write
        STATUS      current
        DESCRIPTION "Enables or disables statistics by syslog feature.

                     This feature allows the unit to send by syslog all RTP
                     statistics at the end of a connection (at the end of the
                     call or the fax)."
        DEFVAL       { disable }
        ::= { sysConfigStats 10 }

sysConfigDownloadConfig OBJECT IDENTIFIER ::= { sysConfigMIBObjects 30 }

    sysConfigDownloadConfigFile OBJECT-TYPE
        SYNTAX      INTEGER  {
                              noFileDownload(0),
                              requestFileDownload(1),
                              automaticInitiateFileDownload(3)
                             }
        MAX-ACCESS  read-write
        STATUS      current
        DESCRIPTION "Indicates if a configuration file is downloaded and how it is downloaded.

                     noFileDownload       : Do not perform a configuration file download.

                     requestFileDownload  : A configuration file is sent by the management server
                                            on request (see sysConfigDownloadConfigMode).
                                            The management server is the initiator of the TFTP
                                            session.

                     automaticInitiateFileDownload : Configuration files are automatically fetched by the
                                                     unit (see configFileFetchingFileName). Refer to
                                                     configFileAutoUpdateOnRestartEnable and
                                                     configFileAutoUpdatePeriodicEnable for details.
                                                     The unit is the initiator of the transfer sessions
                                                     (see configFileTransferProtocol).
                                                     This method facilitates the NAT traversal."
        DEFVAL      { requestFileDownload }
        ::= { sysConfigDownloadConfig 1 }

    sysConfigDownloadConfigMode OBJECT-TYPE
        SYNTAX      INTEGER  {
                              request(-1),
                              record(0),
                              commit(1),
                              undo(2)
                             }
        MAX-ACCESS  read-write
        STATUS      current
        DESCRIPTION "The unit configuration mode when a configuration file is sent by the
                     management server.
                     See sysConfigDownloadConfigFile.

                     request : The unit requests a configuration from the management server.
                               A notification, msTrapConfigInformation, is sent to the management
                               server.

                     record : The unit is recording the new configuration from the management
                              server. Note that the new settings will not be applied until the
                              configuration mode is set to commit(1).
                              A notification, msTrapStatusInformation, is sent to the management
                              server to confirm that the configuration mode was modified.

                     commit : Commit the new recorded settings.
                              A notification, msTrapStatusInformation, is sent to the management
                              server to confirm that the configuration mode was modified.
                              The unit is automatically restarted.

                     undo : Undo all recorded settings.
                            The new recorded configuration is dismissed.
                            A notification, msTrapStatusInformation, is sent to the management
                            server to confirm that the configuration mode was modified."
        DEFVAL      { request }
        ::= { sysConfigDownloadConfig 2 }


    -- ************************************************************************
    -- Local Host Ip address configuration and status
    -- ************************************************************************

ipAddressStatusLocalHost OBJECT IDENTIFIER ::= { ipAddressStatus 1 }
ipAddressConfigLocalHost OBJECT IDENTIFIER ::= { ipAddressConfig 1 }

   -- Add Status of various IP addresses

    localHostConfigSource OBJECT-TYPE
        SYNTAX      MxIpConfigSource
        MAX-ACCESS  read-only
        STATUS      current
        DESCRIPTION "Indicates the source used during the last boot sequence
                     for the provisioning of the localHost objects."
        DEFVAL { dhcp }
        ::=  {  ipAddressStatusLocalHost  1  }

    localHostAddress OBJECT-TYPE
        SYNTAX      MxIpAddress
        MAX-ACCESS  read-only
        STATUS      current
        DESCRIPTION "Local IP address."
        DEFVAL      { "192.168.0.1" }
        ::=  {  ipAddressStatusLocalHost  2  }

    localHostDhcpServer OBJECT-TYPE
        SYNTAX      MxIpAddress
        MAX-ACCESS  read-only
        STATUS      current
        DESCRIPTION "This value indicates the DHCP server IP address obtained
                     from the network after a DHCP broadcast has been sent.
                     In the case no DHPC server were found or DHCP not used,
                     this field will be empty."
        DEFVAL      { "192.168.0.10" }
        ::= {  ipAddressStatusLocalHost  3  }

    localHostPrimaryDns OBJECT-TYPE
        SYNTAX      MxIpAddress
        MAX-ACCESS  read-only
        STATUS      current
        DESCRIPTION "Primary DNS (domain name server) IP address."
        DEFVAL      { "192.168.0.10" }
        ::=  {  ipAddressStatusLocalHost  4  }

    localHostSecondaryDns OBJECT-TYPE
        SYNTAX      MxIpAddress
        MAX-ACCESS  read-only
        STATUS      current
        DESCRIPTION "Secondary DNS (domain name server) IP address.
                     This address is used in case the primary DNS can
                     not be reached."
        DEFVAL      { "192.168.0.10" }
        ::=  {  ipAddressStatusLocalHost  5  }

    localHostDefaultRouter OBJECT-TYPE
        SYNTAX      MxIpAddress
        MAX-ACCESS  read-only
        STATUS      current
        DESCRIPTION "Default router IP address."
        DEFVAL      { "192.168.0.10" }
        ::=  {  ipAddressStatusLocalHost  6  }

     localHostSnmpPort OBJECT-TYPE
        SYNTAX      MxIpPort
        MAX-ACCESS  read-only
        STATUS      current
        DESCRIPTION "The port number used to reach the local host via SNMP protocol."
        DEFVAL { 161 }
        ::= { ipAddressStatusLocalHost 7 }

    localHostSubnetMask OBJECT-TYPE
        SYNTAX      MxIpSubnetMask
        MAX-ACCESS  read-only
        STATUS      current
        DESCRIPTION "Subnet mask."
        DEFVAL      { "255.255.255.0" }
        ::=  {  ipAddressStatusLocalHost  8  }

    localHostFqdnConfigSource OBJECT-TYPE
        SYNTAX      INTEGER {
                             static(0),
                             dhcp(1),
                             dns(2),
                             none(3)
                            }
        MAX-ACCESS  read-only
        STATUS      current
        DESCRIPTION "Indicates the source used during the last boot sequence
                     for the provisioning of the local FQDN.

                     This variable's semantics are different depending on protocol and/or
                     hardware platforms.
                     Please refer to the documentation shipped with your device for more details."
        DEFVAL      { none }
        ::=  {  ipAddressStatusLocalHost  9  }

    localHostFqdn OBJECT-TYPE
        SYNTAX      OCTET STRING (SIZE (0..255))
        MAX-ACCESS  read-only
        STATUS      current
        DESCRIPTION "Local FQDN.

                     This variable's semantics are different depending on protocol and/or
                     hardware platforms.
                     Please refer to the documentation shipped with your device for more details."
        DEFVAL      { "" }
        ::=  {  ipAddressStatusLocalHost  10  }

    localHostWanAddressConfigSource OBJECT-TYPE
        SYNTAX      INTEGER {
                             localAddress(0),
                             static(1),
                             pppoe(2),
                             pppoa(3)
                            }
        MAX-ACCESS  read-only
        STATUS      current
        DESCRIPTION "Indicates the source used during the last boot sequence
                     for the provisioning of the wide area network (WAN) address."
        DEFVAL      { localAddress }
        ::=  {  ipAddressStatusLocalHost  15  }

    localHostWanAddress OBJECT-TYPE
        SYNTAX      MxIpAddress
        MAX-ACCESS  read-only
        STATUS      current
        DESCRIPTION "The wide area network (WAN) address.
                     This address is the public IP address to be used for incoming signaling, media
                     and management traffic."
        DEFVAL      { "0.0.0.0" }
        ::=  {  ipAddressStatusLocalHost  20  }


   -- Parameters to configure IP localHost

    localHostSelectConfigSource OBJECT-TYPE
        SYNTAX      MxIpSelectConfigSource
        MAX-ACCESS  read-write
        STATUS      current
        DESCRIPTION "Indicates the source to be used for the provisioning of the following
                     localHost objects:
                     localHostAddress,
                     localHostDhcpServer,
                     localHostPrimaryDns,
                     localHostSecondaryDns,
                     localHostDefaultRouter,
                     localHostSubnetMask.

                     If localHostDnsOverrideEnable is enabled, localHostPrimaryDns and
                     localHostSecondaryDns objects are always set with static values."
        DEFVAL      { dhcp }
        ::=  {  ipAddressConfigLocalHost  1  }


    localHostFqdnSelectConfigSource OBJECT-TYPE
        SYNTAX      INTEGER {
                             static(0),
                             dhcp(1),
                             dns(2),
                             none(3)
                            }
        MAX-ACCESS  read-write
        STATUS      current
        DESCRIPTION "Indicates the source to be used for the provisioning of
                     the local FQDN.

                     This variable's semantics are different depending on protocol and/or
                     hardware platforms.
                     Please refer to the documentation shipped with your device for more details."
        DEFVAL      { none }
        ::=  {  ipAddressConfigLocalHost  2  }

    localHostWanAddressSelectConfigSource OBJECT-TYPE
        SYNTAX      INTEGER {
                             localAddress(0),
                             static(1),
                             pppoe(2),
                             pppoa(3),
                             automatic(9999)
                            }
        MAX-ACCESS  read-write
        STATUS      current
        DESCRIPTION "Indicates the source to be used for the provisioning of the wide area network
                     (WAN) address.

                     The WAN address is the IP address to be used for incoming signaling, media
                     and management traffic.

                     localAddress : The WAN address is the one that is set in the localHostAddress
                                    variable, whereas the localHostStaticWanAddress is ignored.

                     static :       The unit has a static WAN address. The address is configured in
                                    localHostStaticWanAddress. This setting allows a limited NAT
                                    traversal scheme.

                     pppoe :        The unit uses the PPP over Ethernet in order to obtain its WAN IP
                                    address. The PPPoE service must be enabled. See also the pppoeEnable
                                    variable.

                     pppoa :        The unit uses the PPP over ATM in order to obtain its WAN IP address.
                                    The PPPoA service must be enabled. See also the pppoaEnable variable.

                     automatic :    If the PPPoE service is enabled, the unit uses 'pppoe' as the
                                    configuration source. If the PPPoA service is enabled, the unit
                                    uses 'pppoa' as the configuration source. Otherwise the unit
                                    uses 'localAddress'.

                     This variable's semantics are different depending on protocol and/or
                     hardware platforms.
                     Please refer to the documentation shipped with your device for more details."
        DEFVAL      { automatic }
        ::=  {  ipAddressConfigLocalHost  5  }

    localHostDnsOverrideEnable OBJECT-TYPE
        SYNTAX      MxEnableState
        MAX-ACCESS  read-write
        STATUS      current
        DESCRIPTION "If localHostDnsOverrideEnable is enabled, the localHostPrimaryDns and
                    localHostSecondaryDns objects are always overridden with static values.

                    If localHostDnsOverrideEnable is disabled, the variable localHostSelectConfigSource
                    indicates the source for the provisioning of the localHost objects:
                    localHostPrimaryDns and localHostSecondaryDns."
        DEFVAL       { disable }
        ::= { ipAddressConfigLocalHost 6 }

    ipAddressConfigLocalHostStatic OBJECT IDENTIFIER ::= { ipAddressConfigLocalHost 10 }

   -- ADD static ip address parameters

    localHostStaticAddress OBJECT-TYPE
        SYNTAX      MxIpAddress
        MAX-ACCESS  read-write
        STATUS      current
        DESCRIPTION "User-defined local IP address."
        DEFVAL      { "192.168.0.1" }
        ::= { ipAddressConfigLocalHostStatic  1  }

    localHostStaticPrimaryDns OBJECT-TYPE
        SYNTAX      MxIpAddress
        MAX-ACCESS  read-write
        STATUS      current
        DESCRIPTION "User-defined static primary DNS (domain name server) IP
                     address. The DNS is used mainly to resolve a FQDN (Fully qualified
                     domain name) into the proper IP address or to get the FQDN from
                     a specified IP address."
        DEFVAL      { "192.168.0.10" }
        ::= {  ipAddressConfigLocalHostStatic 2 }

    localHostStaticSecondaryDns OBJECT-TYPE
        SYNTAX      MxIpAddress
        MAX-ACCESS  read-write
        STATUS      current
        DESCRIPTION "User-defined static secondary DNS (domain name server) IP address.
                     This address is used in case the primary DNS cannot be reached."
        DEFVAL      { "192.168.0.10" }
        ::=    {  ipAddressConfigLocalHostStatic  3  }

    localHostStaticDefaultRouter OBJECT-TYPE
        SYNTAX      MxIpAddress
        MAX-ACCESS  read-write
        STATUS      current
        DESCRIPTION "User-defined default router IP address."
        DEFVAL      { "192.168.0.10" }
        ::=  {  ipAddressConfigLocalHostStatic  4  }

    localHostStaticSnmpPort OBJECT-TYPE
        SYNTAX      MxIpPort
        MAX-ACCESS  read-write
        STATUS      current
        DESCRIPTION "The port number to use to reach the local host via SNMP protocol."
        DEFVAL { 161 }
        ::= { ipAddressConfigLocalHostStatic 5 }

    localHostStaticSubnetMask OBJECT-TYPE
        SYNTAX      MxIpSubnetMask
        MAX-ACCESS  read-write
        STATUS      current
        DESCRIPTION "User-defined subnet mask."
        DEFVAL      { "255.255.255.0" }
        ::=  {  ipAddressConfigLocalHostStatic  6  }

    localHostStaticFqdn OBJECT-TYPE
        SYNTAX      OCTET STRING (SIZE (0..255))
        MAX-ACCESS  read-write
        STATUS      current
        DESCRIPTION "User-defined local FQDN.

                     This variable's semantics are different depending on protocol and/or
                     hardware platforms.
                     Please refer to the documentation shipped with your device for more details."
        DEFVAL      { "" }
        ::= { ipAddressConfigLocalHostStatic  7  }

    localHostStaticWanAddress OBJECT-TYPE
        SYNTAX      MxIpAddress
        MAX-ACCESS  read-write
        STATUS      current
        DESCRIPTION "User-defined wide area network (WAN) address."
        DEFVAL      { "0.0.0.0" }
        ::= { ipAddressConfigLocalHostStatic  10  }

    -- ************************************************************************
    -- Telephony DNS configuration and status
    -- ************************************************************************

ipAddressConfigTelephonyDns OBJECT IDENTIFIER ::= { ipAddressConfig 120 }

    telephonyDnsOverrideEnable OBJECT-TYPE
        SYNTAX      MxEnableState
        MAX-ACCESS  read-write
        STATUS      current
        DESCRIPTION "If telephonyDnsOverrideEnable is disabled, DNS IP addresses are
                    provisioned by the variables localHostPrimaryDns and localHostSecondaryDns.

                    If telephonyDnsOverrideEnable is enabled, DNS IP addresses are overridden
                    by the variables telephonyDnsPrimaryDns and telephonyDnsSecondaryDns.

                    This is useful when a unit and a networked PC (linked in a LAN with the unit)
                    need to use a different DNS."

        DEFVAL       { disable }
        ::= { ipAddressConfigTelephonyDns 1 }

ipAddressConfigTelephonyDnsStatic OBJECT IDENTIFIER ::= { ipAddressConfigTelephonyDns 50 }

    telephonyDnsStaticPrimaryDns OBJECT-TYPE
        SYNTAX      MxIpAddress
        MAX-ACCESS  read-write
        STATUS      current
        DESCRIPTION "If telephonyDnsOverrideEnable is enabled, the unit uses this static primary DNS.

                     If telephonyDnsOverrideEnable is disabled, this variable is not used."
        DEFVAL      { "192.168.0.10" }
        ::= { ipAddressConfigTelephonyDnsStatic  10  }

    telephonyDnsStaticSecondaryDns OBJECT-TYPE
        SYNTAX      MxIpAddress
        MAX-ACCESS  read-write
        STATUS      current
        DESCRIPTION "If telephonyDnsOverrideEnable is enabled, the unit uses this static secondary DNS.

                     If telephonyDnsOverrideEnable is disabled, this variable is not used."
        DEFVAL      { "192.168.0.10" }
        ::= { ipAddressConfigTelephonyDnsStatic  15  }

ipAddressStatusTelephonyDns OBJECT IDENTIFIER ::= { ipAddressStatus 100 }

    telephonyDnsPrimaryDns OBJECT-TYPE
        SYNTAX      MxIpAddress
        MAX-ACCESS  read-only
        STATUS      current
        DESCRIPTION "If telephonyDnsOverrideEnable is disabled, the telephonyDnsPrimaryDns variable
                    takes its value from the variable localHostPrimaryDns.

                    If telephonyDnsOverrideEnable is enabled, the telephonyDnsPrimaryDns variable
                    takes its value from the variable telephonyDnsStaticPrimaryDns."
        DEFVAL      { "192.168.0.10" }
        ::= { ipAddressStatusTelephonyDns  10  }

    telephonyDnsSecondaryDns OBJECT-TYPE
        SYNTAX      MxIpAddress
        MAX-ACCESS  read-only
        STATUS      current
        DESCRIPTION "If telephonyDnsOverrideEnable is disabled, the telephonyDnsSecondaryDns variable
                    takes its value from the variable localHostSecondaryDns.

                    If telephonyDnsOverrideEnable is enabled, the telephonyDnsSecondaryDns variable
                    takes its value from the variable telephonyDnsStaticSecondaryDns."
        DEFVAL      { "192.168.0.10" }
        ::= { ipAddressStatusTelephonyDns  15  }

    -- ************************************************************************
    -- Conformance information
    -- ************************************************************************
    sysConfigCompliances OBJECT IDENTIFIER ::= { sysConfigConformance 1 }

    sysConfigComplVer1 MODULE-COMPLIANCE
        STATUS      current
        DESCRIPTION
            ""
        MODULE -- This Module
            MANDATORY-GROUPS {
                                sysConfigGroupVer1,
                                commonLocalHostGroupVer1,
                                telephonyDnsGroupVer1
                             }
        ::= { sysConfigCompliances 1 }

    -- ************************************************************************
    -- MIB variable grouping
    -- ************************************************************************
    sysConfigGroups OBJECT IDENTIFIER ::= { sysConfigConformance 2 }

    sysConfigGroupVer1 OBJECT-GROUP
        OBJECTS {
                 sysConfigNetworkEthernetSpeed,
                 sysConfigComputerEthernetSpeed,
                 sysConfigMinDynamicPort,
                 sysConfigMaxDynamicPort,
                 sysConfigDhcpWait,
                 sysConfigDhcpWaitDelay,
                 sysConfigStatsPeriodLength,
                 sysConfigStatsNumberPeriods,
                 sysConfigStatsBySyslogEnable,
                 sysConfigDownloadConfigFile,
                 sysConfigDownloadConfigMode
                }
        STATUS current
        DESCRIPTION
            "This group holds the objects that define the system parameters"
        ::= { sysConfigGroups 1 }

    commonLocalHostGroupVer1 OBJECT-GROUP
        OBJECTS {
                 localHostConfigSource,
                 localHostAddress,
                 localHostDhcpServer,
                 localHostPrimaryDns,
                 localHostSecondaryDns,
                 localHostDefaultRouter,
                 localHostSnmpPort,
                 localHostSubnetMask,
                 localHostFqdnConfigSource,
                 localHostFqdn,
                 localHostWanAddressConfigSource,
                 localHostWanAddress,
                 localHostSelectConfigSource,
                 localHostFqdnSelectConfigSource,
                 localHostWanAddressSelectConfigSource,
                 localHostDnsOverrideEnable,
                 localHostStaticAddress,
                 localHostStaticPrimaryDns,
                 localHostStaticSecondaryDns,
                 localHostStaticDefaultRouter,
                 localHostStaticSnmpPort,
                 localHostStaticSubnetMask,
                 localHostStaticFqdn,
                 localHostStaticWanAddress
                }
        STATUS current
        DESCRIPTION
            "This group holds the objects that define the local host IP
             address information."
       ::= { sysConfigGroups 2 }

       telephonyDnsGroupVer1 OBJECT-GROUP
        OBJECTS {
                telephonyDnsOverrideEnable,
                telephonyDnsStaticPrimaryDns,
                telephonyDnsStaticSecondaryDns,
                telephonyDnsPrimaryDns,
                telephonyDnsSecondaryDns
                }
        STATUS current
        DESCRIPTION
            "This group holds the objects that define the telephony DNS"
        ::= { sysConfigGroups 5 }

END
