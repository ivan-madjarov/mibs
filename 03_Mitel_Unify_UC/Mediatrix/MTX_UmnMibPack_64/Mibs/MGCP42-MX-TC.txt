-- ****************************************************************************
-- ****************************************************************************
--
--             Copyright(c) 2001 Mediatrix Telecom, Inc. 
--
--  NOTICE:
--   This document contains information that is confidential and proprietary
--   to Mediatrix Telecom, Inc. 
--
--   Mediatrix Telecom, Inc. reserves all rights to this document as well as
--   to the Intellectual Property of the document and the technology and
--   know-how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

MGCP42-MX-TC
DEFINITIONS ::= BEGIN

IMPORTS
        TEXTUAL-CONVENTION
    FROM SNMPv2-TC
        MODULE-IDENTITY,
        Unsigned32
    FROM SNMPv2-SMI
        mediatrixModules
    FROM MX-SMI;

mxTextualConventions MODULE-IDENTITY
    LAST-UPDATED "0202220000Z"
    ORGANIZATION "Mediatrix Telecom, Inc."
    CONTACT-INFO "Mediatrix Telecom, Inc. 
                  4229, Garlock Street
                  Sherbrooke (Quebec)
                  Canada
                  Phone: (819) 829-8749
                  "
    DESCRIPTION "This MIB describes Mediatrix textual conventions used in
                 Mediatrix enterprise MIBs."
    -- ************************************************************************
    -- Revision history
    -- ************************************************************************
    REVISION    "0202220000Z"
    DESCRIPTION "February 22, 2002
    			 	Created new type MxAdvancedIpPort to reinclude zero
    			 	value for TCP/UPD port number.    
    			 October 25, 2001
                    Excluded zero from TCP/UDP port number range.
                 August 07, 2001
                    Creation"
    ::= { mediatrixModules 1 }

MxIpHostName ::= TEXTUAL-CONVENTION
    STATUS    current
    DESCRIPTION
        "Represents an IP address or a domain name."
    SYNTAX OCTET STRING (SIZE (1..255))
    
MxIpAddress ::= TEXTUAL-CONVENTION
    STATUS    current
    DESCRIPTION
        "Represents an IP address."
    SYNTAX OCTET STRING (SIZE (1..255))

MxIpPort ::= TEXTUAL-CONVENTION
    STATUS    current
    DESCRIPTION
        "The TCP or UDP port number range."
    SYNTAX Unsigned32 ( 1..65535 )

MxAdvancedIpPort ::= TEXTUAL-CONVENTION
    STATUS    current
    DESCRIPTION
        "The TCP or UDP port number range.
         The port number value 0 will be used for special
         functionnality which will be defined in the variable
         definition."
    SYNTAX Unsigned32 ( 0..65535 )

MxIpSubnetMask ::= TEXTUAL-CONVENTION
    STATUS    current
    DESCRIPTION
        "Represents an Internet subnet mask."
    SYNTAX OCTET STRING (SIZE (1..255))

MxIpSelectConfigSource ::= TEXTUAL-CONVENTION
    STATUS    current
    DESCRIPTION
        "Indicates the source to use during the next boot sequence
         for the provisioning of the localHost MIB objects.
         
             static  -> static values provided by the user are used
                        such as DNS addresses, router etc.

             dhcp    -> the DHCP (Dynamic host configuration protocol)
                        is used to retrieve the configuration of the
                        localHost MIB objects."
    SYNTAX INTEGER { 
                      static(0),
                      dhcp(1)
                    }

MxIpConfigSource ::= TEXTUAL-CONVENTION
    STATUS    current
    DESCRIPTION
        "Indicates the source used during the last boot sequence
         for the provisioning of the localHost MIB objects.
         
             static  -> static values were provided by the user
                        such as DNS addresses, router etc.

             dhcp    -> the DHCP (Dynamic host configuration protocol)
                        was used to retrieve the configuration of the
                        localHost MIB objects.

             Default -> Default factory settings was used."
    SYNTAX INTEGER { 
                      static(0),
                      dhcp(1),
                      default(99)
                    }
MxIpDhcpSiteSpecificCode ::= TEXTUAL-CONVENTION
    STATUS    current
    DESCRIPTION
        "Represents a DHCP site specific code."
    SYNTAX Unsigned32 (0 | 128..254)

MxFloatingPoint ::= TEXTUAL-CONVENTION
    STATUS    current
    DESCRIPTION
        "Represents a floating point number."
    SYNTAX OCTET STRING (SIZE (1..255))


END
