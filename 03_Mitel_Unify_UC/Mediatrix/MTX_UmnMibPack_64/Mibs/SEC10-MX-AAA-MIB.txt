-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************
  
SEC10-MX-AAA-MIB
DEFINITIONS ::= BEGIN

IMPORTS
        MODULE-IDENTITY,
        OBJECT-TYPE,
        Unsigned32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices       
    FROM MX-SMI2;

aaaMIB MODULE-IDENTITY                                                         
    LAST-UPDATED   "0511080000Z"                                               
    ORGANIZATION " Mediatrix Telecom, Inc. "                                   
    CONTACT-INFO " Mediatrix Telecom, Inc.                                     
                   4229, Garlock Street                                        
                   Sherbrooke (Quebec)                                         
                   Canada                                                      
                   Phone: (819) 829-8749                                       
                   "                                                           
    DESCRIPTION  " Authentication, Authorization and Accounting                
                                                                               
                   The AAA service administers the user name database and      
                   grants or denies access to various functionalities.         
                   "                                                           
    -- *************************************************************************
                                                                               
    -- Revision history                                                        
                                                                               
    -- *************************************************************************
    REVISION       "0511080000Z"                                               
    DESCRIPTION  " Initial Revision "                                          
    ::= { mediatrixServices 1000 }                                             

aaaMIBObjects OBJECT IDENTIFIER ::= { aaaMIB 1 }

-- *****************************************************************************
                                                                               
-- Table:  Users                                                               
                                                                               
-- *****************************************************************************
                                                                               
usersTable OBJECT-TYPE                                                         
    SYNTAX        SEQUENCE OF UsersEntry                                       
    MAX-ACCESS    not-accessible                                               
    STATUS        current                                                      
    DESCRIPTION " Users                                                        
                                                                               
                  This table contains the users that are allowed in the system.
                  "                                                            
    ::= { aaaMIBObjects 100 }                                                  
                                                                               
                                                                               
    usersEntry OBJECT-TYPE                                                     
        SYNTAX         UsersEntry                                              
        MAX-ACCESS     not-accessible                                          
        STATUS         current                                                 
        DESCRIPTION  " A row in the Users. "                                   
        INDEX          {                                                       
                           userName                                            
                       }                                                       
                                                                               
        ::= { usersTable 1 }                                                   
                                                                               
    UsersEntry ::= SEQUENCE                                                    
    {                                                                          
        userName OCTET STRING,                                                 
        password OCTET STRING                                                  
    }                                                                          
                                                                               
    -- Index:  User Name                                                       
                                                                               
    usersUserName OBJECT-TYPE                                                  
        SYNTAX         OCTET STRING                                            
        MAX-ACCESS     read-only                                               
        STATUS         current                                                 
        DESCRIPTION  " User Name                                               
                                                                               
                       Contains the user name.                                 
                       "                                                       
        DEFVAL         { "" }                                                  
        ::= { usersEntry 100 }                                                 
                                                                               
    -- Columnar:  Password                                                     
                                                                               
    usersPassword OBJECT-TYPE                                                  
        SYNTAX         OCTET STRING                                            
        MAX-ACCESS     read-write                                              
        STATUS         current                                                 
        DESCRIPTION  " Password                                                
                                                                               
                       Contains the user's password.                           
                       "                                                       
        DEFVAL         { "" }                                                  
        ::= { usersEntry 200 }                                                 
                                                                               
                                                                               
-- End of table:  Users                                                        

-- Scalar:  Batch User                                        
                                                              
batchUser OBJECT-TYPE                                         
    SYNTAX         OCTET STRING                               
    MAX-ACCESS     read-write                                 
    STATUS         current                                    
    DESCRIPTION  " Batch User                                 
                                                              
                   User name that is used for scheduled tasks.
                   "                                          
    DEFVAL         { "" }                                     
    ::= { aaaMIBObjects 200 }                                 

-- *****************************************************************************
                                                                               
-- Group:  Notification Messages Configuration                                 
                                                                               
-- *****************************************************************************
                                                                               
notificationsGroup OBJECT IDENTIFIER                                           
    ::= { aaaMIBObjects 60010 }                                                
                                                                               
                                                                               
    -- Scalar:  Minimal Severity of Notification                               
                                                                               
    minSeverity OBJECT-TYPE                                                    
        SYNTAX        INTEGER { disable(0) , debug(100) , info(200) , warning  
                      (300) , error(400) , critical (500) }                    
        MAX-ACCESS    read-write                                               
        STATUS        current                                                  
        DESCRIPTION " Minimal Severity of Notification                         
                                                                               
                      Sets the minimal severity to issue a notification message
                      incoming from this service.                              
                                                                               
                        * Disable: No notification is issued.                  
                        * Debug: All notification messages are issued.         
                        * Info: Notification messages with severity            
                          'Informational' and higher are issued.               
                        * Warning: Notification messages with severity         
                          'Warning' and higher are issued.                     
                        * Error: Notification messages with severity 'Error'   
                          and higher are issued.                               
                        * Critical: Notification messages with severity        
                          'Critical' are issued.                               
                                                                               
                                                                               
                      "                                                        
        DEFVAL        { warning }                                              
        ::= { notificationsGroup 100 }                                         
                                                                               
-- End of group:  Notification Messages Configuration                          

-- ****************************************************************************
                                                                              
-- Group:  Configuration Settings                                             
                                                                              
-- ****************************************************************************
                                                                              
configurationGroup OBJECT IDENTIFIER                                          
    ::= { aaaMIBObjects 60020 }                                               
                                                                              
                                                                              
    -- Scalar:  Need Restart                                                  
                                                                              
    needRestartInfo OBJECT-TYPE                                               
        SYNTAX        INTEGER { no(0) , yes(100) }                            
        MAX-ACCESS    read-only                                               
        STATUS        current                                                 
        DESCRIPTION " Need Restart                                            
                                                                              
                      Indicates if the service needs to be restarted for its  
                      configuration to fully take effect.                     
                                                                              
                        * Yes: Service needs to be restarted.                 
                        * No: Service does not need to be restarted.          
                                                                              
                      Services can be restarted by using the command          
                      Scm.ServiceCommands.Restart.                            
                                                                              
                                                                              
                      "                                                       
        ::= { configurationGroup 100 }                                        
                                                                              
-- End of group:  Configuration Settings                                      

END
