-- **SDOC***********************************************************************
-- *****************************************************************************
--
--             Copyright(c) 2003 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- *****************************************************************************
-- **EDOC***********************************************************************

MGCP44-MX-PRODUCT-NAMING-MIB
DEFINITIONS ::= BEGIN

IMPORTS
        MODULE-IDENTITY,
        OBJECT-TYPE
    FROM SNMPv2-SMI
        MODULE-COMPLIANCE,
        OBJECT-GROUP
    FROM SNMPv2-CONF
        mediatrixProducts
    FROM MX-SMI;

productNamingMIB MODULE-IDENTITY
    LAST-UPDATED "0302250000Z"
    ORGANIZATION "Mediatrix Telecom, Inc."
    CONTACT-INFO "Mediatrix Telecom, Inc.
                  4229, Garlock Street
                  Sherbrooke (Quebec)
                  Canada, J1L 2C8
                  Phone: (819) 829-8749
                  http://www.mediatrix.com"
    DESCRIPTION  "This MIB is used to customize the names of Mediatrix products."


    -- *************************************************************************
    -- Revision history
    -- *************************************************************************
    REVISION    "0302250000Z"
    DESCRIPTION "February 25, 2003
                    Creation."
    ::= { mediatrixProducts 1000 }

productNamingMIBObjects OBJECT IDENTIFIER ::= { productNamingMIB 1 }
productNamingConformance OBJECT IDENTIFIER ::= { productNamingMIB 5 }


    -- *************************************************************************
    -- PlatformName variables.
    -- *************************************************************************
    productNamingPlatformName OBJECT-TYPE
        SYNTAX      OCTET STRING (SIZE(0..255))
        MAX-ACCESS  read-only
        STATUS      current
        DESCRIPTION "This object contains the product name for this IAD."
        DEFVAL      { "" }
        ::= { productNamingMIBObjects  15 }

    -- *************************************************************************
    -- PlatformNames variables.
    -- *************************************************************************
    productNamingPlatforms OBJECT IDENTIFIER ::= { productNamingMIBObjects 20 }

    productNaming1102 OBJECT-TYPE
        SYNTAX      OCTET STRING (SIZE(0..127))
        MAX-ACCESS  read-only
        STATUS      current
        DESCRIPTION "This object represents the custom product name for a
                     Mediatrix 1102 hardware platform."
        DEFVAL      { "Mediatrix 1102" }
        ::= { productNamingPlatforms  5 }

    productNaming1104 OBJECT-TYPE
        SYNTAX      OCTET STRING (SIZE(0..127))
        MAX-ACCESS  read-only
        STATUS      current
        DESCRIPTION "This object represents the custom product name for a
                     Mediatrix 1104 hardware platform."
        DEFVAL      { "Mediatrix 1104" }
        ::= { productNamingPlatforms  10 }

    productNaming1124 OBJECT-TYPE
        SYNTAX      OCTET STRING (SIZE(0..127))
        MAX-ACCESS  read-only
        STATUS      current
        DESCRIPTION "This object represents the custom product name for a
                     Mediatrix 1124 hardware platform."
        DEFVAL      { "Mediatrix 1124" }
        ::= { productNamingPlatforms  15 }

    productNaming1204 OBJECT-TYPE
        SYNTAX      OCTET STRING (SIZE(0..127))
        MAX-ACCESS  read-only
        STATUS      current
        DESCRIPTION "This object represents the custom product name for a
                     Mediatrix 1204 hardware platform."
        DEFVAL      { "Mediatrix 1204" }
        ::= { productNamingPlatforms  20 }


    -- *************************************************************************
    -- Conformance information
    -- *************************************************************************
    productNamingCompliances OBJECT IDENTIFIER ::= { productNamingConformance 1 }

    productNamingComplVer1 MODULE-COMPLIANCE
        STATUS      current
        DESCRIPTION
            "List of groups required to support product naming customization."
        MODULE  -- This Module
            MANDATORY-GROUPS {
                                productNamingPlatformsVer1
                             }
        ::= { productNamingCompliances 1 }

    -- *************************************************************************
    --  MIB variable grouping
    -- *************************************************************************
    productNamingGroups OBJECT IDENTIFIER ::= { productNamingConformance 5 }

    productNamingPlatformsVer1 OBJECT-GROUP
        OBJECTS {
                    productNamingPlatformName,
                    productNaming1102,
                    productNaming1104,
                    productNaming1124,
                    productNaming1204
                }
        STATUS current
        DESCRIPTION
            "A collection of objects that defines the characteristics of
            product naming customization."
        ::= { productNamingGroups 10 }
END
