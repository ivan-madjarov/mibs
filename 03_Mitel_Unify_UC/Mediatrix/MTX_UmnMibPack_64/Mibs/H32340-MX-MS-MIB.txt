-- ****************************************************************************
-- ****************************************************************************
--
--             Copyright(c) 2001-2004 Mediatrix Telecom, Inc. 
--
--  NOTICE:
--   This document contains information that is confidential and proprietary
--   to Mediatrix Telecom, Inc. 
--
--   Mediatrix Telecom, Inc. reserves all rights to this document as well as
--   to the Intellectual Property of the document and the technology and
--   know how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

H32340-MX-MS-MIB
DEFINITIONS ::= BEGIN

IMPORTS
        MODULE-IDENTITY,
        OBJECT-TYPE,
        NOTIFICATION-TYPE,
        Unsigned32,
        Integer32
    FROM SNMPv2-SMI
        OBJECT-GROUP,
        NOTIFICATION-GROUP,
        MODULE-COMPLIANCE
    FROM SNMPv2-CONF
        MxIpHostName,
        MxIpConfigSource,
        MxIpPort,
        MxIpSelectConfigSource,
        MxIpDhcpSiteSpecificCode
    FROM MX-TC
        ipAddressStatus,
        ipAddressConfig,
        mediatrixConfig
    FROM MX-SMI
        sysObjectID
    FROM RFC1213-MIB
        sysMacAddress
    FROM MX-SYSTEM-MGMT-MIB
        sysConfigDownloadConfigMode,
        sysConfigDownloadConfigFile
    FROM MX-SYSTEM-CONFIG-MIB;

msMIB MODULE-IDENTITY
    LAST-UPDATED "200405250000Z"
    ORGANIZATION "Mediatrix Telecom, Inc."
    CONTACT-INFO "Mediatrix Telecom, Inc. 
                  4229, Garlock Street
                  Sherbrooke (Quebec)
                  Canada
                  Phone: (819) 829-8749
                  "
    DESCRIPTION "This MIB describes the parameters to configure the Management Server."
    -- ************************************************************************
    -- Revision history
    -- ************************************************************************
    REVISION    "200405250000Z"
    DESCRIPTION "Added range to msTrapRetransmissionPeriod"
    REVISION    "0311110000Z"
    DESCRIPTION "November 11, 2003
                    Clarified descriptions.
                 July 11, 2002
                    Renamed msTrapApaConfigInformation to msTrapConfigInformation
                            msTrapApaStatusInformation to msTrapStatusInformation
                            msTrapApaStatusConfigFile  to msTrapStatusConfigFile
                 July 10, 2002
                    In different DESCRIPTIONs, replaced the term 'APA' with 'unit'.
                 November 02, 2001
                    msSource was renamed msConfigSource for standardization.
                 August 07, 2001
                    Creation"
    ::= { mediatrixConfig 15 }

msMIBObjects  OBJECT IDENTIFIER ::= { msMIB 1 }
msConformance OBJECT IDENTIFIER ::= { msMIB 2 }
msEvents      OBJECT IDENTIFIER ::= { msMIB 3 }

-- Add the ms general parameters.

    msEnable OBJECT-TYPE
        SYNTAX      INTEGER {
                             disable(0),
                             enable(1)
                            }
        MAX-ACCESS  read-write
        STATUS      current
        DESCRIPTION "Enable/Disable the management server.

                     enable : Notifications (SNMP traps) can be sent to the management server.

                     disable: No notification (SNMP trap) is sent to the management server."
        DEFVAL { enable }
        ::=  { msMIBObjects 5 }

    msTrapRetransmissionPeriod OBJECT-TYPE
        SYNTAX      Unsigned32 (10..604800000)
        MAX-ACCESS  read-write
        STATUS      current
        DESCRIPTION "Retransmission period for the SNMP trap msTrapConfigInformation.

                     The trap is retransmitted with this period until the management server
                     replies or the msTrapRetransmissionRetryCount is reached.

                     This value is expressed in milliseconds (ms)."
        DEFVAL      { 60000 }
        ::=  {    msMIBObjects  20    }

    msTrapRetransmissionRetryCount OBJECT-TYPE
        SYNTAX      Integer32 (-1..2147483647)
        MAX-ACCESS  read-write
        STATUS      current
        DESCRIPTION "Retransmission retry count for the SNMP trap msTrapConfigInformation.

                     The trap is retransmitted until the management server replies or 
                     this retry count is reached.

                     -1 = infinite (always retransmit)"
        DEFVAL       { 10 }
        ::=  {    msMIBObjects  21    }


    -- ************************************************************************
    -- MS IP addresses: Placed in the mediatrixMgmt.ipAddressStatus and
    --                  in mediatrixConfig.ipAddressConfig.
    -- ************************************************************************

-- Add the MS ip addresses specific parameters.

    ipAddressStatusMs OBJECT IDENTIFIER ::= { ipAddressStatus 10 }
    ipAddressConfigMs OBJECT IDENTIFIER ::= { ipAddressConfig 10 }

-- Add the management server status information.

    msConfigSource OBJECT-TYPE
        SYNTAX      MxIpConfigSource
        MAX-ACCESS  read-only
        STATUS      current
        DESCRIPTION "Indicates the source used for the provisioning of 
                     the management server MIB objects."
        DEFVAL      { dhcp }
        ::=  {  ipAddressStatusMs  1  }
        
     msHost OBJECT-TYPE
        SYNTAX      MxIpHostName
        MAX-ACCESS  read-only
        STATUS      current
        DESCRIPTION "Management server IP address or domain name."
        DEFVAL      { "192.168.0.10" }
        ::=  {    ipAddressStatusMs  2    }

    msTrapPort OBJECT-TYPE
        SYNTAX      MxIpPort
        MAX-ACCESS  read-only
        STATUS      current
        DESCRIPTION "Management server IP port number on which the SNMP traps are received."
        DEFVAL      { 162 }
        ::=  {    ipAddressStatusMs  3    }

-- Add the management server configuration information.

    msSelectConfigSource OBJECT-TYPE
        SYNTAX      MxIpSelectConfigSource
        MAX-ACCESS  read-write
        STATUS      current
        DESCRIPTION "Indicates the source to be used for the provisioning of 
                     the management server MIB objects."
        DEFVAL      { dhcp }
        ::=  {  ipAddressConfigMs  1  } 

    ipAddressConfigMsStatic OBJECT IDENTIFIER ::= { ipAddressConfigMs 10 }
    
    -- Add the static parameters.
    
    msStaticHost OBJECT-TYPE
        SYNTAX      MxIpHostName
        MAX-ACCESS  read-write
        STATUS      current
        DESCRIPTION "Static management server IP address or domain name."
        DEFVAL      { "192.168.0.10" }
        ::=  {    ipAddressConfigMsStatic  1  }

    msStaticTrapPort OBJECT-TYPE
        SYNTAX      MxIpPort
        MAX-ACCESS  read-write
        STATUS      current
        DESCRIPTION "Static management server IP port number on which the SNMP traps are received."
        DEFVAL      { 162 }
        ::=  {    ipAddressConfigMsStatic  2  }

    ipAddressConfigMsDhcp OBJECT IDENTIFIER ::= { ipAddressConfigMs 30 }
    
    -- Add the dhcp parameters.
    
    msDhcpSiteSpecificCode OBJECT-TYPE
        SYNTAX      MxIpDhcpSiteSpecificCode
        MAX-ACCESS  read-write
        STATUS      current
        DESCRIPTION "DHCP management server site specific code.
                     If set to 0, use vendor-specific code #200."
        DEFVAL      { 0 }
        ::=  {    ipAddressConfigMsDhcp  1    }



    -- ************************************************************************
    -- Events 
    -- ************************************************************************
    msNotifications        OBJECT IDENTIFIER ::= { msEvents 2 }

    msTrapConfigInformation NOTIFICATION-TYPE
        OBJECTS     { 
                      sysObjectID,
                      sysMacAddress,
                      sysConfigDownloadConfigFile
                    }
        STATUS      current
        DESCRIPTION "The Management system is trapped with the sysObjectID, 
                     the MAC address and the request configuration of the unit
                     (the unit requests a configuration from the Management system)."
        ::= { msNotifications 700 }

    msTrapStatusInformation NOTIFICATION-TYPE
        OBJECTS     { 
                      sysMacAddress,
                      sysConfigDownloadConfigMode
                    }
        STATUS      current
        DESCRIPTION "The Management system is trapped with the MAC address and
                     the configuration mode of the unit (the unit confirms its 
                     configuration mode modification)."
        ::= { msNotifications 800 }

    msTrapStatusConfigFile NOTIFICATION-TYPE
        OBJECTS     { 
                      sysMacAddress,
                      sysConfigDownloadConfigFile
                    }
        STATUS      current
        DESCRIPTION "The Management system is trapped with the MAC address 
                     and the configuration file download status."
        ::= { msNotifications 900 }

    -- ************************************************************************
    -- Conformance information
    -- ************************************************************************
    msCompliances OBJECT IDENTIFIER ::= { msConformance 1 }

    msBasicComplVer1 MODULE-COMPLIANCE
        STATUS      current
        DESCRIPTION
            "Minimal parameters definitions to support the ms messaging system."
        MODULE -- This Module
            MANDATORY-GROUPS { 
                                msBasicGroupVer1,
                                msServerGroupVer1,
                                msBasicNotificationGroupVer1
                             }
        ::= { msCompliances 1 }

    -- ************************************************************************
    -- MIB variable grouping
    -- ************************************************************************
    msGroups OBJECT IDENTIFIER ::= { msConformance 2 }

    msBasicGroupVer1 OBJECT-GROUP
        OBJECTS {
                    msEnable,
                    msTrapRetransmissionPeriod,
                    msTrapRetransmissionRetryCount
                }
        STATUS current
        DESCRIPTION
            "This group holds the minimal set of objects that enables the user to use 
             management server."
        ::= { msGroups 1 }

    msServerGroupVer1 OBJECT-GROUP
        OBJECTS {
                    msConfigSource,
                    msHost,
                    msTrapPort,
                    msSelectConfigSource,
                    msStaticHost,
                    msStaticTrapPort,
                    msDhcpSiteSpecificCode
                }
        STATUS current
        DESCRIPTION
            "This group holds the minimal set of objects that define the management server."
        ::= { msGroups 2 }


    msBasicNotificationGroupVer1 NOTIFICATION-GROUP
        NOTIFICATIONS   {
                            msTrapConfigInformation,
                            msTrapStatusInformation,
                            msTrapStatusConfigFile
                        }
        STATUS          current
        DESCRIPTION 
           "This group contains the objects necessary to realize the basic
             Notification for the configuration file download."
        ::= { msGroups 3 }


END
