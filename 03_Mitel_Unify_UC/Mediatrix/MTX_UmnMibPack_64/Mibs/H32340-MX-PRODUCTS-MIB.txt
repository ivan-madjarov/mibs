-- ****************************************************************************
-- ****************************************************************************
--
--             Copyright(c) 2005 Mediatrix Telecom, Inc.
--
--  NOTICE:
--   This document contains information that is confidential and proprietary
--   to Mediatrix Telecom, Inc.
--
--   Mediatrix Telecom, Inc. reserves all rights to this document as well as
--   to the Intellectual Property of the document and the technology and
--   know how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

H32340-MX-PRODUCTS-MIB
DEFINITIONS ::= BEGIN

IMPORTS
        MODULE-IDENTITY
    FROM SNMPv2-SMI
        mediatrixModules,
        mediatrixProducts
    FROM MX-SMI;

mxProductsMIB MODULE-IDENTITY
    LAST-UPDATED "200506230000Z"
    ORGANIZATION "Mediatrix Telecom, Inc."
    CONTACT-INFO "Mediatrix Telecom, Inc.
                  4229, Garlock Street
                  Sherbrooke (Quebec)
                  Canada
                  Phone: (819) 829-8749
                  Web: http://www.Mediatrix.com"
    DESCRIPTION "This module contains objectID for each Mediatrix product.
                 This objectID is used in the sysObjectID to identify the product."
    REVISION    "200506230000Z"
    DESCRIPTION "Added mediatrixLiaison312 and mediatrixLiaison322 product names."
    REVISION    "200503290000Z"
    DESCRIPTION "Modified mediatrix512 and mediatrix522 product names for
                 mediatrixLiaison512 and mediatrixLiaison522."
    REVISION    "200502240000Z"
    DESCRIPTION "Added Mediatrix 512 and 522 product names."
    REVISION    "200402020000Z"
    DESCRIPTION "Added the Mediatrix 2102 product."
    REVISION    "200302210000Z"
    DESCRIPTION "Added the Mediatrix 1204 product."
    REVISION    "200202120000Z"
    DESCRIPTION "Added the Mediatrix-III-4FXS-4M product."
    REVISION    "200108210000Z"
    DESCRIPTION "Creation"

        ::= { mediatrixModules 2 }

    mediatrix-III-4FXS       OBJECT IDENTIFIER ::= { mediatrixProducts 1 }
    mediatrix-III-4FXO       OBJECT IDENTIFIER ::= { mediatrixProducts 2 }
    mediatrix1102            OBJECT IDENTIFIER ::= { mediatrixProducts 3 }
    mediatrix1104            OBJECT IDENTIFIER ::= { mediatrixProducts 4 }
    mediatrix1124            OBJECT IDENTIFIER ::= { mediatrixProducts 5 }
    mediatrix-III-4FXS-4M    OBJECT IDENTIFIER ::= { mediatrixProducts 6 }
    mediatrix1204            OBJECT IDENTIFIER ::= { mediatrixProducts 7 }
    mediatrix2102            OBJECT IDENTIFIER ::= { mediatrixProducts 8 }
    mediatrixLiaison312      OBJECT IDENTIFIER ::= { mediatrixProducts 9 }
    mediatrixLiaison322      OBJECT IDENTIFIER ::= { mediatrixProducts 10 }
    mediatrixLiaison512      OBJECT IDENTIFIER ::= { mediatrixProducts 18 }
    mediatrixLiaison522      OBJECT IDENTIFIER ::= { mediatrixProducts 19 }

END
