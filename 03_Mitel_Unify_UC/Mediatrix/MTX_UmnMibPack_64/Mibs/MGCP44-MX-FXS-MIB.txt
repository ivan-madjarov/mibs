-- ****************************************************************************
--
--             Copyright(c) 2001-2002 Mediatrix Telecom, Inc. 
--
--  NOTICE:
--   This document contains information that is confidential and proprietary
--   to Mediatrix Telecom, Inc. 
--
--   Mediatrix Telecom, Inc. reserves all rights to this document as well as
--   to the Intellectual Property of the document and the technology and
--   know how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

MGCP44-MX-FXS-MIB
DEFINITIONS ::= BEGIN

IMPORTS
        MODULE-IDENTITY,
        OBJECT-TYPE,
        Unsigned32
    FROM SNMPv2-SMI
        MODULE-COMPLIANCE,
        OBJECT-GROUP
    FROM SNMPv2-CONF
        mediatrixConfig
    FROM MX-SMI;

fxsMIB MODULE-IDENTITY
    LAST-UPDATED "0208300000Z"
    ORGANIZATION "Mediatrix Telecom, Inc."
    CONTACT-INFO "Mediatrix Telecom, Inc.
                  4229, Garlock Street
                  Sherbrooke (Quebec)
                  Canada
                  Phone: (819) 829-8749
                  "
    DESCRIPTION  "This MIB provides Foreign eXchange Station (FXS) parameters."
    -- ************************************************************************
    -- Revision history
    -- ************************************************************************
    REVISION    "0208300000Z"
    DESCRIPTION "August 30, 2002
                    Updated fxsLoopCurrent DESCRIPTION to remove reference to
                    explicit hardware platform.
                 August 22, 2002
                    Updated range of fxsLoopCurrent and augmented description.
                 November 05, 2001
                    Added fxsFlashHookDetectionDelayMin and fxsFlashHookDetectionDelayMax.
                 August 29, 2001
                    Creation"
    ::= { mediatrixConfig 40 }

fxsMIBObjects     OBJECT IDENTIFIER ::= { fxsMIB 1 }
fxsConformance    OBJECT IDENTIFIER ::= { fxsMIB 2 }


    fxsByPassEnable OBJECT-TYPE
        SYNTAX      INTEGER {
                             disable(0),
                             enable(1)
                            }
        MAX-ACCESS  read-write
        STATUS      current
        DESCRIPTION "Enable the bypass service.

                     disable : The port with the bypass service is never 
                               redirected on the bypass line.

                     enable : When the port with the bypass service is unusable
                              (ifAdminUsageState is idle-unusable), it will be 
                              redirected to the bypass line. When this port 
                              becomes usable again (ifAdminUsageState is idle),
                              the redirection is stopped within 10 seconds if 
                              the bypass line is unused or 10 seconds after 
                              the termination of the call.                   
                              
                     NOTE: The control of the bypass service is only possible
                           when the unit is powered on. When power is off, the
                           bypass service is always enabled."
        DEFVAL      { enable }
        ::= { fxsMIBObjects 1 }
 
    fxsLoopCurrent OBJECT-TYPE
        SYNTAX Unsigned32 (20..50)
        MAX-ACCESS read-write
        STATUS current
        DESCRIPTION "Current flowing through the current detector that
                     permits the detection of the on-hook and off-hook states.
                     The loop current is in mA.
                     
                     Some hardware platforms may support less than the available
                     range.
                     
                     Please refer to the documentation shipped with your device 
                     for more details."
        DEFVAL { 30 }
        ::= { fxsMIBObjects 2 }

    fxsFlashHookDetectionDelayMin OBJECT-TYPE
        SYNTAX Unsigned32 (10..1200)
        MAX-ACCESS read-write
        STATUS current
        DESCRIPTION "Minimum time in ms the hook switch must remain pressed
                     to perform a flash hook."
        DEFVAL { 100 }
        ::= { fxsMIBObjects 3 }

    fxsFlashHookDetectionDelayMax OBJECT-TYPE
        SYNTAX Unsigned32 (10..1200)
        MAX-ACCESS read-write
        STATUS current
        DESCRIPTION "Maximum time in ms the hook switch can remain pressed 
                     to perform a flash hook."
        DEFVAL { 1200 }
        ::= { fxsMIBObjects 4 }


    -- ************************************************************************
    -- Conformance information
    -- ************************************************************************
    fxsCompliances OBJECT IDENTIFIER ::= { fxsConformance 1 }

    fxsComplVer1 MODULE-COMPLIANCE
        STATUS      current
        DESCRIPTION     
            "This is the list of conformance groups to support FXS parameters."
        MODULE -- This Module
            MANDATORY-GROUPS { 
                                fxsGroupVer1
                             }
        ::= { fxsCompliances 1 }

    -- ************************************************************************
    -- MIB variable grouping
    -- ************************************************************************
    fxsGroups OBJECT IDENTIFIER ::= { fxsConformance 2 }

    fxsGroupVer1 OBJECT-GROUP
        OBJECTS {
                 fxsByPassEnable,
                 fxsLoopCurrent,
                 fxsFlashHookDetectionDelayMin,
                 fxsFlashHookDetectionDelayMax
                }
        STATUS current
        DESCRIPTION
            "This group holds the objects to define FXS specific parameters."
        ::= { fxsGroups 1 }


END
