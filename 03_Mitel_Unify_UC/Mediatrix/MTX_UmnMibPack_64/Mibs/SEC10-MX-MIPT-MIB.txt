-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************
  
SEC10-MX-MIPT-MIB
DEFINITIONS ::= BEGIN

IMPORTS
        MODULE-IDENTITY,
        OBJECT-TYPE,
        Unsigned32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices       
    FROM MX-SMI2;

miptMIB MODULE-IDENTITY                                                        
    LAST-UPDATED   "0511290000Z"                                               
    ORGANIZATION " Mediatrix Telecom, Inc. "                                   
    CONTACT-INFO " Mediatrix Telecom, Inc.                                     
                   4229, Garlock Street                                        
                   Sherbrooke (Quebec)                                         
                   Canada                                                      
                   Phone: (819) 829-8749                                       
                   "                                                           
    DESCRIPTION  " Media IP Transport                                          
                                                                               
                   The Media IP Transport service allows to configure the voice
                   and data capabilities of each endpoint.                     
                   "                                                           
    -- *************************************************************************
                                                                               
    -- Revision history                                                        
                                                                               
    -- *************************************************************************
    REVISION       "0511290000Z"                                               
    DESCRIPTION  " Initial Revision "                                          
    ::= { mediatrixServices 1600 }                                             

miptMIBObjects OBJECT IDENTIFIER ::= { miptMIB 1 }

-- *****************************************************************************
                                                                                   
-- Group:  Voice Codec                                                             
                                                                                   
-- *****************************************************************************
                                                                                   
codecGroup OBJECT IDENTIFIER                                                       
    ::= { miptMIBObjects 100 }                                                     
                                                                                   
                                                                                   
    -- Scalar:  Default Generic VAD Configuration                                  
                                                                                   
    defaultCodecGenericVoiceActivityDetection OBJECT-TYPE                          
        SYNTAX        INTEGER { disable(100) , transparent(200) , conservative     
                      (300) }                                                      
        MAX-ACCESS    read-write                                                   
        STATUS        current                                                      
        DESCRIPTION " Default Generic VAD Configuration                            
                                                                                   
                      If Voice Activity Detection (VAD) is enabled, then speech    
                      frames are only sent during talkspurts (periods of audio     
                      activity).                                                   
                                                                                   
                      During silence periods, no speech frames are sent, but       
                      Comfort Noise (CN) packets containing information about      
                      background noise may be sent (see                            
                      draft-ietf-avt-rtp-cn-05.txt). This variable specifies the   
                      sensitivity of the VAD algorithm to silence periods.         
                                                                                   
                      The generic VAD is used by codecs without built-in VAD like  
                      G.711 and G.726.                                             
                                                                                   
                        * Disable: VAD disabled.                                   
                        * Transparent: VAD enabled - low sensitivity to silence    
                          periods.                                                 
                        * Conservative: VAD enabled - normal sensitivity to        
                          silence periods.                                         
                                                                                   
                      If a specific configuration is set in the                    
                      EpSpecificCodec.GenericVoiceActivityDetection variable and   
                      the EpSpecificCodec.EnableConfig variable is set to          
                      'Enable', then it overrides the current default              
                      configuration.                                               
                                                                                   
                                                                                   
                      "                                                            
        DEFVAL        { conservative }                                             
        ::= { codecGroup 100 }                                                     
                                                                                   
    -- ***************************************************************************
                                                                                   
    -- Table:  Endpoint Specific Voice Codec Configuration                         
                                                                                   
    -- ***************************************************************************
                                                                                   
    epSpecificCodecTable OBJECT-TYPE                                               
        SYNTAX                SEQUENCE OF EpSpecificCodecEntry                     
        MAX-ACCESS            not-accessible                                       
        STATUS                current                                              
        DESCRIPTION         " Endpoint Specific Voice Codec Configuration          
                                                                                   
                              Endpoint specific configuration.                     
                              "                                                    
        ::= { codecGroup 200 }                                                     
                                                                                   
                                                                                   
        epSpecificCodecEntry OBJECT-TYPE                                           
            SYNTAX        EpSpecificCodecEntry                                     
            MAX-ACCESS    not-accessible                                           
            STATUS        current                                                  
            DESCRIPTION " A row in the Endpoint Specific Voice Codec Configuration 
                          . "                                                      
            INDEX         {                                                        
                              epId                                                 
                          }                                                        
                                                                                   
            ::= { epSpecificCodecTable 1 }                                         
                                                                                   
        EpSpecificCodecEntry ::= SEQUENCE                                          
        {                                                                          
            epId                          OCTET STRING,                            
            enableConfig                  MxEnableState,                           
            genericVoiceActivityDetection INTEGER                                  
        }                                                                          
                                                                                   
        -- Index:  Endpoint Identifier                                             
                                                                                   
        epSpecificCodecEpId OBJECT-TYPE                                            
            SYNTAX         OCTET STRING                                            
            MAX-ACCESS     read-only                                               
            STATUS         current                                                 
            DESCRIPTION  " Endpoint Identifier                                     
                                                                                   
                           String that identifies an endpoint in other tables.     
                           "                                                       
            ::= { epSpecificCodecEntry 100 }                                       
                                                                                   
        -- Columnar:  Enable Configuration                                         
                                                                                   
        epSpecificCodecEnableConfig OBJECT-TYPE                                    
            SYNTAX        MxEnableState                                            
            MAX-ACCESS    read-write                                               
            STATUS        current                                                  
            DESCRIPTION " Enable Configuration                                     
                                                                                   
                          Defines the configuration to use for a specific          
                          endpoint.                                                
                                                                                   
                            * Disable: The endpoint uses the default configuration 
                              as defined in the                                    
                              DefaultCodecGenericVoiceActivityDetection variable.  
                            * Enable: The endpoint uses the specific configuration 
                              as defined in the                                    
                              EpSpecificCodec.GenericVoiceActivityDetection        
                              variable.                                            
                                                                                   
                                                                                   
                          "                                                        
            DEFVAL        { disable }                                              
            ::= { epSpecificCodecEntry 200 }                                       
                                                                                   
        -- Columnar:  Endpoint Specific G.711 VAD Configuraion                     
                                                                                   
        epSpecificCodecGenericVoiceActivityDetection OBJECT-TYPE                   
            SYNTAX        INTEGER { disable(100) , transparent(200) , conservative 
                          (300) }                                                  
            MAX-ACCESS    read-write                                               
            STATUS        current                                                  
            DESCRIPTION " Endpoint Specific G.711 VAD Configuraion                 
                                                                                   
                          If Voice Activity Detection (VAD) is enabled, then       
                          speech frames are only sent during talkspurts (periods   
                          of audio activity).                                      
                                                                                   
                          During silence periods, no speech frames are sent, but   
                          Comfort Noise (CN) packets containing information about  
                          background noise may be sent (see                        
                          draft-ietf-avt-rtp-cn-05.txt). This variable specifies   
                          the sensitivity of the VAD algorithm to silence periods. 
                                                                                   
                          The generic VAD is used by codecs without built-in VAD   
                          like G.711 and G.726.                                    
                                                                                   
                            * Disable: VAD disabled.                               
                            * Transparent: VAD enabled - low sensitivity to        
                              silence periods.                                     
                            * Conservative: VAD enabled - normal sensitivity to    
                              silence periods.                                     
                                                                                   
                          This configuration overrides the default configuration   
                          set in the DefaultCodecGenericVoiceActivityDetection     
                          variable if the EpSpecificCodec.EnableConfig variable is 
                          set to 'Enable'.                                         
                                                                                   
                                                                                   
                          "                                                        
            DEFVAL        { conservative }                                         
            ::= { epSpecificCodecEntry 300 }                                       
                                                                                   
                                                                                   
    -- End of table:  Endpoint Specific Voice Codec Configuration                  
                                                                                   
    -- ***************************************************************************
                                                                                   
    -- Group:  G.711 Voice Codec                                                   
                                                                                   
    -- ***************************************************************************
                                                                                   
    codecG711Group OBJECT IDENTIFIER                                               
        ::= { codecGroup 300 }                                                     
                                                                                   
                                                                                   
        -- ************************************************************************
                                                                                   
        -- Group:  G.711 Mu-Law Voice Codec Group                                  
                                                                                   
        -- ************************************************************************
                                                                                   
        codecG711MulawGroup OBJECT IDENTIFIER                                      
            ::= { codecG711Group 100 }                                             
                                                                                   
                                                                                   
            -- Scalar:  Default G.711 Mu-Law Enable/Disable Configuration for Voice
                                                                                   
            defaultCodecG711MulawVoiceEnable OBJECT-TYPE                           
                SYNTAX        MxEnableState                                        
                MAX-ACCESS    read-write                                           
                STATUS        current                                              
                DESCRIPTION " Default G.711 Mu-Law Enable/Disable Configuration for
                              Voice                                                
                                                                                   
                              Indicates if the codec can be selected for voice     
                              transmission. If enabled, this codec is listed as    
                              supported for this specific endpoint. Otherwise, it  
                              is ignored.                                          
                                                                                   
                              PCMA and PCMU are specified in ITU-T Recommendation  
                              G.711. Audio data is encoded as eight bits per       
                              sample, after logarithmic scaling. PCMU denotes      
                              mu-law scaling, PCMA A-law scaling.                  
                                                                                   
                              This codec uses generic voice activity detection. See
                              the DefaultCodecGenericVoiceActivityDetection and    
                              EpSpecificCodec.GenericVoiceActivityDetection        
                              variables.                                           
                                                                                   
                              This codec always uses the RTP transport.            
                                                                                   
                              If a specific configuration is set in the            
                              EpSpecificCodecG711Mulaw.VoiceEnable variable and the
                              EpSpecificCodecG711Mulaw.EnableConfig variable is set
                              to 'Enable', then it overrides the current default   
                              configuration.                                       
                                                                                   
                                                                                   
                              "                                                    
                DEFVAL        { enable }                                           
                ::= { codecG711MulawGroup 100 }                                    
                                                                                   
            -- Scalar:  Default G.711 Mu-Law Priority Configuration for Voice      
                                                                                   
            defaultCodecG711MulawVoicePriority OBJECT-TYPE                         
                SYNTAX        Unsigned32 ( 0..10 )                                 
                MAX-ACCESS    read-write                                           
                STATUS        current                                              
                DESCRIPTION " Default G.711 Mu-Law Priority Configuration for Voice
                                                                                   
                              Indicates the priority of this voice codec versus the
                              other voice codecs. The voice codec with the highest 
                              priority will be offered first when an outgoing call 
                              is initiated. This priority is not used in incoming  
                              call.                                                
                                                                                   
                              The application uses an internal order for codecs    
                              with the same priority.                              
                                                                                   
                              10 is the highest priority and 0 the lowest.         
                                                                                   
                              If a specific configuration is set in the            
                              EpSpecificCodecG711Mulaw.VoicePriority variable and  
                              the EpSpecificCodecG711Mulaw.EnableConfig variable is
                              set to 'Enable', then it overrides the current       
                              default configuration.                               
                                                                                   
                                                                                   
                              "                                                    
                DEFVAL        { 0 }                                                
                ::= { codecG711MulawGroup 200 }                                    
                                                                                   
            -- Scalar:  Default G.711 Mu-Law Enable/Disable Configuration for Data 
                                                                                   
            defaultCodecG711MulawDataEnable OBJECT-TYPE                            
                SYNTAX        MxEnableState                                        
                MAX-ACCESS    read-write                                           
                STATUS        current                                              
                DESCRIPTION " Default G.711 Mu-Law Enable/Disable Configuration for
                              Data                                                 
                                                                                   
                              Indicates if the codec can be selected for data      
                              transmission. If enabled, this codec is listed as    
                              supported for this specific endpoint. Otherwise, it  
                              is ignored.                                          
                                                                                   
                              If a specific configuration is set in the            
                              EpSpecificCodecG711Mulaw.DataEnable variable and the 
                              EpSpecificCodecG711Mulaw.EnableConfig variable is set
                              to 'Enable', then it overrides the current default   
                              configuration.                                       
                                                                                   
                                                                                   
                              "                                                    
                DEFVAL        { enable }                                           
                ::= { codecG711MulawGroup 300 }                                    
                                                                                   
            -- Scalar:  Default G.711 Mu-Law Priority Configuration for Data       
                                                                                   
            defaultCodecG711MulawDataPriority OBJECT-TYPE                          
                SYNTAX        Unsigned32 ( 0..10 )                                 
                MAX-ACCESS    read-write                                           
                STATUS        current                                              
                DESCRIPTION " Default G.711 Mu-Law Priority Configuration for Data 
                                                                                   
                              Indicates the priority of this data codec versus the 
                              other data codecs. The data codec with the highest   
                              priority will be offered first when an outgoing call 
                              is initiated. This priority is not used in incoming  
                              call.                                                
                                                                                   
                              The application uses an internal order for codecs    
                              with the same priority.                              
                                                                                   
                              10 is the highest priority and 0 the lowest.         
                                                                                   
                              If a specific configuration is set in the            
                              EpSpecificCodecG711Mulaw.DataPriority variable and   
                              the EpSpecificCodecG711Mulaw.EnableConfig variable is
                              set to 'Enable', then it overrides the current       
                              default configuration.                               
                                                                                   
                                                                                   
                              "                                                    
                DEFVAL        { 0 }                                                
                ::= { codecG711MulawGroup 400 }                                    
                                                                                   
            -- Scalar:  Default G.711 Mu-Law Minimum Packetization Period          
            -- Configuration                                                          
                                                                                   
            defaultCodecG711MulawMinPTime OBJECT-TYPE                              
                SYNTAX        Unsigned32 ( 10..30 )                                
                MAX-ACCESS    read-write                                           
                STATUS        current                                              
                DESCRIPTION " Default G.711 Mu-Law Minimum Packetization Period    
                              Configuration                                        
                                                                                   
                              Lower boundary for the packetization period of the   
                              given codec.                                         
                                                                                   
                              PCMU -> (10 ms..30 ms)                               
                                                                                   
                              This value is expressed in ms, with increments of 1  
                              ms.                                                  
                                                                                   
                              If a specific configuration is set in the            
                              EpSpecificCodecG711Mulaw.MinPTime variable and the   
                              EpSpecificCodecG711Mulaw.EnableConfig variable is set
                              to 'Enable', then it overrides the current default   
                              configuration.                                       
                                                                                   
                                                                                   
                              "                                                    
                DEFVAL        { 10 }                                               
                ::= { codecG711MulawGroup 500 }                                    
                                                                                   
            -- Scalar:  Default G.711 Mu-Law Maximum Packetization Period          
            -- Configuration                                                          
                                                                                   
            defaultCodecG711MulawMaxPTime OBJECT-TYPE                              
                SYNTAX        Unsigned32 ( 10..30 )                                
                MAX-ACCESS    read-write                                           
                STATUS        current                                              
                DESCRIPTION " Default G.711 Mu-Law Maximum Packetization Period    
                              Configuration                                        
                                                                                   
                              Upper boundary for the packetization period of the   
                              given codec.                                         
                                                                                   
                              PCMU -> (10 ms..30 ms)                               
                                                                                   
                              This value is expressed in ms, with increments of 1  
                              ms.                                                  
                                                                                   
                              If a specific configuration is set in the            
                              EpSpecificCodecG711Mulaw.MaxPTime variable and the   
                              EpSpecificCodecG711Mulaw.EnableConfig variable is set
                              to 'Enable', then it overrides the current default   
                              configuration.                                       
                                                                                   
                                                                                   
                              "                                                    
                DEFVAL        { 30 }                                               
                ::= { codecG711MulawGroup 600 }                                    
                                                                                   
            -- *********************************************************************
                                                                                   
            -- Table:  Endpoint Specific Voice Codec Configuration                 
                                                                                   
            -- *********************************************************************
                                                                                   
            epSpecificCodecG711MulawTable OBJECT-TYPE                              
                SYNTAX               SEQUENCE OF EpSpecificCodecG711MulawEntry     
                MAX-ACCESS           not-accessible                                
                STATUS               current                                       
                DESCRIPTION        " Endpoint Specific Voice Codec Configuration   
                                                                                   
                                     Endpoint specific configuration.              
                                     "                                             
                ::= { codecG711MulawGroup 700 }                                    
                                                                                   
                                                                                   
                epSpecificCodecG711MulawEntry OBJECT-TYPE                          
                    SYNTAX        EpSpecificCodecG711MulawEntry                    
                    MAX-ACCESS    not-accessible                                   
                    STATUS        current                                          
                    DESCRIPTION " A row in the Endpoint Specific Voice Codec       
                                  Configuration . "                                
                    INDEX         {                                                
                                      epId                                         
                                  }                                                
                                                                                   
                    ::= { epSpecificCodecG711MulawTable 1 }                        
                                                                                   
                EpSpecificCodecG711MulawEntry ::= SEQUENCE                         
                {                                                                  
                     epId              OCTET STRING,                               
                     enableConfig      MxEnableState,                              
                     voiceEnable       MxEnableState,                              
                     voicePriority     Unsigned32,                                 
                     dataEnable        MxEnableState,                              
                     dataPriority      Unsigned32,                                 
                     minPTime          Unsigned32,                                 
                     maxPTime          Unsigned32                                  
                }                                                                  
                                                                                   
                -- Index:  Endpoint Identifier                                     
                                                                                   
                epSpecificCodecG711MulawEpId OBJECT-TYPE                           
                    SYNTAX        OCTET STRING                                     
                    MAX-ACCESS    read-only                                        
                    STATUS        current                                          
                    DESCRIPTION " Endpoint Identifier                              
                                                                                   
                                  String that identifies an endpoint in other      
                                  tables.                                          
                                  "                                                
                    ::= { epSpecificCodecG711MulawEntry 100 }                      
                                                                                   
                -- Columnar:  Enable Configuration                                 
                                                                                   
                epSpecificCodecG711MulawEnableConfig OBJECT-TYPE                   
                    SYNTAX        MxEnableState                                    
                    MAX-ACCESS    read-write                                       
                    STATUS        current                                          
                    DESCRIPTION " Enable Configuration                             
                                                                                   
                                  Defines the configuration to use for a specific  
                                  endpoint.                                        
                                                                                   
                                    * Disable: The endpoint uses the default       
                                      configuration as defined in the              
                                      DefaultCodecG711MulawVoiceEnable,            
                                      DefaultCodecG711MulawVoicePriority,          
                                      DefaultCodecG711MulawDataEnable,             
                                      DefaultCodecG711MulawDataPriority,           
                                      DefaultCodecG711MulawMinPTime and            
                                      DefaultCodecG711MulawMaxPTime variables.     
                                    * Enable: The endpoint uses the specific       
                                      configuration as defined in the              
                                      EpSpecificCodecG711Mulaw.VoiceEnable,        
                                      EpSpecificCodecG711Mulaw.VoicePriority,      
                                      EpSpecificCodecG711Mulaw.DataEnable,         
                                      EpSpecificCodecG711Mulaw.DataPriority,       
                                      EpSpecificCodecG711Mulaw.MinPTime and        
                                      EpSpecificCodecG711Mulaw.MaxPTime variables. 
                                                                                   
                                                                                   
                                  "                                                
                    DEFVAL        { disable }                                      
                    ::= { epSpecificCodecG711MulawEntry 200 }                      
                                                                                   
                -- Columnar:  Endpoint Specific G.711 Mu-Law Enable/Disable        
                -- Configuration for Voice                                            
                                                                                   
                epSpecificCodecG711MulawVoiceEnable OBJECT-TYPE                    
                    SYNTAX        MxEnableState                                    
                    MAX-ACCESS    read-write                                       
                    STATUS        current                                          
                    DESCRIPTION " Endpoint Specific G.711 Mu-Law Enable/Disable    
                                  Configuration for Voice                          
                                                                                   
                                  Indicates if the codec can be selected for voice 
                                  transmission. If enabled, this codec is listed as
                                  supported for this specific endpoint. Otherwise, 
                                  it is ignored.                                   
                                                                                   
                                  PCMA and PCMU are specified in ITU-T             
                                  Recommendation G.711. Audio data is encoded as   
                                  eight bits per sample, after logarithmic scaling.
                                  PCMU denotes mu-law scaling, PCMA A-law scaling. 
                                                                                   
                                  This codec uses generic voice activity detection.
                                  See the DefaultCodecGenericVoiceActivityDetection
                                  and EpSpecificCodec.GenericVoiceActivityDetection
                                  variables.                                       
                                                                                   
                                  This codec always uses the RTP transport.        
                                                                                   
                                  This configuration overrides the default         
                                  configuration set in the                         
                                  DefaultCodecG711MulawVoiceEnable variable if the 
                                  EpSpecificCodecG711Mulaw.EnableConfig variable is
                                  set to 'Enable'.                                 
                                                                                   
                                                                                   
                                  "                                                
                    DEFVAL        { enable }                                       
                    ::= { epSpecificCodecG711MulawEntry 300 }                      
                                                                                   
                -- Columnar:  Endpoint Specific G.711 Mu-Law Priority Configuration
                -- for Voice                                                          
                                                                                   
                epSpecificCodecG711MulawVoicePriority OBJECT-TYPE                  
                    SYNTAX        Unsigned32 ( 0..10 )                             
                    MAX-ACCESS    read-write                                       
                    STATUS        current                                          
                    DESCRIPTION " Endpoint Specific G.711 Mu-Law Priority          
                                  Configuration for Voice                          
                                                                                   
                                  Indicates the priority of this voice codec versus
                                  the other voice codecs. The voice codec with the 
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG711MulawVoicePriority variable if   
                                  the EpSpecificCodecG711Mulaw.EnableConfig        
                                  variable is set to 'Enable'.                     
                                                                                   
                                                                                   
                                  "                                                
                    DEFVAL        { 0 }                                            
                    ::= { epSpecificCodecG711MulawEntry 400 }                      
                                                                                   
                -- Columnar:  Endpoint Specific G.711 Mu-Law Enable/Disable        
                -- Configuration for Data                                             
                                                                                   
                epSpecificCodecG711MulawDataEnable OBJECT-TYPE                     
                    SYNTAX        MxEnableState                                    
                    MAX-ACCESS    read-write                                       
                    STATUS        current                                          
                    DESCRIPTION " Endpoint Specific G.711 Mu-Law Enable/Disable    
                                  Configuration for Data                           
                                                                                   
                                  Indicates if the codec can be selected for data  
                                  transmission. If enabled, this codec is listed as
                                  supported for this specific endpoint. Otherwise, 
                                  it is ignored.                                   
                                                                                   
                                  This configuration overrides the default         
                                  configuration set in the                         
                                  DefaultCodecG711MulawDataEnable variable if the  
                                  EpSpecificCodecG711Mulaw.EnableConfig variable is
                                  set to 'Enable'.                                 
                                                                                   
                                                                                   
                                  "                                                
                    DEFVAL        { enable }                                       
                    ::= { epSpecificCodecG711MulawEntry 500 }                      
                                                                                   
                -- Columnar:  Endpoint Specific G.711 Mu-Law Priority Configuration
                -- for Data                                                           
                                                                                   
                epSpecificCodecG711MulawDataPriority OBJECT-TYPE                   
                    SYNTAX        Unsigned32 ( 0..10 )                             
                    MAX-ACCESS    read-write                                       
                    STATUS        current                                          
                    DESCRIPTION " Endpoint Specific G.711 Mu-Law Priority          
                                  Configuration for Data                           
                                                                                   
                                  Indicates the priority of this data codec versus 
                                  the other data codecs. The data codec with the   
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG711MulawDataPriority variable if the
                                  EpSpecificCodecG711Mulaw.EnableConfig variable is
                                  set to 'Enable'.                                 
                                                                                   
                                                                                   
                                  "                                                
                    DEFVAL        { 0 }                                            
                    ::= { epSpecificCodecG711MulawEntry 600 }                      
                                                                                   
                -- Columnar:  Endpoint Specific G.711 Mu-Law Minimum Packetization 
                -- Period Configuration                                               
                                                                                   
                epSpecificCodecG711MulawMinPTime OBJECT-TYPE                       
                    SYNTAX        Unsigned32 ( 10..30 )                            
                    MAX-ACCESS    read-write                                       
                    STATUS        current                                          
                    DESCRIPTION " Endpoint Specific G.711 Mu-Law Minimum           
                                  Packetization Period Configuration               
                                                                                   
                                  Lower boundary for the packetization period of   
                                  the given codec.                                 
                                                                                   
                                  PCMU -> (10 ms..30 ms)                           
                                                                                   
                                  This value is expressed in ms, with increments of
                                  1 ms.                                            
                                                                                   
                                  This configuration overrides the default         
                                  configuration set in the                         
                                  DefaultCodecG711MulawMinPTime variable if the    
                                  EpSpecificCodecG711Mulaw.EnableConfig variable is
                                  set to 'Enable'.                                 
                                                                                   
                                                                                   
                                  "                                                
                    DEFVAL        { 10 }                                           
                    ::= { epSpecificCodecG711MulawEntry 700 }                      
                                                                                   
                -- Columnar:  Endpoint Specific G.711 Mu-Law Maximum Packetization 
                -- Period Configuration                                               
                                                                                   
                epSpecificCodecG711MulawMaxPTime OBJECT-TYPE                       
                    SYNTAX        Unsigned32 ( 10..30 )                            
                    MAX-ACCESS    read-write                                       
                    STATUS        current                                          
                    DESCRIPTION " Endpoint Specific G.711 Mu-Law Maximum           
                                  Packetization Period Configuration               
                                                                                   
                                  Upper boundary for the packetization period of   
                                  the given codec.                                 
                                                                                   
                                  PCMU -> (10 ms..30 ms)                           
                                                                                   
                                  This value is expressed in ms, with increments of
                                  1 ms.                                            
                                                                                   
                                  This configuration overrides the default         
                                  configuration set in the                         
                                  DefaultCodecG711MulawMaxPTime variable if the    
                                  EpSpecificCodecG711Mulaw.EnableConfig variable is
                                  set to 'Enable'.                                 
                                                                                   
                                                                                   
                                  "                                                
                    DEFVAL        { 30 }                                           
                    ::= { epSpecificCodecG711MulawEntry 800 }                      
                                                                                   
                                                                                   
            -- End of table:  Endpoint Specific Voice Codec Configuration          
                                                                                   
        -- End of group:  G.711 Mu-Law Voice Codec Group                           
                                                                                   
        -- ************************************************************************
                                                                                   
        -- Group:  G.711 A-law Voice Codec Group                                   
                                                                                   
        -- ************************************************************************
                                                                                   
        codecG711AlawGroup OBJECT IDENTIFIER                                       
            ::= { codecG711Group 200 }                                             
                                                                                   
                                                                                   
            -- Scalar:  Default G.711 A-law Enable/Disable Configuration for Voice 
                                                                                   
            defaultCodecG711AlawVoiceEnable OBJECT-TYPE                            
                SYNTAX        MxEnableState                                        
                MAX-ACCESS    read-write                                           
                STATUS        current                                              
                DESCRIPTION " Default G.711 A-law Enable/Disable Configuration for 
                              Voice                                                
                                                                                   
                              Indicates if the codec can be selected for voice     
                              transmission. If enabled, this codec is listed as    
                              supported for this specific endpoint. Otherwise, it  
                              is ignored.                                          
                                                                                   
                              PCMA and PCMU are specified in ITU-T Recommendation  
                              G.711. Audio data is encoded as eight bits per       
                              sample, after logarithmic scaling. PCMU denotes      
                              mu-law scaling, PCMA A-law scaling.                  
                                                                                   
                              This codec uses generic voice activity detection. See
                              the DefaultCodecGenericVoiceActivityDetection and    
                              EpSpecificCodec.GenericVoiceActivityDetection        
                              variables.                                           
                                                                                   
                              This codec always uses the RTP transport.            
                                                                                   
                              If a specific configuration is set in the            
                              EpSpecificCodecG711Alaw.VoiceEnable variable and the 
                              EpSpecificCodecG711Alaw.EnableConfig variable is set 
                              to 'Enable', then it overrides the current default   
                              configuration.                                       
                                                                                   
                                                                                   
                              "                                                    
                DEFVAL        { enable }                                           
                ::= { codecG711AlawGroup 100 }                                     
                                                                                   
            -- Scalar:  Default G.711 A-Law Priority Configuration for Voice       
                                                                                   
            defaultCodecG711AlawVoicePriority OBJECT-TYPE                          
                SYNTAX        Unsigned32 ( 0..10 )                                 
                MAX-ACCESS    read-write                                           
                STATUS        current                                              
                DESCRIPTION " Default G.711 A-Law Priority Configuration for Voice 
                                                                                   
                              Indicates the priority of this voice codec versus the
                              other voice codecs. The voice codec with the highest 
                              priority will be offered first when an outgoing call 
                              is initiated. This priority is not used in incoming  
                              calls.                                               
                                                                                   
                              The application uses an internal order for codecs    
                              with the same priority.                              
                                                                                   
                              10 is the highest priority and 0 the lowest.         
                                                                                   
                              If a specific configuration is set in the            
                              EpSpecificCodecG711Alaw.VoicePriority variable and   
                              the EpSpecificCodecG711Alaw.EnableConfig variable is 
                              set to 'Enable', then it overrides the current       
                              default configuration.                               
                                                                                   
                                                                                   
                              "                                                    
                DEFVAL        { 0 }                                                
                ::= { codecG711AlawGroup 200 }                                     
                                                                                   
            -- Scalar:  Default G.711 A-Law Enable/Disable Configuration for Data  
                                                                                   
            defaultCodecG711AlawDataEnable OBJECT-TYPE                             
                SYNTAX        MxEnableState                                        
                MAX-ACCESS    read-write                                           
                STATUS        current                                              
                DESCRIPTION " Default G.711 A-Law Enable/Disable Configuration for 
                              Data                                                 
                                                                                   
                              Indicates if the codec can be selected for data      
                              transmission. If enabled, this codec is listed as    
                              supported for this specific endpoint. Otherwise, it  
                              is ignored.                                          
                                                                                   
                              If a specific configuration is set in the            
                              EpSpecificCodecG711Alaw.DataEnable variable and the  
                              EpSpecificCodecG711Alaw.EnableConfig variables is set
                              to 'Enable', then it overrides the current default   
                              configuration.                                       
                                                                                   
                                                                                   
                              "                                                    
                DEFVAL        { enable }                                           
                ::= { codecG711AlawGroup 300 }                                     
                                                                                   
            -- Scalar:  Default G.711 A-Law Priority Configuration for Data        
                                                                                   
            defaultCodecG711AlawDataPriority OBJECT-TYPE                           
                SYNTAX        Unsigned32 ( 0..10 )                                 
                MAX-ACCESS    read-write                                           
                STATUS        current                                              
                DESCRIPTION " Default G.711 A-Law Priority Configuration for Data  
                                                                                   
                              Indicates the priority of this data codec versus the 
                              other data codecs. The data codec with the highest   
                              priority will be offered first when an outgoing call 
                              is initiated. This priority is not used in incoming  
                              calls.                                               
                                                                                   
                              The application uses an internal order for codecs    
                              with the same priority.                              
                                                                                   
                              10 is the highest priority and 0 the lowest.         
                                                                                   
                              If a specific configuration is set in the            
                              EpSpecificCodecG711Alaw.DataPriority variable and the
                              EpSpecificCodecG711Alaw.EnableConfig variable is set 
                              to 'Enable', then it overrides the current default   
                              configuration.                                       
                                                                                   
                                                                                   
                              "                                                    
                DEFVAL        { 0 }                                                
                ::= { codecG711AlawGroup 400 }                                     
                                                                                   
            -- Scalar:  Default G.711 A-Law Minimum Packetization Period           
            -- Configuration                                                          
                                                                                   
            defaultCodecG711AlawMinPTime OBJECT-TYPE                               
                SYNTAX        Unsigned32 ( 10..30 )                                
                MAX-ACCESS    read-write                                           
                STATUS        current                                              
                DESCRIPTION " Default G.711 A-Law Minimum Packetization Period     
                              Configuration                                        
                                                                                   
                              Lower boundary for the packetization period of the   
                              given codec.                                         
                                                                                   
                              PCMA -> (10 ms..30 ms)                               
                                                                                   
                              This value is expressed in ms, with increments of 1  
                              ms.                                                  
                                                                                   
                              If a specific configuration is set in the            
                              EpSpecificCodecG711Alaw.MinPTime variable and the    
                              EpSpecificCodecG711Alaw.EnableConfig variable is set 
                              to 'Enable', then it overrides the current default   
                              configuration.                                       
                                                                                   
                                                                                   
                              "                                                    
                DEFVAL        { 10 }                                               
                ::= { codecG711AlawGroup 500 }                                     
                                                                                   
            -- Scalar:  Default G.711 A-Law Maximum Packetization Period           
            -- Configuration                                                          
                                                                                   
            defaultCodecG711AlawMaxPTime OBJECT-TYPE                               
                SYNTAX        Unsigned32 ( 10..30 )                                
                MAX-ACCESS    read-write                                           
                STATUS        current                                              
                DESCRIPTION " Default G.711 A-Law Maximum Packetization Period     
                              Configuration                                        
                                                                                   
                              Upper boundary for the packetization period of the   
                              given codec.                                         
                                                                                   
                              PCMA -> (10 ms..30 ms)                               
                                                                                   
                              This value is expressed in ms, with increments of 1  
                              ms.                                                  
                                                                                   
                              If a specific configuration is set in the            
                              EpSpecificCodecG711Alaw.MaxPTime variable and the    
                              EpSpecificCodecG711Alaw.EnableConfig variable is set 
                              to 'Enable', then it overrides the current default   
                              configuration.                                       
                                                                                   
                                                                                   
                              "                                                    
                DEFVAL        { 30 }                                               
                ::= { codecG711AlawGroup 600 }                                     
                                                                                   
            -- *********************************************************************
                                                                                   
            -- Table:  Endpoint Specific Voice Codec Configuration                 
                                                                                   
            -- *********************************************************************
                                                                                   
            epSpecificCodecG711AlawTable OBJECT-TYPE                               
                SYNTAX               SEQUENCE OF EpSpecificCodecG711AlawEntry      
                MAX-ACCESS           not-accessible                                
                STATUS               current                                       
                DESCRIPTION        " Endpoint Specific Voice Codec Configuration   
                                                                                   
                                     Endpoint specific configuration.              
                                     "                                             
                ::= { codecG711AlawGroup 700 }                                     
                                                                                   
                                                                                   
                epSpecificCodecG711AlawEntry OBJECT-TYPE                           
                    SYNTAX        EpSpecificCodecG711AlawEntry                     
                    MAX-ACCESS    not-accessible                                   
                    STATUS        current                                          
                    DESCRIPTION " A row in the Endpoint Specific Voice Codec       
                                  Configuration . "                                
                    INDEX         {                                                
                                      epId                                         
                                  }                                                
                                                                                   
                    ::= { epSpecificCodecG711AlawTable 1 }                         
                                                                                   
                EpSpecificCodecG711AlawEntry ::= SEQUENCE                          
                {                                                                  
                    epId              OCTET STRING,                                
                    enableConfig      MxEnableState,                               
                    voiceEnable       MxEnableState,                               
                    voicePriority     Unsigned32,                                  
                    dataEnable        MxEnableState,                               
                    dataPriority      Unsigned32,                                  
                    minPTime          Unsigned32,                                  
                    maxPTime          Unsigned32                                   
                }                                                                  
                                                                                   
                -- Index:  Endpoint Identifier                                     
                                                                                   
                epSpecificCodecG711AlawEpId OBJECT-TYPE                            
                    SYNTAX        OCTET STRING                                     
                    MAX-ACCESS    read-only                                        
                    STATUS        current                                          
                    DESCRIPTION " Endpoint Identifier                              
                                                                                   
                                  String that identifies an endpoint in other      
                                  tables.                                          
                                  "                                                
                    ::= { epSpecificCodecG711AlawEntry 100 }                       
                                                                                   
                -- Columnar:  Enable Configuration                                 
                                                                                   
                epSpecificCodecG711AlawEnableConfig OBJECT-TYPE                    
                    SYNTAX        MxEnableState                                    
                    MAX-ACCESS    read-write                                       
                    STATUS        current                                          
                    DESCRIPTION " Enable Configuration                             
                                                                                   
                                  Defines the configuration to use for a specific  
                                  endpoint.                                        
                                                                                   
                                    * Disable: The endpoint uses the default       
                                      configuration as defined in the              
                                      DefaultCodecG711AlawVoiceEnable,             
                                      DefaultCodecG711AlawVoicePriority,           
                                      DefaultCodecG711AlawDataEnable,              
                                      DefaultCodecG711AlawDataPriority,            
                                      DefaultCodecG711AlawMinPTime and             
                                      DefaultCodecG711AlawMaxPTime variables.      
                                    * Enable: The endpoint uses the specific       
                                      configuration as defined in the              
                                      EpSpecificCodecG711Alaw.VoiceEnable,         
                                      EpSpecificCodecG711Alaw.VoicePriority,       
                                      EpSpecificCodecG711Alaw.DataEnable,          
                                      EpSpecificCodecG711Alaw.DataPriority,        
                                      EpSpecificCodecG711Alaw.MinPTime and         
                                      EpSpecificCodecG711Alaw.MaxPTime variables.  
                                                                                   
                                                                                   
                                  "                                                
                    DEFVAL        { disable }                                      
                    ::= { epSpecificCodecG711AlawEntry 200 }                       
                                                                                   
                -- Columnar:  Endpoint Specific G.711 A-Law Enable/Disable         
                -- Configuration for Voice                                            
                                                                                   
                epSpecificCodecG711AlawVoiceEnable OBJECT-TYPE                     
                    SYNTAX        MxEnableState                                    
                    MAX-ACCESS    read-write                                       
                    STATUS        current                                          
                    DESCRIPTION " Endpoint Specific G.711 A-Law Enable/Disable     
                                  Configuration for Voice                          
                                                                                   
                                  Indicates if the codec can be selected for voice 
                                  transmission. If enabled, this codec is listed as
                                  supported for this specific endpoint. Otherwise, 
                                  it is ignored.                                   
                                                                                   
                                  PCMA and PCMU are specified in ITU-T             
                                  Recommendation G.711. Audio data is encoded as   
                                  eight bits per sample, after logarithmic scaling.
                                  PCMU denotes mu-law scaling, PCMA A-law scaling. 
                                                                                   
                                  This codec uses generic voice activity detection.
                                  See the DefaultCodecGenericVoiceActivityDetection
                                  and EpSpecificCodec.GenericVoiceActivityDetection
                                  variables.                                       
                                                                                   
                                  This codec always uses the RTP transport.        
                                                                                   
                                  This configuration overrides the default         
                                  configuration set in the                         
                                  DefaultCodecG711AlawVoiceEnable variable if the  
                                  EpSpecificCodecG711Alaw.EnableConfig variable is 
                                  set to 'Enable'.                                 
                                                                                   
                                                                                   
                                  "                                                
                    DEFVAL        { enable }                                       
                    ::= { epSpecificCodecG711AlawEntry 300 }                       
                                                                                   
                -- Columnar:  Endpoint Specific G.711 A-Law Priority Configuration 
                -- for Voice                                                          
                                                                                   
                epSpecificCodecG711AlawVoicePriority OBJECT-TYPE                   
                    SYNTAX        Unsigned32 ( 0..10 )                             
                    MAX-ACCESS    read-write                                       
                    STATUS        current                                          
                    DESCRIPTION " Endpoint Specific G.711 A-Law Priority           
                                  Configuration for Voice                          
                                                                                   
                                  Indicates the priority of this voice codec versus
                                  the other voice codecs. The voice codec with the 
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG711AlawVoicePriority variable if the
                                  EpSpecificCodecG711Alaw.EnableConfig variable is 
                                  set to 'Enable'.                                 
                                                                                   
                                                                                   
                                  "                                                
                    DEFVAL        { 0 }                                            
                    ::= { epSpecificCodecG711AlawEntry 400 }                       
                                                                                   
                -- Columnar:  Endpoint Specific G.711 A-Law Enable/Disable         
                -- Configuration for Data                                             
                                                                                   
                epSpecificCodecG711AlawDataEnable OBJECT-TYPE                      
                    SYNTAX        MxEnableState                                    
                    MAX-ACCESS    read-write                                       
                    STATUS        current                                          
                    DESCRIPTION " Endpoint Specific G.711 A-Law Enable/Disable     
                                  Configuration for Data                           
                                                                                   
                                  Indicates if the codec can be selected for data  
                                  transmission. If enabled, this codec is listed as
                                  supported for this specific endpoint. Otherwise, 
                                  it is ignored.                                   
                                                                                   
                                  This configuration overrides the default         
                                  configuration set in the                         
                                  DefaultCodecG711AlawDataEnable variable if the   
                                  EpSpecificCodecG711Alaw.EnableConfig variable is 
                                  set to 'Enable'.                                 
                                                                                   
                                                                                   
                                  "                                                
                    DEFVAL        { enable }                                       
                    ::= { epSpecificCodecG711AlawEntry 500 }                       
                                                                                   
                -- Columnar:  Endpoint Specific G.711 A-Law Priority Configuration 
                -- for Data                                                           
                                                                                   
                epSpecificCodecG711AlawDataPriority OBJECT-TYPE                    
                    SYNTAX        Unsigned32 ( 0..10 )                             
                    MAX-ACCESS    read-write                                       
                    STATUS        current                                          
                    DESCRIPTION " Endpoint Specific G.711 A-Law Priority           
                                  Configuration for Data                           
                                                                                   
                                  Indicates the priority of this data codec versus 
                                  the other data codecs. The data codec with the   
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG711AlawDataPriority variable if the 
                                  EpSpecificCodecG711Alaw.EnableConfig variable is 
                                  set to 'Enable'.                                 
                                                                                   
                                                                                   
                                  "                                                
                    DEFVAL        { 0 }                                            
                    ::= { epSpecificCodecG711AlawEntry 600 }                       
                                                                                   
                -- Columnar:  Endpoint Specific G.711 A-Law Minimum Packetization  
                -- Period Configuration                                               
                                                                                   
                epSpecificCodecG711AlawMinPTime OBJECT-TYPE                        
                    SYNTAX        Unsigned32 ( 10..30 )                            
                    MAX-ACCESS    read-write                                       
                    STATUS        current                                          
                    DESCRIPTION " Endpoint Specific G.711 A-Law Minimum            
                                  Packetization Period Configuration               
                                                                                   
                                  Lower boundary for the packetization period of   
                                  the given codec.                                 
                                                                                   
                                  PCMA -> (10 ms..30 ms)                           
                                                                                   
                                  This value is expressed in ms, with increments of
                                  1 ms.                                            
                                                                                   
                                  This configuration overrides the default         
                                  configuration set in the                         
                                  DefaultCodecG711AlawMinPTime variable if the     
                                  EpSpecificCodecG711Alaw.EnableConfig variable is 
                                  set to 'Enable'.                                 
                                                                                   
                                                                                   
                                  "                                                
                    DEFVAL        { 10 }                                           
                    ::= { epSpecificCodecG711AlawEntry 700 }                       
                                                                                   
                -- Columnar:  Endpoint Specific G.711 A-Law Maximum Packetization  
                -- Period Configuration                                               
                                                                                   
                epSpecificCodecG711AlawMaxPTime OBJECT-TYPE                        
                    SYNTAX        Unsigned32 ( 10..30 )                            
                    MAX-ACCESS    read-write                                       
                    STATUS        current                                          
                    DESCRIPTION " Endpoint Specific G.711 A-Law Maximum            
                                  Packetization Period Configuration               
                                                                                   
                                  Upper boundary for the packetization period of   
                                  the given codec.                                 
                                                                                   
                                  PCMA -> (10 ms..30 ms)                           
                                                                                   
                                  This value is expressed in ms, with increments of
                                  1 ms.                                            
                                                                                   
                                  This configuration overrides the default         
                                  configuration set in the                         
                                  DefaultCodecG711AlawMaxPTime variable if the     
                                  EpSpecificCodecG711Alaw.EnableConfig variable is 
                                  set to 'Enable'.                                 
                                                                                   
                                                                                   
                                  "                                                
                    DEFVAL        { 30 }                                           
                    ::= { epSpecificCodecG711AlawEntry 800 }                       
                                                                                   
                                                                                   
            -- End of table:  Endpoint Specific Voice Codec Configuration          
                                                                                   
        -- End of group:  G.711 A-law Voice Codec Group                            
                                                                                   
    -- End of group:  G.711 Voice Codec                                            
                                                                                   
    -- ***************************************************************************
                                                                                   
    -- Group:  G.723 Voice Codec Group                                             
                                                                                   
    --                                                                             
    -- ***************************************************************************
                                                                                   
    codecG723Group OBJECT IDENTIFIER                                               
        ::= { codecGroup 400 }                                                     
                                                                                   
                                                                                   
        -- Scalar:  Default G.723.1 Enable/Disable Configuration for Voice         
                                                                                   
        defaultCodecG723VoiceEnable OBJECT-TYPE                                    
            SYNTAX        MxEnableState                                            
            MAX-ACCESS    read-write                                               
            STATUS        current                                                  
            DESCRIPTION " Default G.723.1 Enable/Disable Configuration for Voice   
                                                                                   
                          Indicates if the codec can be selected for voice         
                          transmission. If enabled, this codec is listed as        
                          supported for this specific endpoint. Otherwise, it is   
                          ignored.                                                 
                                                                                   
                          G.723.1 is specified in ITU Recommendation G.723.1,      
                          Dual-rate speech coder for multimedia communications     
                          transmitting at 5.3 and 6.3 kbit/s. This Recommendation  
                          specifies a coded representation that can be used for    
                          compressing the speech signal component of multi-media   
                          services at a very low bit rate. Audio is encoded in 30  
                          ms frames. A G.723.1 frame can be one of three sizes: 24 
                          octets (6.3 kb/s frame), 20 octets (5.3 kb/s frame), or  
                          4 octets. These 4-octet frames are called SID frames     
                          (Silence Insertion Descriptor) and are used to specify   
                          comfort noise parameters.                                
                                                                                   
                          This codec always uses the RTP transport.                
                                                                                   
                          If a specific configuration is set in the                
                          EpSpecificCodecG723.VoiceEnable variable and the         
                          EpSpecificCodecG723.EnableConfig variable is set to      
                          'Enable', then it overrides the current default          
                          configuration.                                           
                                                                                   
                                                                                   
                          "                                                        
            DEFVAL        { enable }                                               
            ::= { codecG723Group 100 }                                             
                                                                                   
        -- Scalar:  Default G.723 Priority Configuration for Voice                 
                                                                                   
        defaultCodecG723VoicePriority OBJECT-TYPE                                  
            SYNTAX        Unsigned32 ( 0..10 )                                     
            MAX-ACCESS    read-write                                               
            STATUS        current                                                  
            DESCRIPTION " Default G.723 Priority Configuration for Voice           
                                                                                   
                          Indicates the priority of this voice codec versus the    
                          other voice codecs. The voice codec with the highest     
                          priority will be offered first when an outgoing call is  
                          initiated. This priority is not used in incoming calls.  
                                                                                   
                          The application uses an internal order for codecs with   
                          the same priority.                                       
                                                                                   
                          10 is the highest priority and 0 the lowest.             
                                                                                   
                          If a specific configuration is set in the                
                          EpSpecificCodecG723.VoicePriority variable and the       
                          EpSpecificCodecG723.EnableConfig variable is set to      
                          'Enable', then it overrides the current default          
                          configuration.                                           
                                                                                   
                                                                                   
                          "                                                        
            DEFVAL        { 0 }                                                    
            ::= { codecG723Group 200 }                                             
                                                                                   
        -- Scalar:  Default G.723.1 Bit Rate                                       
                                                                                   
        defaultCodecG723Bitrate OBJECT-TYPE                                        
            SYNTAX        INTEGER { rate53kbps(100) , rate63kbps(200) }            
            MAX-ACCESS    read-write                                               
            STATUS        current                                                  
            DESCRIPTION " Default G.723.1 Bit Rate                                 
                                                                                   
                          Indicates the G.723.1 bit rate to use.                   
                                                                                   
                          If a specific configuration is set in the                
                          EpSpecificCodecG723.Bitrate variable and the             
                          EpSpecificCodecG723.EnableConfig variable is set to      
                          'Enable', then it overrides the current default          
                          configuration.                                           
                                                                                   
                                                                                   
                          "                                                        
            DEFVAL        { rate63kbps }                                           
            ::= { codecG723Group 300 }                                             
                                                                                   
        -- Scalar:  Default G.723.1 Minimum Packetization Period Configuration     
                                                                                   
        defaultCodecG723MinPTime OBJECT-TYPE                                       
            SYNTAX        Unsigned32 ( 30..30 | 60..60 )                           
            MAX-ACCESS    read-write                                               
            STATUS        current                                                  
            DESCRIPTION " Default G.723.1 Minimum Packetization Period             
                          Configuration                                            
                                                                                   
                          Lower boundary for the packetization period of the given 
                          codec.                                                   
                                                                                   
                          G.723 -> (30 ms|60 ms)                                   
                                                                                   
                          This value is expressed in ms, with increments of 30 ms. 
                                                                                   
                          If a specific configuration is set in the                
                          EpSpecificCodecG723.MinPTime variable and the            
                          EpSpecificCodecG723.EnableConfig variable is set to      
                          'Enable', then it overrides the current default          
                          configuration.                                           
                                                                                   
                                                                                   
                          "                                                        
            DEFVAL        { 30 }                                                   
            ::= { codecG723Group 400 }                                             
                                                                                   
        -- Scalar:  Default G.723.1 Maximum Packetization Period Configuration     
                                                                                   
        defaultCodecG723MaxPTime OBJECT-TYPE                                       
            SYNTAX        Unsigned32 ( 30..30 | 60..60 )                           
            MAX-ACCESS    read-write                                               
            STATUS        current                                                  
            DESCRIPTION " Default G.723.1 Maximum Packetization Period             
                          Configuration                                            
                                                                                   
                          Upper boundary for the packetization period of the given 
                          codec.                                                   
                                                                                   
                          G.723 -> (30 ms|60 ms)                                   
                                                                                   
                          This value is expressed in ms, with increments of 30 ms. 
                                                                                   
                          If a specific configuration is set in the                
                          EpSpecificCodecG723.MaxPTime variable and the            
                          EpSpecificCodecG723.EnableConfig variable is set to      
                          'Enable', then it overrides the current default          
                          configuration.                                           
                                                                                   
                                                                                   
                          "                                                        
            DEFVAL        { 60 }                                                   
            ::= { codecG723Group 500 }                                             
                                                                                   
        -- ************************************************************************
                                                                                   
        -- Table:  Endpoint Specific Voice Codec Configuration                     
                                                                                   
        -- ************************************************************************
                                                                                   
        epSpecificCodecG723Table OBJECT-TYPE                                       
            SYNTAX                    SEQUENCE OF EpSpecificCodecG723Entry         
            MAX-ACCESS                not-accessible                               
            STATUS                    current                                      
            DESCRIPTION             " Endpoint Specific Voice Codec Configuration  
                                                                                   
                                      Endpoint specific configuration.             
                                      "                                            
            ::= { codecG723Group 700 }                                             
                                                                                   
                                                                                   
            epSpecificCodecG723Entry OBJECT-TYPE                                   
                SYNTAX        EpSpecificCodecG723Entry                             
                MAX-ACCESS    not-accessible                                       
                STATUS        current                                              
                DESCRIPTION " A row in the Endpoint Specific Voice Codec           
                              Configuration . "                                    
                INDEX         {                                                    
                                  epId                                             
                              }                                                    
                                                                                   
                ::= { epSpecificCodecG723Table 1 }                                 
                                                                                   
            EpSpecificCodecG723Entry ::= SEQUENCE                                  
            {                                                                      
                epId            OCTET STRING,                                      
                enableConfig    MxEnableState,                                     
                voiceEnable     MxEnableState,                                     
                voicePriority   Unsigned32,                                        
                bitrate         INTEGER,                                           
                minPTime        Unsigned32,                                        
                maxPTime        Unsigned32                                         
            }                                                                      
                                                                                   
            -- Index:  Endpoint Identifier                                         
                                                                                   
            epSpecificCodecG723EpId OBJECT-TYPE                                    
                SYNTAX         OCTET STRING                                        
                MAX-ACCESS     read-only                                           
                STATUS         current                                             
                DESCRIPTION  " Endpoint Identifier                                 
                                                                                   
                               String that identifies an endpoint in other tables. 
                               "                                                   
                ::= { epSpecificCodecG723Entry 100 }                               
                                                                                   
            -- Columnar:  Enable Configuration                                     
                                                                                   
            epSpecificCodecG723EnableConfig OBJECT-TYPE                            
                SYNTAX        MxEnableState                                        
                MAX-ACCESS    read-write                                           
                STATUS        current                                              
                DESCRIPTION " Enable Configuration                                 
                                                                                   
                              Defines the configuration to use for a specific      
                              endpoint.                                            
                                                                                   
                                * Disable: The endpoint uses the default           
                                  configuration as defined in the                  
                                  DefaultCodecG723VoiceEnable,                     
                                  DefaultCodecG723VoicePriority,                   
                                  DefaultCodecG723Bitrate,                         
                                  DefaultCodecG723MinPTime,                        
                                  DefaultCodecG723MaxPTime and                     
                                  DefaultCodecG723VoiceActivityDetection           
                                  variables.                                       
                                * Enable: The endpoint uses the specific           
                                  configuration as defined in the                  
                                  EpSpecificCodecG723.VoiceEnable,                 
                                  EpSpecificCodecG723.VoicePriority,               
                                  EpSpecificCodecG723.Bitrate,                     
                                  EpSpecificCodecG723.MinPTime,                    
                                  EpSpecificCodecG723.MaxPTime and                 
                                  EpSpecificCodecG723.VoiceActivityDetection       
                                  variables.                                       
                                                                                   
                                                                                   
                              "                                                    
                DEFVAL        { disable }                                          
                ::= { epSpecificCodecG723Entry 200 }                               
                                                                                   
            -- Columnar:  Endpoint Specific G.723.1 Enable/Disable Configuration   
            -- for Voice                                                              
                                                                                   
            epSpecificCodecG723VoiceEnable OBJECT-TYPE                             
                SYNTAX        MxEnableState                                        
                MAX-ACCESS    read-write                                           
                STATUS        current                                              
                DESCRIPTION " Endpoint Specific G.723.1 Enable/Disable             
                              Configuration for Voice                              
                                                                                   
                              Indicates if the codec can be selected for voice     
                              transmission. If enabled, this codec is listed as    
                              supported for this specific endpoint. Otherwise, it  
                              is ignored.                                          
                                                                                   
                              G.723.1 is specified in ITU Recommendation G.723.1,  
                              Dual-rate speech coder for multimedia communications 
                              transmitting at 5.3 and 6.3 kbit/s. This             
                              Recommendation specifies a coded representation that 
                              can be used for compressing the speech signal        
                              component of multi-media services at a very low bit  
                              rate. Audio is encoded in 30 ms frames. A G.723.1    
                              frame can be one of three sizes: 24 octets (6.3 kb/s 
                              frame), 20 octets (5.3 kb/s frame), or 4 octets.     
                              These 4-octet frames are called SID frames (Silence  
                              Insertion Descriptor) and are used to specify        
                              comfort noise parameters.                            
                                                                                   
                              This codec always uses the RTP transport.            
                                                                                   
                              This configuration overrides the default             
                              configuration set in the DefaultCodecG723VoiceEnable 
                              variable if the EpSpecificCodecG723.EnableConfig     
                              variable is set to 'Enable'.                         
                                                                                   
                                                                                   
                              "                                                    
                DEFVAL        { enable }                                           
                ::= { epSpecificCodecG723Entry 300 }                               
                                                                                   
            -- Columnar:  Endpoint Specific G.723 Priority Configuration for Voice 
                                                                                   
            epSpecificCodecG723VoicePriority OBJECT-TYPE                           
                SYNTAX        Unsigned32 ( 0..10 )                                 
                MAX-ACCESS    read-write                                           
                STATUS        current                                              
                DESCRIPTION " Endpoint Specific G.723 Priority Configuration for   
                              Voice                                                
                                                                                   
                              Indicates the priority of this voice codec versus    
                              the other voice codecs. The voice codec with the     
                              highest priority will be offered first when an       
                              outgoing call is initiated. This priority is not     
                              used in incoming calls.                              
                                                                                   
                              The application uses an internal order for codecs    
                              with the same priority.                              
                                                                                   
                              10 is the highest priority and 0 the lowest.         
                                                                                   
                              This configuration overrides the default             
                              configuration set in the                             
                              DefaultCodecG723VoicePriority variable if the        
                              EpSpecificCodecG723.EnableConfig variable is set to  
                              'Enable'.                                            
                                                                                   
                                                                                   
                              "                                                    
                DEFVAL        { 0 }                                                
                ::= { epSpecificCodecG723Entry 400 }                               
                                                                                   
            -- Columnar:  Endpoint Specific G.723.1 Bit Rate                       
                                                                                   
            epSpecificCodecG723Bitrate OBJECT-TYPE                                 
                SYNTAX        INTEGER { rate53kbps(100) , rate63kbps(200) }        
                MAX-ACCESS    read-write                                           
                STATUS        current                                              
                DESCRIPTION " Endpoint Specific G.723.1 Bit Rate                   
                                                                                   
                              Indicates the G.723.1 bit rate to use.               
                                                                                   
                              This configuration overrides the default             
                              configuration set in the DefaultCodecG723Bitrate     
                              variable if the EpSpecificCodecG723.EnableConfig     
                              variable is set to 'Enable'.                         
                                                                                   
                                                                                   
                              "                                                    
                DEFVAL        { rate63kbps }                                       
                ::= { epSpecificCodecG723Entry 500 }                               
                                                                                   
            -- Columnar:  Endpoint Specific G.723.1 Minimum Packetization Period   
            -- Configuration                                                          
                                                                                   
            epSpecificCodecG723MinPTime OBJECT-TYPE                                
                SYNTAX        Unsigned32 ( 30..30 | 60..60 )                       
                MAX-ACCESS    read-write                                           
                STATUS        current                                              
                DESCRIPTION " Endpoint Specific G.723.1 Minimum Packetization      
                              Period Configuration                                 
                                                                                   
                              Lower boundary for the packetization period of the   
                              given codec.                                         
                                                                                   
                              G.723 -> (30 ms|60 ms)                               
                                                                                   
                              This value is expressed in ms, with increments of 30 
                              ms.                                                  
                                                                                   
                              This configuration overrides the default             
                              configuration set in the DefaultCodecG723MinPTime    
                              variable if the EpSpecificCodecG723.EnableConfig     
                              variable is set to 'Enable'.                         
                                                                                   
                                                                                   
                              "                                                    
                DEFVAL        { 30 }                                               
                ::= { epSpecificCodecG723Entry 600 }                               
                                                                                   
            -- Columnar:  Endpoint Specific G.723.1 Maximum Packetization Period   
            -- Configuration                                                          
                                                                                   
            epSpecificCodecG723MaxPTime OBJECT-TYPE                                
                SYNTAX        Unsigned32 ( 30..30 | 60..60 )                       
                MAX-ACCESS    read-write                                           
                STATUS        current                                              
                DESCRIPTION " Endpoint Specific G.723.1 Maximum Packetization      
                              Period Configuration                                 
                                                                                   
                              Upper boundary for the packetization period of the   
                              given codec.                                         
                                                                                   
                              G.723 -> (30 ms|60 ms)                               
                                                                                   
                              This value is expressed in ms, with increments of 30 
                              ms.                                                  
                                                                                   
                              This configuration overrides the default             
                              configuration set in the DefaultCodecG723MaxPTime    
                              variable if the EpSpecificCodecG723.EnableConfig     
                              variable is set to 'Enable'.                         
                                                                                   
                                                                                   
                              "                                                    
                DEFVAL        { 60 }                                               
                ::= { epSpecificCodecG723Entry 700 }                               
                                                                                   
                                                                                   
        -- End of table:  Endpoint Specific Voice Codec Configuration              
                                                                                   
    -- End of group:  G.723 Voice Codec Group                                      
                                                                                   
    -- ***************************************************************************
                                                                                   
    -- Group:  G.726 Voice Codec Group                                             
                                                                                   
    -- ***************************************************************************
                                                                                   
    codecG726Group OBJECT IDENTIFIER                                               
        ::= { codecGroup 500 }                                                     
                                                                                   
                                                                                   
        -- ************************************************************************
                                                                                   
        -- Group:  G.726 16 Kbit/s Voice Codec Group                               
                                                                                   
        -- ************************************************************************
                                                                                   
        codecG726r16kbpsGroup OBJECT IDENTIFIER                                    
            ::= { codecG726Group 100 }                                             
                                                                                   
                                                                                   
            -- Scalar:  Default G.726 16 Kbit/s Enable/Disable Configuration       
                                                                                   
            defaultCodecG726r16kbpsVoiceEnable OBJECT-TYPE                         
                SYNTAX        MxEnableState                                        
                MAX-ACCESS    read-write                                           
                STATUS        current                                              
                DESCRIPTION " Default G.726 16 Kbit/s Enable/Disable Configuration 
                                                                                   
                              Indicates if the codec can be selected for voice     
                              transmission. If enabled, this codec is listed as    
                              supported for this specific endpoint. Otherwise, it  
                              is ignored.                                          
                                                                                   
                                * Disable: Disable G.726 at 16 kbps.               
                                * Enable: Enable G.726 at 16 kbps.                 
                                                                                   
                              G.726 is specified in ITU-T Recommendation G.726: 40,
                              32, 24, 16 kbit/s adaptive differential pulse code   
                              modulation (ADPCM). It describes the algorithm       
                              recommended for conversion of a single 64 kbit/s     
                              A-law or U-law PCM channel encoded at 8000 samples/  
                              sec to and from a 40, 32, 24, or 16 kbit/s channel.  
                              The conversion is applied to the PCM stream using an 
                              Adaptive Differential Pulse Code Modulation (ADPCM)  
                              transcoding technique.                               
                                                                                   
                              This codec uses generic voice activity detection. See
                              the DefaultCodecGenericVoiceActivityDetection and    
                              EpSpecificCodec.GenericVoiceActivityDetection        
                              variables.                                           
                                                                                   
                              This codec always uses the RTP transport.            
                                                                                   
                              If a specific configuration is set in the            
                              EpSpecificCodecG726r16kbps.VoiceEnable variable and  
                              the EpSpecificCodecG726r16kbps.EnableConfig variable 
                              is set to 'Enable', then it overrides the current    
                              default configuration.                               
                                                                                   
                                                                                   
                              "                                                    
                DEFVAL        { disable }                                          
                ::= { codecG726r16kbpsGroup 100 }                                  
                                                                                   
            -- Scalar:  Default G.726 16 Kbit/s Priority Configuration for Voice   
                                                                                   
            defaultCodecG726r16kbpsVoicePriority OBJECT-TYPE                       
                SYNTAX        Unsigned32 ( 0..10 )                                 
                MAX-ACCESS    read-write                                           
                STATUS        current                                              
                DESCRIPTION " Default G.726 16 Kbit/s Priority Configuration for   
                              Voice                                                
                                                                                   
                              Indicates the priority of this voice codec versus the
                              other voice codecs. The voice codec with the highest 
                              priority will be offered first when an outgoing call 
                              is initiated. This priority is not used in incoming  
                              calls.                                               
                                                                                   
                              The application uses an internal order for codecs    
                              with the same priority.                              
                                                                                   
                              10 is the highest priority and 0 the lowest.         
                                                                                   
                              If a specific configuration is set in the            
                              EpSpecificCodecG726r16kbps.VoicePriority variable and
                              the EpSpecificCodecG726r16kbps.EnableConfig variable 
                              is set to 'Enable', then it overrides the current    
                              default configuration.                               
                                                                                   
                                                                                   
                              "                                                    
                DEFVAL        { 0 }                                                
                ::= { codecG726r16kbpsGroup 200 }                                  
                                                                                   
            -- Scalar:  Default G.726 16 Kbit/s Payload Type                       
                                                                                   
            defaultCodecG726r16kbpsPayloadType OBJECT-TYPE                         
                SYNTAX        Unsigned32 ( 96..127 )                               
                MAX-ACCESS    read-write                                           
                STATUS        current                                              
                DESCRIPTION " Default G.726 16 Kbit/s Payload Type                 
                                                                                   
                              Determines the actual RTP dynamic payload type used  
                              in an initial offer when enabling G.726 at 16 kbps   
                              for voice and data transmission.                     
                                                                                   
                              The payload types available are as per RFC 3551.     
                                                                                   
                              If a specific configuration is set in the            
                              EpSpecificCodecG726r16kbps.PayloadType variable and  
                              the EpSpecificCodecG726r16kbps.EnableConfig variable 
                              is set to 'Enable', then it overrides the current    
                              default configuration.                               
                                                                                   
                                                                                   
                              "                                                    
                DEFVAL        { 97 }                                               
                ::= { codecG726r16kbpsGroup 300 }                                  
                                                                                   
            -- Scalar:  Default G.726 16 Kbit/s Minimum Packetization Period       
            -- Configuration                                                          
                                                                                   
            defaultCodecG726r16kbpsMinPTime OBJECT-TYPE                            
                SYNTAX        Unsigned32 ( 10..30 )                                
                MAX-ACCESS    read-write                                           
                STATUS        current                                              
                DESCRIPTION " Default G.726 16 Kbit/s Minimum Packetization Period 
                              Configuration                                        
                                                                                   
                              Lower boundary for the packetization period of the   
                              given codec.                                         
                                                                                   
                              G.726 at 16 kbps -> (10 ms..30 ms)                   
                                                                                   
                              This value is expressed in ms, with increments of 1  
                              ms.                                                  
                                                                                   
                              If a specific configuration is set in the            
                              EpSpecificCodecG726r16kbps.MinPTime variable and the 
                              EpSpecificCodecG726r16kbps.EnableConfig variable is  
                              set to 'Enable', then it overrides the current       
                              default configuration.                               
                                                                                   
                                                                                   
                              "                                                    
                DEFVAL        { 10 }                                               
                ::= { codecG726r16kbpsGroup 400 }                                  
                                                                                   
            -- Scalar:  Default G.726 16 Kbit/s Maximum Packetization Period       
            -- Configuration                                                          
                                                                                   
            defaultCodecG726r16kbpsMaxPTime OBJECT-TYPE                            
                SYNTAX        Unsigned32 ( 10..30 )                                
                MAX-ACCESS    read-write                                           
                STATUS        current                                              
                DESCRIPTION " Default G.726 16 Kbit/s Maximum Packetization Period 
                              Configuration                                        
                                                                                   
                              Upper boundary for the packetization period of the   
                              given codec.                                         
                                                                                   
                              G.726 at 16 kbps -> (10 ms..30 ms)                   
                                                                                   
                              This value is expressed in ms, with increments of 1  
                              ms.                                                  
                                                                                   
                              If a specific configuration is set in the            
                              EpSpecificCodecG726r16kbps.MaxPTime variable and the 
                              EpSpecificCodecG726r16kbps.EnableConfig variable is  
                              set to 'Enable', then it overrides the current       
                              default configuration.                               
                                                                                   
                                                                                   
                              "                                                    
                DEFVAL        { 30 }                                               
                ::= { codecG726r16kbpsGroup 500 }                                  
                                                                                   
            -- *********************************************************************
                                                                                   
            -- Table:  Endpoint Specific Voice Codec Configuration                 
                                                                                   
            -- *********************************************************************
                                                                                   
            epSpecificCodecG726r16kbpsTable OBJECT-TYPE                            
                SYNTAX                 SEQUENCE OF EpSpecificCodecG726r16kbpsEntry 
                MAX-ACCESS             not-accessible                              
                STATUS                 current                                     
                DESCRIPTION          " Endpoint Specific Voice Codec Configuration 
                                                                                   
                                       Endpoint specific configuration.            
                                       "                                           
                ::= { codecG726r16kbpsGroup 600 }                                  
                                                                                   
                                                                                   
                epSpecificCodecG726r16kbpsEntry OBJECT-TYPE                        
                    SYNTAX        EpSpecificCodecG726r16kbpsEntry                  
                    MAX-ACCESS    not-accessible                                   
                    STATUS        current                                          
                    DESCRIPTION " A row in the Endpoint Specific Voice Codec       
                                  Configuration . "                                
                    INDEX         {                                                
                                      epId                                         
                                  }                                                
                                                                                   
                    ::= { epSpecificCodecG726r16kbpsTable 1 }                      
                                                                                   
                EpSpecificCodecG726r16kbpsEntry ::= SEQUENCE                       
                {                                                                  
                     epId               OCTET STRING,                              
                     enableConfig       MxEnableState,                             
                     voiceEnable        MxEnableState,                             
                     voicePriority      Unsigned32,                                
                     payloadType        Unsigned32,                                
                     minPTime           Unsigned32,                                
                     maxPTime           Unsigned32                                 
                }                                                                  
                                                                                   
                -- Index:  Endpoint Identifier                                     
                                                                                   
                epSpecificCodecG726r16kbpsEpId OBJECT-TYPE                         
                    SYNTAX        OCTET STRING                                     
                    MAX-ACCESS    read-only                                        
                    STATUS        current                                          
                    DESCRIPTION " Endpoint Identifier                              
                                                                                   
                                  String that identifies an endpoint in other      
                                  tables.                                          
                                  "                                                
                    ::= { epSpecificCodecG726r16kbpsEntry 100 }                    
                                                                                   
                -- Columnar:  Enable Configuration                                 
                                                                                   
                epSpecificCodecG726r16kbpsEnableConfig OBJECT-TYPE                 
                    SYNTAX        MxEnableState                                    
                    MAX-ACCESS    read-write                                       
                    STATUS        current                                          
                    DESCRIPTION " Enable Configuration                             
                                                                                   
                                  Defines the configuration to use for a specific  
                                  endpoint.                                        
                                                                                   
                                    * Disable: The endpoint uses the default       
                                      configuration as defined in the              
                                      DefaultCodecG726r16kbpsVoiceEnable,          
                                      DefaultCodecG726r16kbpsVoicePriority,        
                                      DefaultCodecG726r16kbpsPayloadType,          
                                      DefaultCodecG726r16kbpsMinPTime and          
                                      DefaultCodecG726r16kbpsMaxPTime variables.   
                                    * Enable: The endpoint uses the specific       
                                      configuration as defined in the              
                                      EpSpecificCodecG726r16kbps.VoiceEnable,      
                                      EpSpecificCodecG726r16kbps.VoicePriority,    
                                      EpSpecificCodecG726r16kbps.PayloadType,      
                                      EpSpecificCodecG726r16kbps.MinPTime and      
                                      EpSpecificCodecG726r16kbps.MaxPTime          
                                      variables.                                   
                                                                                   
                                                                                   
                                  "                                                
                    DEFVAL        { disable }                                      
                    ::= { epSpecificCodecG726r16kbpsEntry 200 }                    
                                                                                   
                -- Columnar:  Endpoint Specific G.726 16 Kbit/s Enable/Disable     
                -- Configuration for Voice                                            
                                                                                   
                epSpecificCodecG726r16kbpsVoiceEnable OBJECT-TYPE                  
                    SYNTAX        MxEnableState                                    
                    MAX-ACCESS    read-write                                       
                    STATUS        current                                          
                    DESCRIPTION " Endpoint Specific G.726 16 Kbit/s Enable/Disable 
                                  Configuration for Voice                          
                                                                                   
                                  Indicates if the codec can be selected for voice 
                                  transmission. If enabled, this codec is listed as
                                  supported for this specific endpoint. Otherwise, 
                                  it is ignored.                                   
                                                                                   
                                    * Disable: Disable G.726 at 16 kbps.           
                                    * Enable: Enable G.726 at 16 kbps.             
                                                                                   
                                  G.726 is specified in ITU-T Recommendation G.726:
                                  40, 32, 24, 16 kbit/s adaptive differential pulse
                                  code modulation (ADPCM). It describes the        
                                  algorithm recommended for conversion of a single 
                                  64 kbit/s A-law or U-law PCM channel encoded at  
                                  8000 samples/sec to and from a 40, 32, 24, or 16 
                                  kbit/s channel. The conversion is applied to the 
                                  PCM stream using an Adaptive Differential Pulse  
                                  Code Modulation (ADPCM) transcoding technique.   
                                                                                   
                                  This codec uses generic voice activity detection.
                                  See the DefaultCodecGenericVoiceActivityDetection
                                  and EpSpecificCodec.GenericVoiceActivityDetection
                                  variables.                                       
                                                                                   
                                  This codec always uses the RTP transport.        
                                                                                   
                                  This configuration overrides the default         
                                  configuration set in the                         
                                  DefaultCodecG726r16kbpsVoiceEnable variable if   
                                  the EpSpecificCodecG726r16kbps.EnableConfig      
                                  variable is set to 'Enable'.                     
                                                                                   
                                                                                   
                                  "                                                
                    DEFVAL        { disable }                                      
                    ::= { epSpecificCodecG726r16kbpsEntry 300 }                    
                                                                                   
                -- Columnar:  Endpoint Specific G.726 16 Kbit/s Priority           
                -- Configuration for Voice                                            
                                                                                   
                epSpecificCodecG726r16kbpsVoicePriority OBJECT-TYPE                
                    SYNTAX        Unsigned32 ( 0..10 )                             
                    MAX-ACCESS    read-write                                       
                    STATUS        current                                          
                    DESCRIPTION " Endpoint Specific G.726 16 Kbit/s Priority       
                                  Configuration for Voice                          
                                                                                   
                                  Indicates the priority of this voice codec versus
                                  the other voice codecs. The voice codec with the 
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG726r16kbpsVoicePriority variable if 
                                  the EpSpecificCodecG726r16kbps.EnableConfig      
                                  variable is set to 'Enable'.                     
                                                                                   
                                                                                   
                                  "                                                
                    DEFVAL        { 0 }                                            
                    ::= { epSpecificCodecG726r16kbpsEntry 400 }                    
                                                                                   
                -- Columnar:  Endpoint Specific G.726 16 Kbit/s Payload Type       
                                                                                   
                epSpecificCodecG726r16kbpsPayloadType OBJECT-TYPE                  
                    SYNTAX        Unsigned32 ( 96..127 )                           
                    MAX-ACCESS    read-write                                       
                    STATUS        current                                          
                    DESCRIPTION " Endpoint Specific G.726 16 Kbit/s Payload Type   
                                                                                   
                                  Determines the actual RTP dynamic payload type   
                                  used in an initial offer when enabling G.726 at  
                                  16 kbps for voice and data transmission.         
                                                                                   
                                  The payload types available are as per RFC 3551. 
                                                                                   
                                  This configuration overrides the default         
                                  configuration set in the                         
                                  DefaultCodecG726r16kbpsPayloadType variable if   
                                  the EpSpecificCodecG726r16kbps.EnableConfig      
                                  variable is set to 'Enable'.                     
                                                                                   
                                                                                   
                                  "                                                
                    DEFVAL        { 97 }                                           
                    ::= { epSpecificCodecG726r16kbpsEntry 500 }                    
                                                                                   
                -- Columnar:  Endpoint Specific G.726 16 Kbit/s Minimum            
                -- Packetization Period Configuration                                 
                                                                                   
                epSpecificCodecG726r16kbpsMinPTime OBJECT-TYPE                     
                    SYNTAX        Unsigned32 ( 10..30 )                            
                    MAX-ACCESS    read-write                                       
                    STATUS        current                                          
                    DESCRIPTION " Endpoint Specific G.726 16 Kbit/s Minimum        
                                  Packetization Period Configuration               
                                                                                   
                                  Lower boundary for the packetization period of   
                                  the given codec.                                 
                                                                                   
                                  G.726 at 16 kbps -> (10 ms..30 ms)               
                                                                                   
                                  This value is expressed in ms, with increments of
                                  1 ms.                                            
                                                                                   
                                  This configuration overrides the default         
                                  configuration set in the                         
                                  DefaultCodecG726r16kbpsMinPTime variable if the  
                                  EpSpecificCodecG726r16kbps.EnableConfig variable 
                                  is set to 'Enable'.                              
                                                                                   
                                                                                   
                                  "                                                
                    DEFVAL        { 10 }                                           
                    ::= { epSpecificCodecG726r16kbpsEntry 600 }                    
                                                                                   
                -- Columnar:  Endpoint Specific G.726 16 Kbit/s Maximum            
                -- Packetization Period Configuration                                 
                                                                                   
                epSpecificCodecG726r16kbpsMaxPTime OBJECT-TYPE                     
                    SYNTAX        Unsigned32 ( 10..30 )                            
                    MAX-ACCESS    read-write                                       
                    STATUS        current                                          
                    DESCRIPTION " Endpoint Specific G.726 16 Kbit/s Maximum        
                                  Packetization Period Configuration               
                                                                                   
                                  Upper boundary for the packetization period of   
                                  the given codec.                                 
                                                                                   
                                  G.726 at 16 kbps -> (10 ms..30 ms)               
                                                                                   
                                  This value is expressed in ms, with increments of
                                  1 ms.                                            
                                                                                   
                                  This configuration overrides the default         
                                  configuration set in the                         
                                  DefaultCodecG726r16kbpsMaxPTime variable if the  
                                  EpSpecificCodecG726r16kbps.EnableConfig variable 
                                  is set to 'Enable'.                              
                                                                                   
                                                                                   
                                  "                                                
                    DEFVAL        { 30 }                                           
                    ::= { epSpecificCodecG726r16kbpsEntry 700 }                    
                                                                                   
                                                                                   
            -- End of table:  Endpoint Specific Voice Codec Configuration          
                                                                                   
        -- End of group:  G.726 16 Kbit/s Voice Codec Group                        
                                                                                   
        -- ************************************************************************
                                                                                   
        -- Group:  G.726 24 Kbit/s Voice Codec Group                               
                                                                                   
        --                                                                         
        -- ************************************************************************
                                                                                   
        codecG726r24kbpsGroup OBJECT IDENTIFIER                                    
            ::= { codecG726Group 200 }                                             
                                                                                   
                                                                                   
            -- Scalar:  Default G.726 24 Kbit/s Enable/Disable Configuration for   
            -- Voice                                                                  
                                                                                   
            defaultCodecG726r24kbpsVoiceEnable OBJECT-TYPE                         
                SYNTAX        MxEnableState                                        
                MAX-ACCESS    read-write                                           
                STATUS        current                                              
                DESCRIPTION " Default G.726 24 Kbit/s Enable/Disable Configuration 
                              for Voice                                            
                                                                                   
                              Indicates if the codec can be selected for voice     
                              transmission. If enabled, this codec is listed as    
                              supported for this specific endpoint. Otherwise, it  
                              is ignored.                                          
                                                                                   
                                * Disable: Disable G.726 at 24 kbps.               
                                * Enable: Enable G.726 at 24 kbps.                 
                                                                                   
                              G.726 is specified in ITU-T Recommendation G.726: 40,
                              32, 24, 16 kbit/s adaptive differential pulse code   
                              modulation (ADPCM). It describes the algorithm       
                              recommended for conversion of a single 64 kbit/s     
                              A-law or U-law PCM channel encoded at 8000 samples/  
                              sec to and from a 40, 32, 24, or 16 kbit/s channel.  
                              The conversion is applied to the PCM stream using an 
                              Adaptive Differential Pulse Code Modulation (ADPCM)  
                              transcoding technique.                               
                                                                                   
                              This codec uses generic voice activity detection. See
                              the DefaultCodecGenericVoiceActivityDetection and    
                              EpSpecificCodec.GenericVoiceActivityDetection        
                              variables.                                           
                                                                                   
                              This codec always uses the RTP transport.            
                                                                                   
                              If a specific configuration is set in the            
                              EpSpecificCodecG726r24kbps.VoiceEnable variable and  
                              the EpSpecificCodecG726r24kbps.EnableConfig variable 
                              is set to 'Enable', then it overrides the current    
                              default configuration.                               
                                                                                   
                                                                                   
                              "                                                    
                DEFVAL        { disable }                                          
                ::= { codecG726r24kbpsGroup 100 }                                  
                                                                                   
            -- Scalar:  Default G.726 24 Kbit/s Priority Configuration for Voice   
                                                                                   
            defaultCodecG726r24kbpsVoicePriority OBJECT-TYPE                       
                SYNTAX        Unsigned32 ( 0..10 )                                 
                MAX-ACCESS    read-write                                           
                STATUS        current                                              
                DESCRIPTION " Default G.726 24 Kbit/s Priority Configuration for   
                              Voice                                                
                                                                                   
                              Indicates the priority of this voice codec versus the
                              other voice codecs. The voice codec with the highest 
                              priority will be offered first when an outgoing call 
                              is initiated. This priority is not used in incoming  
                              calls.                                               
                                                                                   
                              The application uses an internal order for codecs    
                              with the same priority.                              
                                                                                   
                              10 is the highest priority and 0 the lowest.         
                                                                                   
                              If a specific configuration is set in the            
                              EpSpecificCodecG726r24kbps.VoicePriority variable and
                              the EpSpecificCodecG726r24kbps.EnableConfig variable 
                              is set to 'Enable', then it overrides the current    
                              default configuration.                               
                                                                                   
                                                                                   
                              "                                                    
                DEFVAL        { 0 }                                                
                ::= { codecG726r24kbpsGroup 200 }                                  
                                                                                   
            -- Scalar:  Default G.726 24 Kbit/s Payload Type                       
                                                                                   
            defaultCodecG726r24kbpsPayloadType OBJECT-TYPE                         
                SYNTAX        Unsigned32 ( 96..127 )                               
                MAX-ACCESS    read-write                                           
                STATUS        current                                              
                DESCRIPTION " Default G.726 24 Kbit/s Payload Type                 
                                                                                   
                              When enabling G.726 at 24 kbps for voice and data    
                              transmission, this variable determines the actual RTP
                              dynamic payload type used in an initial offer.       
                                                                                   
                              The payload types available are as per RFC 3551.     
                                                                                   
                              If a specific configuration is set in the            
                              EpSpecificCodecG726r24kbps.PayloadType variable and  
                              the EpSpecificCodecG726r24kbps.EnableConfig variable 
                              is set to 'Enable', then it overrides the current    
                              default configuration.                               
                                                                                   
                                                                                   
                              "                                                    
                DEFVAL        { 98 }                                               
                ::= { codecG726r24kbpsGroup 300 }                                  
                                                                                   
            -- Scalar:  Default G.726 24 Kbit/s Minimum Packetization Period       
            -- Configuration                                                          
                                                                                   
            defaultCodecG726r24kbpsMinPTime OBJECT-TYPE                            
                SYNTAX        Unsigned32 ( 10..30 )                                
                MAX-ACCESS    read-write                                           
                STATUS        current                                              
                DESCRIPTION " Default G.726 24 Kbit/s Minimum Packetization Period 
                              Configuration                                        
                                                                                   
                              Lower boundary for the packetization period of the   
                              given codec.                                         
                                                                                   
                              G.726 at 24 kbps -> (10 ms..30 ms)                   
                                                                                   
                              This value is expressed in ms, with increments of 1  
                              ms.                                                  
                                                                                   
                              If a specific configuration is set in the            
                              EpSpecificCodecG726r24kbps.MinPTime variable and the 
                              EpSpecificCodecG726r24kbps.EnableConfig variable is  
                              set to 'Enable', then it overrides the current       
                              default configuration.                               
                                                                                   
                                                                                   
                              "                                                    
                DEFVAL        { 10 }                                               
                ::= { codecG726r24kbpsGroup 400 }                                  
                                                                                   
            -- Scalar:  Default G.726 24 Kbit/s Maximum Packetization Period       
            -- Configuration                                                          
                                                                                   
            defaultCodecG726r24kbpsMaxPTime OBJECT-TYPE                            
                SYNTAX        Unsigned32 ( 10..30 )                                
                MAX-ACCESS    read-write                                           
                STATUS        current                                              
                DESCRIPTION " Default G.726 24 Kbit/s Maximum Packetization Period 
                              Configuration                                        
                                                                                   
                              Upper boundary for the packetization period of the   
                              given codec.                                         
                                                                                   
                              G.726 at 24 kbps -> (10 ms..30 ms)                   
                                                                                   
                              This value is expressed in ms, with increments of 1  
                              ms.                                                  
                                                                                   
                              If a specific configuration is set in the            
                              EpSpecificCodecG726r24kbps.MaxPTime variable and the 
                              EpSpecificCodecG726r24kbps.EnableConfig variable is  
                              set to 'Enable', then it overrides the current       
                              default configuration.                               
                                                                                   
                                                                                   
                              "                                                    
                DEFVAL        { 30 }                                               
                ::= { codecG726r24kbpsGroup 500 }                                  
                                                                                   
            -- *********************************************************************
                                                                                   
            -- Table:  Endpoint Specific Voice Codec Configuration                 
                                                                                   
            -- *********************************************************************
                                                                                   
            epSpecificCodecG726r24kbpsTable OBJECT-TYPE                            
                SYNTAX                 SEQUENCE OF EpSpecificCodecG726r24kbpsEntry 
                MAX-ACCESS             not-accessible                              
                STATUS                 current                                     
                DESCRIPTION          " Endpoint Specific Voice Codec Configuration 
                                                                                   
                                       Endpoint specific configuration.            
                                       "                                           
                ::= { codecG726r24kbpsGroup 600 }                                  
                                                                                   
                                                                                   
                epSpecificCodecG726r24kbpsEntry OBJECT-TYPE                        
                    SYNTAX        EpSpecificCodecG726r24kbpsEntry                  
                    MAX-ACCESS    not-accessible                                   
                    STATUS        current                                          
                    DESCRIPTION " A row in the Endpoint Specific Voice Codec       
                                  Configuration . "                                
                    INDEX         {                                                
                                      epId                                         
                                  }                                                
                                                                                   
                    ::= { epSpecificCodecG726r24kbpsTable 1 }                      
                                                                                   
                EpSpecificCodecG726r24kbpsEntry ::= SEQUENCE                       
                {                                                                  
                     epId               OCTET STRING,                              
                     enableConfig       MxEnableState,                             
                     voiceEnable        MxEnableState,                             
                     voicePriority      Unsigned32,                                
                     payloadType        Unsigned32,                                
                     minPTime           Unsigned32,                                
                     maxPTime           Unsigned32                                 
                }                                                                  
                                                                                   
                -- Index:  Endpoint Identifier                                     
                                                                                   
                epSpecificCodecG726r24kbpsEpId OBJECT-TYPE                         
                    SYNTAX        OCTET STRING                                     
                    MAX-ACCESS    read-only                                        
                    STATUS        current                                          
                    DESCRIPTION " Endpoint Identifier                              
                                                                                   
                                  String that identifies an endpoint in other      
                                  tables.                                          
                                  "                                                
                    ::= { epSpecificCodecG726r24kbpsEntry 100 }                    
                                                                                   
                -- Columnar:  Enable Configuration                                 
                                                                                   
                epSpecificCodecG726r24kbpsEnableConfig OBJECT-TYPE                 
                    SYNTAX        MxEnableState                                    
                    MAX-ACCESS    read-write                                       
                    STATUS        current                                          
                    DESCRIPTION " Enable Configuration                             
                                                                                   
                                  Defines the configuration to use for a specific  
                                  endpoint.                                        
                                                                                   
                                    * Disable: The endpoint uses the default       
                                      configuration as defined in the              
                                      DefaultCodecG726r24kbpsVoiceEnable,          
                                      DefaultCodecG726r24kbpsVoicePriority,        
                                      DefaultCodecG726r24kbpsPayloadType,          
                                      DefaultCodecG726r24kbpsMinPTime and          
                                      DefaultCodecG726r24kbpsMaxPTime variables.   
                                    * Enable: The endpoint uses the specific       
                                      configuration as defined in the              
                                      EpSpecificCodecG726r24kbps.VoiceEnable,      
                                      EpSpecificCodecG726r24kbps.VoicePriority,    
                                      EpSpecificCodecG726r24kbps.PayloadType,      
                                      EpSpecificCodecG726r24kbps.MinPTime and      
                                      EpSpecificCodecG726r24kbps.MaxPTime variable.
                                                                                   
                                                                                   
                                  "                                                
                    DEFVAL        { disable }                                      
                    ::= { epSpecificCodecG726r24kbpsEntry 200 }                    
                                                                                   
                -- Columnar:  Endpoint Specific G.726 24 Kbit/s Enable/Disable     
                -- Configuration for Voice                                            
                                                                                   
                epSpecificCodecG726r24kbpsVoiceEnable OBJECT-TYPE                  
                    SYNTAX        MxEnableState                                    
                    MAX-ACCESS    read-write                                       
                    STATUS        current                                          
                    DESCRIPTION " Endpoint Specific G.726 24 Kbit/s Enable/Disable 
                                  Configuration for Voice                          
                                                                                   
                                  Indicates if the codec can be selected for voice 
                                  transmission. If enabled, this codec is listed as
                                  supported for this specific endpoint. Otherwise, 
                                  it is ignored.                                   
                                                                                   
                                    * Disable: Disable G.726 at 24 kbps.           
                                    * Enable: Enable G.726 at 24 kbps.             
                                                                                   
                                  G.726 is specified in ITU-T Recommendation G.726:
                                  40, 32, 24, 16 kbit/s adaptive differential pulse
                                  code modulation (ADPCM). It describes the        
                                  algorithm recommended for conversion of a single 
                                  64 kbit/s A-law or U-law PCM channel encoded at  
                                  8000 samples/sec to and from a 40, 32, 24, or 16 
                                  kbit/s channel. The conversion is applied to the 
                                  PCM stream using an Adaptive Differential Pulse  
                                  Code Modulation (ADPCM) transcoding technique.   
                                                                                   
                                  This codec uses generic voice activity detection.
                                  See the DefaultCodecGenericVoiceActivityDetection
                                  and EpSpecificCodec.GenericVoiceActivityDetection
                                  variables.                                       
                                                                                   
                                  This codec always uses the RTP transport.        
                                                                                   
                                  This configuration overrides the default         
                                  configuration set in the                         
                                  DefaultCodecG726r24kbpsVoiceEnable variable if   
                                  the EpSpecificCodecG726r24kbps.EnableConfig      
                                  variable is set to 'Enable'.                     
                                                                                   
                                                                                   
                                  "                                                
                    DEFVAL        { disable }                                      
                    ::= { epSpecificCodecG726r24kbpsEntry 300 }                    
                                                                                   
                -- Columnar:  Endpoint Specific G.726 24 Kbit/s Priority           
                -- Configuration for Voice                                            
                                                                                   
                epSpecificCodecG726r24kbpsVoicePriority OBJECT-TYPE                
                    SYNTAX        Unsigned32 ( 0..10 )                             
                    MAX-ACCESS    read-write                                       
                    STATUS        current                                          
                    DESCRIPTION " Endpoint Specific G.726 24 Kbit/s Priority       
                                  Configuration for Voice                          
                                                                                   
                                  Indicates the priority of this voice codec versus
                                  the other voice codecs. The voice codec with the 
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG726r24kbpsVoicePriority variable if 
                                  the EpSpecificCodecG726r24kbps.EnableConfig      
                                  variable is set to 'Enable'.                     
                                                                                   
                                                                                   
                                  "                                                
                    DEFVAL        { 0 }                                            
                    ::= { epSpecificCodecG726r24kbpsEntry 400 }                    
                                                                                   
                -- Columnar:  Endpoint Specific G.726 24 Kbit/s Payload Type       
                                                                                   
                epSpecificCodecG726r24kbpsPayloadType OBJECT-TYPE                  
                    SYNTAX        Unsigned32 ( 96..127 )                           
                    MAX-ACCESS    read-write                                       
                    STATUS        current                                          
                    DESCRIPTION " Endpoint Specific G.726 24 Kbit/s Payload Type   
                                                                                   
                                  Determines the actual RTP dynamic payload type   
                                  used in an initial offer when enabling G.726 at  
                                  24 kbps for voice and data transmission.         
                                                                                   
                                  The payload types available are as per RFC 3551. 
                                                                                   
                                  This configuration overrides the default         
                                  configuration set in the                         
                                  DefaultCodecG726r24kbpsPayloadType variable if   
                                  the EpSpecificCodecG726r24kbps.EnableConfig      
                                  variable is set to 'Enable'.                     
                                                                                   
                                                                                   
                                  "                                                
                    DEFVAL        { 98 }                                           
                    ::= { epSpecificCodecG726r24kbpsEntry 500 }                    
                                                                                   
                -- Columnar:  Endpoint Specific G.726 24 Kbit/s Minimum            
                -- Packetization Period Configuration                                 
                                                                                   
                epSpecificCodecG726r24kbpsMinPTime OBJECT-TYPE                     
                    SYNTAX        Unsigned32 ( 10..30 )                            
                    MAX-ACCESS    read-write                                       
                    STATUS        current                                          
                    DESCRIPTION " Endpoint Specific G.726 24 Kbit/s Minimum        
                                  Packetization Period Configuration               
                                                                                   
                                  Lower boundary for the packetization period of   
                                  the given codec.                                 
                                                                                   
                                  G.726 at 24 kbps -> (10 ms..30 ms)               
                                                                                   
                                  This value is expressed in ms, with increments of
                                  1 ms.                                            
                                                                                   
                                  This configuration overrides the default         
                                  configuration set in the                         
                                  DefaultCodecG726r24kbpsMinPTime variable if the  
                                  EpSpecificCodecG726r24kbps.EnableConfig variable 
                                  is set to 'Enable'.                              
                                                                                   
                                                                                   
                                  "                                                
                    DEFVAL        { 10 }                                           
                    ::= { epSpecificCodecG726r24kbpsEntry 600 }                    
                                                                                   
                -- Columnar:  Endpoint Specific G.726 24 Kbit/s Maximum            
                -- Packetization Period Configuration                                 
                                                                                   
                epSpecificCodecG726r24kbpsMaxPTime OBJECT-TYPE                     
                    SYNTAX        Unsigned32 ( 10..30 )                            
                    MAX-ACCESS    read-write                                       
                    STATUS        current                                          
                    DESCRIPTION " Endpoint Specific G.726 24 Kbit/s Maximum        
                                  Packetization Period Configuration               
                                                                                   
                                  Upper boundary for the packetization period of   
                                  the given codec.                                 
                                                                                   
                                  G.726 at 24 kbps -> (10 ms..30 ms)               
                                                                                   
                                  This value is expressed in ms, with increments of
                                  1 ms.                                            
                                                                                   
                                  This configuration overrides the default         
                                  configuration set in the                         
                                  DefaultCodecG726r24kbpsMaxPTime variable if the  
                                  EpSpecificCodecG726r24kbps.EnableConfig variable 
                                  is set to 'Enable'.                              
                                                                                   
                                                                                   
                                  "                                                
                    DEFVAL        { 30 }                                           
                    ::= { epSpecificCodecG726r24kbpsEntry 700 }                    
                                                                                   
                                                                                   
            -- End of table:  Endpoint Specific Voice Codec Configuration          
                                                                                   
        -- End of group:  G.726 24 Kbit/s Voice Codec Group                        
                                                                                   
        -- ************************************************************************
                                                                                   
        -- Group:  G.726 32 Kbit/s Voice Codec Group                               
                                                                                   
        --                                                                         
        -- ************************************************************************
                                                                                   
        codecG726r32kbpsGroup OBJECT IDENTIFIER                                    
            ::= { codecG726Group 300 }                                             
                                                                                   
                                                                                   
            -- Scalar:  Default G.726 32 Kbit/s Enable/Disable Configuration for   
            -- Voice                                                                  
                                                                                   
            defaultCodecG726r32kbpsVoiceEnable OBJECT-TYPE                         
                SYNTAX        MxEnableState                                        
                MAX-ACCESS    read-write                                           
                STATUS        current                                              
                DESCRIPTION " Default G.726 32 Kbit/s Enable/Disable Configuration 
                              for Voice                                            
                                                                                   
                              Indicates if the codec can be selected for voice     
                              transmission. If enabled, this codec is listed as    
                              supported for this specific endpoint. Otherwise, it  
                              is ignored.                                          
                                                                                   
                                * Disable: Disable G.726 at 32 kbps.               
                                * Enable: Enable G.726 at 32 kbps.                 
                                                                                   
                              G.726 is specified in ITU-T Recommendation G.726: 40,
                              32, 24, 16 kbit/s adaptive differential pulse code   
                              modulation (ADPCM). It describes the algorithm       
                              recommended for conversion of a single 64 kbit/s     
                              A-law or U-law PCM channel encoded at 8000 samples/  
                              sec to and from a 40, 32, 24, or 16 kbit/s channel.  
                              The conversion is applied to the PCM stream using an 
                              Adaptive Differential Pulse Code Modulation (ADPCM)  
                              transcoding technique.                               
                                                                                   
                              This codec uses generic voice activity detection. See
                              the DefaultCodecGenericVoiceActivityDetection and    
                              EpSpecificCodec.GenericVoiceActivityDetection        
                              variables.                                           
                                                                                   
                              This codec always uses the RTP transport.            
                                                                                   
                                                                                   
                              "                                                    
                DEFVAL        { disable }                                          
                ::= { codecG726r32kbpsGroup 100 }                                  
                                                                                   
            -- Scalar:  Default G.726 32 Kbit/s Priority Configuration for Voice   
                                                                                   
            defaultCodecG726r32kbpsVoicePriority OBJECT-TYPE                       
                SYNTAX        Unsigned32 ( 0..10 )                                 
                MAX-ACCESS    read-write                                           
                STATUS        current                                              
                DESCRIPTION " Default G.726 32 Kbit/s Priority Configuration for   
                              Voice                                                
                                                                                   
                              Indicates the priority of this voice codec versus the
                              other voice codecs. The voice codec with the à       
                              highest priority will be offered first when an       
                              outgoing call is initiated. This priority is not used
                              in incoming calls.                                   
                                                                                   
                              The application uses an internal order for codecs    
                              with the same priority.                              
                                                                                   
                              10 is the highest priority and 0 the lowest.         
                                                                                   
                              If a specific configuration is set in the            
                              EpSpecificCodecG726r32kbps.VoiceEnable variable and  
                              the EpSpecificCodecG726r32kbps.EnableConfig variable 
                              is set to 'Enable', then it overrides the current    
                              default configuration.                               
                                                                                   
                                                                                   
                              "                                                    
                DEFVAL        { 0 }                                                
                ::= { codecG726r32kbpsGroup 200 }                                  
                                                                                   
            -- Scalar:  Default G.726 32 Kbit/s Enable/Disable Configuration for   
            -- Data                                                                   
                                                                                   
            defaultCodecG726r32kbpsDataEnable OBJECT-TYPE                          
                SYNTAX        MxEnableState                                        
                MAX-ACCESS    read-write                                           
                STATUS        current                                              
                DESCRIPTION " Default G.726 32 Kbit/s Enable/Disable Configuration 
                              for Data                                             
                                                                                   
                              Indicates if the codec can be selected for data      
                              transmission. If enabled, this codec is listed as    
                              supported for this specific endpoint. Otherwise, it  
                              is ignored.                                          
                                                                                   
                                * Disable: Disable G.726 at 32 kbps.               
                                * Enable: Enable G.726 at 32 kbps.                 
                                                                                   
                              If a specific configuration is set in the            
                              EpSpecificCodecG726r32kbps.DataEnable variable and   
                              the EpSpecificCodecG726r32kbps.EnableConfig variable 
                              is set to 'Enable', then it overrides the current    
                              default configuration.                               
                                                                                   
                                                                                   
                              "                                                    
                DEFVAL        { disable }                                          
                ::= { codecG726r32kbpsGroup 300 }                                  
                                                                                   
            -- Scalar:  Default G.726 32 Kbit/s Priority Configuration for Data    
                                                                                   
            defaultCodecG726r32kbpsDataPriority OBJECT-TYPE                        
                SYNTAX        Unsigned32 ( 0..10 )                                 
                MAX-ACCESS    read-write                                           
                STATUS        current                                              
                DESCRIPTION " Default G.726 32 Kbit/s Priority Configuration for   
                              Data                                                 
                                                                                   
                              Indicates the priority of this data codec versus the 
                              other data codecs. The data codec with the highest   
                              priority will be offered first when an outgoing call 
                              is initiated. This priority is not used in incoming  
                              calls.                                               
                                                                                   
                              The application uses an internal order for codecs    
                              with the same priority.                              
                                                                                   
                              10 is the highest priority and 0 the lowest.         
                                                                                   
                              If a specific configuration is set in the            
                              EpSpecificCodecG726r32kbps.DataPriority variable and 
                              the EpSpecificCodecG726r32kbps.EnableConfig variable 
                              is set to 'Enable', then it overrides the current    
                              default configuration.                               
                                                                                   
                                                                                   
                              "                                                    
                DEFVAL        { 0 }                                                
                ::= { codecG726r32kbpsGroup 400 }                                  
                                                                                   
            -- Scalar:  Default G.726 32 Kbit/s Payload Type                       
                                                                                   
            defaultCodecG726r32kbpsPayloadType OBJECT-TYPE                         
                SYNTAX        Unsigned32 ( 96..127 )                               
                MAX-ACCESS    read-write                                           
                STATUS        current                                              
                DESCRIPTION " Default G.726 32 Kbit/s Payload Type                 
                                                                                   
                              Determines the actual RTP dynamic payload type used  
                              in an initial offer when enabling G.726 at 32 kbps   
                              for voice and data transmission.                     
                                                                                   
                              The payload types available are as per RFC 3551.     
                                                                                   
                              If a specific configuration is set in the            
                              EpSpecificCodecG726r32kbps.PayloadType variable and  
                              the EpSpecificCodecG726r32kbps.EnableConfig variable 
                              is set to 'Enable', then it overrides the current    
                              default configuration.                               
                                                                                   
                                                                                   
                              "                                                    
                DEFVAL        { 99 }                                               
                ::= { codecG726r32kbpsGroup 500 }                                  
                                                                                   
            -- Scalar:  Default G.726 32 Kbit/s Minimum Packetization Period       
            -- Configuration                                                          
                                                                                   
            defaultCodecG726r32kbpsMinPTime OBJECT-TYPE                            
                SYNTAX        Unsigned32 ( 10..30 )                                
                MAX-ACCESS    read-write                                           
                STATUS        current                                              
                DESCRIPTION " Default G.726 32 Kbit/s Minimum Packetization Period 
                              Configuration                                        
                                                                                   
                              Lower boundary for the packetization period of the   
                              given codec.                                         
                                                                                   
                              G.726 at 32 kbps -> (10 ms..30 ms)                   
                                                                                   
                              This value is expressed in ms, with increments of 1  
                              ms.                                                  
                                                                                   
                              If a specific configuration is set in the            
                              EpSpecificCodecG726r32kbps.MinPTime variable and the 
                              EpSpecificCodecG726r32kbps.EnableConfig variable is  
                              set to 'Enable', then it overrides the current       
                              default configuration.                               
                                                                                   
                                                                                   
                              "                                                    
                DEFVAL        { 10 }                                               
                ::= { codecG726r32kbpsGroup 600 }                                  
                                                                                   
            -- Scalar:  Default G.726 32 Kbit/s Maximum Packetization Period       
            -- Configuration                                                          
                                                                                   
            defaultCodecG726r32kbpsMaxPTime OBJECT-TYPE                            
                SYNTAX        Unsigned32 ( 10..30 )                                
                MAX-ACCESS    read-write                                           
                STATUS        current                                              
                DESCRIPTION " Default G.726 32 Kbit/s Maximum Packetization Period 
                              Configuration                                        
                                                                                   
                              Upper boundary for the packetization period of the   
                              given codec.                                         
                                                                                   
                              G.726 at 32 kbps -> (10 ms..30 ms)                   
                                                                                   
                              This value is expressed in ms, with increments of 1  
                              ms.                                                  
                                                                                   
                              If a specific configuration is set in the            
                              EpSpecificCodecG726r32kbps.MaxPTime variable and the 
                              EpSpecificCodecG726r32kbps.EnableConfig variable is  
                              set to 'Enable', then it overrides the current       
                              default configuration.                               
                                                                                   
                                                                                   
                              "                                                    
                DEFVAL        { 30 }                                               
                ::= { codecG726r32kbpsGroup 700 }                                  
                                                                                   
            -- *********************************************************************
                                                                                   
            -- Table:  Endpoint Specific Voice Codec Configuration                 
                                                                                   
            -- *********************************************************************
                                                                                   
            epSpecificCodecG726r32kbpsTable OBJECT-TYPE                            
                SYNTAX                 SEQUENCE OF EpSpecificCodecG726r32kbpsEntry 
                MAX-ACCESS             not-accessible                              
                STATUS                 current                                     
                DESCRIPTION          " Endpoint Specific Voice Codec Configuration 
                                                                                   
                                       Endpoint specific configuration.            
                                       "                                           
                ::= { codecG726r32kbpsGroup 800 }                                  
                                                                                   
                                                                                   
                epSpecificCodecG726r32kbpsEntry OBJECT-TYPE                        
                    SYNTAX        EpSpecificCodecG726r32kbpsEntry                  
                    MAX-ACCESS    not-accessible                                   
                    STATUS        current                                          
                    DESCRIPTION " A row in the Endpoint Specific Voice Codec       
                                  Configuration . "                                
                    INDEX         {                                                
                                      epId                                         
                                  }                                                
                                                                                   
                    ::= { epSpecificCodecG726r32kbpsTable 1 }                      
                                                                                   
                EpSpecificCodecG726r32kbpsEntry ::= SEQUENCE                       
                {                                                                  
                     epId               OCTET STRING,                              
                     enableConfig       MxEnableState,                             
                     voiceEnable        MxEnableState,                             
                     voicePriority      Unsigned32,                                
                     dataEnable         MxEnableState,                             
                     dataPriority       Unsigned32,                                
                     payloadType        Unsigned32,                                
                     minPTime           Unsigned32,                                
                     maxPTime           Unsigned32                                 
                }                                                                  
                                                                                   
                -- Index:  Endpoint Identifier                                     
                                                                                   
                epSpecificCodecG726r32kbpsEpId OBJECT-TYPE                         
                    SYNTAX        OCTET STRING                                     
                    MAX-ACCESS    read-only                                        
                    STATUS        current                                          
                    DESCRIPTION " Endpoint Identifier                              
                                                                                   
                                  String that identifies an endpoint in other      
                                  tables.                                          
                                  "                                                
                    ::= { epSpecificCodecG726r32kbpsEntry 100 }                    
                                                                                   
                -- Columnar:  Enable Configuration                                 
                                                                                   
                epSpecificCodecG726r32kbpsEnableConfig OBJECT-TYPE                 
                    SYNTAX        MxEnableState                                    
                    MAX-ACCESS    read-write                                       
                    STATUS        current                                          
                    DESCRIPTION " Enable Configuration                             
                                                                                   
                                  Defines the configuration to use for a specific  
                                  endpoint.                                        
                                                                                   
                                    * Disable: The endpoint uses the default       
                                      configuration as defined in the              
                                      DefaultCodecG726r32kbpsVoiceEnable,          
                                      DefaultCodecG726r32kbpsVoicePriority,        
                                      DefaultCodecG726r32kbpsDataEnable,           
                                      DefaultCodecG726r32kbpsDataPriority,         
                                      DefaultCodecG726r32kbpsPayloadType,          
                                      DefaultCodecG726r32kbpsMinPTime and          
                                      DefaultCodecG726r32kbpsMaxPTime variables.   
                                    * Enable: The endpoint uses the specific       
                                      configuration as defined in the              
                                      EpSpecificCodecG726r32kbps.VoiceEnable,      
                                      EpSpecificCodecG726r32kbps.VoicePriority,    
                                      EpSpecificCodecG726r32kbps.DataEnable,       
                                      EpSpecificCodecG726r32kbps.DataPriority,     
                                      EpSpecificCodecG726r32kbps.PayloadType,      
                                      EpSpecificCodecG726r32kbps.MinPTime and      
                                      EpSpecificCodecG726r32kbps.MaxPTime          
                                      variables.                                   
                                                                                   
                                                                                   
                                  "                                                
                    DEFVAL        { disable }                                      
                    ::= { epSpecificCodecG726r32kbpsEntry 200 }                    
                                                                                   
                -- Columnar:  Endpoint Specific G.726 32 Kbit/s Enable/Disable     
                -- Configuration for Voice                                            
                                                                                   
                epSpecificCodecG726r32kbpsVoiceEnable OBJECT-TYPE                  
                    SYNTAX        MxEnableState                                    
                    MAX-ACCESS    read-write                                       
                    STATUS        current                                          
                    DESCRIPTION " Endpoint Specific G.726 32 Kbit/s Enable/Disable 
                                  Configuration for Voice                          
                                                                                   
                                  Indicates if the codec can be selected for voice 
                                  transmission. If enabled, this codec is listed as
                                  supported for this specific endpoint. Otherwise, 
                                  it is ignored.                                   
                                                                                   
                                    * Disable: Disable G.726 at 32 kbps.           
                                    * Enable: Enable G.726 at 32 kbps.             
                                                                                   
                                  G.726 is specified in ITU-T Recommendation G.726:
                                  40, 32, 24, 16 kbit/s adaptive differential pulse
                                  code modulation (ADPCM). It describes the        
                                  algorithm recommended for conversion of a single 
                                  64 kbit/s A-law or U-law PCM channel encoded at  
                                  8000 samples/sec to and from a 40, 32, 24, or 16 
                                  kbit/s channel. The conversion is applied to the 
                                  PCM stream using an Adaptive Differential Pulse  
                                  Code Modulation (ADPCM) transcoding technique.   
                                                                                   
                                  This codec uses generic voice activity detection.
                                  See the DefaultCodecGenericVoiceActivityDetection
                                  and EpSpecificCodec.GenericVoiceActivityDetection
                                  variables.                                       
                                                                                   
                                  This codec always uses the RTP transport.        
                                                                                   
                                  This configuration overrides the default         
                                  configuration set in the                         
                                  DefaultCodecG726r32kbpsVoiceEnable variable if   
                                  the EpSpecificCodecG726r32kbps.EnableConfig      
                                  variable is set to 'Enable'.                     
                                                                                   
                                                                                   
                                  "                                                
                    DEFVAL        { disable }                                      
                    ::= { epSpecificCodecG726r32kbpsEntry 300 }                    
                                                                                   
                -- Columnar:  Endpoint Specific G.726 32 Kbit/s Priority           
                -- Configuration for Voice                                            
                                                                                   
                epSpecificCodecG726r32kbpsVoicePriority OBJECT-TYPE                
                    SYNTAX        Unsigned32 ( 0..10 )                             
                    MAX-ACCESS    read-write                                       
                    STATUS        current                                          
                    DESCRIPTION " Endpoint Specific G.726 32 Kbit/s Priority       
                                  Configuration for Voice                          
                                                                                   
                                  Indicates the priority of this voice codec versus
                                  the other voice codecs. The voice codec with the 
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG726r32kbpsVoicePriority variable if 
                                  the EpSpecificCodecG726r32kbps.EnableConfig      
                                  variable is set to 'Enable'.                     
                                                                                   
                                                                                   
                                  "                                                
                    DEFVAL        { 0 }                                            
                    ::= { epSpecificCodecG726r32kbpsEntry 400 }                    
                                                                                   
                -- Columnar:  Endpoint Specific G.726 32 Kbit/s Enable/Disable     
                -- Configuration for Data                                             
                                                                                   
                epSpecificCodecG726r32kbpsDataEnable OBJECT-TYPE                   
                    SYNTAX        MxEnableState                                    
                    MAX-ACCESS    read-write                                       
                    STATUS        current                                          
                    DESCRIPTION " Endpoint Specific G.726 32 Kbit/s Enable/Disable 
                                  Configuration for Data                           
                                                                                   
                                  Indicates if the codec can be selected for data  
                                  transmission. If enabled, this codec is listed as
                                  supported for this specific endpoint. Otherwise, 
                                  it is ignored.                                   
                                                                                   
                                    * Disable: Disable G.726 at 32 kbps.           
                                    * Enable: Enable G.726 at 32 kbps.             
                                                                                   
                                  This configuration overrides the default         
                                  configuration set in the                         
                                  DefaultCodecG726r32kbpsDataEnable variable if the
                                  EpSpecificCodecG726r32kbps.EnableConfig variable 
                                  is set to 'Enable'.                              
                                                                                   
                                                                                   
                                  "                                                
                    DEFVAL        { disable }                                      
                    ::= { epSpecificCodecG726r32kbpsEntry 500 }                    
                                                                                   
                -- Columnar:  Endpoint Specific G.726 32 Kbit/s Priority           
                -- Configuration for Data                                             
                                                                                   
                epSpecificCodecG726r32kbpsDataPriority OBJECT-TYPE                 
                    SYNTAX        Unsigned32 ( 0..10 )                             
                    MAX-ACCESS    read-write                                       
                    STATUS        current                                          
                    DESCRIPTION " Endpoint Specific G.726 32 Kbit/s Priority       
                                  Configuration for Data                           
                                                                                   
                                  Indicates the priority of this data codec versus 
                                  the other data codecs. The data codec with the   
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG726r32kbpsDataPriority variable if  
                                  the EpSpecificCodecG726r32kbps.EnableConfig      
                                  variable is set to 'Enable'.                     
                                                                                   
                                                                                   
                                  "                                                
                    DEFVAL        { 0 }                                            
                    ::= { epSpecificCodecG726r32kbpsEntry 600 }                    
                                                                                   
                -- Columnar:  Endpoint Specific G.726 32 Kbit/s Payload Type       
                                                                                   
                epSpecificCodecG726r32kbpsPayloadType OBJECT-TYPE                  
                    SYNTAX        Unsigned32 ( 96..127 )                           
                    MAX-ACCESS    read-write                                       
                    STATUS        current                                          
                    DESCRIPTION " Endpoint Specific G.726 32 Kbit/s Payload Type   
                                                                                   
                                  Determines the actual RTP dynamic payload type   
                                  used in an initial offer when enabling G.726 at  
                                  32 kbps for voice and data transmission.         
                                                                                   
                                  The payload types available are as per RFC 3551. 
                                                                                   
                                  This configuration overrides the default         
                                  configuration set in the                         
                                  DefaultCodecG726r32kbpsPayloadType variable if   
                                  the EpSpecificCodecG726r32kbps.EnableConfig      
                                  variable is set to 'Enable'.                     
                                                                                   
                                                                                   
                                  "                                                
                    DEFVAL        { 99 }                                           
                    ::= { epSpecificCodecG726r32kbpsEntry 700 }                    
                                                                                   
                -- Columnar:  Endpoint Specific G.726 32 Kbit/s Minimum            
                -- Packetization Period Configuration                                 
                                                                                   
                epSpecificCodecG726r32kbpsMinPTime OBJECT-TYPE                     
                    SYNTAX        Unsigned32 ( 10..30 )                            
                    MAX-ACCESS    read-write                                       
                    STATUS        current                                          
                    DESCRIPTION " Endpoint Specific G.726 32 Kbit/s Minimum        
                                  Packetization Period Configuration               
                                                                                   
                                  Lower boundary for the packetization period of   
                                  the given codec.                                 
                                                                                   
                                  G.726 at 32 kbps -> (10 ms..30 ms)               
                                                                                   
                                  This value is expressed in ms, with increments of
                                  1 ms.                                            
                                                                                   
                                  This configuration overrides the default         
                                  configuration set in the                         
                                  DefaultCodecG726r32kbpsMinPTime variable if the  
                                  EpSpecificCodecG726r32kbps.EnableConfig variable 
                                  is set to 'Enable'.                              
                                                                                   
                                                                                   
                                  "                                                
                    DEFVAL        { 10 }                                           
                    ::= { epSpecificCodecG726r32kbpsEntry 800 }                    
                                                                                   
                -- Columnar:  Endpoint Specific G.726 32 Kbit/s Maximum            
                -- Packetization Period Configuration                                 
                                                                                   
                epSpecificCodecG726r32kbpsMaxPTime OBJECT-TYPE                     
                    SYNTAX        Unsigned32 ( 10..30 )                            
                    MAX-ACCESS    read-write                                       
                    STATUS        current                                          
                    DESCRIPTION " Endpoint Specific G.726 32 Kbit/s Maximum        
                                  Packetization Period Configuration               
                                                                                   
                                  Upper boundary for the packetization period of   
                                  the given codec.                                 
                                                                                   
                                  G.726 at 32 kbps -> (10 ms..30 ms)               
                                                                                   
                                  This value is expressed in ms, with increments of
                                  1 ms.                                            
                                                                                   
                                  This configuration overrides the default         
                                  configuration set in the                         
                                  DefaultCodecG726r32kbpsMaxPTime variable if the  
                                  EpSpecificCodecG726r32kbps.EnableConfig variable 
                                  is set to 'Enable'.                              
                                                                                   
                                                                                   
                                  "                                                
                    DEFVAL        { 30 }                                           
                    ::= { epSpecificCodecG726r32kbpsEntry 900 }                    
                                                                                   
                                                                                   
            -- End of table:  Endpoint Specific Voice Codec Configuration          
                                                                                   
        -- End of group:  G.726 32 Kbit/s Voice Codec Group                        
                                                                                   
        -- ************************************************************************
                                                                                   
        -- Group:  G.726 40 Kbit/s Voice Codec Group                               
                                                                                   
        --                                                                         
        -- ************************************************************************
                                                                                   
        codecG726r40kbpsGroup OBJECT IDENTIFIER                                    
            ::= { codecG726Group 400 }                                             
                                                                                   
                                                                                   
            -- Scalar:  Default G.726 40 Kbit/s Enable/Disable Configuration for   
            -- Voice                                                                  
                                                                                   
            defaultCodecG726r40kbpsVoiceEnable OBJECT-TYPE                         
                SYNTAX        MxEnableState                                        
                MAX-ACCESS    read-write                                           
                STATUS        current                                              
                DESCRIPTION " Default G.726 40 Kbit/s Enable/Disable Configuration 
                              for Voice                                            
                                                                                   
                              Indicates if the codec can be selected for voice     
                              transmission. If enabled, this codec is listed as    
                              supported for this specific endpoint. Otherwise, it  
                              is ignored.                                          
                                                                                   
                                * Disable: Disable G.726 at 40 kbps.               
                                * Enable: Enable G.726 at 40 kbps.                 
                                                                                   
                              G.726 is specified in ITU-T Recommendation G.726: 40,
                              32, 24, 16 kbit/s adaptive differential pulse code   
                              modulation (ADPCM). It describes the algorithm       
                              recommended for conversion of a single 64 kbit/s     
                              A-law or U-law PCM channel encoded at 8000 samples/  
                              sec to and from a 40, 32, 24, or 16 kbit/s channel.  
                              The conversion is applied to the PCM stream using an 
                              Adaptive Differential Pulse Code Modulation (ADPCM)  
                              transcoding technique.                               
                                                                                   
                              This codec uses generic voice activity detection. See
                              the DefaultCodecGenericVoiceActivityDetection and    
                              EpSpecificCodec.GenericVoiceActivityDetection        
                              variables.                                           
                                                                                   
                              This codec always uses the RTP transport.            
                                                                                   
                              If a specific configuration is set in the            
                              EpSpecificCodecG726r40kbps.VoiceEnable variable and  
                              the EpSpecificCodecG726r40kbps.EnableConfig variable 
                              is set to 'Enable', then it overrides the current    
                              default configuration.                               
                                                                                   
                                                                                   
                              "                                                    
                DEFVAL        { disable }                                          
                ::= { codecG726r40kbpsGroup 100 }                                  
                                                                                   
            -- Scalar:  Default G.726 40 Kbit/s Priority Configuration for Voice   
                                                                                   
            defaultCodecG726r40kbpsVoicePriority OBJECT-TYPE                       
                SYNTAX        Unsigned32 ( 0..10 )                                 
                MAX-ACCESS    read-write                                           
                STATUS        current                                              
                DESCRIPTION " Default G.726 40 Kbit/s Priority Configuration for   
                              Voice                                                
                                                                                   
                              Indicates the priority of this voice codec versus the
                              other voice codecs. The voice codec with the highest 
                              priority will be offered first when an outgoing call 
                              is initiated. This priority is not used in incoming  
                              calls.                                               
                                                                                   
                              The application uses an internal order for codecs    
                              with the same priority.                              
                                                                                   
                              10 is the highest priority and 0 the lowest.         
                                                                                   
                              If a specific configuration is set in the            
                              EpSpecificCodecG726r40kbps.VoicePriority variable and
                              the EpSpecificCodecG726r40kbps.EnableConfig variable 
                              is set to 'Enable', then it overrides the current    
                              default configuration.                               
                                                                                   
                                                                                   
                              "                                                    
                DEFVAL        { 0 }                                                
                ::= { codecG726r40kbpsGroup 200 }                                  
                                                                                   
            -- Scalar:  Default G.726 40 Kbit/s Enable/Disable Configuration for   
            -- Data                                                                   
                                                                                   
            defaultCodecG726r40kbpsDataEnable OBJECT-TYPE                          
                SYNTAX        MxEnableState                                        
                MAX-ACCESS    read-write                                           
                STATUS        current                                              
                DESCRIPTION " Default G.726 40 Kbit/s Enable/Disable Configuration 
                              for Data                                             
                                                                                   
                              Indicates if the codec can be selected for data      
                              transmission. If enabled, this codec is listed as    
                              supported for this specific endpoint. Otherwise, it  
                              is ignored.                                          
                                                                                   
                                * Disable: Disable G.726 at 40 kbps.               
                                * Enable: Enable G.726 at 40 kbps.                 
                                                                                   
                              If a specific configuration is set in the            
                              EpSpecificCodecG726r40kbps.DataEnable variable and   
                              the EpSpecificCodecG726r40kbps.EnableConfig variable 
                              is set to 'Enable', then it overrides the current    
                              default configuration.                               
                                                                                   
                                                                                   
                              "                                                    
                DEFVAL        { disable }                                          
                ::= { codecG726r40kbpsGroup 300 }                                  
                                                                                   
            -- Scalar:  Default G.726 40 Kbit/s Priority Configuration for Data    
                                                                                   
            defaultCodecG726r40kbpsDataPriority OBJECT-TYPE                        
                SYNTAX        Unsigned32 ( 0..10 )                                 
                MAX-ACCESS    read-write                                           
                STATUS        current                                              
                DESCRIPTION " Default G.726 40 Kbit/s Priority Configuration for   
                              Data                                                 
                                                                                   
                              Indicates the priority of this data codec versus the 
                              other data codecs. The data codec with the highest   
                              priority will be offered first when an outgoing call 
                              is initiated. This priority is not used in incoming  
                              calls.                                               
                                                                                   
                              The application uses an internal order for codecs    
                              with the same priority.                              
                                                                                   
                              10 is the highest priority and 0 the lowest.         
                                                                                   
                              If a specific configuration is set in the            
                              EpSpecificCodecG726r40kbps.DataPriority variable and 
                              the EpSpecificCodecG726r40kbps.EnableConfig variable 
                              is set to 'Enable', then it overrides the current    
                              default configuration.                               
                                                                                   
                                                                                   
                              "                                                    
                DEFVAL        { 0 }                                                
                ::= { codecG726r40kbpsGroup 400 }                                  
                                                                                   
            -- Scalar:  Default G.726 40 Kbit/s Payload Type                       
                                                                                   
            defaultCodecG726r40kbpsPayloadType OBJECT-TYPE                         
                SYNTAX        Unsigned32 ( 96..127 )                               
                MAX-ACCESS    read-write                                           
                STATUS        current                                              
                DESCRIPTION " Default G.726 40 Kbit/s Payload Type                 
                                                                                   
                              Setermines the actual RTP dynamic payload type used  
                              in an initial offer when enabling G.726 at 40 kbps   
                              for voice and data transmission.                     
                                                                                   
                              The payload types available are as per RFC 3551.     
                                                                                   
                              If a specific configuration is set in the            
                              EpSpecificCodecG726r40kbps.PayloadType variable and  
                              the EpSpecificCodecG726r40kbps.EnableConfig variable 
                              is set to 'Enable', then it overrides the current    
                              default configuration.                               
                                                                                   
                                                                                   
                              "                                                    
                DEFVAL        { 100 }                                              
                ::= { codecG726r40kbpsGroup 500 }                                  
                                                                                   
            -- Scalar:  Default G.726 40 Kbit/s Minimum Packetization Period       
            -- Configuration                                                          
                                                                                   
            defaultCodecG726r40kbpsMinPTime OBJECT-TYPE                            
                SYNTAX        Unsigned32 ( 10..30 )                                
                MAX-ACCESS    read-write                                           
                STATUS        current                                              
                DESCRIPTION " Default G.726 40 Kbit/s Minimum Packetization Period 
                              Configuration                                        
                                                                                   
                              Lower boundary for the packetization period of the   
                              given codec.                                         
                                                                                   
                              G.726 at 40 kbps -> (10 ms..30 ms)                   
                                                                                   
                              This value is expressed in ms, with increments of 1  
                              ms.                                                  
                                                                                   
                              If a specific configuration is set in the            
                              EpSpecificCodecG726r40kbps.MinPTime variable and the 
                              EpSpecificCodecG726r40kbps.EnableConfig variable is  
                              set to 'Enable', then it overrides the current       
                              default configuration.                               
                                                                                   
                                                                                   
                              "                                                    
                DEFVAL        { 10 }                                               
                ::= { codecG726r40kbpsGroup 600 }                                  
                                                                                   
            -- Scalar:  Default G.726 40 Kbit/s Maximum Packetization Period       
            -- Configuration                                                          
                                                                                   
            defaultCodecG726r40kbpsMaxPTime OBJECT-TYPE                            
                SYNTAX        Unsigned32 ( 10..30 )                                
                MAX-ACCESS    read-write                                           
                STATUS        current                                              
                DESCRIPTION " Default G.726 40 Kbit/s Maximum Packetization Period 
                              Configuration                                        
                                                                                   
                              Upper boundary for the packetization period of the   
                              given codec.                                         
                                                                                   
                              G.726 at 40 kbps -> (10 ms..30 ms)                   
                                                                                   
                              This value is expressed in ms, with increments of 1  
                              ms.                                                  
                                                                                   
                              If a specific configuration is set in the            
                              EpSpecificCodecG726r40kbps.MaxPTime variable and the 
                              EpSpecificCodecG726r40kbps.EnableConfig variable is  
                              set to 'Enable', then it overrides the current       
                              default configuration.                               
                                                                                   
                                                                                   
                              "                                                    
                DEFVAL        { 30 }                                               
                ::= { codecG726r40kbpsGroup 700 }                                  
                                                                                   
            -- *********************************************************************
                                                                                   
            -- Table:  Endpoint Specific Voice Codec Configuration                 
                                                                                   
            -- *********************************************************************
                                                                                   
            epSpecificCodecG726r40kbpsTable OBJECT-TYPE                            
                SYNTAX                 SEQUENCE OF EpSpecificCodecG726r40kbpsEntry 
                MAX-ACCESS             not-accessible                              
                STATUS                 current                                     
                DESCRIPTION          " Endpoint Specific Voice Codec Configuration 
                                                                                   
                                       Endpoint specific configuration.            
                                       "                                           
                ::= { codecG726r40kbpsGroup 800 }                                  
                                                                                   
                                                                                   
                epSpecificCodecG726r40kbpsEntry OBJECT-TYPE                        
                    SYNTAX        EpSpecificCodecG726r40kbpsEntry                  
                    MAX-ACCESS    not-accessible                                   
                    STATUS        current                                          
                    DESCRIPTION " A row in the Endpoint Specific Voice Codec       
                                  Configuration . "                                
                    INDEX         {                                                
                                      epId                                         
                                  }                                                
                                                                                   
                    ::= { epSpecificCodecG726r40kbpsTable 1 }                      
                                                                                   
                EpSpecificCodecG726r40kbpsEntry ::= SEQUENCE                       
                {                                                                  
                     epId               OCTET STRING,                              
                     enableConfig       MxEnableState,                             
                     voiceEnable        MxEnableState,                             
                     voicePriority      Unsigned32,                                
                     dataEnable         MxEnableState,                             
                     dataPriority       Unsigned32,                                
                     payloadType        Unsigned32,                                
                     minPTime           Unsigned32,                                
                     maxPTime           Unsigned32                                 
                }                                                                  
                                                                                   
                -- Index:  Endpoint Identifier                                     
                                                                                   
                epSpecificCodecG726r40kbpsEpId OBJECT-TYPE                         
                    SYNTAX        OCTET STRING                                     
                    MAX-ACCESS    read-only                                        
                    STATUS        current                                          
                    DESCRIPTION " Endpoint Identifier                              
                                                                                   
                                  String that identifies an endpoint in other      
                                  tables.                                          
                                  "                                                
                    ::= { epSpecificCodecG726r40kbpsEntry 100 }                    
                                                                                   
                -- Columnar:  Enable Configuration                                 
                                                                                   
                epSpecificCodecG726r40kbpsEnableConfig OBJECT-TYPE                 
                    SYNTAX        MxEnableState                                    
                    MAX-ACCESS    read-write                                       
                    STATUS        current                                          
                    DESCRIPTION " Enable Configuration                             
                                                                                   
                                  Defines the configuration to use for a specific  
                                  endpoint.                                        
                                                                                   
                                    * Disable: The endpoint uses the default       
                                      configuration as defined in the              
                                      DefaultCodecG726r40kbpsVoiceEnable,          
                                      DefaultCodecG726r40kbpsVoicePriority,        
                                      DefaultCodecG726r40kbpsDataEnable,           
                                      DefaultCodecG726r40kbpsDataPriority,         
                                      DefaultCodecG726r40kbpsPayloadType,          
                                      DefaultCodecG726r40kbpsMinPTime and          
                                      DefaultCodecG726r40kbpsMaxPTime variables.   
                                    * Enable: The endpoint uses the specific       
                                      configuration as defined in the              
                                      EpSpecificCodecG726r40kbps.VoiceEnable,      
                                      EpSpecificCodecG726r40kbps.VoicePriority,    
                                      EpSpecificCodecG726r40kbps.DataEnable,       
                                      EpSpecificCodecG726r40kbps.DataPriority,     
                                      EpSpecificCodecG726r40kbps.PayloadType,      
                                      EpSpecificCodecG726r40kbps.MinPTime and      
                                      EpSpecificCodecG726r40kbps.MaxPTime variable.
                                                                                   
                                                                                   
                                  "                                                
                    DEFVAL        { disable }                                      
                    ::= { epSpecificCodecG726r40kbpsEntry 200 }                    
                                                                                   
                -- Columnar:  Endpoint Specific G.726 40 Kbit/s Enable/Disable     
                -- Configuration of Voice                                             
                                                                                   
                epSpecificCodecG726r40kbpsVoiceEnable OBJECT-TYPE                  
                    SYNTAX        MxEnableState                                    
                    MAX-ACCESS    read-write                                       
                    STATUS        current                                          
                    DESCRIPTION " Endpoint Specific G.726 40 Kbit/s Enable/Disable 
                                  Configuration of Voice                           
                                                                                   
                                  Indicates if the codec can be selected for voice 
                                  transmission. If enabled, this codec is listed as
                                  supported for this specific endpoint. Otherwise, 
                                  it is ignored.                                   
                                                                                   
                                    * Disable: Disable G.726 at 40 kbps.           
                                    * Enable: Enable G.726 at 40 kbps.             
                                                                                   
                                  G.726 is specified in ITU-T Recommendation G.726:
                                  40, 32, 24, 16 kbit/s adaptive differential pulse
                                  code modulation (ADPCM). It describes the        
                                  algorithm recommended for conversion of a single 
                                  64 kbit/s A-law or U-law PCM channel encoded at  
                                  8000 samples/sec to and from a 40, 32, 24, or 16 
                                  kbit/s channel. The conversion is applied to the 
                                  PCM stream using an Adaptive Differential Pulse  
                                  Code Modulation (ADPCM) transcoding technique.   
                                                                                   
                                  This codec uses generic voice activity detection.
                                  See the DefaultCodecGenericVoiceActivityDetection
                                  and EpSpecificCodec.GenericVoiceActivityDetection
                                  variables.                                       
                                                                                   
                                  This codec always uses the RTP transport.        
                                                                                   
                                  This configuration overrides the default         
                                  configuration set in the                         
                                  DefaultCodecG726r40kbpsVoiceEnable variable if   
                                  the EpSpecificCodecG726r40kbps.EnableConfig      
                                  variable is set to 'Enable'.                     
                                                                                   
                                                                                   
                                  "                                                
                    DEFVAL        { disable }                                      
                    ::= { epSpecificCodecG726r40kbpsEntry 300 }                    
                                                                                   
                -- Columnar:  Endpoint Specific G.726 40 Kbit/s Priority           
                -- Configuration for Voice                                            
                                                                                   
                epSpecificCodecG726r40kbpsVoicePriority OBJECT-TYPE                
                    SYNTAX        Unsigned32 ( 0..10 )                             
                    MAX-ACCESS    read-write                                       
                    STATUS        current                                          
                    DESCRIPTION " Endpoint Specific G.726 40 Kbit/s Priority       
                                  Configuration for Voice                          
                                                                                   
                                  Indicates the priority of this voice codec versus
                                  the other voice codecs. The voice codec with the 
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG726r40kbpsVoicePriority variable if 
                                  the EpSpecificCodecG726r40kbps.EnableConfig      
                                  variable is set to 'Enable'.                     
                                                                                   
                                                                                   
                                  "                                                
                    DEFVAL        { 0 }                                            
                    ::= { epSpecificCodecG726r40kbpsEntry 400 }                    
                                                                                   
                -- Columnar:  Endpoint Specific G.726 40 Kbit/s Enable/Disable     
                -- Configuration of Data                                              
                                                                                   
                epSpecificCodecG726r40kbpsDataEnable OBJECT-TYPE                   
                    SYNTAX        MxEnableState                                    
                    MAX-ACCESS    read-write                                       
                    STATUS        current                                          
                    DESCRIPTION " Endpoint Specific G.726 40 Kbit/s Enable/Disable 
                                  Configuration of Data                            
                                                                                   
                                  Indicates if the codec can be selected for data  
                                  transmission. If enabled, this codec is listed as
                                  supported for this specific endpoint. Otherwise, 
                                  it is ignored.                                   
                                                                                   
                                    * Disable: Disable G.726 at 40 kbps.           
                                    * Enable: Enable G.726 at 40 kbps.             
                                                                                   
                                  This configuration overrides the default         
                                  configuration set in the                         
                                  DefaultCodecG726r40kbpsDataEnable variable if the
                                  EpSpecificCodecG726r40kbps.EnableConfig variable 
                                  is set to 'Enable'.                              
                                                                                   
                                                                                   
                                  "                                                
                    DEFVAL        { disable }                                      
                    ::= { epSpecificCodecG726r40kbpsEntry 500 }                    
                                                                                   
                -- Columnar:  Default G.726 40 Kbit/s Priority Configuration for   
                -- Data                                                               
                                                                                   
                epSpecificCodecG726r40kbpsDataPriority OBJECT-TYPE                 
                    SYNTAX        Unsigned32 ( 0..10 )                             
                    MAX-ACCESS    read-write                                       
                    STATUS        current                                          
                    DESCRIPTION " Default G.726 40 Kbit/s Priority Configuration   
                                  for Data                                         
                                                                                   
                                  Indicates the priority of this data codec versus 
                                  the other data codecs. The data codec with the   
                                  highest priority will be offered first when an   
                                  outgoing call is initiated. This priority is not 
                                  used in incoming calls.                          
                                                                                   
                                  The application uses an internal order for codecs
                                  with the same priority.                          
                                                                                   
                                  10 is the highest priority and 0 the lowest.     
                                                                                   
                                  This configuration overrides the default         
                                  configuration set in the                         
                                  DefaultCodecG726r40kbpsDataPriority variable if  
                                  the EpSpecificCodecG726r40kbps.EnableConfig      
                                  variable is set to 'Enable'.                     
                                                                                   
                                                                                   
                                  "                                                
                    DEFVAL        { 0 }                                            
                    ::= { epSpecificCodecG726r40kbpsEntry 600 }                    
                                                                                   
                -- Columnar:  Endpoint Specific G.726 40 Kbit/s Payload Type       
                                                                                   
                epSpecificCodecG726r40kbpsPayloadType OBJECT-TYPE                  
                    SYNTAX        Unsigned32 ( 96..127 )                           
                    MAX-ACCESS    read-write                                       
                    STATUS        current                                          
                    DESCRIPTION " Endpoint Specific G.726 40 Kbit/s Payload Type   
                                                                                   
                                  Determines the actual RTP dynamic payload type   
                                  used in an initial offer when enabling G.726 at  
                                  40 kbps for voice and data transmission.         
                                                                                   
                                  The payload types available are as per RFC 3551. 
                                                                                   
                                  This configuration overrides the default         
                                  configuration set in the                         
                                  DefaultCodecG726r40kbpsPayloadType variable if   
                                  the EpSpecificCodecG726r40kbps.EnableConfig      
                                  variable is set to 'Enable'.                     
                                                                                   
                                                                                   
                                  "                                                
                    DEFVAL        { 100 }                                          
                    ::= { epSpecificCodecG726r40kbpsEntry 700 }                    
                                                                                   
                -- Columnar:  Endpoint Specific G.726 40 Kbit/s Minimum            
                -- Packetization Period Configuration                                 
                                                                                   
                epSpecificCodecG726r40kbpsMinPTime OBJECT-TYPE                     
                    SYNTAX        Unsigned32 ( 10..30 )                            
                    MAX-ACCESS    read-write                                       
                    STATUS        current                                          
                    DESCRIPTION " Endpoint Specific G.726 40 Kbit/s Minimum        
                                  Packetization Period Configuration               
                                                                                   
                                  Lower boundary for the packetization period of   
                                  the given codec.                                 
                                                                                   
                                  G.726 at 40 kbps -> (10 ms..30 ms)               
                                                                                   
                                  This value is expressed in ms, with increments of
                                  1 ms.                                            
                                                                                   
                                  This configuration overrides the default         
                                  configuration set in the                         
                                  DefaultCodecG726r40kbpsMinPTime variable if the  
                                  EpSpecificCodecG726r40kbps.EnableConfig variable 
                                  is set to 'Enable'.                              
                                                                                   
                                                                                   
                                  "                                                
                    DEFVAL        { 10 }                                           
                    ::= { epSpecificCodecG726r40kbpsEntry 800 }                    
                                                                                   
                -- Columnar:  Endpoint Specific G.726 40 Kbit/s Maximum            
                -- Packetization Period Configuration                                 
                                                                                   
                epSpecificCodecG726r40kbpsMaxPTime OBJECT-TYPE                     
                    SYNTAX        Unsigned32 ( 10..30 )                            
                    MAX-ACCESS    read-write                                       
                    STATUS        current                                          
                    DESCRIPTION " Endpoint Specific G.726 40 Kbit/s Maximum        
                                  Packetization Period Configuration               
                                                                                   
                                  Upper boundary for the packetization period of   
                                  the given codec.                                 
                                                                                   
                                  G.726 at 40 kbps -> (10 ms..30 ms)               
                                                                                   
                                  This value is expressed in ms, with increments of
                                  1 ms.                                            
                                                                                   
                                  This configuration overrides the default         
                                  configuration set in the                         
                                  DefaultCodecG726r40kbpsMaxPTime variable if the  
                                  EpSpecificCodecG726r40kbps.EnableConfig variable 
                                  is set to 'Enable'.                              
                                                                                   
                                                                                   
                                  "                                                
                    DEFVAL        { 30 }                                           
                    ::= { epSpecificCodecG726r40kbpsEntry 900 }                    
                                                                                   
                                                                                   
            -- End of table:  Endpoint Specific Voice Codec Configuration          
                                                                                   
        -- End of group:  G.726 40 Kbit/s Voice Codec Group                        
                                                                                   
    -- End of group:  G.726 Voice Codec Group                                      
                                                                                   
    -- ***************************************************************************
                                                                                   
    -- Group:  G.729 Voice Codec Group                                             
                                                                                   
    -- ***************************************************************************
                                                                                   
    codecG729Group OBJECT IDENTIFIER                                               
        ::= { codecGroup 600 }                                                     
                                                                                   
                                                                                   
        -- Scalar:  Default G.729 Enable/Disable Configuration                     
                                                                                   
        defaultCodecG729VoiceEnable OBJECT-TYPE                                    
            SYNTAX        MxEnableState                                            
            MAX-ACCESS    read-write                                               
            STATUS        current                                                  
            DESCRIPTION " Default G.729 Enable/Disable Configuration               
                                                                                   
                          Indicates if the codec can be selected for voice         
                          transmission. If enabled, this codec is listed as        
                          supported for this specific endpoint. Otherwise, it is   
                          ignored.                                                 
                                                                                   
                          G729 is specified in ITU-T Recommendation G.729, Coding  
                          of speech at 8 kbit/s using conjugate                    
                          structure-algebraic code excited linear prediction       
                          (CS-ACELP). For all data rates, the sampling frequency   
                          (and RTP timestamp clock rate) is 8000 Hz. A voice       
                          activity detector (VAD) and comfort noise generator      
                          (CNG) algorithm in Annex B of G.729 is RECOMMENDED for   
                          digital simultaneous voice and data applications and can 
                          be used in conjunction with G.729 or G.729 Annex A. A    
                          G.729 or G.729 Annex A frame contains 10 octets, while   
                          the G.729 Annex B comfort noise frame occupies 2 octets. 
                                                                                   
                          This codec always uses the RTP transport.                
                                                                                   
                          If a specific configuration is set in the                
                          EpSpecificCodecG729.VoiceEnable variable and the         
                          EpSpecificCodecG729.EnableConfig variable is set to      
                          'Enable', then it overrides the current default          
                          configuration.                                           
                                                                                   
                                                                                   
                          "                                                        
            DEFVAL        { enable }                                               
            ::= { codecG729Group 100 }                                             
                                                                                   
        -- Scalar:  Default G.729 Priority Configuration for Voice                 
                                                                                   
        defaultCodecG729VoicePriority OBJECT-TYPE                                  
            SYNTAX        Unsigned32 ( 0..10 )                                     
            MAX-ACCESS    read-write                                               
            STATUS        current                                                  
            DESCRIPTION " Default G.729 Priority Configuration for Voice           
                                                                                   
                          Indicates the priority of this voice codec versus the    
                          other voice codecs. The voice codec with the highest     
                          priority will be offered first when an outgoing call is  
                          initiated. This priority is not used in incoming calls.  
                                                                                   
                          The application uses an internal order for codecs with   
                          the same priority.                                       
                                                                                   
                          10 is the highest priority and 0 the lowest.             
                                                                                   
                          If a specific configuration is set in the                
                          EpSpecificCodecG729.VoicePriority variable and the       
                          EpSpecificCodecG729.EnableConfig variable is set to      
                          'Enable', then it overrides the current default          
                          configuration.                                           
                                                                                   
                                                                                   
                          "                                                        
            DEFVAL        { 0 }                                                    
            ::= { codecG729Group 200 }                                             
                                                                                   
        -- Scalar:  Default G.729 Minimum Packetization Period Configuration       
                                                                                   
        defaultCodecG729MinPTime OBJECT-TYPE                                       
            SYNTAX        Unsigned32 ( 20..20 | 30..30 | 40..40 | 50..50 | 60..60  
                          | 70..70 | 80..80 )                                      
            MAX-ACCESS    read-write                                               
            STATUS        current                                                  
            DESCRIPTION " Default G.729 Minimum Packetization Period Configuration 
                                                                                   
                          Lower boundary for the packetization period of the given 
                          codec.                                                   
                                                                                   
                          G.729 -> (20 ms|30 ms|40 ms|50 ms|60 ms|70 ms|80 ms)     
                                                                                   
                          This value is expressed in ms, with increments of 10 ms. 
                                                                                   
                          If a specific configuration is set in the                
                          EpSpecificCodecG729.MinPTime variable and the            
                          EpSpecificCodecG729.EnableConfig variable is set to      
                          'Enable', then it overrides the current default          
                          configuration.                                           
                                                                                   
                                                                                   
                          "                                                        
            DEFVAL        { 20 }                                                   
            ::= { codecG729Group 300 }                                             
                                                                                   
        -- Scalar:  Default G.729 Maximum Packetization Period Configuration       
                                                                                   
        defaultCodecG729MaxPTime OBJECT-TYPE                                       
            SYNTAX        Unsigned32 ( 20..20 | 30..30 | 40..40 | 50..50 | 60..60  
                          | 70..70 | 80..80 )                                      
            MAX-ACCESS    read-write                                               
            STATUS        current                                                  
            DESCRIPTION " Default G.729 Maximum Packetization Period Configuration 
                                                                                   
                          Upper boundary for the packetization period of the given 
                          codec.                                                   
                                                                                   
                          G.729 -> (20 ms|30 ms|40 ms|50 ms|60 ms|70 ms|80 ms)     
                                                                                   
                          This value is expressed in ms, with increments of 10 ms. 
                                                                                   
                          If a specific configuration is set in the                
                          EpSpecificCodecG729.MaxPTime variable and the            
                          EpSpecificCodecG729.EnableConfig variable is set to      
                          'Enable', then it overrides the current default          
                          configuration.                                           
                                                                                   
                                                                                   
                          "                                                        
            DEFVAL        { 80 }                                                   
            ::= { codecG729Group 400 }                                             
                                                                                   
        -- Scalar:  Default G.729 VAD Configuration                                
                                                                                   
        defaultCodecG729VoiceActivityDetection OBJECT-TYPE                         
            SYNTAX        MxEnableState                                            
            MAX-ACCESS    read-write                                               
            STATUS        current                                                  
            DESCRIPTION " Default G.729 VAD Configuration                          
                                                                                   
                          If Voice Activity Detection (VAD) is enabled, then       
                          speech frames are only sent during talkspurts (periods   
                          of audio activity).                                      
                                                                                   
                          During silence periods, no speech frames are sent, but   
                          Comfort Noise (CN) packets containing information about  
                          background noise may be sent in accordance with annex B  
                          of G.729.                                                
                                                                                   
                            * Disable: G.729 uses annex A only.                    
                            * Enable: G.729 annex A is used with annex B.          
                                                                                   
                          If a specific configuration is set in the                
                          EpSpecificCodecG729.VoiceActivityDetection variable and  
                          the EpSpecificCodecG729.EnableConfig variable is set to  
                          'Enable', then it overrides the current default          
                          configuration.                                           
                                                                                   
                                                                                   
                          "                                                        
            DEFVAL        { enable }                                               
            ::= { codecG729Group 500 }                                             
                                                                                   
        -- ************************************************************************
                                                                                   
        -- Table:  Endpoint Specific Voice Codec Configuration                     
                                                                                   
        -- ************************************************************************
                                                                                   
        epSpecificCodecG729Table OBJECT-TYPE                                       
            SYNTAX                    SEQUENCE OF EpSpecificCodecG729Entry         
            MAX-ACCESS                not-accessible                               
            STATUS                    current                                      
            DESCRIPTION             " Endpoint Specific Voice Codec Configuration  
                                                                                   
                                      Endpoint specific configuration.             
                                      "                                            
            ::= { codecG729Group 600 }                                             
                                                                                   
                                                                                   
            epSpecificCodecG729Entry OBJECT-TYPE                                   
                SYNTAX        EpSpecificCodecG729Entry                             
                MAX-ACCESS    not-accessible                                       
                STATUS        current                                              
                DESCRIPTION " A row in the Endpoint Specific Voice Codec           
                              Configuration . "                                    
                INDEX         {                                                    
                                  epId                                             
                              }                                                    
                                                                                   
                ::= { epSpecificCodecG729Table 1 }                                 
                                                                                   
            EpSpecificCodecG729Entry ::= SEQUENCE                                  
            {                                                                      
                epId                   OCTET STRING,                               
                enableConfig           MxEnableState,                              
                voiceEnable            MxEnableState,                              
                voicePriority          Unsigned32,                                 
                minPTime               Unsigned32,                                 
                maxPTime               Unsigned32,                                 
                voiceActivityDetection MxEnableState                               
            }                                                                      
                                                                                   
            -- Index:  Endpoint Identifier                                         
                                                                                   
            epSpecificCodecG729EpId OBJECT-TYPE                                    
                SYNTAX         OCTET STRING                                        
                MAX-ACCESS     read-only                                           
                STATUS         current                                             
                DESCRIPTION  " Endpoint Identifier                                 
                                                                                   
                               String that identifies an endpoint in other tables. 
                               "                                                   
                ::= { epSpecificCodecG729Entry 100 }                               
                                                                                   
            -- Columnar:  Enable Configuration                                     
                                                                                   
            epSpecificCodecG729EnableConfig OBJECT-TYPE                            
                SYNTAX        MxEnableState                                        
                MAX-ACCESS    read-write                                           
                STATUS        current                                              
                DESCRIPTION " Enable Configuration                                 
                                                                                   
                              Defines the configuration to use for a specific      
                              endpoint.                                            
                                                                                   
                                * Disable: The endpoint uses the default           
                                  configuration as defined in the                  
                                  DefaultCodecG729VoiceEnable,                     
                                  DefaultCodecG729VoicePriority,                   
                                  DefaultCodecG729MinPTime,                        
                                  DefaultCodecG729MaxPTime and                     
                                  DefaultCodecG729VoiceActivityDetection           
                                  variables.                                       
                                * Enable: The endpoint uses the specific           
                                  configuration as defined in the                  
                                  EpSpecificCodecG729.EnableVoice                  
                                  EpSpecificCodecG729.VoicePriority,               
                                  EpSpecificCodecG729.MinPTime,                    
                                  EpSpecificCodecG729.MaxPTime and                 
                                  EpSpecificCodecG729.VoiceActivityDetection       
                                  variables.                                       
                                                                                   
                                                                                   
                              "                                                    
                DEFVAL        { disable }                                          
                ::= { epSpecificCodecG729Entry 200 }                               
                                                                                   
            -- Columnar:  Endpoint Specific G.729 Enable/Disable Configuration for 
            -- Voice                                                                  
                                                                                   
            epSpecificCodecG729VoiceEnable OBJECT-TYPE                             
                SYNTAX        MxEnableState                                        
                MAX-ACCESS    read-write                                           
                STATUS        current                                              
                DESCRIPTION " Endpoint Specific G.729 Enable/Disable Configuration 
                              for Voice                                            
                                                                                   
                              Indicates if the codec can be selected for voice     
                              transmission. If enabled, this codec is listed as    
                              supported for this specific endpoint. Otherwise, it  
                              is ignored.                                          
                                                                                   
                              G729 is specified in ITU-T Recommendation G.729,     
                              Coding of speech at 8 kbit/s using conjugate         
                              structure-algebraic code excited linear prediction   
                              (CS-ACELP). For all data rates, the sampling         
                              frequency (and RTP timestamp clock rate) is 8000 Hz. 
                              A voice activity detector (VAD) and comfort noise    
                              generator (CNG) algorithm in Annex B of G.729 is     
                              RECOMMENDED for digital simultaneous voice and data  
                              applications and can be used in conjunction with     
                              G.729 or G.729 Annex A. A G.729 or G.729 Annex A     
                              frame contains 10 octets, while the G.729 Annex B    
                              comfort noise frame occupies 2 octets.               
                                                                                   
                              This codec always uses the RTP transport.            
                                                                                   
                              This configuration overrides the default             
                              configuration set in the DefaultCodecG729VoiceEnable 
                              variable if the EpSpecificCodecG729.EnableConfig     
                              variable is set to 'Enable'.                         
                                                                                   
                                                                                   
                              "                                                    
                DEFVAL        { enable }                                           
                ::= { epSpecificCodecG729Entry 300 }                               
                                                                                   
            -- Columnar:  Endpoint Specific G.729 Priority Configuration for Voice 
                                                                                   
            epSpecificCodecG729VoicePriority OBJECT-TYPE                           
                SYNTAX        Unsigned32 ( 0..10 )                                 
                MAX-ACCESS    read-write                                           
                STATUS        current                                              
                DESCRIPTION " Endpoint Specific G.729 Priority Configuration for   
                              Voice                                                
                                                                                   
                              Indicates the priority of this voice codec versus    
                              the other voice codecs. The voice codec with the     
                              highest priority will be offered first when an       
                              outgoing call is initiated. This priority is not     
                              used in incoming calls.                              
                                                                                   
                              The application uses an internal order for codecs    
                              with the same priority.                              
                                                                                   
                              10 is the highest priority and 0 the lowest.         
                                                                                   
                              This configuration overrides the default             
                              configuration set in the                             
                              DefaultCodecG729VoicePriority variable if the        
                              EpSpecificCodecG729.EnableConfig variable is set to  
                              'Enable'.                                            
                                                                                   
                                                                                   
                              "                                                    
                DEFVAL        { 0 }                                                
                ::= { epSpecificCodecG729Entry 400 }                               
                                                                                   
            -- Columnar:  Endpoint Specific G.729 Minimum Packetization Period     
            -- Configuration                                                          
                                                                                   
            epSpecificCodecG729MinPTime OBJECT-TYPE                                
                SYNTAX        Unsigned32 ( 20..20 | 30..30 | 40..40 | 50..50 |     
                              60..60 | 70..70 | 80..80 )                           
                MAX-ACCESS    read-write                                           
                STATUS        current                                              
                DESCRIPTION " Endpoint Specific G.729 Minimum Packetization Period 
                              Configuration                                        
                                                                                   
                              Lower boundary for the packetization period of the   
                              given codec.                                         
                                                                                   
                              G.729 -> (20 ms|30 ms|40 ms|50 ms|60 ms|70 ms|80 ms) 
                                                                                   
                              This value is expressed in ms, with increments of 10 
                              ms.                                                  
                                                                                   
                              This configuration overrides the default             
                              configuration set in the DefaultCodecG729MinPTime    
                              variable if the EpSpecificCodecG729.EnableConfig     
                              variable is set to 'Enable'.                         
                                                                                   
                                                                                   
                              "                                                    
                DEFVAL        { 20 }                                               
                ::= { epSpecificCodecG729Entry 500 }                               
                                                                                   
            -- Columnar:  Endpoint Specific G.729 Maximum Packetization Period     
            -- Configuration                                                          
                                                                                   
            epSpecificCodecG729MaxPTime OBJECT-TYPE                                
                SYNTAX        Unsigned32 ( 20..20 | 30..30 | 40..40 | 50..50 |     
                              60..60 | 70..70 | 80..80 )                           
                MAX-ACCESS    read-write                                           
                STATUS        current                                              
                DESCRIPTION " Endpoint Specific G.729 Maximum Packetization Period 
                              Configuration                                        
                                                                                   
                              Upper boundary for the packetization period of the   
                              given codec.                                         
                                                                                   
                              G.729 -> (20 ms|30 ms|40 ms|50 ms|60 ms|70 ms|80 ms) 
                                                                                   
                              This value is expressed in ms, with increments of 10 
                              ms.                                                  
                                                                                   
                              This configuration overrides the default             
                              configuration set in the DefaultCodecG729MaxPTime    
                              variable if the EpSpecificCodecG729.EnableConfig     
                              variable is set to 'Enable'.                         
                                                                                   
                                                                                   
                              "                                                    
                DEFVAL        { 80 }                                               
                ::= { epSpecificCodecG729Entry 600 }                               
                                                                                   
            -- Columnar:  Endpoint Specific G.729 VAD Configuration                
                                                                                   
            epSpecificCodecG729VoiceActivityDetection OBJECT-TYPE                  
                SYNTAX        MxEnableState                                        
                MAX-ACCESS    read-write                                           
                STATUS        current                                              
                DESCRIPTION " Endpoint Specific G.729 VAD Configuration            
                                                                                   
                              If Voice Activity Detection (VAD) is enabled, then   
                              speech frames are only sent during talkspurts        
                              (periods of audio activity).                         
                                                                                   
                              During silence periods, no speech frames are sent,   
                              but Comfort Noise (CN) packets containing            
                              information about background noise may be sent in    
                              accordance with annex B of G.729.                    
                                                                                   
                                * Disable: G.729 uses annex A only.                
                                * Enable: G.729 annex A is used with annex B.      
                                                                                   
                              This configuration overrides the default             
                              configuration set in the                             
                              DefaultCodecG729VoiceActivityDetection variable if   
                              the EpSpecificCodecG729.EnableConfig variable is set 
                              to 'Enable'.                                         
                                                                                   
                                                                                   
                              "                                                    
                DEFVAL        { enable }                                           
                ::= { epSpecificCodecG729Entry 700 }                               
                                                                                   
                                                                                   
        -- End of table:  Endpoint Specific Voice Codec Configuration              
                                                                                   
    -- End of group:  G.729 Voice Codec Group                                      
                                                                                   
    -- ***************************************************************************
                                                                                   
    -- Group:  T.38 Codec Related Configuration Group                              
                                                                                   
    -- ***************************************************************************
                                                                                   
    codecT38Group OBJECT IDENTIFIER                                                
        ::= { codecGroup 700 }                                                     
                                                                                   
                                                                                   
        -- Scalar:  Default T.38 Enable/Disable Configuration for Data             
                                                                                   
        defaultCodecT38DataEnable OBJECT-TYPE                                      
            SYNTAX        MxEnableState                                            
            MAX-ACCESS    read-write                                               
            STATUS        current                                                  
            DESCRIPTION " Default T.38 Enable/Disable Configuration for Data       
                                                                                   
                          If enabled, the T.38 protocol is used for fax            
                          transmission.                                            
                          "                                                        
            DEFVAL        { enable }                                               
            ::= { codecT38Group 100 }                                              
                                                                                   
        -- Scalar:   Default T.38 Priority Configuration for Data                  
                                                                                   
        defaultCodecT38DataPriority OBJECT-TYPE                                    
            SYNTAX        Unsigned32 ( 10..10 )                                    
            MAX-ACCESS    read-write                                               
            STATUS        current                                                  
            DESCRIPTION " Default T.38 Priority Configuration for Data             
                                                                                   
                          Indicates the priority of this data codec versus the     
                          other data codecs. The data codec with the highest       
                          priority will be offered first when an outgoing call is  
                          initiated. This priority is not used in incoming calls.  
                                                                                   
                          The application uses an internal order for codecs with   
                          the same priority.                                       
                                                                                   
                          10 is the highest priority and 0 the lowest.             
                                                                                   
                          If a specific configuration is set in the                
                          EpSpecificCodecT38.DataEnable variable and the           
                          EpSpecificCodecT38.EnableConfig variable is set to       
                          'Enable', then it overrides the current default          
                          configuration.                                           
                                                                                   
                                                                                   
                          "                                                        
            DEFVAL        { 10 }                                                   
            ::= { codecT38Group 200 }                                              
                                                                                   
        -- Scalar:  Default T.38 Protection Level                                  
                                                                                   
        defaultCodecT38RedundancyLevel OBJECT-TYPE                                 
            SYNTAX        Unsigned32 ( 1..5 )                                      
            MAX-ACCESS    read-write                                               
            STATUS        current                                                  
            DESCRIPTION " Default T.38 Protection Level                            
                                                                                   
                          Number of redundancy packets. This is the standard       
                          redundancy offered by T.38.                              
                                                                                   
                          Refer to the DefaultCodecT38FinalFramesRedundancy        
                          variable for additional T.38 reliability options.        
                                                                                   
                          If a specific configuration is set in the                
                          EpSpecificCodecT38.RedundancyLevel variable and the      
                          EpSpecificCodecT38.EnableConfig variable is set to       
                          'Enable', then it overrides the current default          
                          configuration.                                           
                                                                                   
                                                                                   
                          "                                                        
            DEFVAL        { 3 }                                                    
            ::= { codecT38Group 400 }                                              
                                                                                   
        -- Scalar:  Default T.38 Redundancy for Final Frame                        
                                                                                   
        defaultCodecT38FinalFramesRedundancy OBJECT-TYPE                           
            SYNTAX        Unsigned32 ( 0..3 )                                      
            MAX-ACCESS    read-write                                               
            STATUS        current                                                  
            DESCRIPTION " Default T.38 Redundancy for Final Frame                  
                                                                                   
                          Defines the number of times T.38 packets will be         
                          retransmitted. This only applies to the T.38 packets     
                          where the PrimaryUDPTL contains the following T.38 data  
                          type: HDLC_SIG_END, HDLC_FCS_OK_SIG_END,                 
                          HDLC_FCS_BAD_SIG_END and T4_NON_ECM_SIG_END.             
                                                                                   
                          Refer to the DefaultCodecT38ProtectionLevel variable for 
                          standard T.38 reliability options.                       
                                                                                   
                                                                                   
                          "                                                        
            DEFVAL        { 0 }                                                    
            ::= { codecT38Group 500 }                                              
                                                                                   
        -- Scalar:  Default T.38 No Signal Enable/Disable Configuration.           
                                                                                   
        defaultCodecT38NoSignalEnable OBJECT-TYPE                                  
            SYNTAX        MxEnableState                                            
            MAX-ACCESS    read-write                                               
            STATUS        current                                                  
            DESCRIPTION " Default T.38 No Signal Enable/Disable Configuration.     
                                                                                   
                          Enables/disables the sending of T.38 no-signal packets.  
                          When enabled, the unit ensures that, during a T.38 fax   
                          transmission, data is sent out at least every time the   
                          DefaultCodecT38NoSignalTimeout delay expires. In the     
                          absence of meaningful data to send, no-signal packets    
                          are output.                                              
                          "                                                        
            DEFVAL        { disable }                                              
            ::= { codecT38Group 600 }                                              
                                                                                   
        -- Scalar:  Default T.38 No Signal Timeout                                 
                                                                                   
        defaultCodecT38NoSignalTimeout OBJECT-TYPE                                 
            SYNTAX        Unsigned32 ( 1..2147483647 )                             
            MAX-ACCESS    read-write                                               
            STATUS        current                                                  
            DESCRIPTION " Default T.38 No Signal Timeout                           
                                                                                   
                          The period, in seconds, at which no-signal packets are   
                          sent during a T.38 transmission, in the absence of valid 
                          data.                                                    
                          "                                                        
            DEFVAL        { 1 }                                                    
            ::= { codecT38Group 700 }                                              
                                                                                   
        -- ************************************************************************
                                                                                   
        -- Table:  Endpoint Specific Voice Codec Configuration                     
                                                                                   
        -- ************************************************************************
                                                                                   
        epSpecificCodecT38Table OBJECT-TYPE                                        
            SYNTAX             SEQUENCE OF EpSpecificCodecT38Entry                 
            MAX-ACCESS         not-accessible                                      
            STATUS             current                                             
            DESCRIPTION      " Endpoint Specific Voice Codec Configuration         
                                                                                   
                               Endpoint specific configuration.                    
                               "                                                   
            ::= { codecT38Group 800 }                                              
                                                                                   
                                                                                   
            epSpecificCodecT38Entry OBJECT-TYPE                                    
                SYNTAX        EpSpecificCodecT38Entry                              
                MAX-ACCESS    not-accessible                                       
                STATUS        current                                              
                DESCRIPTION " A row in the Endpoint Specific Voice Codec           
                              Configuration . "                                    
                INDEX         {                                                    
                                  epId                                             
                              }                                                    
                                                                                   
                ::= { epSpecificCodecT38Table 1 }                                  
                                                                                   
            EpSpecificCodecT38Entry ::= SEQUENCE                                   
            {                                                                      
                 epId             OCTET STRING,                                    
                 enableConfig     MxEnableState,                                   
                 dataEnable       MxEnableState,                                   
                 dataPriority     Unsigned32,                                      
                 redundancyLevel  Unsigned32                                       
            }                                                                      
                                                                                   
            -- Index:  Endpoint Identifier                                         
                                                                                   
            epSpecificCodecT38EpId OBJECT-TYPE                                     
                SYNTAX         OCTET STRING                                        
                MAX-ACCESS     read-only                                           
                STATUS         current                                             
                DESCRIPTION  " Endpoint Identifier                                 
                                                                                   
                               String that identifies an endpoint in other tables. 
                               "                                                   
                ::= { epSpecificCodecT38Entry 100 }                                
                                                                                   
            -- Columnar:  Enable Configuration                                     
                                                                                   
            epSpecificCodecT38EnableConfig OBJECT-TYPE                             
                SYNTAX        MxEnableState                                        
                MAX-ACCESS    read-write                                           
                STATUS        current                                              
                DESCRIPTION " Enable Configuration                                 
                                                                                   
                              Defines the configuration to use for a specific      
                              endpoint.                                            
                                                                                   
                                * Disable: The endpoint uses the default           
                                  configuration as defined in the                  
                                  DefaultCodecT38DataEnable,                       
                                  DefaultCodecT38DataPriority and                  
                                  DefaultCodecT38RedundancyLevel variables.        
                                * Enable: The endpoint uses the specific           
                                  configuration as defined in the                  
                                  EpSpecificCodecT38.DataEnable,                   
                                  EpSpecificCodecT38.DataPriority and              
                                  EpSpecificCodecT38.RedundancyLevel variables.    
                                                                                   
                                                                                   
                              "                                                    
                DEFVAL        { disable }                                          
                ::= { epSpecificCodecT38Entry 200 }                                
                                                                                   
            -- Columnar:  Endpoint Specific T.38 Enable/Disable Configuration for  
            -- Data                                                                   
                                                                                   
            epSpecificCodecT38DataEnable OBJECT-TYPE                               
                SYNTAX        MxEnableState                                        
                MAX-ACCESS    read-write                                           
                STATUS        current                                              
                DESCRIPTION " Endpoint Specific T.38 Enable/Disable Configuration  
                              for Data                                             
                                                                                   
                              If enabled, the T.38 protocol is used for fax        
                              transmission.                                        
                                                                                   
                              This configuration overrides the default             
                              configuration set in the DefaultCodecT38DataEnable   
                              variable if the EpSpecificCodecT38.EnableConfig      
                              variable is set to 'Enable'.                         
                                                                                   
                                                                                   
                              "                                                    
                DEFVAL        { enable }                                           
                ::= { epSpecificCodecT38Entry 300 }                                
                                                                                   
            -- Columnar:  Endpoint Specific T.38 Priority Configuration for Data   
                                                                                   
            epSpecificCodecT38DataPriority OBJECT-TYPE                             
                SYNTAX        Unsigned32 ( 10..10 )                                
                MAX-ACCESS    read-write                                           
                STATUS        current                                              
                DESCRIPTION " Endpoint Specific T.38 Priority Configuration for    
                              Data                                                 
                                                                                   
                              Indicates the priority of this data codec versus the 
                              other data codecs. The data codec with the highest   
                              priority will be offered first when an outgoing call 
                              is initiated. This priority is not used in incoming  
                              calls.                                               
                                                                                   
                              The application uses an internal order for codecs    
                              with the same priority.                              
                                                                                   
                              10 is the highest priority and 0 the lowest.         
                                                                                   
                              This configuration overrides the default             
                              configuration set in the DefaultCodecT38DataPriority 
                              variable if the EpSpecificCodecT38.EnableConfig      
                              variable is set to 'Enable'.                         
                                                                                   
                                                                                   
                              "                                                    
                DEFVAL        { 10 }                                               
                ::= { epSpecificCodecT38Entry 400 }                                
                                                                                   
            -- Columnar:  Endpoint Specific T.38 Protection Level.                 
                                                                                   
            epSpecificCodecT38RedundancyLevel OBJECT-TYPE                          
                SYNTAX        Unsigned32 ( 1..5 )                                  
                MAX-ACCESS    read-write                                           
                STATUS        current                                              
                DESCRIPTION " Endpoint Specific T.38 Protection Level.             
                                                                                   
                              Number of redundancy packets. This is the standard   
                              redundancy offered by T.38.                          
                                                                                   
                              Refer to the DefaultCodecT38FinalFramesRedundancy    
                              variable for additional T.38 reliability options.    
                                                                                   
                              This configuration overrides the default             
                              configuration set in the                             
                              DefaultCodecT38RedundancyLevel variable if the       
                              EpSpecificCodecT38.EnableConfig variable is set to   
                              'Enable'.                                            
                                                                                   
                                                                                   
                              "                                                    
                DEFVAL        { 3 }                                                
                ::= { epSpecificCodecT38Entry 600 }                                
                                                                                   
                                                                                   
        -- End of table:  Endpoint Specific Voice Codec Configuration              
                                                                                   
    -- End of group:  T.38 Codec Related Configuration Group                       
                                                                                   
-- End of group:  Voice Codec                                                      

-- ****************************************************************************
                                                                              
-- Group:  Data Related Configuration Group                                   
                                                                              
-- ****************************************************************************
                                                                              
jitterBufferGroup OBJECT IDENTIFIER                                           
    ::= { miptMIBObjects 200 }                                                
                                                                              
                                                                              
    -- Scalar:  Default Jitter Bufffer Level                                  
                                                                              
    defaultJitterBufferLevel OBJECT-TYPE                                      
        SYNTAX        INTEGER { optimizeLatency(100) , normal(200) ,          
                      optimizeQuality(300) , faxModem(400) , custom(500) }    
        MAX-ACCESS    read-write                                              
        STATUS        current                                                 
        DESCRIPTION " Default Jitter Bufffer Level                            
                                                                              
                      Jitter is an abrupt and unwanted variation of one or    
                      more signal characteristics, such as the interval       
                      between successive pulses or the frequency or phase of  
                      successive cycles. An adaptive jitter buffer usually    
                      consists of an elastic buffer in which the signal is    
                      temporarily stored and then retransmitted at a rate     
                      based on the average rate of the incoming signal.       
                                                                              
                        * OptimizeLatency: The jitter buffer is set to the    
                          lowest effective value to minimize the latency.     
                          Voice cut can be heard if the network is not        
                          optimal.                                            
                        * Normal: The jitter buffer tries to find a good      
                          compromise between the latency and the voice        
                          quality. This setting is recommended in private     
                          networks.                                           
                        * OptimizeQuality: The jitter buffer is set to a high 
                          value to minimize the voice cuts at cost of high    
                          latency. This setting is recommended in public      
                          networks.                                           
                        * FaxModem: The jitter buffer is set to maximum. The  
                          Fax/Modem transmission is very sensitive to voice   
                          cuts but not to latency, so the fax has a better    
                          chance of success with a high buffer.               
                        * Custom: The jitter buffer uses the configuration of 
                          the 'DefaultJitterBufferCustomMinLength' and        
                          'DefaultJitterBufferCustomMaxLength' variables.     
                                                                              
                      If a specific configuration is set in the               
                      EpSpecificJitterBuffer.Level variable and the           
                      EpSpecificJitterBuffer.EnableConfig variable is set to  
                      'Enable', then it overrides the current default         
                      configuration.                                          
                                                                              
                                                                              
                      "                                                       
        DEFVAL        { normal }                                              
        ::= { jitterBufferGroup 100 }                                         
                                                                              
    -- Scalar:  Default Custom Jitter Buffer Minimum Length                   
                                                                              
    defaultJitterBufferCustomMinLength OBJECT-TYPE                            
        SYNTAX        Unsigned32 ( 0..135 )                                   
        MAX-ACCESS    read-write                                              
        STATUS        current                                                 
        DESCRIPTION " Default Custom Jitter Buffer Minimum Length             
                                                                              
                      The adaptive jitter buffer attempts to hold packets to  
                      the minimal holding time. This is the minimum delay the 
                      jitter buffer adds to the system.                       
                                                                              
                      The minimal jitter buffer length is in ms.              
                                                                              
                      The minimal jitter buffer MUST be equal to or smaller   
                      than the maximum jitter buffer.                         
                                                                              
                      This value is used only when the                        
                      DefaultJitterBufferLevel variable is set to 'Custom'    
                                                                              
                      If a specific configuration is set in the               
                      EpSpecificJitterBuffer.CustomMinLength variable and the 
                      EpSpecificJitterBuffer.EnableConfig variable is set to  
                      'Enable', then it overrides the current default         
                      configuration.                                          
                                                                              
                                                                              
                      "                                                       
        DEFVAL        { 30 }                                                  
        ::= { jitterBufferGroup 200 }                                         
                                                                              
    -- Scalar:  Default Custom Jitter Buffer Maximum Length                   
                                                                              
    defaultJitterBufferCustomMaxLength OBJECT-TYPE                            
        SYNTAX        Unsigned32 ( 0..135 )                                   
        MAX-ACCESS    read-write                                              
        STATUS        current                                                 
        DESCRIPTION " Default Custom Jitter Buffer Maximum Length             
                                                                              
                      Maximum jitter the adaptive jitter buffer can handle.   
                                                                              
                      The jitter buffer length is in ms.                      
                                                                              
                      The maximum jitter buffer MUST be equal to or greater   
                      than the minimal jitter buffer.                         
                                                                              
                      The maximum jitter buffer length allowed on some        
                      products is smaller than 300 ms.                        
                                                                              
                      This value is used only when the                        
                      DefaultJitterBufferLevel variable is set to 'Custom'    
                                                                              
                      If a specific configuration is set in the               
                      EpSpecificJitterBuffer.CustomMaxLength variable and the 
                      EpSpecificJitterBuffer.EnableConfig variable is set to  
                      'Enable', then it overrides the current default         
                      configuration.                                          
                                                                              
                                                                              
                      "                                                       
        DEFVAL        { 125 }                                                 
        ::= { jitterBufferGroup 300 }                                         
                                                                              
    -- ************************************************************************
                                                                              
    -- Table:  Endpoint Specific Jitter Buffer Configuration                  
                                                                              
    -- ************************************************************************
                                                                              
    epSpecificJitterBufferTable OBJECT-TYPE                                   
        SYNTAX                SEQUENCE OF EpSpecificJitterBufferEntry         
        MAX-ACCESS            not-accessible                                  
        STATUS                current                                         
        DESCRIPTION         " Endpoint Specific Jitter Buffer Configuration   
                                                                              
                              Endpoint specific configuration.                
                              "                                               
        ::= { jitterBufferGroup 400 }                                         
                                                                              
                                                                              
        epSpecificJitterBufferEntry OBJECT-TYPE                               
            SYNTAX        EpSpecificJitterBufferEntry                         
            MAX-ACCESS    not-accessible                                      
            STATUS        current                                             
            DESCRIPTION " A row in the Endpoint Specific Jitter Buffer        
                          Configuration . "                                   
            INDEX         {                                                   
                              epId                                            
                          }                                                   
                                                                              
            ::= { epSpecificJitterBufferTable 1 }                             
                                                                              
        EpSpecificJitterBufferEntry ::= SEQUENCE                              
        {                                                                     
             epId               OCTET STRING,                                 
             enableConfig       MxEnableState,                                
             level              INTEGER,                                      
             customMinLength    Unsigned32,                                   
             customMaxLength    Unsigned32                                    
        }                                                                     
                                                                              
        -- Index:  Endpoint Identifier                                        
                                                                              
        epSpecificJitterBufferEpId OBJECT-TYPE                                
            SYNTAX         OCTET STRING                                       
            MAX-ACCESS     read-only                                          
            STATUS         current                                            
            DESCRIPTION  " Endpoint Identifier                                
                                                                              
                           String that identifies an endpoint in other tables.
                           "                                                  
            ::= { epSpecificJitterBufferEntry 100 }                           
                                                                              
        -- Columnar:  Enable Configuration                                    
                                                                              
        epSpecificJitterBufferEnableConfig OBJECT-TYPE                        
            SYNTAX        MxEnableState                                       
            MAX-ACCESS    read-write                                          
            STATUS        current                                             
            DESCRIPTION " Enable Configuration                                
                                                                              
                          Defines the configuration to use for a specific     
                          endpoint.                                           
                                                                              
                            * Disable: The endpoint uses the default          
                              configuration as defined in the                 
                              DefaultJitterBufferLevel,                       
                              DefaultJitterBufferCustomMinLength and          
                              DefaultJitterBufferCustomMaxLength variables.   
                            * Enable: The endpoint uses the specific          
                              configuration as defined in the                 
                              EpSpecificJitterBuffer.Level,                   
                              EpSpecificJitterBuffer.CustomMinLength and      
                              EpSpecificJitterBuffer.CustomMaxLength          
                              variables.                                      
                                                                              
                                                                              
                          "                                                   
            DEFVAL        { disable }                                         
            ::= { epSpecificJitterBufferEntry 200 }                           
                                                                              
        -- Columnar:  Endpoint Specific Jitter Buffer Level                   
                                                                              
        epSpecificJitterBufferLevel OBJECT-TYPE                               
            SYNTAX        INTEGER { optimizeLatency(100) , normal(200) ,      
                          optimizeQuality(300) , faxModem(400) , custom(500) }
            MAX-ACCESS    read-write                                          
            STATUS        current                                             
            DESCRIPTION " Endpoint Specific Jitter Buffer Level               
                                                                              
                          Jitter is an abrupt and unwanted variation of one or
                          more signal characteristics, such as the interval   
                          between successive pulses or the frequency or phase 
                          of successive cycles. An adaptive jitter buffer     
                          usually consists of an elastic buffer in which the  
                          signal is temporarily stored and then retransmitted 
                          at a rate based on the average rate of the incoming 
                          signal.                                             
                                                                              
                            * OptimizeLatency: The jitter buffer is set to the
                              lowest effective value to minimize the latency. 
                              Voice cut can be heard if the network is not    
                              optimal.                                        
                            * Normal: The jitter buffer tries to find a good  
                              compromise between the latency and the voice    
                              quality. This setting is recommended in private 
                              networks.                                       
                            * OptimizeQuality: The jitter buffer is set to a  
                              high value to minimize the voice cuts at cost of
                              high latency. This setting is recommended in    
                              public networks.                                
                            * FaxModem: The jitter buffer is set to maximum.  
                              The Fax/Modem transmission is very sensitive to 
                              voice cuts but not to latency, so the fax has a 
                              better chance of success with a high buffer.    
                            * Custom: The jitter buffer uses the configuration
                              of the DefaultJitterBufferCustomMinLength and   
                              DefaultJitterBufferCustomMaxLength variables.   
                                                                              
                          This configuration overrides the default            
                          configuration set in the DefaultJitterBufferLevel   
                          variable if the EpSpecificJitterBuffer.EnableConfig 
                          variable is set to 'Enable'.                        
                                                                              
                                                                              
                          "                                                   
            DEFVAL        { normal }                                          
            ::= { epSpecificJitterBufferEntry 300 }                           
                                                                              
        -- Columnar:  Endpoint Specific Custom Jitter Buffer Minimal Length   
                                                                              
        epSpecificJitterBufferCustomMinLength OBJECT-TYPE                     
            SYNTAX        Unsigned32 ( 0..135 )                               
            MAX-ACCESS    read-write                                          
            STATUS        current                                             
            DESCRIPTION " Endpoint Specific Custom Jitter Buffer Minimal      
                          Length                                              
                                                                              
                          The adaptive jitter buffer attempts to hold packets 
                          to the minimal holding time. This is the minimum    
                          delay the jitter buffer adds to the system.         
                                                                              
                          The minimal jitter buffer length is in ms.          
                                                                              
                          The minimal jitter buffer MUST be equal to or       
                          smaller than the maximum jitter buffer.             
                                                                              
                          This value is used only when the Level variable is  
                          set to 'Custom'.                                    
                                                                              
                          This configuration overrides the default            
                          configuration set in the                            
                          DefaultJitterBufferCustomMinLength variable if the  
                          EpSpecificJitterBuffer.EnableConfig variable is set 
                          to 'Enable'.                                        
                                                                              
                                                                              
                          "                                                   
            DEFVAL        { 30 }                                              
            ::= { epSpecificJitterBufferEntry 400 }                           
                                                                              
        -- Columnar:  Endpoint Specific Custom Jitter Buffer Maximum Length   
                                                                              
        epSpecificJitterBufferCustomMaxLength OBJECT-TYPE                     
            SYNTAX        Unsigned32 ( 0..135 )                               
            MAX-ACCESS    read-write                                          
            STATUS        current                                             
            DESCRIPTION " Endpoint Specific Custom Jitter Buffer Maximum      
                          Length                                              
                                                                              
                          Maximum jitter the adaptive jitter buffer can       
                          handle.                                             
                                                                              
                          The jitter buffer length is in ms.                  
                                                                              
                          The maximum jitter buffer MUST be equal to or       
                          greater than the minimal jitter buffer.             
                                                                              
                          The maximum jitter buffer length allowed on some    
                          products is smaller than 300 ms.                    
                                                                              
                          This value is used only when the Level variable is  
                          set to 'Custom'.                                    
                                                                              
                          This configuration overrides the default            
                          configuration set in the                            
                          DefaultJitterBufferCustomMaxLength variable if the  
                          EpSpecificJitterBuffer.EnableConfig variable is set 
                          to 'Enable'.                                        
                                                                              
                                                                              
                          "                                                   
            DEFVAL        { 125 }                                             
            ::= { epSpecificJitterBufferEntry 500 }                           
                                                                              
                                                                              
    -- End of table:  Endpoint Specific Jitter Buffer Configuration           
                                                                              
-- End of group:  Data Related Configuration Group                            

-- ****************************************************************************
                                                                              
-- Group:  DTMF Transport Group                                               
                                                                              
-- ****************************************************************************
                                                                              
dtmfTransportGroup OBJECT IDENTIFIER                                          
    ::= { miptMIBObjects 300 }                                                
                                                                              
                                                                              
    -- Scalar:  Default DTMF Transport Method Configuration                   
                                                                              
    defaultDtmfTransportMethod OBJECT-TYPE                                    
        SYNTAX        INTEGER { inBand(100) , outOfBandUsingRtp(200) ,        
                      outOfBandUsingSignalingProtocol(300) ,                  
                      signalingProtocolDependent(400) }                       
        MAX-ACCESS    read-write                                              
        STATUS        current                                                 
        DESCRIPTION " Default DTMF Transport Method Configuration             
                                                                              
                      Type of DTMF transport. If 'SignalingProtocolDependent' 
                      is selected, the signaling protocol has the control to  
                      select the DTMF transport mode.                         
                                                                              
                      If a specific configuration is set in the               
                      EpSpecificDtmfTransport.Method variable and the         
                      EpSpecificDtmfTransport.EnableConfig variable is set to 
                      'Enable', then it overrides the current default         
                      configuration.                                          
                                                                              
                                                                              
                      "                                                       
        DEFVAL        { inBand }                                              
        ::= { dtmfTransportGroup 100 }                                        
                                                                              
    -- Scalar:  Default DTMF Transport Payload Type                           
                                                                              
    defaultDtmfTransportPayloadType OBJECT-TYPE                               
        SYNTAX        Unsigned32 ( 96..127 )                                  
        MAX-ACCESS    read-write                                              
        STATUS        current                                                 
        DESCRIPTION " Default DTMF Transport Payload Type                     
                                                                              
                      Determines the actual RTP dynamic payload type used for 
                      telephone-event in an initial offer when selecting the  
                      'OutOfBandUsingRtp' DTMF transport mode (see the        
                      DefaultDtmfTransportMethod variable). The payload types 
                      available are as per RFC 1890.                          
                                                                              
                      If a specific configuration is set in the               
                      EpSpecificDtmfTransport.PayloadType variable and the    
                      EpSpecificDtmfTransport.EnableConfig variable is set to 
                      'Enable', then it overrides the current default         
                      configuration.                                          
                                                                              
                                                                              
                      "                                                       
        DEFVAL        { 96 }                                                  
        ::= { dtmfTransportGroup 200 }                                        
                                                                              
    -- ************************************************************************
                                                                              
    -- Table:  Endpoint Specific Voice Codec Configuration                    
                                                                              
    -- ************************************************************************
                                                                              
    epSpecificDtmfTransportTable OBJECT-TYPE                                  
        SYNTAX              SEQUENCE OF EpSpecificDtmfTransportEntry          
        MAX-ACCESS          not-accessible                                    
        STATUS              current                                           
        DESCRIPTION      "  Endpoint Specific Voice Codec Configuration       
                                                                              
                            Endpoint specific configuration.                  
                            "                                                 
        ::= { dtmfTransportGroup 300 }                                        
                                                                              
                                                                              
        epSpecificDtmfTransportEntry OBJECT-TYPE                              
            SYNTAX        EpSpecificDtmfTransportEntry                        
            MAX-ACCESS    not-accessible                                      
            STATUS        current                                             
            DESCRIPTION " A row in the Endpoint Specific Voice Codec          
                          Configuration . "                                   
            INDEX         {                                                   
                              epId                                            
                          }                                                   
                                                                              
            ::= { epSpecificDtmfTransportTable 1 }                            
                                                                              
        EpSpecificDtmfTransportEntry ::= SEQUENCE                             
        {                                                                     
             epId             OCTET STRING,                                   
             enableConfig     MxEnableState,                                  
             method           INTEGER,                                        
             payloadType      Unsigned32                                      
        }                                                                     
                                                                              
        -- Index:  Endpoint Identifier                                        
                                                                              
        epSpecificDtmfTransportEpId OBJECT-TYPE                               
            SYNTAX         OCTET STRING                                       
            MAX-ACCESS     read-only                                          
            STATUS         current                                            
            DESCRIPTION  " Endpoint Identifier                                
                                                                              
                           String that identifies an endpoint in other tables.
                           "                                                  
            ::= { epSpecificDtmfTransportEntry 100 }                          
                                                                              
        -- Columnar:  Enable Configuration                                    
                                                                              
        epSpecificDtmfTransportEnableConfig OBJECT-TYPE                       
            SYNTAX        MxEnableState                                       
            MAX-ACCESS    read-write                                          
            STATUS        current                                             
            DESCRIPTION " Enable Configuration                                
                                                                              
                          Defines the configuration to use for a specific     
                          endpoint.                                           
                                                                              
                            * Disable: The endpoint uses the default          
                              configuration as defined in the                 
                              DefaultDtmfTransportMethod and                  
                              DefaultDtmfTransportPayloadType variables.      
                            * Enable: The endpoint uses the specific          
                              configuration as defined in the                 
                              EpSpecificDtmfTransport.Method and              
                              EpSpecificDtmfTransport.PayloadType variables.  
                                                                              
                                                                              
                          "                                                   
            DEFVAL        { disable }                                         
            ::= { epSpecificDtmfTransportEntry 200 }                          
                                                                              
        -- Columnar:  Endpoint Specific DTMF Transport Method Configuration   
                                                                              
        epSpecificDtmfTransportMethod OBJECT-TYPE                             
            SYNTAX        INTEGER { inBand(100) , outOfBandUsingRtp(200) ,    
                          outOfBandUsingSignalingProtocol(300) ,              
                          signalingProtocolDependent(400) }                   
            MAX-ACCESS    read-write                                          
            STATUS        current                                             
            DESCRIPTION " Endpoint Specific DTMF Transport Method             
                          Configuration                                       
                                                                              
                          Type of DTMF transport. If                          
                          'SignalingProtocolDependent' is selected, the       
                          signaling protocol has the control to select the    
                          DTMF transport mode.                                
                                                                              
                          This configuration overrides the default            
                          configuration set in the DefaultDtmfTransportMethod 
                          variable if the EpSpecificDtmfTransport.EnableConfig
                          variable is set to 'Enable'.                        
                                                                              
                                                                              
                          "                                                   
            DEFVAL        { inBand }                                          
            ::= { epSpecificDtmfTransportEntry 300 }                          
                                                                              
        -- Columnar:  Endpoint Specific DTMF Transport Payload Type           
                                                                              
        epSpecificDtmfTransportPayloadType OBJECT-TYPE                        
            SYNTAX        Unsigned32 ( 96..127 )                              
            MAX-ACCESS    read-write                                          
            STATUS        current                                             
            DESCRIPTION " Endpoint Specific DTMF Transport Payload Type       
                                                                              
                          Determines the actual RTP dynamic payload type used 
                          for telephone-event in an initial offer when        
                          selecting the 'OutOfBandUsingRtp' DTMF transport    
                          mode (see the Method variable). The payload types   
                          available are as per RFC 1890.                      
                                                                              
                          This configuration overrides the default            
                          configuration set in the                            
                          DefaultDtmfTransportPayloadType variable if the     
                          EpSpecificDtmfTransport.EnableConfig variable is set
                          to 'Enable'.                                        
                                                                              
                                                                              
                          "                                                   
            DEFVAL        { 96 }                                              
            ::= { epSpecificDtmfTransportEntry 400 }                          
                                                                              
                                                                              
    -- End of table:  Endpoint Specific Voice Codec Configuration             
                                                                              
-- End of group:  DTMF Transport Group                                        

-- ****************************************************************************
                                                                               
-- Group:  IP Transport                                                        
                                                                               
-- ****************************************************************************
                                                                               
ipTransportGroup OBJECT IDENTIFIER                                             
    ::= { miptMIBObjects 400 }                                                 
                                                                               
                                                                               
    -- ************************************************************************
                                                                               
    -- Group:  RTP                                                             
                                                                               
    -- ************************************************************************
                                                                               
    ipTransportRtpGroup OBJECT IDENTIFIER                                      
        ::= { ipTransportGroup 100 }                                           
                                                                               
                                                                               
        -- Scalar:  RTP IP Transport Base Port                                 
                                                                               
        ipTransportRtpBasePort OBJECT-TYPE                                     
            SYNTAX        Unsigned32 ( 1025..64535 )                           
            MAX-ACCESS    read-write                                           
            STATUS        current                                              
            DESCRIPTION " RTP IP Transport Base Port                           
                                                                               
                          UDP base port for the RTP/RTCP protocols.            
                                                                               
                          The RTP/RTCP ports are allocated starting from this  
                          base port.                                           
                                                                               
                          The unit may use two or four RTP/RTCP ports per FXS/ 
                          FXO endpoint.                                        
                                                                               
                          It uses two ports in case of a standard call, while  
                          it uses four ports in other types of calls such as a 
                          conference call, a call transfer, etc.               
                                                                               
                          Example: let's say that a unit has two FXS endpoints 
                          and the base port is defined on 5004:                
                                                                               
                            * if there is currently no ongoing call and FXS    
                              endpoint 1 has an incoming or outgoing call, it  
                              will use the RTP/RTCP ports 5004 and 5005.       
                            * if there is currently a standard call on FXS     
                              endpoint 1 and FXS endpoint 2 has a conference   
                              call, then FXS endpoint 2 will use the RTP/RTCP  
                              ports 5006, 5007, 5008, and 5009, which are the  
                              next available ports.                            
                                                                               
                                                                               
                          "                                                    
            DEFVAL        { 5004 }                                             
            ::= { ipTransportRtpGroup 100 }                                    
                                                                               
    -- End of group:  RTP                                                      
                                                                               
    -- ************************************************************************
                                                                               
    -- Group:  T.38                                                            
                                                                               
    -- ************************************************************************
                                                                               
    ipTransportT38Group OBJECT IDENTIFIER                                      
        ::= { ipTransportGroup 200 }                                           
                                                                               
                                                                               
        -- Scalar:  T.38 IP Transport Base Port                                
                                                                               
        ipTransportT38BasePort OBJECT-TYPE                                     
            SYNTAX        Unsigned32 ( 1025..64535 )                           
            MAX-ACCESS    read-write                                           
            STATUS        current                                              
            DESCRIPTION " T.38 IP Transport Base Port                          
                                                                               
                          T.38 base port.                                      
                                                                               
                          The T.38 ports are allocated starting from this base 
                          port. The units use as many T.38 ports as the number 
                          of FXS/FXO endpoints.                                
                                                                               
                          Example: let's say that a unit has two FXS endpoints 
                          and the base port is defined on 6004:                
                                                                               
                            * if there is currently no ongoing call and FXS    
                              endpoint 1 has an incoming or outgoing call, it  
                              will use the T.38 port 6004.                     
                            * if there is currently a call on FXS endpoint 1   
                              and FXS endpoint 2 has an incoming or outgoing   
                              call, then FXS endpoint 2 will use the T.38 port 
                              6005.                                            
                                                                               
                                                                               
                          "                                                    
            DEFVAL        { 6004 }                                             
            ::= { ipTransportT38Group 100 }                                    
                                                                               
    -- End of group:  T.38                                                     
                                                                               
-- End of group:  IP Transport                                                 

-- *****************************************************************************
                                                                               
-- Group:  Notification Messages Configuration                                 
                                                                               
-- *****************************************************************************
                                                                               
notificationsGroup OBJECT IDENTIFIER                                           
    ::= { miptMIBObjects 60010 }                                               
                                                                               
                                                                               
    -- Scalar:  Minimal Severity of Notification                               
                                                                               
    minSeverity OBJECT-TYPE                                                    
        SYNTAX        INTEGER { disable(0) , debug(100) , info(200) , warning  
                      (300) , error(400) , critical (500) }                    
        MAX-ACCESS    read-write                                               
        STATUS        current                                                  
        DESCRIPTION " Minimal Severity of Notification                         
                                                                               
                      Sets the minimal severity to issue a notification message
                      incoming from this service.                              
                                                                               
                        * Disable: No notification is issued.                  
                        * Debug: All notification messages are issued.         
                        * Info: Notification messages with severity            
                          'Informational' and higher are issued.               
                        * Warning: Notification messages with severity         
                          'Warning' and higher are issued.                     
                        * Error: Notification messages with severity 'Error'   
                          and higher are issued.                               
                        * Critical: Notification messages with severity        
                          'Critical' are issued.                               
                                                                               
                                                                               
                      "                                                        
        DEFVAL        { warning }                                              
        ::= { notificationsGroup 100 }                                         
                                                                               
-- End of group:  Notification Messages Configuration                          

-- ****************************************************************************
                                                                              
-- Group:  Configuration Settings                                             
                                                                              
-- ****************************************************************************
                                                                              
configurationGroup OBJECT IDENTIFIER                                          
    ::= { miptMIBObjects 60020 }                                              
                                                                              
                                                                              
    -- Scalar:  Need Restart                                                  
                                                                              
    needRestartInfo OBJECT-TYPE                                               
        SYNTAX        INTEGER { no(0) , yes(100) }                            
        MAX-ACCESS    read-only                                               
        STATUS        current                                                 
        DESCRIPTION " Need Restart                                            
                                                                              
                      Indicates if the service needs to be restarted for its  
                      configuration to fully take effect.                     
                                                                              
                        * Yes: Service needs to be restarted.                 
                        * No: Service does not need to be restarted.          
                                                                              
                      Services can be restarted by using the command          
                      Scm.ServiceCommands.Restart.                            
                                                                              
                                                                              
                      "                                                       
        ::= { configurationGroup 100 }                                        
                                                                              
-- End of group:  Configuration Settings                                      

END
