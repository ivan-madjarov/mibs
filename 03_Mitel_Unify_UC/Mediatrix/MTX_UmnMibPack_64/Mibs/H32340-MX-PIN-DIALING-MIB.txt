-- ****************************************************************************
-- ****************************************************************************
--
--             Copyright(c) 2004 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part, in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

H32340-MX-PIN-DIALING-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        ifIndex
    FROM RFC1213-MIB
        MxEnableState
    FROM MX-TC
        mediatrixExperimental
    FROM MX-SMI;

pinDialingMIB MODULE-IDENTITY
    LAST-UPDATED "200408190000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains PIN dialing configuration objects."

    -- ************************************************************************
    -- Revision history
    -- ************************************************************************
    REVISION    "200408190000Z"
    DESCRIPTION "Creation"
    ::= { mediatrixExperimental 90 }

pinDialingMIBObjects  OBJECT IDENTIFIER ::= { pinDialingMIB 1 }
pinDialingConformance OBJECT IDENTIFIER ::= { pinDialingMIB 2 }

    pinDialingIfTable OBJECT-TYPE
        SYNTAX      SEQUENCE OF PinDialingIfEntry
        MAX-ACCESS  not-accessible
        STATUS      current
        DESCRIPTION "This table holds the PIN Dialling Configuration of each line.

                     The PIN Dialling Feature allows the administrator to configure
                     a PIN (Personal Identification Number) that would be dialled
                     in “n” milliseconds after an outgoing call was established."
        ::= { pinDialingMIBObjects  10 }

        pinDialingIfEntry OBJECT-TYPE
            SYNTAX      PinDialingIfEntry
            MAX-ACCESS  not-accessible
            STATUS      current
            DESCRIPTION "Table entry of the table that contains PIN dialing
                         configuration."
            INDEX       {
                         ifIndex
                        }
            ::= { pinDialingIfTable 1 }

            PinDialingIfEntry ::= SEQUENCE
            {
                pinDialingEnable MxEnableState,
                pinDialingPin OCTET STRING (SIZE(0..255)),
                pinDialingDelay Unsigned32 (0..300000)
            }

        pinDialingEnable OBJECT-TYPE
            SYNTAX      MxEnableState
            MAX-ACCESS  read-write
            STATUS      current
            DESCRIPTION "Enables or disables the PIN Dialling Feature."
            DEFVAL      { disable }
            ::=  {  pinDialingIfEntry 10  }

        pinDialingPin OBJECT-TYPE
            SYNTAX      OCTET STRING (SIZE(0..255))
            MAX-ACCESS  read-write
            STATUS      current
            DESCRIPTION "The PIN to dial.

                         The PIN contains the DTMFs to be dialed. The supported
                         digits are “0123456789*#abcdABCD”. Pause characters “,”,
                         “;”, and “p” are also supported and represent 1 second."
            DEFVAL      { "" }
            ::=  {  pinDialingIfEntry 20  }

        pinDialingDelay OBJECT-TYPE
            SYNTAX      Unsigned32 (0..300000)
            MAX-ACCESS  read-write
            STATUS      current
            DESCRIPTION "The delay prior to sending the PIN.

                         This value is expressed in milliseconds (ms)."
            DEFVAL      { 1000 }
            ::=  {  pinDialingIfEntry 30  }


    -- ************************************************************************
    -- Conformance information
    -- ************************************************************************
    pinDialingCompliances OBJECT IDENTIFIER ::= { pinDialingConformance 1 }

    pinDialingBasicComplVer1 MODULE-COMPLIANCE
        STATUS      current
        DESCRIPTION "Minimal definitions for the PIN dialing group."
        MODULE -- This Module
            MANDATORY-GROUPS {
                                pinDialingGroupVer1
                             }
        ::= { pinDialingCompliances 1 }

    -- ************************************************************************
    -- MIB variable grouping
    -- ************************************************************************
    pinDialingGroups OBJECT IDENTIFIER ::= {pinDialingConformance 2 }

    pinDialingGroupVer1 OBJECT-GROUP
        OBJECTS {
                  pinDialingEnable,
                  pinDialingPin,
                  pinDialingDelay
                }
        STATUS      current
        DESCRIPTION "This group holds the objects that define the basic
                     PIN dialing group."
        ::= { pinDialingGroups 1 }

END
