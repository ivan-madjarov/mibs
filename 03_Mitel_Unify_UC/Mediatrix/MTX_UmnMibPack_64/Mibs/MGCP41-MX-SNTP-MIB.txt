-- ****************************************************************************
-- ****************************************************************************
--
--             Copyright(c) 2001 Mediatrix Telecom, Inc. 
--
--  NOTICE:
--   This document contains information that is confidential and proprietary
--   to Mediatrix Telecom, Inc. 
--
--   Mediatrix Telecom, Inc. reserves all rights to this document as well as
--   to the Intellectual Property of the document and the technology and
--   know-how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************
MGCP41-MX-SNTP-MIB
DEFINITIONS ::= BEGIN

IMPORTS
        MODULE-IDENTITY,
        OBJECT-TYPE,
        Unsigned32
    FROM SNMPv2-SMI
        OBJECT-GROUP,
        MODULE-COMPLIANCE
    FROM SNMPv2-CONF
        MxIpHostName,
        MxIpConfigSource,
        MxIpPort,
        MxIpSelectConfigSource,
        MxIpDhcpSiteSpecificCode
    FROM MX-TC
        mediatrixExperimental
    FROM MX-SMI;

sntpMIB MODULE-IDENTITY
    LAST-UPDATED "0203160000Z"
    ORGANIZATION "Mediatrix Telecom, Inc."
    CONTACT-INFO "Mediatrix Telecom, Inc. 
                  4229, Garlock Street
                  Sherbrooke (Quebec)
                  Canada
                  Phone: (819) 829-8749
                  "
    DESCRIPTION "This MIB describes the parameters used by the SNTP
                 protocol."
    -- ************************************************************************
    -- Revision history
    -- ************************************************************************
    REVISION    "0203160000Z"
    DESCRIPTION "March 16, 2002
                 Creation"
    ::= { mediatrixExperimental 15 }

sntpMIBObjects  OBJECT IDENTIFIER ::= { sntpMIB 1 }
sntpConformance OBJECT IDENTIFIER ::= { sntpMIB 2 }

-- Add the SNTP general parameters

	sntpEnable OBJECT-TYPE
		SYNTAX		INTEGER {
                        	 disable(0),
                        	 enable(1)
                        	}
		MAX-ACCESS	read-write
		STATUS		current
		DESCRIPTION	"Enable/Disable the SNTP client."
		DEFVAL 		{ disable }
		::= { sntpMIBObjects 5 }

	sntpSynchronizationPeriod OBJECT-TYPE
		SYNTAX  	Unsigned32 (1..1440)
		MAX-ACCESS	read-write
		STATUS		current
		DESCRIPTION	"Time interval (in minutes) between request made to the SNTP server.
					 The result will be used to synchronize the unit with the time server.
					 The maximum value is set to 1 440 minutes which corresponds to 24 hours."
		DEFVAL 		{ 1440 }
		::= { sntpMIBObjects 10 }

	sntpSynchronizationPeriodOnError OBJECT-TYPE
		SYNTAX  	Unsigned32 (1..1440)
		MAX-ACCESS	read-write
		STATUS		current
		DESCRIPTION "Time interval (in minutes) between retries after an unsuccessfull
					 attempt to reach the SNTP server.
					 The maximum value is set to 1 440 minutes which corresponds to 24 hours."
		DEFVAL 		{ 60 }
		::= {  sntpMIBObjects 15 }
		
	sntpTimeZoneConfig OBJECT IDENTIFIER ::= { sntpMIBObjects 25 }
	
	sntpSelectTimeZoneSource OBJECT-TYPE
		SYNTAX		INTEGER {
							 usePosixString(0),
                        	 usePredefinedList(1)
                        	}		
		MAX-ACCESS	read-write
		STATUS		current
		DESCRIPTION	"Select the time zone using either : 
		
					 a) a pre-defined list of time zone
					 b) a time zone string in POSIX format
					 
					 If the POSIX string is selected, the format
					 of the string is validated.
					 
					 See sntpTimeZoneStringIsValid"
		DEFVAL { usePredefinedList }
		::= { sntpTimeZoneConfig 5 }

	sntpTimeZoneList OBJECT-TYPE
		SYNTAX		INTEGER {
							 pacificTime(0),    -- Pacific Time (Canada & US)(GMT - 8h)
							 mountainTime(1),   -- Mountain Time (Canada & US) (GMT - 7h)
							 centralTime(2),    -- Central Time (Canada & US) (GMT - 6h)
							 easternTime(3),    -- Eastern Time (Canada & US) (GMT - 5h)
							 atlanticTime(4),   -- Atlantic Time (Canada) (GMT - 4h)
							 gmtTime(5),        -- GMT Standard Time
							 wEuropeTime(6),    -- W. Europe Standard Time (GMT + 1h)
							 chinaTime(7),      -- China Standard Time (GMT + 8h)
							 tokyoTime(8),      -- Tokyo Standard Time (GMT + 9h)
							 centralAustraliaTime(9),   -- Central Australia Standard Time (GMT + 9h30)
							 easternAustraliaTime(10),  -- Australia Eastern Standard Time (GMT + 10h)
							 utc(11)        -- UTC (Universal Time Coordinated)
							}
		MAX-ACCESS	read-write
		STATUS		current
		DESCRIPTION	"Predefined list of time zone selection. 
					NOTE: The clock is automatically adjusted for daylight 
					saving time changes if applicable."
		DEFVAL { easternTime }
		::= { sntpTimeZoneConfig 10 }

	sntpTimeZoneString OBJECT-TYPE
		SYNTAX		OCTET STRING (SIZE(0..255))
		MAX-ACCESS	read-write
		STATUS		current
		DESCRIPTION	"String describing the time zone to be used.  This string MUST use the
					 POSIX strings format.
					 
					 The format of the string will be validated and the result returned
					 in the sntpTimeZoneStringIsValid variable."
		DEFVAL 		{ "EST5DST4,M4.1.0/02:00:00,M10.5.0/02:00:00" }
		::= { sntpTimeZoneConfig 15 }

	sntpTimeZoneStringIsValid OBJECT-TYPE
		SYNTAX		INTEGER {
							 invalid(0),
                        	 valid(1)
                        	}		
		MAX-ACCESS	read-only
		STATUS		current
		DESCRIPTION	"Diagnosis of the string entered in
                     sntpPosixTimeZone.

                     Possible values are: invalid (0)
                                          valid   (1)

					 If the value is invalid, an error was found in the
                     entered string, please make sure that the syntax
                     respects the POSIX string format."
		DEFVAL { invalid }
		::= { sntpTimeZoneConfig 20 }		

-- Add the SNTP IP addresses specifics parameters

    ipAddressStatusSntp OBJECT IDENTIFIER ::= { sntpMIBObjects 1 }
    ipAddressConfigSntp OBJECT IDENTIFIER ::= { sntpMIBObjects 2 }

-- Add the SNTP status information

    sntpConfigSource OBJECT-TYPE
        SYNTAX      MxIpConfigSource
        MAX-ACCESS  read-only
        STATUS      current
        DESCRIPTION "Indicates the source used for the provisioning of 
                     the SNTP MIB objects."
        DEFVAL { static }
        ::= { ipAddressStatusSntp  1  } 

    sntpHost OBJECT-TYPE
        SYNTAX      MxIpHostName
        MAX-ACCESS  read-only
        STATUS      current
        DESCRIPTION "SNTP server IP address or domain name."
        DEFVAL      { "192.168.0.10" }
        ::= { ipAddressStatusSntp  2 }

    sntpPort OBJECT-TYPE
        SYNTAX      MxIpPort
        MAX-ACCESS  read-only
        STATUS      current
        DESCRIPTION "SNTP server IP port number."
        DEFVAL { 123 }
        ::= { ipAddressStatusSntp 3 }

-- Add the SNTP configuration information

    sntpSelectConfigSource OBJECT-TYPE
        SYNTAX      MxIpSelectConfigSource
        MAX-ACCESS  read-write
        STATUS      current
        DESCRIPTION "Indicates the source to be used for the provisioning of 
                     the SNTP MIB objects."
        DEFVAL      { static }
        ::= { ipAddressConfigSntp 1 }

    ipAddressConfigSntpStatic OBJECT IDENTIFIER ::= { ipAddressConfigSntp 10 }
    
    -- Add the static parameters
    
    sntpStaticHost OBJECT-TYPE
        SYNTAX      MxIpHostName
        MAX-ACCESS  read-write
        STATUS      current
        DESCRIPTION "Static SNTP server IP address or domain name."
        DEFVAL      { "192.168.0.10" }
        ::= { ipAddressConfigSntpStatic 1 }

    sntpStaticPort OBJECT-TYPE
        SYNTAX      MxIpPort
        MAX-ACCESS  read-write
        STATUS      current
        DESCRIPTION "Static SNTP server IP port number."
        DEFVAL      { 123 }
        ::= { ipAddressConfigSntpStatic 2 }

    ipAddressConfigSntpDhcp OBJECT IDENTIFIER ::= { ipAddressConfigSntp 30 }
    
    -- Add the dhcp parameters
    sntpDhcpSiteSpecificCode OBJECT-TYPE
        SYNTAX      MxIpDhcpSiteSpecificCode
        MAX-ACCESS  read-write
        STATUS      current
        DESCRIPTION "DHCP SNTP server site specific code.
        			 If set to 0, use vendor-specific code #208"
        DEFVAL      { 0 }
        ::= { ipAddressConfigSntpDhcp 1 }

    -- ************************************************************************
    -- Conformance information
    -- ************************************************************************
    sntpCompliances OBJECT IDENTIFIER ::= { sntpConformance 1 }

    sntpBasicComplVer1 MODULE-COMPLIANCE
        STATUS      current
        DESCRIPTION
            "Minimal parameters definitions to support SNTP."
        MODULE -- This Module
            MANDATORY-GROUPS { 
                                sntpBasicGroupVer1,
                                sntpServerGroupVer1
                             }
        ::= { sntpCompliances 1 }

     -- ************************************************************************
    -- MIB variable grouping
    -- ************************************************************************
    sntpGroups OBJECT IDENTIFIER ::= { sntpConformance 2 }

    sntpBasicGroupVer1 OBJECT-GROUP
        OBJECTS {
                 sntpEnable,
                 sntpSynchronizationPeriod,
                 sntpSynchronizationPeriodOnError,
                 sntpSelectTimeZoneSource,
                 sntpTimeZoneList,
                 sntpTimeZoneString,
                 sntpTimeZoneStringIsValid
                }
        STATUS current
        DESCRIPTION
            "This group holds the minimal set of objects to configure the SNTP
             service."
        ::= { sntpGroups 1 } 

    sntpServerGroupVer1 OBJECT-GROUP
        OBJECTS {
                    sntpConfigSource,
                    sntpHost,
                    sntpPort,
                    sntpSelectConfigSource,
                    sntpStaticHost,
                    sntpStaticPort,
                    sntpDhcpSiteSpecificCode
                }
        STATUS current
        DESCRIPTION
            "This group holds the minimal set of objects that define 
             SNTP server."
        ::= { sntpGroups 2 }

END
