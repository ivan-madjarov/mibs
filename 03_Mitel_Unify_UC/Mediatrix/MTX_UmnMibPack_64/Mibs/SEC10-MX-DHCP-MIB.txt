-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************
  
SEC10-MX-DHCP-MIB
DEFINITIONS ::= BEGIN

IMPORTS
        MODULE-IDENTITY,
        OBJECT-TYPE,
        Unsigned32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices       
    FROM MX-SMI2;

dhcpMIB MODULE-IDENTITY                                                        
    LAST-UPDATED   "0511180000Z"                                               
    ORGANIZATION " Mediatrix Telecom, Inc. "                                   
    CONTACT-INFO " Mediatrix Telecom, Inc.                                     
                   4229, Garlock Street                                        
                   Sherbrooke (Quebec)                                         
                   Canada                                                      
                   Phone: (819) 829-8749                                       
                   "                                                           
    DESCRIPTION  " Dynamic Host Configuration Protocol Server                  
                                                                               
                   The Dynamic Host Configuration Protocol Server service      
                   allows the administrator to configure the DHCP server       
                   parameters on network interfaces.                           
                   "                                                           
    -- *************************************************************************
                                                                               
    -- Revision history                                                        
                                                                               
    -- *************************************************************************
    REVISION       "0511180000Z"                                               
    DESCRIPTION  " Initial Revision "                                          
    ::= { mediatrixServices 1900 }                                             

dhcpMIBObjects OBJECT IDENTIFIER ::= { dhcpMIB 1 }

-- *****************************************************************************
                                                                               
-- Table:  Subnets                                                             
                                                                               
-- *****************************************************************************
                                                                               
subnetsTable OBJECT-TYPE                                                       
    SYNTAX        SEQUENCE OF SubnetsEntry                                     
    MAX-ACCESS    not-accessible                                               
    STATUS        current                                                      
    DESCRIPTION " Subnets                                                      
                                                                               
                  This table configures the subnets of the DHCP server. The    
                  NetworkInterfaceName variable must match a network interface 
                  that is Up and the EnableSubnet variable must be set to      
                  'Enable' to properly activate the DHCP server on that        
                  interface.                                                   
                                                                               
                  Type the SNMP command 'AddSubnet' to add a new subnet to the 
                  SubnetsTable and to all subnet-specific configuration tables.
                                                                               
                                                                               
                  "                                                            
    ::= { dhcpMIBObjects 100 }                                                 
                                                                               
                                                                               
    subnetsEntry OBJECT-TYPE                                                   
        SYNTAX         SubnetsEntry                                            
        MAX-ACCESS     not-accessible                                          
        STATUS         current                                                 
        DESCRIPTION  " A row in the Subnets. "                                 
        INDEX          {                                                       
                           networkInterfaceName                                
                       }                                                       
                                                                               
        ::= { subnetsTable 1 }                                                 
                                                                               
    SubnetsEntry ::= SEQUENCE                                                  
    {                                                                          
        networkInterfaceName OCTET STRING,                                     
        enableSubnet         MxEnableState,                                    
        startAddress         MxIpAddr,                                         
        endAddress           MxIpAddr,                                         
        configStatus         INTEGER,                                          
        delete               INTEGER                                           
    }                                                                          
                                                                               
    -- Index:  Network Interface                                               
                                                                               
    subnetsNetworkInterfaceName OBJECT-TYPE                                    
        SYNTAX        OCTET STRING                                             
        MAX-ACCESS    read-only                                                
        STATUS        current                                                  
        DESCRIPTION " Network Interface                                        
                                                                               
                      Network interface on which the DHCP server is active.    
                      That interface must be up for the DHCP server to become  
                      active.                                                  
                      "                                                        
        ::= { subnetsEntry 100 }                                               
                                                                               
    -- Columnar:  Enable                                                       
                                                                               
    subnetsEnableSubnet OBJECT-TYPE                                            
        SYNTAX        MxEnableState                                            
        MAX-ACCESS    read-write                                               
        STATUS        current                                                  
        DESCRIPTION " Enable                                                   
                                                                               
                      Enables the subnet configuration. Activates the DHCP     
                      server on the subnet when enabled.                       
                      "                                                        
        DEFVAL        { disable }                                              
        ::= { subnetsEntry 200 }                                               
                                                                               
    -- Columnar:  Start Address                                                
                                                                               
    subnetsStartAddress OBJECT-TYPE                                            
        SYNTAX        MxIpAddr                                                 
        MAX-ACCESS    read-write                                               
        STATUS        current                                                  
        DESCRIPTION " Start Address                                            
                                                                               
                      Start address of the subnet range. It MUST be within the 
                      network interface's CIDR range.                          
                      "                                                        
        DEFVAL        { "" }                                                   
        ::= { subnetsEntry 300 }                                               
                                                                               
    -- Columnar:  End Address                                                  
                                                                               
    subnetsEndAddress OBJECT-TYPE                                              
        SYNTAX        MxIpAddr                                                 
        MAX-ACCESS    read-write                                               
        STATUS        current                                                  
        DESCRIPTION " End Address                                              
                                                                               
                      End address of the subnet range. It MUST be within the   
                      network interface's CIDR range and higher than or equal  
                      to the StartAddress value.                               
                      "                                                        
        DEFVAL        { "" }                                                   
        ::= { subnetsEntry 400 }                                               
                                                                               
    -- Columnar:  Status                                                       
                                                                               
    subnetsConfigStatus OBJECT-TYPE                                            
        SYNTAX        INTEGER { disabled(100) , invalidConfig(200) , ok(300) } 
        MAX-ACCESS    read-only                                                
        STATUS        current                                                  
        DESCRIPTION " Status                                                   
                                                                               
                      Subnet configuration status.                             
                                                                               
                        * Disabled: The EnableSubnet variable is disabled or   
                          the NetworkInterfaceName variable does not match a   
                          network interface that is Up.                        
                        * InvalidConfig: The range start or end address is out 
                          of the network interface's CIDR range, or both       
                          parameters are incompatible.                         
                        * Ok: The EnableSubnet variable is enabled and the     
                          subnet configuration is valid.                       
                                                                               
                                                                               
                      "                                                        
        ::= { subnetsEntry 500 }                                               
                                                                               
    -- Row command:  Delete                                                    
                                                                               
    subnetsDelete OBJECT-TYPE                                                  
        SYNTAX         INTEGER { noOp(0), delete(10) }                         
        MAX-ACCESS     read-write                                              
        STATUS         current                                                 
        DESCRIPTION  " Delete                                                  
                                                                               
                       Deletes a row from the table.                           
                       "                                                       
        DEFVAL         { noOp }                                                
        ::= { subnetsEntry 600 }                                               
                                                                               
                                                                               
-- End of table:  Subnets                                                      

-- *****************************************************************************
                                                                               
-- Group:  Domain Name                                                         
                                                                               
-- *****************************************************************************
                                                                               
domainNameGroup OBJECT IDENTIFIER                                              
    ::= { dhcpMIBObjects 200 }                                                 
                                                                               
                                                                               
    -- Scalar:  Configuration Source                                           
                                                                               
    generalDomainNameConfigSource OBJECT-TYPE                                  
        SYNTAX        INTEGER { hostConfiguration(200) , static(400) }         
        MAX-ACCESS    read-write                                               
        STATUS        current                                                  
        DESCRIPTION " Configuration Source                                     
                                                                               
                      Default configuration source of all subnets.             
                                                                               
                        * HostConfiguration: The domain name is obtained from  
                          the host configuration.                              
                        * Static: The domain name is specified in the          
                          GeneralStaticDomainName variable.                    
                                                                               
                                                                               
                      "                                                        
        DEFVAL        { hostConfiguration }                                    
        ::= { domainNameGroup 100 }                                            
                                                                               
    -- Scalar:  Static Domain Name                                             
                                                                               
    generalStaticDomainName OBJECT-TYPE                                        
        SYNTAX         MxIpHostName                                            
        MAX-ACCESS     read-write                                              
        STATUS         current                                                 
        DESCRIPTION  " Static Domain Name                                      
                                                                               
                       Default static domain name for all subnets.             
                       "                                                       
        DEFVAL         { "" }                                                  
        ::= { domainNameGroup 200 }                                            
                                                                               
    -- *************************************************************************
                                                                               
    -- Table:  Subnet Domain Names                                             
                                                                               
    -- *************************************************************************
                                                                               
    specificDomainNamesTable OBJECT-TYPE                                       
        SYNTAX        SEQUENCE OF SpecificDomainNamesEntry                     
        MAX-ACCESS    not-accessible                                           
        STATUS        current                                                  
        DESCRIPTION " Subnet Domain Names                                      
                                                                               
                      This table specifies subnet-specific domain names        
                      configurations. All subnets use the general configuration
                      unless the SpecificDomainNames.EnableSpecific variable is
                      set to 'Enable'.                                         
                                                                               
                      Type the SNMP command 'AddSubnet' to add a new subnet to 
                      the SubnetsTable and to all subnet-specific configuration
                      tables.                                                  
                                                                               
                                                                               
                      "                                                        
        ::= { domainNameGroup 300 }                                            
                                                                               
                                                                               
        specificDomainNamesEntry OBJECT-TYPE                                   
            SYNTAX         SpecificDomainNamesEntry                            
            MAX-ACCESS     not-accessible                                      
            STATUS         current                                             
            DESCRIPTION  " A row in the Subnet Domain Names. "                 
            INDEX          {                                                   
                               subnetName                                      
                           }                                                   
                                                                               
            ::= { specificDomainNamesTable 1 }                                 
                                                                               
        SpecificDomainNamesEntry ::= SEQUENCE                                  
        {                                                                      
            subnetName       OCTET STRING,                                     
            enableOption     MxEnableState,                                    
            enableSpecific   MxEnableState,                                    
            configSource     INTEGER,                                          
            staticName       MxIpHostName                                      
        }                                                                      
                                                                               
        -- Index:  Subnet Name                                                 
                                                                               
        specificDomainNamesSubnetName OBJECT-TYPE                              
            SYNTAX         OCTET STRING ( SIZE(1..15) )                        
            MAX-ACCESS     read-only                                           
            STATUS         current                                             
            DESCRIPTION  " Subnet Name                                         
                                                                               
                           Name of the subnet.                                 
                           "                                                   
            ::= { specificDomainNamesEntry 100 }                               
                                                                               
        -- Columnar:  Enable Option                                            
                                                                               
        specificDomainNamesEnableOption OBJECT-TYPE                            
            SYNTAX         MxEnableState                                       
            MAX-ACCESS     read-write                                          
            STATUS         current                                             
            DESCRIPTION  " Enable Option                                       
                                                                               
                           Enables the domain name option.                     
                           "                                                   
            DEFVAL         { disable }                                         
            ::= { specificDomainNamesEntry 200 }                               
                                                                               
        -- Columnar:  Enable                                                   
                                                                               
        specificDomainNamesEnableSpecific OBJECT-TYPE                          
            SYNTAX        MxEnableState                                        
            MAX-ACCESS    read-write                                           
            STATUS        current                                              
            DESCRIPTION " Enable                                               
                                                                               
                          Defines the domain name configuration to use for a   
                          specific endpoint.                                   
                                                                               
                            * Disable: The endpoint uses the default           
                              configuration as defined in the                  
                              GeneralDomainNameConfigSource and                
                              GeneralStaticDomainName variables.               
                            * Enable: The endpoint uses the specific           
                              configuration as defined in the                  
                              SpecificDomainNames.ConfigSource and             
                              SpecificDomainNames.StaticName variables.        
                                                                               
                          The configuration is valid only when the             
                          SpecificDomainNames.EnableOption variable is set to  
                          'Enable'.                                            
                                                                               
                                                                               
                          "                                                    
            DEFVAL        { disable }                                          
            ::= { specificDomainNamesEntry 300 }                               
                                                                               
        -- Columnar:  Configuration Source                                     
                                                                               
        specificDomainNamesConfigSource OBJECT-TYPE                            
            SYNTAX        INTEGER { hostConfiguration(200) , static(400) }     
            MAX-ACCESS    read-write                                           
            STATUS        current                                              
            DESCRIPTION " Configuration Source                                 
                                                                               
                          Subnet's domain name specific configuration source.  
                                                                               
                            * HostConfiguration: The domain name is obtained   
                              from the host configuration.                     
                            * Static: The domain name is specified in the      
                              StaticName variable.                             
                                                                               
                          This configuration overrides the default             
                          configuration set in the                             
                          GeneralDomainNameConfigSource variable when the      
                          SpecificDomainNames.EnableSpecific variable is set to
                          'Enable'.                                            
                                                                               
                                                                               
                          "                                                    
            DEFVAL        { static }                                           
            ::= { specificDomainNamesEntry 400 }                               
                                                                               
        -- Columnar:  Static Domain Name                                       
                                                                               
        specificDomainNamesStaticName OBJECT-TYPE                              
            SYNTAX        MxIpHostName                                         
            MAX-ACCESS    read-write                                           
            STATUS        current                                              
            DESCRIPTION " Static Domain Name                                   
                                                                               
                          Static Domain Name Configuration. The                
                          SpecificDomainNames.ConfigSource variable must be set
                          to 'Static' for this value to be applied.            
                                                                               
                          This configuration overrides the default             
                          configuration set in the GeneralStaticDomainName     
                          variable when the SpecificDomainNames.EnableSpecific 
                          variable is set to 'Enable'.                         
                                                                               
                                                                               
                          "                                                    
            DEFVAL        { "" }                                               
            ::= { specificDomainNamesEntry 500 }                               
                                                                               
                                                                               
    -- End of table:  Subnet Domain Names                                      
                                                                               
    -- **********************************************************************
                                                                               
    -- Table:  Domain Names Information                                        
                                                                               
    -- **********************************************************************
                                                                               
    domainNamesInfoTable OBJECT-TYPE                                           
        SYNTAX         SEQUENCE OF DomainNamesInfoEntry                        
        MAX-ACCESS     not-accessible                                          
        STATUS         current                                                 
        DESCRIPTION  " Domain Names Information                                
                                                                               
                       This table contains the active subnets' domain names.   
                       "                                                       
        ::= { domainNameGroup 400 }                                            
                                                                               
                                                                               
        domainNamesInfoEntry OBJECT-TYPE                                       
            SYNTAX         DomainNamesInfoEntry                                
            MAX-ACCESS     not-accessible                                      
            STATUS         current                                             
            DESCRIPTION  " A row in the Domain Names Information. "            
            INDEX          {                                                   
                               subnetName                                      
                           }                                                   
                                                                               
            ::= { domainNamesInfoTable 1 }                                     
                                                                               
        DomainNamesInfoEntry ::= SEQUENCE                                      
        {                                                                      
            subnetName   OCTET STRING,                                         
            domainName   OCTET STRING                                          
        }                                                                      
                                                                               
        -- Index:  Subnet Name                                                 
                                                                               
        domainNamesInfoSubnetName OBJECT-TYPE                                  
            SYNTAX         OCTET STRING ( SIZE(1..15) )                        
            MAX-ACCESS     read-only                                           
            STATUS         current                                             
            DESCRIPTION  " Subnet Name                                         
                                                                               
                           Name of the subnet.                                 
                           "                                                   
            ::= { domainNamesInfoEntry 100 }                                   
                                                                               
        -- Columnar:  Domain Name                                              
                                                                               
        domainNamesInfoDomainName OBJECT-TYPE                                  
            SYNTAX         OCTET STRING                                        
            MAX-ACCESS     read-only                                           
            STATUS         current                                             
            DESCRIPTION  " Domain Name                                         
                                                                               
                           Indicates the subnet's current domain name.         
                           "                                                   
            ::= { domainNamesInfoEntry 200 }                                   
                                                                               
                                                                               
    -- End of table:  Domain Names Information                                 
                                                                               
-- End of group:  Domain Name                                                  

-- ****************************************************************************
                                                                              
-- Group:  Lease Time Configuration                                           
                                                                              
-- ****************************************************************************
                                                                              
leaseTimeGroup OBJECT IDENTIFIER                                              
    ::= { dhcpMIBObjects 300 }                                                
                                                                              
                                                                              
    -- Scalar:  Lease Time                                                    
                                                                              
    generalLeaseTime OBJECT-TYPE                                              
        SYNTAX        Unsigned32                                              
        MAX-ACCESS    read-write                                              
        STATUS        current                                                 
        DESCRIPTION " Lease Time                                              
                                                                              
                      Specifies the lease time (in seconds) default setting   
                      for all subnets.                                        
                      "                                                       
        DEFVAL        { 86400 }                                               
        ::= { leaseTimeGroup 100 }                                            
                                                                              
    -- ************************************************************************
                                                                              
    -- Table:  Subnet Lease Times                                             
                                                                              
    -- ************************************************************************
                                                                              
    specificLeaseTimesTable OBJECT-TYPE                                       
        SYNTAX        SEQUENCE OF SpecificLeaseTimesEntry                     
        MAX-ACCESS    not-accessible                                          
        STATUS        current                                                 
        DESCRIPTION " Subnet Lease Times                                      
                                                                              
                      This table specifies subnet-specific lease times        
                      configurations. All subnets use the general             
                      configuration unless the                                
                      SpecificLeaseTimes.EnableSpecific variable is set to    
                      'Enable'.                                               
                                                                              
                      Use the SNMP command 'AddSubnet' to add a new subnet to 
                      the SubnetsTable and to all subnet-specific             
                      configuration tables.                                   
                                                                              
                                                                              
                      "                                                       
        ::= { leaseTimeGroup 200 }                                            
                                                                              
                                                                              
        specificLeaseTimesEntry OBJECT-TYPE                                   
            SYNTAX         SpecificLeaseTimesEntry                            
            MAX-ACCESS     not-accessible                                     
            STATUS         current                                            
            DESCRIPTION  " A row in the Subnet Lease Times. "                 
            INDEX          {                                                  
                               subnetName                                     
                           }                                                  
                                                                              
            ::= { specificLeaseTimesTable 1 }                                 
                                                                              
        SpecificLeaseTimesEntry ::= SEQUENCE                                  
        {                                                                     
            subnetName       OCTET STRING,                                    
            enableSpecific   MxEnableState,                                   
            leaseTime        Unsigned32                                       
        }                                                                     
                                                                              
        -- Index:  Subnet Name                                                
                                                                              
        specificLeaseTimesSubnetName OBJECT-TYPE                              
            SYNTAX         OCTET STRING ( SIZE(1..15) )                       
            MAX-ACCESS     read-only                                          
            STATUS         current                                            
            DESCRIPTION  " Subnet Name                                        
                                                                              
                           Name of the subnet.                                
                           "                                                  
            ::= { specificLeaseTimesEntry 100 }                               
                                                                              
        -- Columnar:  Enable                                                  
                                                                              
        specificLeaseTimesEnableSpecific OBJECT-TYPE                          
            SYNTAX        MxEnableState                                       
            MAX-ACCESS    read-write                                          
            STATUS        current                                             
            DESCRIPTION " Enable                                              
                                                                              
                          Defines the lease time configuration to use for a   
                          specific endpoint.                                  
                                                                              
                            * Disable: The endpoint uses the default          
                              configuration as defined in the GeneralLeaseTime
                              variable.                                       
                            * Enable: The endpoint uses the specific          
                              configuration as defined in the                 
                              SpecificLeaseTimes.LeaseTime variable.          
                                                                              
                                                                              
                          "                                                   
            DEFVAL        { disable }                                         
            ::= { specificLeaseTimesEntry 200 }                               
                                                                              
        -- Columnar:  Lease Time                                              
                                                                              
        specificLeaseTimesLeaseTime OBJECT-TYPE                               
            SYNTAX        Unsigned32                                          
            MAX-ACCESS    read-write                                          
            STATUS        current                                             
            DESCRIPTION " Lease Time                                          
                                                                              
                          Specifies the subnet's specific lease time in       
                          seconds.                                            
                                                                              
                          This configuration overrides the default            
                          configuration set in the GeneralLeaseTime variable  
                          when the SpecificLeaseTimes.EnableSpecific variable 
                          is set to 'Enable'.                                 
                                                                              
                                                                              
                          "                                                   
            DEFVAL        { 86400 }                                           
            ::= { specificLeaseTimesEntry 300 }                               
                                                                              
                                                                              
    -- End of table:  Subnet Lease Times                                      
                                                                              
    -- ************************************************************************
                                                                              
    -- Table:  Lease Times                                                    
                                                                              
    -- ************************************************************************
                                                                              
    leaseTimesInfoTable OBJECT-TYPE                                           
        SYNTAX        SEQUENCE OF LeaseTimesInfoEntry                         
        MAX-ACCESS    not-accessible                                          
        STATUS        current                                                 
        DESCRIPTION " Lease Times                                             
                                                                              
                      This table contains the active subnets' lease times.    
                      "                                                       
        ::= { leaseTimeGroup 300 }                                            
                                                                              
                                                                              
        leaseTimesInfoEntry OBJECT-TYPE                                       
            SYNTAX         LeaseTimesInfoEntry                                
            MAX-ACCESS     not-accessible                                     
            STATUS         current                                            
            DESCRIPTION  " A row in the Lease Times. "                        
            INDEX          {                                                  
                               subnetName                                     
                           }                                                  
                                                                              
            ::= { leaseTimesInfoTable 1 }                                     
                                                                              
        LeaseTimesInfoEntry ::= SEQUENCE                                      
        {                                                                     
             subnetName   OCTET STRING,                                       
             default      Unsigned32                                          
        }                                                                     
                                                                              
        -- Index:  Subnet Name                                                
                                                                              
        leaseTimesInfoSubnetName OBJECT-TYPE                                  
            SYNTAX         OCTET STRING ( SIZE(1..15) )                       
            MAX-ACCESS     read-only                                          
            STATUS         current                                            
            DESCRIPTION  " Subnet Name                                        
                                                                              
                           Name of the subnet.                                
                           "                                                  
            ::= { leaseTimesInfoEntry 100 }                                   
                                                                              
        -- Columnar:  Lease Time                                              
                                                                              
        leaseTimesInfoDefault OBJECT-TYPE                                     
            SYNTAX        Unsigned32                                          
            MAX-ACCESS    read-only                                           
            STATUS        current                                             
            DESCRIPTION " Lease Time                                          
                                                                              
                          Indicates the subnet's current default lease time in
                          seconds.                                            
                          "                                                   
            ::= { leaseTimesInfoEntry 200 }                                   
                                                                              
                                                                              
    -- End of table:  Lease Times                                             
                                                                              
-- End of group:  Lease Time Configuration                                    

-- *****************************************************************************
                                                                               
-- Group:  Default Router                                                      
                                                                               
-- *****************************************************************************
                                                                               
defaultRouterGroup OBJECT IDENTIFIER                                           
    ::= { dhcpMIBObjects 400 }                                                 
                                                                               
                                                                               
    -- *************************************************************************
                                                                               
    -- Table:  Subnet Default Routers                                          
                                                                               
    -- *************************************************************************
                                                                               
    specificDefaultRoutersTable OBJECT-TYPE                                    
        SYNTAX        SEQUENCE OF SpecificDefaultRoutersEntry                  
        MAX-ACCESS    not-accessible                                           
        STATUS        current                                                  
        DESCRIPTION " Subnet Default Routers                                   
                                                                               
                      This table specifies subnet-specific default routers     
                      configurations.                                          
                                                                               
                      Use the SNMP command 'AddSubnet' to add a new subnet to  
                      the SubnetsTable and to all subnet-specific configuration
                      tables.                                                  
                                                                               
                                                                               
                      "                                                        
        ::= { defaultRouterGroup 100 }                                         
                                                                               
                                                                               
        specificDefaultRoutersEntry OBJECT-TYPE                                
            SYNTAX         SpecificDefaultRoutersEntry                         
            MAX-ACCESS     not-accessible                                      
            STATUS         current                                             
            DESCRIPTION  " A row in the Subnet Default Routers. "              
            INDEX          {                                                   
                               subnetName                                      
                           }                                                   
                                                                               
            ::= { specificDefaultRoutersTable 1 }                              
                                                                               
        SpecificDefaultRoutersEntry ::= SEQUENCE                               
        {                                                                      
             subnetName      OCTET STRING,                                     
             enableOption    MxEnableState,                                    
             configSource    INTEGER,                                          
             staticRouter    MxIpAddr                                          
        }                                                                      
                                                                               
        -- Index:  Subnet Name                                                 
                                                                               
        specificDefaultRoutersSubnetName OBJECT-TYPE                           
            SYNTAX         OCTET STRING ( SIZE(1..15) )                        
            MAX-ACCESS     read-only                                           
            STATUS         current                                             
            DESCRIPTION  " Subnet Name                                         
                                                                               
                           Name of the subnet.                                 
                           "                                                   
            ::= { specificDefaultRoutersEntry 100 }                            
                                                                               
        -- Columnar:  Enable Option                                            
                                                                               
        specificDefaultRoutersEnableOption OBJECT-TYPE                         
            SYNTAX         MxEnableState                                       
            MAX-ACCESS     read-write                                          
            STATUS         current                                             
            DESCRIPTION  " Enable Option                                       
                                                                               
                           Enables the default router option.                  
                           "                                                   
            DEFVAL         { enable }                                          
            ::= { specificDefaultRoutersEntry 200 }                            
                                                                               
        -- Columnar:  Configuration Source                                     
                                                                               
        specificDefaultRoutersConfigSource OBJECT-TYPE                         
            SYNTAX        INTEGER { hostInterface(100) , static(400) }         
            MAX-ACCESS    read-write                                           
            STATUS        current                                              
            DESCRIPTION " Configuration Source                                 
                                                                               
                          The subnet's specific router configuration source.   
                                                                               
                            * HostInterface: The default router is the host    
                              address within the client's subnet.              
                            * Static: The default router is specified in the   
                              SpecificDefaultRouters.StaticRouter variable.    
                                                                               
                                                                               
                          "                                                    
            DEFVAL        { hostInterface }                                    
            ::= { specificDefaultRoutersEntry 300 }                            
                                                                               
        -- Columnar:  Static Default Router                                    
                                                                               
        specificDefaultRoutersStaticRouter OBJECT-TYPE                         
            SYNTAX        MxIpAddr                                             
            MAX-ACCESS    read-write                                           
            STATUS        current                                              
            DESCRIPTION " Static Default Router                                
                                                                               
                          Specifies the subnet's default router. The           
                          SpecificDefaultRouters.ConfigSource variable must be 
                          set to 'Static' for this value to be applied.        
                          "                                                    
            DEFVAL        { "" }                                               
            ::= { specificDefaultRoutersEntry 400 }                            
                                                                               
                                                                               
    -- End of table:  Subnet Default Routers                                   
                                                                               
    -- *************************************************************************
                                                                               
    -- Table:  Default Routers                                                 
                                                                               
    -- *************************************************************************
                                                                               
    defaultRoutersInfoTable OBJECT-TYPE                                        
        SYNTAX         SEQUENCE OF DefaultRoutersInfoEntry                     
        MAX-ACCESS     not-accessible                                          
        STATUS         current                                                 
        DESCRIPTION  " Default Routers                                         
                                                                               
                       This table contains the active subnets' default routers.
                       "                                                       
        ::= { defaultRouterGroup 200 }                                         
                                                                               
                                                                               
        defaultRoutersInfoEntry OBJECT-TYPE                                    
            SYNTAX         DefaultRoutersInfoEntry                             
            MAX-ACCESS     not-accessible                                      
            STATUS         current                                             
            DESCRIPTION  " A row in the Default Routers. "                     
            INDEX          {                                                   
                               subnetName                                      
                           }                                                   
                                                                               
            ::= { defaultRoutersInfoTable 1 }                                  
                                                                               
        DefaultRoutersInfoEntry ::= SEQUENCE                                   
        {                                                                      
            subnetName       OCTET STRING,                                     
            defaultRouter    MxIpAddr                                          
        }                                                                      
                                                                               
        -- Index:  Subnet Name                                                 
                                                                               
        defaultRoutersInfoSubnetName OBJECT-TYPE                               
            SYNTAX         OCTET STRING ( SIZE(1..15) )                        
            MAX-ACCESS     read-only                                           
            STATUS         current                                             
            DESCRIPTION  " Subnet Name                                         
                                                                               
                           Name of the subnet.                                 
                           "                                                   
            ::= { defaultRoutersInfoEntry 100 }                                
                                                                               
        -- Columnar:  Default Router                                           
                                                                               
        defaultRoutersInfoDefaultRouter OBJECT-TYPE                            
            SYNTAX         MxIpAddr                                            
            MAX-ACCESS     read-only                                           
            STATUS         current                                             
            DESCRIPTION  " Default Router                                      
                                                                               
                           Indicates the subnet's current default router.      
                           "                                                   
            ::= { defaultRoutersInfoEntry 200 }                                
                                                                               
                                                                               
    -- End of table:  Default Routers                                          
                                                                               
-- End of group:  Default Router                                               

-- *****************************************************************************
                                                                               
-- Group:  DNS Servers                                                         
                                                                               
-- *****************************************************************************
                                                                               
dnsServersGroup OBJECT IDENTIFIER                                              
    ::= { dhcpMIBObjects 500 }                                                 
                                                                               
                                                                               
    -- Scalar:  Configuration Source                                           
                                                                               
    generalDnsServersConfigSource OBJECT-TYPE                                  
        SYNTAX        INTEGER { hostConfiguration(200) , automatic(300) ,      
                      static(400) }                                            
        MAX-ACCESS    read-write                                               
        STATUS        current                                                  
        DESCRIPTION " Configuration Source                                     
                                                                               
                      Default configuration source for the DNS servers of all  
                      subnets.                                                 
                                                                               
                        * HostConfiguration: The DNS servers are obtained from 
                          the host configuration.                              
                        * Automatic: The DNS servers are automatically obtained
                          from the Uplink network.                             
                        * Static: The DNS servers are specified in the         
                          GeneralStaticDnsServers table.                       
                                                                               
                                                                               
                      "                                                        
        DEFVAL        { hostConfiguration }                                    
        ::= { dnsServersGroup 100 }                                            
                                                                               
    -- *************************************************************************
                                                                               
    -- Table:  Static DNS Servers                                              
                                                                               
    -- *************************************************************************
                                                                               
    generalStaticDnsServersTable OBJECT-TYPE                                   
        SYNTAX        SEQUENCE OF GeneralStaticDnsServersEntry                 
        MAX-ACCESS    not-accessible                                           
        STATUS        current                                                  
        DESCRIPTION " Static DNS Servers                                       
                                                                               
                      This table contains the list of default static DNS       
                      servers for all subnets. The DNS servers are sorted by   
                      priority. These DNS servers are used as the current DNS  
                      servers when the GeneralDnsServersConfigSource variable  
                      is set to 'Static'.                                      
                      "                                                        
        ::= { dnsServersGroup 200 }                                            
                                                                               
                                                                               
        generalStaticDnsServersEntry OBJECT-TYPE                               
            SYNTAX         GeneralStaticDnsServersEntry                        
            MAX-ACCESS     not-accessible                                      
            STATUS         current                                             
            DESCRIPTION  " A row in the Static DNS Servers. "                  
            INDEX          {                                                   
                               priority                                        
                           }                                                   
                                                                               
            ::= { generalStaticDnsServersTable 1 }                             
                                                                               
        GeneralStaticDnsServersEntry ::= SEQUENCE                              
        {                                                                      
              priority        Unsigned32,                                      
              ipAddress       MxIpAddr                                         
        }                                                                      
                                                                               
        -- Index:  Priority                                                    
                                                                               
        generalStaticDnsServersPriority OBJECT-TYPE                            
            SYNTAX        Unsigned32 ( 1..4 )                                  
            MAX-ACCESS    read-only                                            
            STATUS        current                                              
            DESCRIPTION " Priority                                             
                                                                               
                          Priority number of this static DNS server. The lower 
                          the number is, the higher the priority is.           
                          "                                                    
            ::= { generalStaticDnsServersEntry 100 }                           
                                                                               
        -- Columnar:  IP Address                                               
                                                                               
        generalStaticDnsServersIpAddress OBJECT-TYPE                           
            SYNTAX         MxIpAddr                                            
            MAX-ACCESS     read-write                                          
            STATUS         current                                             
            DESCRIPTION  " IP Address                                          
                                                                               
                           Static DNS server's IP address.                     
                           "                                                   
            ::= { generalStaticDnsServersEntry 200 }                           
                                                                               
                                                                               
    -- End of table:  Static DNS Servers                                       
                                                                               
    -- *************************************************************************
                                                                               
    -- Table:  Subnet DNS Servers                                              
                                                                               
    -- *************************************************************************
                                                                               
    specificDnsServersTable OBJECT-TYPE                                        
        SYNTAX        SEQUENCE OF SpecificDnsServersEntry                      
        MAX-ACCESS    not-accessible                                           
        STATUS        current                                                  
        DESCRIPTION " Subnet DNS Servers                                       
                                                                               
                      This table specifies subnet-specific DNS servers         
                      configurations. All subnets use the default configuration
                      unless the SpecificDnsServersEnableSpecific variable is  
                      set to 'Enable'.                                         
                                                                               
                      Use the SNMP command 'AddSubnet' to add a new subnet to  
                      the SubnetsTable and to all subnet-specific configuration
                      tables.                                                  
                                                                               
                                                                               
                      "                                                        
        ::= { dnsServersGroup 300 }                                            
                                                                               
                                                                               
        specificDnsServersEntry OBJECT-TYPE                                    
            SYNTAX         SpecificDnsServersEntry                             
            MAX-ACCESS     not-accessible                                      
            STATUS         current                                             
            DESCRIPTION  " A row in the Subnet DNS Servers. "                  
            INDEX          {                                                   
                               subnetName                                      
                           }                                                   
                                                                               
            ::= { specificDnsServersTable 1 }                                  
                                                                               
        SpecificDnsServersEntry ::= SEQUENCE                                   
        {                                                                      
            subnetName       OCTET STRING,                                     
            enableOption     MxEnableState,                                    
            enableSpecific   MxEnableState,                                    
            configSource     INTEGER,                                          
            staticDns1       MxIpAddr,                                         
            staticDns2       MxIpAddr,                                         
            staticDns3       MxIpAddr,                                         
            staticDns4       MxIpAddr                                          
        }                                                                      
                                                                               
        -- Index:  Subnet Name                                                 
                                                                               
        specificDnsServersSubnetName OBJECT-TYPE                               
            SYNTAX         OCTET STRING ( SIZE(1..15) )                        
            MAX-ACCESS     read-only                                           
            STATUS         current                                             
            DESCRIPTION  " Subnet Name                                         
                                                                               
                           Name of the subnet.                                 
                           "                                                   
            ::= { specificDnsServersEntry 100 }                                
                                                                               
        -- Columnar:  Enable Option                                            
                                                                               
        specificDnsServersEnableOption OBJECT-TYPE                             
            SYNTAX         MxEnableState                                       
            MAX-ACCESS     read-write                                          
            STATUS         current                                             
            DESCRIPTION  " Enable Option                                       
                                                                               
                           Enables the DNS servers option.                     
                           "                                                   
            DEFVAL         { enable }                                          
            ::= { specificDnsServersEntry 200 }                                
                                                                               
        -- Columnar:  Enable                                                   
                                                                               
        specificDnsServersEnableSpecific OBJECT-TYPE                           
            SYNTAX        MxEnableState                                        
            MAX-ACCESS    read-write                                           
            STATUS        current                                              
            DESCRIPTION " Enable                                               
                                                                               
                          Defines the DNS servers configuration to use for a   
                          specific endpoint.                                   
                                                                               
                            * Disable: The endpoint uses the default           
                              configuration as defined in the                  
                              GeneralDnsServersConfigSource and                
                              GeneralStaticDnsServers.IpAddress variables.     
                            * Enable: The endpoint uses the specific           
                              configuration as defined in the                  
                              SpecificDnsServers.ConfigSource,                 
                              SpecificDnsServers.StaticDns1,                   
                              SpecificDnsServers.StaticDns2,                   
                              SpecificDnsServers.StaticDns3, and               
                              SpecificDnsServers.StaticDns4 variables.         
                                                                               
                          The configuration is valid only when the             
                          SpecificDnsServers.EnableOption variable is set to   
                          'Enable'.                                            
                                                                               
                                                                               
                          "                                                    
            DEFVAL        { disable }                                          
            ::= { specificDnsServersEntry 300 }                                
                                                                               
        -- Columnar:  Configuration Source                                     
                                                                               
        specificDnsServersConfigSource OBJECT-TYPE                             
            SYNTAX        INTEGER { hostConfiguration(200) , automatic(300) ,  
                          static(400) }                                        
            MAX-ACCESS    read-write                                           
            STATUS        current                                              
            DESCRIPTION " Configuration Source                                 
                                                                               
                          DNS servers specific configuration source for the    
                          subnet.                                              
                                                                               
                            * HostConfiguration: The DNS servers are obtained  
                              from the host configuration.                     
                            * Automatic: The DNS servers are automatically     
                              obtained from the Uplink network.                
                            * Static: The DNS servers are specified in the     
                              StaticDns variables of this table.               
                                                                               
                          This configuration overrides the default             
                          configuration set in the                             
                          GeneralDnsServersConfigSource variable when the      
                          SpecificDnsServers.EnableSpecific variable is set to 
                          'Enable'.                                            
                                                                               
                                                                               
                          "                                                    
            DEFVAL        { static }                                           
            ::= { specificDnsServersEntry 400 }                                
                                                                               
        -- Columnar:  Static DNS 1                                             
                                                                               
        specificDnsServersStaticDns1 OBJECT-TYPE                               
            SYNTAX        MxIpAddr                                             
            MAX-ACCESS    read-write                                           
            STATUS        current                                              
            DESCRIPTION " Static DNS 1                                         
                                                                               
                          IP address of the first DNS server of the subnet. The
                          SpecificDnsServers.ConfigSource variable must be set 
                          to 'Static' for this value to be applied.            
                                                                               
                          This configuration overrides the default             
                          configuration set in the                             
                          GeneralStaticDnsServers.IpAddress variable when the  
                          SpecificDnsServers.EnableSpecific variable is set to 
                          'Enable'.                                            
                                                                               
                                                                               
                          "                                                    
            DEFVAL        { "" }                                               
            ::= { specificDnsServersEntry 500 }                                
                                                                               
        -- Columnar:  Static DNS 2                                             
                                                                               
        specificDnsServersStaticDns2 OBJECT-TYPE                               
            SYNTAX        MxIpAddr                                             
            MAX-ACCESS    read-write                                           
            STATUS        current                                              
            DESCRIPTION " Static DNS 2                                         
                                                                               
                          IP address of the second DNS server of the subnet.   
                          The SpecificDnsServers.ConfigSource variable must be 
                          set to 'Static' for this value to be applied.        
                                                                               
                          This configuration overrides the default             
                          configuration set in the                             
                          GeneralStaticDnsServers.IpAddress variable when the  
                          SpecificDnsServers.EnableSpecific variable is set to 
                          'Enable'.                                            
                                                                               
                                                                               
                          "                                                    
            DEFVAL        { "" }                                               
            ::= { specificDnsServersEntry 600 }                                
                                                                               
        -- Columnar:  Static DNS 3                                             
                                                                               
        specificDnsServersStaticDns3 OBJECT-TYPE                               
            SYNTAX        MxIpAddr                                             
            MAX-ACCESS    read-write                                           
            STATUS        current                                              
            DESCRIPTION " Static DNS 3                                         
                                                                               
                          IP address of the third DNS server of the subnet. The
                          SpecificDnsServers.ConfigSource variable must be set 
                          to 'Static' for this value to be applied.            
                                                                               
                          This configuration overrides the default             
                          configuration set in the                             
                          GeneralStaticDnsServers.IpAddress variable when the  
                          SpecificDnsServers.EnableSpecific variable is set to 
                          'Enable'.                                            
                                                                               
                                                                               
                          "                                                    
            DEFVAL        { "" }                                               
            ::= { specificDnsServersEntry 700 }                                
                                                                               
        -- Columnar:  Static DNS 4                                             
                                                                               
        specificDnsServersStaticDns4 OBJECT-TYPE                               
            SYNTAX        MxIpAddr                                             
            MAX-ACCESS    read-write                                           
            STATUS        current                                              
            DESCRIPTION " Static DNS 4                                         
                                                                               
                          IP address of the fourth DNS server of the subnet.   
                          The SpecificDnsServers.ConfigSource variable must be 
                          set to 'Static' for this value to be applied.        
                                                                               
                          This configuration overrides the default             
                          configuration set in the                             
                          GeneralStaticDnsServers.IpAddress variable when the  
                          SpecificDnsServers.EnableSpecific variable is set to 
                          'Enable'.                                            
                                                                               
                                                                               
                          "                                                    
            DEFVAL        { "" }                                               
            ::= { specificDnsServersEntry 800 }                                
                                                                               
                                                                               
    -- End of table:  Subnet DNS Servers                                       
                                                                               
    -- *********************************************************************
                                                                               
    -- Table:  DNS Servers                                                     
                                                                               
    -- *********************************************************************
                                                                               
    dnsServersInfoTable OBJECT-TYPE                                            
        SYNTAX         SEQUENCE OF DnsServersInfoEntry                         
        MAX-ACCESS     not-accessible                                          
        STATUS         current                                                 
        DESCRIPTION  " DNS Servers                                             
                                                                               
                       This table contains the active subnets' DNS servers.    
                       "                                                       
        ::= { dnsServersGroup 400 }                                            
                                                                               
                                                                               
        dnsServersInfoEntry OBJECT-TYPE                                        
            SYNTAX         DnsServersInfoEntry                                 
            MAX-ACCESS     not-accessible                                      
            STATUS         current                                             
            DESCRIPTION  " A row in the DNS Servers. "                         
            INDEX          {                                                   
                               subnetName                                      
                           }                                                   
                                                                               
            ::= { dnsServersInfoTable 1 }                                      
                                                                               
        DnsServersInfoEntry ::= SEQUENCE                                       
        {                                                                      
             subnetName   OCTET STRING,                                        
             dns1         MxIpAddr,                                            
             dns2         MxIpAddr,                                            
             dns3         MxIpAddr,                                            
             dns4         MxIpAddr                                             
        }                                                                      
                                                                               
        -- Index:  Subnet Name                                                 
                                                                               
        dnsServersInfoSubnetName OBJECT-TYPE                                   
            SYNTAX         OCTET STRING ( SIZE(1..15) )                        
            MAX-ACCESS     read-only                                           
            STATUS         current                                             
            DESCRIPTION  " Subnet Name                                         
                                                                               
                           Name of the subnet.                                 
                           "                                                   
            ::= { dnsServersInfoEntry 100 }                                    
                                                                               
        -- Columnar:  DNS 1                                                    
                                                                               
        dnsServersInfoDns1 OBJECT-TYPE                                         
            SYNTAX         MxIpAddr                                            
            MAX-ACCESS     read-only                                           
            STATUS         current                                             
            DESCRIPTION  " DNS 1                                               
                                                                               
                           Indicates the subnets' first DNS server.            
                           "                                                   
            ::= { dnsServersInfoEntry 200 }                                    
                                                                               
        -- Columnar:  DNS 2                                                    
                                                                               
        dnsServersInfoDns2 OBJECT-TYPE                                         
            SYNTAX         MxIpAddr                                            
            MAX-ACCESS     read-only                                           
            STATUS         current                                             
            DESCRIPTION  " DNS 2                                               
                                                                               
                           Indicates the subnets' second DNS server.           
                           "                                                   
            ::= { dnsServersInfoEntry 300 }                                    
                                                                               
        -- Columnar:  DNS 3                                                    
                                                                               
        dnsServersInfoDns3 OBJECT-TYPE                                         
            SYNTAX         MxIpAddr                                            
            MAX-ACCESS     read-only                                           
            STATUS         current                                             
            DESCRIPTION  " DNS 3                                               
                                                                               
                           Indicates the subnets' third DNS server.            
                           "                                                   
            ::= { dnsServersInfoEntry 400 }                                    
                                                                               
        -- Columnar:  DNS 4                                                    
                                                                               
        dnsServersInfoDns4 OBJECT-TYPE                                         
            SYNTAX         MxIpAddr                                            
            MAX-ACCESS     read-only                                           
            STATUS         current                                             
            DESCRIPTION  " DNS 4                                               
                                                                               
                           Indicates the subnets' fourth DNS server.           
                           "                                                   
            ::= { dnsServersInfoEntry 500 }                                    
                                                                               
                                                                               
    -- End of table:  DNS Servers                                              
                                                                               
-- End of group:  DNS Servers                                                  

-- *****************************************************************************
                                                                               
-- Group:  NTP Servers                                                         
                                                                               
-- *****************************************************************************
                                                                               
ntpServersGroup OBJECT IDENTIFIER                                              
    ::= { dhcpMIBObjects 600 }                                                 
                                                                               
                                                                               
    -- Scalar:  Configuration Source                                           
                                                                               
    generalNtpServersConfigSource OBJECT-TYPE                                  
        SYNTAX        INTEGER { hostConfiguration(200) , automatic(300) ,      
                      static(400) }                                            
        MAX-ACCESS    read-write                                               
        STATUS        current                                                  
        DESCRIPTION " Configuration Source                                     
                                                                               
                      Default configuration source for the NTP servers of all  
                      subnets.                                                 
                                                                               
                        * HostConfiguration: The NTP servers are obtained from 
                          the host configuration.                              
                        * Automatic: The NTP servers are automatically obtained
                          from the Uplink network.                             
                        * Static: The NTP servers are specified in the         
                          GeneralStaticNtpServers table.                       
                                                                               
                                                                               
                      "                                                        
        DEFVAL        { hostConfiguration }                                    
        ::= { ntpServersGroup 100 }                                            
                                                                               
    -- *************************************************************************
                                                                               
    -- Table:  Static NTP Servers                                              
                                                                               
    -- *************************************************************************
                                                                               
    generalStaticNtpServersTable OBJECT-TYPE                                   
        SYNTAX        SEQUENCE OF GeneralStaticNtpServersEntry                 
        MAX-ACCESS    not-accessible                                           
        STATUS        current                                                  
        DESCRIPTION " Static NTP Servers                                       
                                                                               
                      This table contains the list of default static NTP       
                      servers for all subnets. The NTP servers are sorted by   
                      priority. These NTP servers are used as the current NTP  
                      servers when the GeneralNtpServersConfigSource variable  
                      is set to 'Static'.                                      
                      "                                                        
        ::= { ntpServersGroup 200 }                                            
                                                                               
                                                                               
        generalStaticNtpServersEntry OBJECT-TYPE                               
            SYNTAX         GeneralStaticNtpServersEntry                        
            MAX-ACCESS     not-accessible                                      
            STATUS         current                                             
            DESCRIPTION  " A row in the Static NTP Servers. "                  
            INDEX          {                                                   
                               priority                                        
                           }                                                   
                                                                               
            ::= { generalStaticNtpServersTable 1 }                             
                                                                               
        GeneralStaticNtpServersEntry ::= SEQUENCE                              
        {                                                                      
              priority        Unsigned32,                                      
              ipAddress       MxIpAddr                                         
        }                                                                      
                                                                               
        -- Index:  Priority                                                    
                                                                               
        generalStaticNtpServersPriority OBJECT-TYPE                            
            SYNTAX        Unsigned32 ( 1..4 )                                  
            MAX-ACCESS    read-only                                            
            STATUS        current                                              
            DESCRIPTION " Priority                                             
                                                                               
                          Priority number of this static NTP server. The lower 
                          the number is, the higher the priority is.           
                          "                                                    
            ::= { generalStaticNtpServersEntry 100 }                           
                                                                               
        -- Columnar:  IP Address                                               
                                                                               
        generalStaticNtpServersIpAddress OBJECT-TYPE                           
            SYNTAX         MxIpAddr                                            
            MAX-ACCESS     read-write                                          
            STATUS         current                                             
            DESCRIPTION  " IP Address                                          
                                                                               
                           NTP server's static IP address.                     
                           "                                                   
            ::= { generalStaticNtpServersEntry 200 }                           
                                                                               
                                                                               
    -- End of table:  Static NTP Servers                                       
                                                                               
    -- *************************************************************************
                                                                               
    -- Table:  Subnet NTP Servers                                              
                                                                               
    -- *************************************************************************
                                                                               
    specificNtpServersTable OBJECT-TYPE                                        
        SYNTAX        SEQUENCE OF SpecificNtpServersEntry                      
        MAX-ACCESS    not-accessible                                           
        STATUS        current                                                  
        DESCRIPTION " Subnet NTP Servers                                       
                                                                               
                      This table specifies subnet-specific NTP servers         
                      configurations. All subnets use the default configuration
                      unless the SpecificNtpServersEnableSpecific variable is  
                      set to 'Enable'.                                         
                                                                               
                      Use the SNMP command 'AddSubnet' to add a new subnet to  
                      the SubnetsTable and to all subnet-specific configuration
                      tables.                                                  
                                                                               
                                                                               
                      "                                                        
        ::= { ntpServersGroup 300 }                                            
                                                                               
                                                                               
        specificNtpServersEntry OBJECT-TYPE                                    
            SYNTAX         SpecificNtpServersEntry                             
            MAX-ACCESS     not-accessible                                      
            STATUS         current                                             
            DESCRIPTION  " A row in the Subnet NTP Servers. "                  
            INDEX          {                                                   
                               subnetName                                      
                           }                                                   
                                                                               
            ::= { specificNtpServersTable 1 }                                  
                                                                               
        SpecificNtpServersEntry ::= SEQUENCE                                   
        {                                                                      
            subnetName       OCTET STRING,                                     
            enableOption     MxEnableState,                                    
            enableSpecific   MxEnableState,                                    
            configSource     INTEGER,                                          
            staticNtp1       MxIpAddr,                                         
            staticNtp2       MxIpAddr,                                         
            staticNtp3       MxIpAddr,                                         
            staticNtp4       MxIpAddr                                          
        }                                                                      
                                                                               
        -- Index:  Subnet Name                                                 
                                                                               
        specificNtpServersSubnetName OBJECT-TYPE                               
            SYNTAX         OCTET STRING ( SIZE(1..15) )                        
            MAX-ACCESS     read-only                                           
            STATUS         current                                             
            DESCRIPTION  " Subnet Name                                         
                                                                               
                           Name of the subnet.                                 
                           "                                                   
            ::= { specificNtpServersEntry 100 }                                
                                                                               
        -- Columnar:  Enable Option                                            
                                                                               
        specificNtpServersEnableOption OBJECT-TYPE                             
            SYNTAX         MxEnableState                                       
            MAX-ACCESS     read-write                                          
            STATUS         current                                             
            DESCRIPTION  " Enable Option                                       
                                                                               
                           Enables the NTP servers option.                     
                           "                                                   
            DEFVAL         { disable }                                         
            ::= { specificNtpServersEntry 200 }                                
                                                                               
        -- Columnar:  Enable                                                   
                                                                               
        specificNtpServersEnableSpecific OBJECT-TYPE                           
            SYNTAX        MxEnableState                                        
            MAX-ACCESS    read-write                                           
            STATUS        current                                              
            DESCRIPTION " Enable                                               
                                                                               
                          Defines the NTP servers configuration to use for a   
                          specific endpoint.                                   
                                                                               
                            * Disable: The endpoint uses the default           
                              configuration as defined in the                  
                              GeneralNtpServersConfigSource and                
                              GeneralStaticNtpServers.IpAddress variables.     
                            * Enable: The endpoint uses the specific           
                              configuration as defined in the                  
                              SpecificNtpServers.ConfigSource,                 
                              SpecificNtpServers.StaticNtp1,                   
                              SpecificNtpServers.StaticNtp2,                   
                              SpecificNtpServers.StaticNtp3, and               
                              SpecificNtpServers.StaticNtp4 variables.         
                                                                               
                          The configuration is valid only when the             
                          SpecificNtpServers.EnableOption variable is set to   
                          'Enable'.                                            
                                                                               
                                                                               
                          "                                                    
            DEFVAL        { disable }                                          
            ::= { specificNtpServersEntry 300 }                                
                                                                               
        -- Columnar:  Configuration Source                                     
                                                                               
        specificNtpServersConfigSource OBJECT-TYPE                             
            SYNTAX        INTEGER { hostConfiguration(200) , automatic(300) ,  
                          static(400) }                                        
            MAX-ACCESS    read-write                                           
            STATUS        current                                              
            DESCRIPTION " Configuration Source                                 
                                                                               
                          NTP servers specific configuration source for the    
                          subnet.                                              
                                                                               
                            * HostConfiguration: The NTP servers are obtained  
                              from the host configuration.                     
                            * Automatic: The NTP servers are automatically     
                              obtained from the Uplink network.                
                            * Static: The NTP servers are specified in the     
                              StaticNtp variables of this table.               
                                                                               
                          This configuration overrides the default             
                          configuration set in the                             
                          GeneralNtpServersConfigSource variable when the      
                          SpecificNtpServers.EnableSpecific variable is set to 
                          'Enable'.                                            
                                                                               
                                                                               
                          "                                                    
            DEFVAL        { hostConfiguration }                                
            ::= { specificNtpServersEntry 400 }                                
                                                                               
        -- Columnar:  Static NTP 1                                             
                                                                               
        specificNtpServersStaticNtp1 OBJECT-TYPE                               
            SYNTAX        MxIpAddr                                             
            MAX-ACCESS    read-write                                           
            STATUS        current                                              
            DESCRIPTION " Static NTP 1                                         
                                                                               
                          IP address of the first NTP server of the subnet. The
                          SpecificNtpServers.ConfigSource variable must be set 
                          to 'Static' for this value to be applied.            
                                                                               
                          This configuration overrides the default             
                          configuration set in the                             
                          GeneralStaticNtpServers.IpAddress variable when the  
                          SpecificNtpServers.EnableSpecific variable is set to 
                          'Enable'.                                            
                                                                               
                                                                               
                          "                                                    
            DEFVAL        { "" }                                               
            ::= { specificNtpServersEntry 500 }                                
                                                                               
        -- Columnar:  Static NTP 2                                             
                                                                               
        specificNtpServersStaticNtp2 OBJECT-TYPE                               
            SYNTAX        MxIpAddr                                             
            MAX-ACCESS    read-write                                           
            STATUS        current                                              
            DESCRIPTION " Static NTP 2                                         
                                                                               
                          IP address of the second NTP server of the subnet.   
                          The SpecificNtpServers.ConfigSource variable must be 
                          set to 'Static' for this value to be applied.        
                                                                               
                          This configuration overrides the default             
                          configuration set in the                             
                          GeneralStaticNtpServers.IpAddress variable when the  
                          SpecificNtpServers.EnableSpecific variable is set to 
                          'Enable'.                                            
                                                                               
                                                                               
                          "                                                    
            DEFVAL        { "" }                                               
            ::= { specificNtpServersEntry 600 }                                
                                                                               
        -- Columnar:  Static NTP 3                                             
                                                                               
        specificNtpServersStaticNtp3 OBJECT-TYPE                               
            SYNTAX        MxIpAddr                                             
            MAX-ACCESS    read-write                                           
            STATUS        current                                              
            DESCRIPTION " Static NTP 3                                         
                                                                               
                          IP address of the third NTP server of the subnet. The
                          SpecificNtpServers.ConfigSource variable must be set 
                          to 'Static' for this value to be applied.            
                                                                               
                          This configuration overrides the default             
                          configuration set in the                             
                          GeneralStaticNtpServers.IpAddress variable when the  
                          SpecificNtpServers.EnableSpecific variable is set to 
                          'Enable'.                                            
                                                                               
                                                                               
                          "                                                    
            DEFVAL        { "" }                                               
            ::= { specificNtpServersEntry 700 }                                
                                                                               
        -- Columnar:  Static NTP 4                                             
                                                                               
        specificNtpServersStaticNtp4 OBJECT-TYPE                               
            SYNTAX        MxIpAddr                                             
            MAX-ACCESS    read-write                                           
            STATUS        current                                              
            DESCRIPTION " Static NTP 4                                         
                                                                               
                          IP address of the fourth NTP server of the subnet.   
                          The SpecificNtpServers.ConfigSource variable must be 
                          set to 'Static' for this value to be applied.        
                                                                               
                          This configuration overrides the default             
                          configuration set in the                             
                          GeneralStaticNtpServers.IpAddress variable when the  
                          SpecificNtpServers.EnableSpecific variable is set to 
                          'Enable'.                                            
                                                                               
                                                                               
                          "                                                    
            DEFVAL        { "" }                                               
            ::= { specificNtpServersEntry 800 }                                
                                                                               
                                                                               
    -- End of table:  Subnet NTP Servers                                       
                                                                               
    -- **********************************************************************
                                                                               
    -- Table:  NTP Servers                                                     
                                                                               
    -- **********************************************************************
                                                                               
    ntpServersInfoTable OBJECT-TYPE                                            
        SYNTAX         SEQUENCE OF NtpServersInfoEntry                         
        MAX-ACCESS     not-accessible                                          
        STATUS         current                                                 
        DESCRIPTION  " NTP Servers                                             
                                                                               
                       This table contains the active subnets's NTP servers.   
                       "                                                       
        ::= { ntpServersGroup 400 }                                            
                                                                               
                                                                               
        ntpServersInfoEntry OBJECT-TYPE                                        
            SYNTAX         NtpServersInfoEntry                                 
            MAX-ACCESS     not-accessible                                      
            STATUS         current                                             
            DESCRIPTION  " A row in the NTP Servers. "                         
            INDEX          {                                                   
                               subnetName                                      
                           }                                                   
                                                                               
            ::= { ntpServersInfoTable 1 }                                      
                                                                               
        NtpServersInfoEntry ::= SEQUENCE                                       
        {                                                                      
             subnetName   OCTET STRING,                                        
             ntp1         MxIpAddr,                                            
             ntp2         MxIpAddr,                                            
             ntp3         MxIpAddr,                                            
             ntp4         MxIpAddr                                             
        }                                                                      
                                                                               
        -- Index:  Subnet Name                                                 
                                                                               
        ntpServersInfoSubnetName OBJECT-TYPE                                   
            SYNTAX         OCTET STRING ( SIZE(1..15) )                        
            MAX-ACCESS     read-only                                           
            STATUS         current                                             
            DESCRIPTION  " Subnet Name                                         
                                                                               
                           Name of the subnet.                                 
                           "                                                   
            ::= { ntpServersInfoEntry 100 }                                    
                                                                               
        -- Columnar:  NTP 1                                                    
                                                                               
        ntpServersInfoNtp1 OBJECT-TYPE                                         
            SYNTAX         MxIpAddr                                            
            MAX-ACCESS     read-only                                           
            STATUS         current                                             
            DESCRIPTION  " NTP 1                                               
                                                                               
                           Indicates the subnets' first NTP server.            
                           "                                                   
            ::= { ntpServersInfoEntry 200 }                                    
                                                                               
        -- Columnar:  NTP 2                                                    
                                                                               
        ntpServersInfoNtp2 OBJECT-TYPE                                         
            SYNTAX         MxIpAddr                                            
            MAX-ACCESS     read-only                                           
            STATUS         current                                             
            DESCRIPTION  " NTP 2                                               
                                                                               
                           Indicates the subnets' second NTP server.           
                           "                                                   
            ::= { ntpServersInfoEntry 300 }                                    
                                                                               
        -- Columnar:  NTP 3                                                    
                                                                               
        ntpServersInfoNtp3 OBJECT-TYPE                                         
            SYNTAX         MxIpAddr                                            
            MAX-ACCESS     read-only                                           
            STATUS         current                                             
            DESCRIPTION  " NTP 3                                               
                                                                               
                           Indicates the subnets' third NTP server.            
                           "                                                   
            ::= { ntpServersInfoEntry 400 }                                    
                                                                               
        -- Columnar:  NTP 4                                                    
                                                                               
        ntpServersInfoNtp4 OBJECT-TYPE                                         
            SYNTAX         MxIpAddr                                            
            MAX-ACCESS     read-only                                           
            STATUS         current                                             
            DESCRIPTION  " NTP 4                                               
                                                                               
                           Indicates the subnets' fourth NTP server.           
                           "                                                   
            ::= { ntpServersInfoEntry 500 }                                    
                                                                               
                                                                               
    -- End of table:  NTP Servers                                              
                                                                               
-- End of group:  NTP Servers                                                  

-- ****************************************************************************
                                                                              
-- Group:  NBNS Servers                                                       
                                                                              
-- ****************************************************************************
                                                                              
nbnsServersGroup OBJECT IDENTIFIER                                            
    ::= { dhcpMIBObjects 700 }                                                
                                                                              
                                                                              
    -- ************************************************************************
                                                                              
    -- Table:  Static NBNS Servers                                            
                                                                              
    -- ************************************************************************
                                                                              
    generalStaticNbnsServersTable OBJECT-TYPE                                 
        SYNTAX        SEQUENCE OF GeneralStaticNbnsServersEntry               
        MAX-ACCESS    not-accessible                                          
        STATUS        current                                                 
        DESCRIPTION " Static NBNS Servers                                     
                                                                              
                      This table contains the list of default static NBNS     
                      servers for all subnets. The NBNS servers are sorted by 
                      priority.                                               
                      "                                                       
        ::= { nbnsServersGroup 100 }                                          
                                                                              
                                                                              
        generalStaticNbnsServersEntry OBJECT-TYPE                             
            SYNTAX         GeneralStaticNbnsServersEntry                      
            MAX-ACCESS     not-accessible                                     
            STATUS         current                                            
            DESCRIPTION  " A row in the Static NBNS Servers. "                
            INDEX          {                                                  
                               priority                                       
                           }                                                  
                                                                              
            ::= { generalStaticNbnsServersTable 1 }                           
                                                                              
        GeneralStaticNbnsServersEntry ::= SEQUENCE                            
        {                                                                     
              priority        Unsigned32,                                     
              ipAddress       MxIpAddr                                        
        }                                                                     
                                                                              
        -- Index:  Priority                                                   
                                                                              
        generalStaticNbnsServersPriority OBJECT-TYPE                          
            SYNTAX        Unsigned32 ( 1..4 )                                 
            MAX-ACCESS    read-only                                           
            STATUS        current                                             
            DESCRIPTION " Priority                                            
                                                                              
                          Priority number of this static NBNS server. The     
                          lower the number is, the higher the priority is.    
                          "                                                   
            ::= { generalStaticNbnsServersEntry 100 }                         
                                                                              
        -- Columnar:  IP Address                                              
                                                                              
        generalStaticNbnsServersIpAddress OBJECT-TYPE                         
            SYNTAX         MxIpAddr                                           
            MAX-ACCESS     read-write                                         
            STATUS         current                                            
            DESCRIPTION  " IP Address                                         
                                                                              
                           NBNS server's static IP address.                   
                           "                                                  
            ::= { generalStaticNbnsServersEntry 200 }                         
                                                                              
                                                                              
    -- End of table:  Static NBNS Servers                                     
                                                                              
    -- ************************************************************************
                                                                              
    -- Table:  Subnet NBNS Servers                                            
                                                                              
    -- ************************************************************************
                                                                              
    specificNbnsServersTable OBJECT-TYPE                                      
        SYNTAX        SEQUENCE OF SpecificNbnsServersEntry                    
        MAX-ACCESS    not-accessible                                          
        STATUS        current                                                 
        DESCRIPTION " Subnet NBNS Servers                                     
                                                                              
                      This table specifies subnet-specific NBNS servers       
                      configurations. All subnets use the general             
                      configuration unless the                                
                      SpecificNbnsServers.EnableSpecific variable is set to   
                      'Enable'.                                               
                                                                              
                      Use the SNMP command 'AddSubnet' to add a new subnet to 
                      the SubnetsTable and to all subnet-specific             
                      configuration tables.                                   
                                                                              
                                                                              
                      "                                                       
        ::= { nbnsServersGroup 200 }                                          
                                                                              
                                                                              
        specificNbnsServersEntry OBJECT-TYPE                                  
            SYNTAX         SpecificNbnsServersEntry                           
            MAX-ACCESS     not-accessible                                     
            STATUS         current                                            
            DESCRIPTION  " A row in the Subnet NBNS Servers. "                
            INDEX          {                                                  
                               subnetName                                     
                           }                                                  
                                                                              
            ::= { specificNbnsServersTable 1 }                                
                                                                              
        SpecificNbnsServersEntry ::= SEQUENCE                                 
        {                                                                     
             subnetName       OCTET STRING,                                   
             enableOption     MxEnableState,                                  
             enableSpecific   MxEnableState,                                  
             staticNbns1      MxIpAddr,                                       
             staticNbns2      MxIpAddr,                                       
             staticNbns3      MxIpAddr,                                       
             staticNbns4      MxIpAddr                                        
        }                                                                     
                                                                              
        -- Index:  Subnet Name                                                
                                                                              
        specificNbnsServersSubnetName OBJECT-TYPE                             
            SYNTAX         OCTET STRING ( SIZE(1..15) )                       
            MAX-ACCESS     read-only                                          
            STATUS         current                                            
            DESCRIPTION  " Subnet Name                                        
                                                                              
                           Name of the subnet.                                
                           "                                                  
            ::= { specificNbnsServersEntry 100 }                              
                                                                              
        -- Columnar:  Enable Option                                           
                                                                              
        specificNbnsServersEnableOption OBJECT-TYPE                           
            SYNTAX         MxEnableState                                      
            MAX-ACCESS     read-write                                         
            STATUS         current                                            
            DESCRIPTION  " Enable Option                                      
                                                                              
                           Enable NBNS servers option.                        
                           "                                                  
            DEFVAL         { disable }                                        
            ::= { specificNbnsServersEntry 200 }                              
                                                                              
        -- Columnar:  Enable                                                  
                                                                              
        specificNbnsServersEnableSpecific OBJECT-TYPE                         
            SYNTAX        MxEnableState                                       
            MAX-ACCESS    read-write                                          
            STATUS        current                                             
            DESCRIPTION " Enable                                              
                                                                              
                          Defines the NBNS servers configuration to use for a 
                          specific endpoint.                                  
                                                                              
                            * Disable: The endpoint uses the default          
                              configuration as defined in the                 
                              GeneralStaticNbnsServers.IpAddress variable.    
                            * Enable: The endpoint uses the specific          
                              configuration as defined in the                 
                              SpecificNbnsServers.StaticNbns1,                
                              SpecificNbnsServers.StaticNbns2,                
                              SpecificNbnsServers.StaticNbns3, and            
                              SpecificNbnsServers.StaticNbns4 variables.      
                                                                              
                          The configuration is valid only when the            
                          SpecificNbnsServers.EnableOption variable is set to 
                          'Enable'.                                           
                                                                              
                                                                              
                          "                                                   
            DEFVAL        { disable }                                         
            ::= { specificNbnsServersEntry 300 }                              
                                                                              
        -- Columnar:  Static NBNS 1                                           
                                                                              
        specificNbnsServersStaticNbns1 OBJECT-TYPE                            
            SYNTAX        MxIpAddr                                            
            MAX-ACCESS    read-write                                          
            STATUS        current                                             
            DESCRIPTION " Static NBNS 1                                       
                                                                              
                          IP address of the first NBNS server of the subnet.  
                          The SpecificNbnsServers.ConfigSource variable must  
                          be set to 'Static' for this value to be applied.    
                                                                              
                          This configuration overrides the default            
                          configuration set in the                            
                          GeneralStaticNbnsServers.IpAddress variable when the
                          SpecificNbnsServers.EnableSpecific variable is set  
                          to 'Enable'.                                        
                                                                              
                                                                              
                          "                                                   
            DEFVAL        { "" }                                              
            ::= { specificNbnsServersEntry 400 }                              
                                                                              
        -- Columnar:  Static NBNS 2                                           
                                                                              
        specificNbnsServersStaticNbns2 OBJECT-TYPE                            
            SYNTAX        MxIpAddr                                            
            MAX-ACCESS    read-write                                          
            STATUS        current                                             
            DESCRIPTION " Static NBNS 2                                       
                                                                              
                          IP address of the second NBNS server of the subnet. 
                          The SpecificNbnsServers.ConfigSource variable must  
                          be set to 'Static' for this value to be applied.    
                                                                              
                          This configuration overrides the default            
                          configuration set in the                            
                          GeneralStaticNbnsServers.IpAddress variable when the
                          SpecificNbnsServers.EnableSpecific variable is set  
                          to 'Enable'.                                        
                                                                              
                                                                              
                          "                                                   
            DEFVAL        { "" }                                              
            ::= { specificNbnsServersEntry 500 }                              
                                                                              
        -- Columnar:  Static NBNS 3                                           
                                                                              
        specificNbnsServersStaticNbns3 OBJECT-TYPE                            
            SYNTAX        MxIpAddr                                            
            MAX-ACCESS    read-write                                          
            STATUS        current                                             
            DESCRIPTION " Static NBNS 3                                       
                                                                              
                          IP address of the third NBNS server of the subnet.  
                          The SpecificNbnsServers.ConfigSource variable must  
                          be set to 'Static' for this value to be applied.    
                                                                              
                          This configuration overrides the default            
                          configuration set in the                            
                          GeneralStaticNbnsServers.IpAddress variable when the
                          SpecificNbnsServers.EnableSpecific variable is set  
                          to 'Enable'.                                        
                                                                              
                                                                              
                          "                                                   
            DEFVAL        { "" }                                              
            ::= { specificNbnsServersEntry 600 }                              
                                                                              
        -- Columnar:  Static NBNS 4                                           
                                                                              
        specificNbnsServersStaticNbns4 OBJECT-TYPE                            
            SYNTAX        MxIpAddr                                            
            MAX-ACCESS    read-write                                          
            STATUS        current                                             
            DESCRIPTION " Static NBNS 4                                       
                                                                              
                          IP address of the fourth NBNS server of the subnet. 
                          The SpecificNbnsServers.ConfigSource variable must  
                          be set to 'Static' for this value to be applied.    
                                                                              
                          This configuration overrides the default            
                          configuration set in the                            
                          GeneralStaticNbnsServers.IpAddress variable when the
                          SpecificNbnsServers.EnableSpecific variable is set  
                          to 'Enable'.                                        
                                                                              
                                                                              
                          "                                                   
            DEFVAL        { "" }                                              
            ::= { specificNbnsServersEntry 700 }                              
                                                                              
                                                                              
    -- End of table:  Subnet NBNS Servers                                     
                                                                              
    -- **********************************************************************
                                                                              
    -- Table:  NBNS Servers                                                   
                                                                              
    -- **********************************************************************
                                                                              
    nbnsServersInfoTable OBJECT-TYPE                                          
        SYNTAX         SEQUENCE OF NbnsServersInfoEntry                       
        MAX-ACCESS     not-accessible                                         
        STATUS         current                                                
        DESCRIPTION  " NBNS Servers                                           
                                                                              
                       This table contains the active subnets' NBNS servers.  
                       "                                                      
        ::= { nbnsServersGroup 300 }                                          
                                                                              
                                                                              
        nbnsServersInfoEntry OBJECT-TYPE                                      
            SYNTAX         NbnsServersInfoEntry                               
            MAX-ACCESS     not-accessible                                     
            STATUS         current                                            
            DESCRIPTION  " A row in the NBNS Servers. "                       
            INDEX          {                                                  
                               subnetName                                     
                           }                                                  
                                                                              
            ::= { nbnsServersInfoTable 1 }                                    
                                                                              
        NbnsServersInfoEntry ::= SEQUENCE                                     
        {                                                                     
            subnetName   OCTET STRING,                                        
            nbns1        MxIpAddr,                                            
            nbns2        MxIpAddr,                                            
            nbns3        MxIpAddr,                                            
            nbns4        MxIpAddr                                             
        }                                                                     
                                                                              
        -- Index:  Subnet Name                                                
                                                                              
        nbnsServersInfoSubnetName OBJECT-TYPE                                 
            SYNTAX         OCTET STRING ( SIZE(1..15) )                       
            MAX-ACCESS     read-only                                          
            STATUS         current                                            
            DESCRIPTION  " Subnet Name                                        
                                                                              
                           Name of the subnet.                                
                           "                                                  
            ::= { nbnsServersInfoEntry 100 }                                  
                                                                              
        -- Columnar:  NBNS 1                                                  
                                                                              
        nbnsServersInfoNbns1 OBJECT-TYPE                                      
            SYNTAX         MxIpAddr                                           
            MAX-ACCESS     read-only                                          
            STATUS         current                                            
            DESCRIPTION  " NBNS 1                                             
                                                                              
                           Indicates the subnets' first NBNS server.          
                           "                                                  
            ::= { nbnsServersInfoEntry 200 }                                  
                                                                              
        -- Columnar:  NBNS 2                                                  
                                                                              
        nbnsServersInfoNbns2 OBJECT-TYPE                                      
            SYNTAX         MxIpAddr                                           
            MAX-ACCESS     read-only                                          
            STATUS         current                                            
            DESCRIPTION  " NBNS 2                                             
                                                                              
                           Indicates the subnets' second NBNS server.         
                           "                                                  
            ::= { nbnsServersInfoEntry 300 }                                  
                                                                              
        -- Columnar:  NBNS 3                                                  
                                                                              
        nbnsServersInfoNbns3 OBJECT-TYPE                                      
            SYNTAX         MxIpAddr                                           
            MAX-ACCESS     read-only                                          
            STATUS         current                                            
            DESCRIPTION  " NBNS 3                                             
                                                                              
                           Indicates the subnets' third NBNS server.          
                           "                                                  
            ::= { nbnsServersInfoEntry 400 }                                  
                                                                              
        -- Columnar:  NBNS 4                                                  
                                                                              
        nbnsServersInfoNbns4 OBJECT-TYPE                                      
            SYNTAX         MxIpAddr                                           
            MAX-ACCESS     read-only                                          
            STATUS         current                                            
            DESCRIPTION  " NBNS 4                                             
                                                                              
                           Indicates the subnets' fourth NBNS server.         
                           "                                                  
            ::= { nbnsServersInfoEntry 500 }                                  
                                                                              
                                                                              
    -- End of table:  NBNS Servers                                            
                                                                              
-- End of group:  NBNS Servers                                                

-- *****************************************************************************
                                                                               
-- Table:  Static Leases                                                       
                                                                               
-- *****************************************************************************
                                                                               
staticLeasesTable OBJECT-TYPE                                                  
    SYNTAX        SEQUENCE OF StaticLeasesEntry                                
    MAX-ACCESS    not-accessible                                               
    STATUS        current                                                      
    DESCRIPTION " Static Leases                                                
                                                                               
                  This table specifies IP addresses that are reserved for      
                  specific hosts.                                              
                  "                                                            
    ::= { dhcpMIBObjects 800 }                                                 
                                                                               
                                                                               
    staticLeasesEntry OBJECT-TYPE                                              
        SYNTAX         StaticLeasesEntry                                       
        MAX-ACCESS     not-accessible                                          
        STATUS         current                                                 
        DESCRIPTION  " A row in the Static Leases. "                           
        INDEX          {                                                       
                           macAddress                                          
                       }                                                       
                                                                               
        ::= { staticLeasesTable 1 }                                            
                                                                               
    StaticLeasesEntry ::= SEQUENCE                                             
    {                                                                          
         macAddress  OCTET STRING,                                             
         ipAddress   MxIpAddr,                                                 
         delete      INTEGER                                                   
    }                                                                          
                                                                               
    -- Index:  MAC Address                                                     
                                                                               
    staticLeasesMacAddress OBJECT-TYPE                                         
        SYNTAX         OCTET STRING                                            
        MAX-ACCESS     read-only                                               
        STATUS         current                                                 
        DESCRIPTION  " MAC Address                                             
                                                                               
                       MAC address of the host.                                
                       "                                                       
        ::= { staticLeasesEntry 100 }                                          
                                                                               
    -- Columnar:  IP Address                                                   
                                                                               
    staticLeasesIpAddress OBJECT-TYPE                                          
        SYNTAX         MxIpAddr                                                
        MAX-ACCESS     read-write                                              
        STATUS         current                                                 
        DESCRIPTION  " IP Address                                              
                                                                               
                       The reserved IP address of the host.                    
                       "                                                       
        DEFVAL         { "" }                                                  
        ::= { staticLeasesEntry 200 }                                          
                                                                               
    -- Row command:  Delete                                                    
                                                                               
    staticLeasesDelete OBJECT-TYPE                                             
        SYNTAX         INTEGER { noOp(0), delete(10) }                         
        MAX-ACCESS     read-write                                              
        STATUS         current                                                 
        DESCRIPTION  " Delete                                                  
                                                                               
                       Deletes a static lease from the table.                  
                       "                                                       
        DEFVAL         { noOp }                                                
        ::= { staticLeasesEntry 300 }                                          
                                                                               
                                                                               
-- End of table:  Static Leases                                                

-- *****************************************************************************
                                                                               
-- Table:  Assigned Leases                                                     
                                                                               
-- *****************************************************************************
                                                                               
assignedLeasesInfoTable OBJECT-TYPE                                            
    SYNTAX        SEQUENCE OF AssignedLeasesInfoEntry                          
    MAX-ACCESS    not-accessible                                               
    STATUS        current                                                      
    DESCRIPTION " Assigned Leases                                              
                                                                               
                  This table lists the IP addresses that are currently         
                  assigned.                                                    
                  "                                                            
    ::= { dhcpMIBObjects 900 }                                                 
                                                                               
                                                                               
    assignedLeasesInfoEntry OBJECT-TYPE                                        
        SYNTAX         AssignedLeasesInfoEntry                                 
        MAX-ACCESS     not-accessible                                          
        STATUS         current                                                 
        DESCRIPTION  " A row in the Assigned Leases. "                         
        INDEX          {                                                       
                           ipAddress                                           
                       }                                                       
                                                                               
        ::= { assignedLeasesInfoTable 1 }                                      
                                                                               
    AssignedLeasesInfoEntry ::= SEQUENCE                                       
    {                                                                          
        ipAddress        MxIpAddr,                                             
        macAddress       OCTET STRING,                                         
        subnetName       OCTET STRING,                                         
        leaseTimeLeft    Unsigned32                                            
    }                                                                          
                                                                               
    -- Index:  IP Address                                                      
                                                                               
    assignedLeasesInfoIpAddress OBJECT-TYPE                                    
        SYNTAX         MxIpAddr                                                
        MAX-ACCESS     read-only                                               
        STATUS         current                                                 
        DESCRIPTION  " IP Address                                              
                                                                               
                       IP Address of the host.                                 
                       "                                                       
        ::= { assignedLeasesInfoEntry 100 }                                    
                                                                               
    -- Columnar:  MAC Address                                                  
                                                                               
    assignedLeasesInfoMacAddress OBJECT-TYPE                                   
        SYNTAX         OCTET STRING                                            
        MAX-ACCESS     read-only                                               
        STATUS         current                                                 
        DESCRIPTION  " MAC Address                                             
                                                                               
                       MAC address of the host.                                
                       "                                                       
        ::= { assignedLeasesInfoEntry 200 }                                    
                                                                               
    -- Columnar:  Subnet Name                                                  
                                                                               
    assignedLeasesInfoSubnetName OBJECT-TYPE                                   
        SYNTAX         OCTET STRING                                            
        MAX-ACCESS     read-only                                               
        STATUS         current                                                 
        DESCRIPTION  " Subnet Name                                             
                                                                               
                       Indicates on which subnet the host is located.          
                       "                                                       
        ::= { assignedLeasesInfoEntry 300 }                                    
                                                                               
    -- Columnar:  Lease Time Left                                              
                                                                               
    assignedLeasesInfoLeaseTimeLeft OBJECT-TYPE                                
        SYNTAX         Unsigned32                                              
        MAX-ACCESS     read-only                                               
        STATUS         current                                                 
        DESCRIPTION  " Lease Time Left                                         
                                                                               
                       Indicates the lease time left in seconds.               
                       "                                                       
        ::= { assignedLeasesInfoEntry 400 }                                    
                                                                               
                                                                               
-- End of table:  Assigned Leases                                              

-- *****************************************************************************
                                                                               
-- Group:  Statistics                                                          
                                                                               
-- *****************************************************************************
                                                                               
statisticsGroup OBJECT IDENTIFIER                                              
          ::= { dhcpMIBObjects 10000 }                                         
                                                                               
                                                                               
          -- *******************************************************************
                                                                               
          -- Table:  Statistics                                                
                                                                               
          -- *******************************************************************
                                                                               
          subnetsStatsTable OBJECT-TYPE                                        
              SYNTAX        SEQUENCE OF SubnetsStatsEntry                      
              MAX-ACCESS    not-accessible                                     
              STATUS        current                                            
              DESCRIPTION " Statistics                                         
                                                                               
                            This table contains the statistics for each subnet.
                            "                                                  
              ::= { statisticsGroup 100 }                                      
                                                                               
                                                                               
              subnetsStatsEntry OBJECT-TYPE                                    
                  SYNTAX         SubnetsStatsEntry                             
                  MAX-ACCESS     not-accessible                                
                  STATUS         current                                       
                  DESCRIPTION  " A row in the Statistics. "                    
                  INDEX          {                                             
                                     subnetName                                
                                 }                                             
                                                                               
                  ::= { subnetsStatsTable 1 }                                  
                                                                               
              SubnetsStatsEntry ::= SEQUENCE                                   
              {                                                                
                  subnetName     OCTET STRING,                                 
                  numberOfLeases Unsigned32                                    
              }                                                                
                                                                               
              -- Index:  Subnet Name                                           
                                                                               
              subnetsStatsSubnetName OBJECT-TYPE                               
                  SYNTAX         OCTET STRING ( SIZE(1..15) )                  
                  MAX-ACCESS     read-only                                     
                  STATUS         current                                       
                  DESCRIPTION  " Subnet Name                                   
                                                                               
                                 Name of the subnet.                           
                                 "                                             
                  ::= { subnetsStatsEntry 100 }                                
                                                                               
              -- Columnar:  Number of Leases                                   
                                                                               
              subnetsStatsNumberOfLeases OBJECT-TYPE                           
                  SYNTAX         Unsigned32                                    
                  MAX-ACCESS     read-only                                     
                  STATUS         current                                       
                  DESCRIPTION  " Number of Leases                              
                                                                               
                                 Number of currently assigned leases.          
                                 "                                             
                  ::= { subnetsStatsEntry 200 }                                
                                                                               
                                                                               
          -- End of table:  Statistics                                         
                                                                               
-- End of group:  Statistics                                                   

-- *****************************************************************************
                                                                               
-- Group:  Notification Messages Configuration                                 
                                                                               
-- *****************************************************************************
                                                                               
notificationsGroup OBJECT IDENTIFIER                                           
    ::= { dhcpMIBObjects 60010 }                                               
                                                                               
                                                                               
    -- Scalar:  Minimal Severity of Notification                               
                                                                               
    minSeverity OBJECT-TYPE                                                    
        SYNTAX        INTEGER { disable(0) , debug(100) , info(200) , warning  
                      (300) , error(400) , critical (500) }                    
        MAX-ACCESS    read-write                                               
        STATUS        current                                                  
        DESCRIPTION " Minimal Severity of Notification                         
                                                                               
                      Sets the minimal severity to issue a notification message
                      incoming from this service.                              
                                                                               
                        * Disable: No notification is issued.                  
                        * Debug: All notification messages are issued.         
                        * Info: Notification messages with severity            
                          'Informational' and higher are issued.               
                        * Warning: Notification messages with severity         
                          'Warning' and higher are issued.                     
                        * Error: Notification messages with severity 'Error'   
                          and higher are issued.                               
                        * Critical: Notification messages with severity        
                          'Critical' are issued.                               
                                                                               
                                                                               
                      "                                                        
        DEFVAL        { warning }                                              
        ::= { notificationsGroup 100 }                                         
                                                                               
-- End of group:  Notification Messages Configuration                          

-- ****************************************************************************
                                                                              
-- Group:  Configuration Settings                                             
                                                                              
-- ****************************************************************************
                                                                              
configurationGroup OBJECT IDENTIFIER                                          
    ::= { dhcpMIBObjects 60020 }                                              
                                                                              
                                                                              
    -- Scalar:  Need Restart                                                  
                                                                              
    needRestartInfo OBJECT-TYPE                                               
        SYNTAX        INTEGER { no(0) , yes(100) }                            
        MAX-ACCESS    read-only                                               
        STATUS        current                                                 
        DESCRIPTION " Need Restart                                            
                                                                              
                      Indicates if the service needs to be restarted for its  
                      configuration to fully take effect.                     
                                                                              
                        * Yes: Service needs to be restarted.                 
                        * No: Service does not need to be restarted.          
                                                                              
                      Services can be restarted by using the command          
                      Scm.ServiceCommands.Restart.                            
                                                                              
                                                                              
                      "                                                       
        ::= { configurationGroup 100 }                                        
                                                                              
-- End of group:  Configuration Settings                                      

END
