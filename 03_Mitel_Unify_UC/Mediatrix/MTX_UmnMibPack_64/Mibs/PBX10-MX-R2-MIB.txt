-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


PBX10-MX-R2-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

r2MIB MODULE-IDENTITY
 LAST-UPDATED   "0707090000Z"
 ORGANIZATION " Mediatrix Telecom, Inc. "
 CONTACT-INFO " Mediatrix Telecom, Inc.
                4229, Garlock Street
                Sherbrooke (Quebec)
                Canada
                Phone: (819) 829-8749
                "
 DESCRIPTION  " R2 Channel Associated Signaling

                The R2 Channel Associated Signaling service allows the
                administrator to configure parameters for the E1 CAS.
                "
 -- ****************************************************************************
 
 -- Revision history
 -- ****************************************************************************
 REVISION       "0707090000Z"
 DESCRIPTION  " Initial Revision "
 REVISION       "0711060000Z"
 DESCRIPTION  " Rename CAS for R2 "
 REVISION       "0711290000Z"
 DESCRIPTION  " Add some variables "
 REVISION       "0801140000Z"
 DESCRIPTION  " Add variables AniRestrictedEnable and FwdGroup1RestrictedAni "
 REVISION       "0801210000Z"
 DESCRIPTION  " Add variable CongestionToneGuardTimeout "
 REVISION       "0805010000Z"
 DESCRIPTION  " Add variable PhysicalLink.MonitorLinkStateEnable. "
 REVISION       "0811120000Z"
 DESCRIPTION  " Removed the DTMF option from the RegisterSignaling variable. "
 REVISION       "0901080000Z"
 DESCRIPTION  " Renamed 'Free' to 'Idle' and 'Used' to 'InUse' in
                BearerChannelGroup.State "
 REVISION       "0905050000Z"
 DESCRIPTION  " Add variable R2TimerVariants.InterCallGuardTimeout "
 REVISION       "0905050000Z"
 DESCRIPTION  " Add variables for country variants Mexico "
 REVISION       "0905050000Z"
 DESCRIPTION  " Extended range of R2TimerVariants.InterCallGuardTimeout "
 REVISION       "0910300000Z"
 DESCRIPTION  " Add variables for country variants Argentina and Saudi Arabia "
 REVISION       "0912160000Z"
 DESCRIPTION  " Add variable PortPinout. "
 REVISION       "0912160000Z"
 DESCRIPTION  " Add variable R2.DigitAttenuation. "
 REVISION       "1001210000Z"
 DESCRIPTION  " Modified the default value of variable
                PhysicalLink.MonitorLinkStateEnable "
 REVISION       "1007090000Z"
 DESCRIPTION  " Add variables R2.IncomingDigitSignaling and
                R2.OutgoingDigitSignaling. "
 REVISION       "1007230000Z"
 DESCRIPTION  " Add variables for country variants Venezuela. "
 REVISION       "1008300000Z"
 DESCRIPTION  " Add country variants Philippines and ITU-T. "
 REVISION       "1009290000Z"
 DESCRIPTION  " Modified the range of the WaitGroupBResponseCompleteTimeout
                variable. "
 ::= { mediatrixServices 1875 }

r2MIBObjects OBJECT IDENTIFIER ::= { r2MIB 1 }

-- ****************************************************************************

-- Group:R2 Configuration

-- ****************************************************************************

r2Group OBJECT IDENTIFIER
 ::= { r2MIBObjects 100 }
 -- ***************************************************************************
 
 -- Table:R2 Channel Associated Signaling (R2 CAS)

 -- ***************************************************************************
 
 r2Table OBJECT-TYPE
  SYNTAX        SEQUENCE OF R2Entry
  MAX-ACCESS    not-accessible
  STATUS        current
  DESCRIPTION " R2 Channel Associated Signaling (R2 CAS)

                Configuration parameters related to the R2 channel associated
                signaling (R2 CAS) on this managed device.
                "
  ::= { r2Group 100 }
  r2Entry OBJECT-TYPE
   SYNTAX        R2Entry
   MAX-ACCESS    not-accessible
   STATUS        current
   DESCRIPTION " A row in table R2 Channel Associated Signaling (R2 CAS). "
   INDEX         {
                   r2Name
                 }

   ::= { r2Table 1 }

  R2Entry ::= SEQUENCE
  {
    r2Name                      OCTET STRING,
    r2ChannelRange              OCTET STRING,
    r2ChannelAllocationStrategy INTEGER,
    r2MaxActiveCalls            Unsigned32,
    r2EncodingScheme            INTEGER,
    r2LineSignaling             INTEGER,
    r2IncomingDigitSignaling    INTEGER,
    r2OutgoingDigitSignaling    INTEGER,
    r2CountrySelection          INTEGER,
    r2DigitAttenuation          Unsigned32
  }

  -- Index:Name

  r2Name OBJECT-TYPE
   SYNTAX        OCTET STRING
   MAX-ACCESS    read-only
   STATUS        current
   DESCRIPTION " Name

                 Name that identifies the interface.
                 "
   ::= { r2Entry 100 }

  -- Columnar:Channel Range

  r2ChannelRange OBJECT-TYPE
   SYNTAX        OCTET STRING ( SIZE(1..10) )
   MAX-ACCESS    read-write
   STATUS        current
   DESCRIPTION " Channel Range

                 Defines the range of active bearer channels.
                 "
   DEFVAL        { "1-30" }
   ::= { r2Entry 200 }

  -- Columnar:Channel Allocation Strategy

  r2ChannelAllocationStrategy OBJECT-TYPE
   SYNTAX        INTEGER { ascending(100) , descending(200) ,
                 roundRobinAscending(300) , roundRobinDescending(400) }
   MAX-ACCESS    read-write
   STATUS        current
   DESCRIPTION " Channel Allocation Strategy

                 Defines the strategy for selecting bearer channels. Available
                 strategies are:

                   * Ascending: select the lowest-numbered non-busy bearer
                     channel
                   * Descending: select the highest-numbered non-busy bearer
                     channel
                   * RoundRobinAscending: use a cyclic round-robin search;
                     starting from the bearer channel that follows the bearer
                     channel used for the last call, select the
                     lowest-numbered non-busy bearer channel
                   * RoundRobinDescending: use a cyclic round-robin search;
                     starting from the bearer channel that precedes the bearer
                     channel used for the last call, select the
                     highest-numbered non-busy bearer channel


                 "
   DEFVAL        { ascending }
   ::= { r2Entry 300 }

  -- Columnar:Maximum Active Calls

  r2MaxActiveCalls OBJECT-TYPE
   SYNTAX        Unsigned32 ( 0..30 )
   MAX-ACCESS    read-write
   STATUS        current
   DESCRIPTION " Maximum Active Calls

                 Defines the maximum number of active calls on the interface.

                 Note: The special value 0 indicates no maximum number of
                 active calls.


                 "
   DEFVAL        { 0 }
   ::= { r2Entry 400 }

  -- Columnar:Encoding Scheme

  r2EncodingScheme OBJECT-TYPE
   SYNTAX        INTEGER { g711alaw(100) , g711ulaw(200) }
   MAX-ACCESS    read-write
   STATUS        current
   DESCRIPTION " Encoding Scheme

                 Defines the voice encoding scheme in the bearer capabilities.
                 "
   DEFVAL        { g711alaw }
   ::= { r2Entry 500 }

  -- Columnar:Line Signaling

  r2LineSignaling OBJECT-TYPE
   SYNTAX        INTEGER { q4212BitsSignaling(100) }
   MAX-ACCESS    read-write
   STATUS        current
   DESCRIPTION " Line Signaling

                 Defines the protocol to use for the line signaling:

                   * Q421-2BitsSignaling: R2 line signaling type ITU-U Q.421.
                     Typically used for PCM systems.


                 "
   DEFVAL        { q4212BitsSignaling }
   ::= { r2Entry 600 }

  -- Columnar:Incoming Digit Signaling

  r2IncomingDigitSignaling OBJECT-TYPE
   SYNTAX        INTEGER { mfcR2(100) , dtmfR2(200) }
   MAX-ACCESS    read-write
   STATUS        current
   DESCRIPTION " Incoming Digit Signaling

                 Defines the R2 incoming digit signaling method.

                   * MfcR2: Multi Frequency Compelled - R2.
                   * DtmfR2: Dual Tone Multi Frequency - R2.


                 "
   DEFVAL        { mfcR2 }
   ::= { r2Entry 750 }

  -- Columnar:Outgoing Digit Signaling

  r2OutgoingDigitSignaling OBJECT-TYPE
   SYNTAX        INTEGER { mfcR2(100) , dtmfR2(200) }
   MAX-ACCESS    read-write
   STATUS        current
   DESCRIPTION " Outgoing Digit Signaling

                 Defines the R2 outgoing digit signaling method.

                   * MfcR2: Multi Frequency Compelled - R2.
                   * DtmfR2: Dual Tone Multi Frequency - R2.


                 "
   DEFVAL        { mfcR2 }
   ::= { r2Entry 760 }

  -- Columnar:Country Selection

  r2CountrySelection OBJECT-TYPE
   SYNTAX        INTEGER { brazilR2(100) , mexicoR2(200) , argentinaR2(300) ,
                 saudiArabiaR2(400) , venezuelaR2(500) , philippinesR2(600) ,
                 iTUTR2(700) }
   MAX-ACCESS    read-write
   STATUS        current
   DESCRIPTION " Country Selection

                 Identifies the country.

                   * Brazil-R2: Brazil R2 setting.
                   * Mexico-R2: Mexico R2 setting.
                   * Argentina-R2: Argentina R2 setting.
                   * SaudiArabia-R2: SaudiArabia R2 setting.
                   * Venezuela-R2: Venezuela R2 setting.
                   * Philippines-R2: Philippines R2 setting.
                   * ITU-T-R2: ITU-T R2 setting.


                 "
   DEFVAL        { brazilR2 }
   ::= { r2Entry 800 }

  -- Columnar:Digit Attenuation

  r2DigitAttenuation OBJECT-TYPE
   SYNTAX        Unsigned32 ( 0..20 )
   MAX-ACCESS    read-write
   STATUS        current
   DESCRIPTION " Digit Attenuation

                 Additional attenuation in dB for MFR2/DTMF digits generation.
                 By default, MFR2/DTMF digits generation power is determined
                 by country selection. This variable provides a mean to reduce
                 this power.
                 "
   DEFVAL        { 0 }
   ::= { r2Entry 900 }


 -- End of table:R2 Channel Associated Signaling (R2 CAS)

 -- ***************************************************************************
 
 -- Table:R2 Signaling Variants

 -- ***************************************************************************
 
 r2SignalingVariantsTable OBJECT-TYPE
  SYNTAX        SEQUENCE OF R2SignalingVariantsEntry
  MAX-ACCESS    not-accessible
  STATUS        current
  DESCRIPTION " R2 Signaling Variants

                This table allows to override or retrieve the default country
                settings for R2 signaling parameters. This table is effective
                only if the OverrideDefault variable is Enabled. If
                OverrideDefault is Disabled, any change in this table have no
                effects.
                "
  ::= { r2Group 200 }
  r2SignalingVariantsEntry OBJECT-TYPE
   SYNTAX        R2SignalingVariantsEntry
   MAX-ACCESS    not-accessible
   STATUS        current
   DESCRIPTION " A row in table R2 Signaling Variants. "
   INDEX         {
                   r2SignalingVariantsInterfaceName
                 }

   ::= { r2SignalingVariantsTable 1 }

  R2SignalingVariantsEntry ::= SEQUENCE
  {
    r2SignalingVariantsInterfaceName                 OCTET STRING,
    r2SignalingVariantsCountrySelection              INTEGER,
    r2SignalingVariantsOverrideDefault               MxEnableState,
    r2SignalingVariantsBitsCD                        Integer32,
    r2SignalingVariantsDnisLength                    Unsigned32,
    r2SignalingVariantsAniLength                     Unsigned32,
    r2SignalingVariantsAniRequestEnable              MxEnableState,
    r2SignalingVariantsSendAniRequestAfterDnisDigits Unsigned32,
    r2SignalingVariantsCollectCallBlocked            MxEnableState,
    r2SignalingVariantsAniCategory                   INTEGER,
    r2SignalingVariantsLineFreeCategory              INTEGER,
    r2SignalingVariantsAniRestrictedEnable           MxEnableState,
    r2SignalingVariantsResetSpecific                 INTEGER
  }

  -- Index:Interface Name

  r2SignalingVariantsInterfaceName OBJECT-TYPE
   SYNTAX         OCTET STRING
   MAX-ACCESS     read-only
   STATUS         current
   DESCRIPTION  " Interface Name

                  Identifies the interface.
                  "
   ::= { r2SignalingVariantsEntry 100 }

  -- Row command:Reset Specific

  r2SignalingVariantsResetSpecific OBJECT-TYPE
   SYNTAX        INTEGER { noOp(0), resetSpecific(10) }
   MAX-ACCESS    read-write
   STATUS        current
   DESCRIPTION " Reset Specific

                 Resets specific settings of R2 Signaling parameters with the
                 default country settings. This command is used to retrieve
                 the default country configuration set in the CountrySelection
                 variable.
                 "
   DEFVAL        { noOp }
   ::= { r2SignalingVariantsEntry 1000 }

  -- Columnar:Country Selection

  r2SignalingVariantsCountrySelection OBJECT-TYPE
   SYNTAX        INTEGER { brazilR2(100) , mexicoR2(200) , argentinaR2(300) ,
                 saudiArabiaR2(400) , venezuelaR2(500) , philippinesR2(600) ,
                 iTUTR2(700) }
   MAX-ACCESS    read-only
   STATUS        current
   DESCRIPTION " Country Selection

                 Identifies the current country selected in the R2 table for
                 the specified interface.

                   * Brazil-R2: Brazil R2 setting.
                   * Mexico-R2: Mexico R2 setting.
                   * Argentina-R2: Argentina R2 setting.
                   * SaudiArabia-R2: SaudiArabia R2 setting.
                   * Venezuela-R2: Venezuela R2 setting.
                   * Philippines-R2: Philippines R2 setting.
                   * ITU-T-R2: ITU-T R2 setting.


                 "
   ::= { r2SignalingVariantsEntry 200 }

  -- Columnar:Override Default

  r2SignalingVariantsOverrideDefault OBJECT-TYPE
   SYNTAX        MxEnableState
   MAX-ACCESS    read-write
   STATUS        current
   DESCRIPTION " Override Default

                 Overrides the default settings of R2 Signaling parameters for
                 the CountrySelection and InterfaceName.

                   * Disable: The interface uses the default country
                     configuration. The configuration set in the current row
                     has no effects on the default country configuration.
                     Refer to the technical documentation to get the default
                     country variants configuration.
                   * Enable: The interface uses the specific country
                     configuration as defined in the current row. To retrieve
                     the default configuration associated with the current
                     country, the variable reset MUST be enabled.


                 "
   DEFVAL        { disable }
   ::= { r2SignalingVariantsEntry 300 }

  -- Columnar:CD Bits

  r2SignalingVariantsBitsCD OBJECT-TYPE
   SYNTAX        Integer32 ( 0..12 )
   MAX-ACCESS    read-write
   STATUS        current
   DESCRIPTION " CD Bits

                 Settings of the C and D bits when the device transmits line
                 signals. C and D bits of received line signals are ignored by
                 the device.
                 "
   DEFVAL        { 1 }
   ::= { r2SignalingVariantsEntry 400 }

  -- Columnar:DNIS Length

  r2SignalingVariantsDnisLength OBJECT-TYPE
   SYNTAX        Unsigned32 ( 0..20 )
   MAX-ACCESS    read-write
   STATUS        current
   DESCRIPTION " DNIS Length

                 This parameter specifies the length of the DNIS expected.
                 DNIS (Dialed Number Identification Service) is the called
                 party or the destination number. If a variable length is
                 defined, then the I-15 digit is used to indicate the end of
                 DNIS.

                   * 0 : Variable DNIS length used.
                   * 1..20 : Number indicates the specific DNIS length
                     expected.


                 "
   DEFVAL        { 0 }
   ::= { r2SignalingVariantsEntry 500 }

  -- Columnar:ANI Length

  r2SignalingVariantsAniLength OBJECT-TYPE
   SYNTAX        Unsigned32 ( 0..20 )
   MAX-ACCESS    read-write
   STATUS        current
   DESCRIPTION " ANI Length

                 Defines the length of ANI (Automatic Number Identification)
                 to be requested or sent. If a variable length ANI is used,
                 the tone set in R2ToneVariants.FwdGroup1EndOfAni is sent to
                 indicate the end of the ANI digits. When fixed length ANI is
                 used and the available ANI digits are longer than the
                 requested length, the last n digits are sent. If available
                 ANI digits are shorter, then the
                 R2ToneVariants.FwdGroup1EndOfAni tone is sent.

                   * 0 : Variable ANI length.
                   * 1..20 : Specific ANI length.


                 "
   DEFVAL        { 0 }
   ::= { r2SignalingVariantsEntry 600 }

  -- Columnar:ANI Request Enable

  r2SignalingVariantsAniRequestEnable OBJECT-TYPE
   SYNTAX        MxEnableState
   MAX-ACCESS    read-write
   STATUS        current
   DESCRIPTION " ANI Request Enable

                 Defines whether or not ANI should be requested. ANI
                 (Automatic Number Identification) is the calling party
                 number. When ANI is requested, the calling party category
                 followed by the actual ANI is sent. If this parameter is
                 enabled, the ANI request is sent after the nth DNIS digits
                 (defined in the SendAniRequestAfterDnisDigits variable)
                 received.
                 "
   DEFVAL        { enable }
   ::= { r2SignalingVariantsEntry 700 }

  -- Columnar:Send ANI Request After DNIS Digits

  r2SignalingVariantsSendAniRequestAfterDnisDigits OBJECT-TYPE
   SYNTAX        Unsigned32 ( 0..10 )
   MAX-ACCESS    read-write
   STATUS        current
   DESCRIPTION " Send ANI Request After DNIS Digits

                 When the AniRequestEnable is Enabled, this variable defines
                 the number of DNIS (Dialed Number Identification Service)
                 digits to be received before sending the ANI request. If a
                 variable number is used, the ANI request is sent after all
                 DNIS digits have been received.

                   * 0 : Variable number of DNIS digits.
                   * 1..10 : Specific number of DNIS digits.


                 "
   DEFVAL        { 0 }
   ::= { r2SignalingVariantsEntry 800 }

  -- Columnar:Collect Call Blocked

  r2SignalingVariantsCollectCallBlocked OBJECT-TYPE
   SYNTAX        MxEnableState
   MAX-ACCESS    read-write
   STATUS        current
   DESCRIPTION " Collect Call Blocked

                 Defines if the Collect Call Blocked Option is used.

                 For an incoming collect call, a signal of Group II8 is sent
                 forward from the caller to the called party. The called party
                 implements the collect call blockage (when CollectCallBlocked
                 is enabled) by sending backward to the caller a signal of
                 Group B7 indicating that the collect calls are not being
                 accepted by the called party. Consequently, the originator of
                 the call gets a busy tone and the local calling party circuit
                 that has been used for the call is dropped when the
                 originator puts the phone on hook.


                 "
   DEFVAL        { enable }
   ::= { r2SignalingVariantsEntry 900 }

  -- Columnar:Category Group II Signal

  r2SignalingVariantsAniCategory OBJECT-TYPE
   SYNTAX        INTEGER { natSubscriberNoPrio(100) , natSubscriberPrio(200) ,
                 natMaintenance(300) , natSpare(400) , natOperator(500) ,
                 natData(600) , intSubscriberNoPrio(700) , intData(800) ,
                 intSubscriberPrio(900) , intOperator(1000) , collectCall
                 (1100) }
   MAX-ACCESS    read-write
   STATUS        current
   DESCRIPTION " Category Group II Signal

                 Specifies the group II forward signal to be sent on receiving
                 a calling party category request. This tone indicates the
                 category of the calling party.

                   * NatSubscriberNoPrio : Call is set up from a national
                     subscriber's line and is non-priority.
                   * NatSubscriberPrio : Call is set up from a national
                     subscriber's line to which priority treatment of calls
                     has been granted.
                   * NatMaintenance : Call comes from a national maintenance
                     equipment.
                   * NatSpare : Spare.
                   * NatOperator : Call is set up from a national operator's
                     position.
                   * NatData : Call will be used for national data
                     transmission.
                   * IntSubscriberNoPrio : Call is set up from an
                     international subscriber's line and is non-priority.
                   * IntData : Call will be used for international data
                     transmission.
                   * IntSubscriberPrio : Call is set up from an international
                     subscriber's line to which priority treatment of calls
                     has been granted.
                   * IntOperator : Call is set up from an international
                     operator's position.
                   * CollectCall : Call is set up for Call Collect.


                 "
   DEFVAL        { natSubscriberNoPrio }
   ::= { r2SignalingVariantsEntry 920 }

  -- Columnar:Line Free Group B signal

  r2SignalingVariantsLineFreeCategory OBJECT-TYPE
   SYNTAX        INTEGER { lineFreeCharge(100) , lineFreeNoCharge(200) }
   MAX-ACCESS    read-write
   STATUS        current
   DESCRIPTION " Line Free Group B signal

                 Specifies the group B backward signal to be sent by the
                 incoming R2 register to indicate line free condition of the
                 destination party.

                   * LineFreeCharge : Called party's line is free but is to be
                     charged on answer.
                   * LineFreeNoCharge : Called party's line is free but is not
                     to be charged on answer.


                 "
   DEFVAL        { lineFreeCharge }
   ::= { r2SignalingVariantsEntry 930 }

  -- Columnar:ANI Restricted Enable

  r2SignalingVariantsAniRestrictedEnable OBJECT-TYPE
   SYNTAX        MxEnableState
   MAX-ACCESS    read-write
   STATUS        current
   DESCRIPTION " ANI Restricted Enable

                 This parameter specifies the behaviour of the unit following
                 the reception of a reject request after sending the Send next
                 digit (ANI) request. The request is generally rejected when
                 the calling party is unable to send its identification.

                   * Enable: A congestion tone is sent in response to the
                     reject request and the call should be dropped by the
                     caller.
                   * Disable: The unit uses the same behaviour as the End of
                     ANI Tone and the call continues.


                 "
   DEFVAL        { enable }
   ::= { r2SignalingVariantsEntry 950 }


 -- End of table:R2 Signaling Variants

 -- ***************************************************************************
 
 -- Table:R2 Signaling Timer Variants

 -- ***************************************************************************
 
 r2TimerVariantsTable OBJECT-TYPE
  SYNTAX        SEQUENCE OF R2TimerVariantsEntry
  MAX-ACCESS    not-accessible
  STATUS        current
  DESCRIPTION " R2 Signaling Timer Variants

                This table allows to override or retrieve the default country
                setting for R2 Timers.
                "
  ::= { r2Group 300 }
  r2TimerVariantsEntry OBJECT-TYPE
   SYNTAX        R2TimerVariantsEntry
   MAX-ACCESS    not-accessible
   STATUS        current
   DESCRIPTION " A row in table R2 Signaling Timer Variants. "
   INDEX         {
                   r2TimerVariantsInterfaceName
                 }

   ::= { r2TimerVariantsTable 1 }

  R2TimerVariantsEntry ::= SEQUENCE
  {
    r2TimerVariantsInterfaceName                        OCTET STRING,
    r2TimerVariantsCountrySelection                     INTEGER,
    r2TimerVariantsOverrideDefault                      MxEnableState,
    r2TimerVariantsSeizureAckTimeout                    Integer32,
    r2TimerVariantsFaultSeizureAckTimeout               Integer32,
    r2TimerVariantsDoubleSeizureTimeout                 Integer32,
    r2TimerVariantsDoubleAnswerTimeout                  Integer32,
    r2TimerVariantsReleaseGuardTimeout                  Integer32,
    r2TimerVariantsInterCallGuardTimeout                Integer32,
    r2TimerVariantsCongestionToneGuardTimeout           Integer32,
    r2TimerVariantsUnblockingTimeout                    Integer32,
    r2TimerVariantsAddressCompleteTimeout               Integer32,
    r2TimerVariantsWaitAnswerTimeout                    Integer32,
    r2TimerVariantsDigitCompleteTimeout                 Integer32,
    r2TimerVariantsWaitGroupBResponseCompleteTimeout    Integer32,
    r2TimerVariantsWaitImmediateResponseCompleteTimeout Integer32,
    r2TimerVariantsPlayToneGuardTimeout                 Integer32,
    r2TimerVariantsAcceptCallTimeout                    Integer32,
    r2TimerVariantsClearForwardGuardTimeout             Integer32,
    r2TimerVariantsClearBackwardGuardTimeout            Integer32,
    r2TimerVariantsFaultOnAnsweredGuardTimeout          Integer32,
    r2TimerVariantsFaultOnClearBackwardGuardTimeout     Integer32,
    r2TimerVariantsFaultOnSeizeAckGuardTimeout          Integer32,
    r2TimerVariantsFaultOnSeizeGuardTimeout             Integer32,
    r2TimerVariantsResetSpecific                        INTEGER
  }

  -- Index:Interface Name

  r2TimerVariantsInterfaceName OBJECT-TYPE
   SYNTAX        OCTET STRING
   MAX-ACCESS    read-only
   STATUS        current
   DESCRIPTION " Interface Name

                 Identifies the interface.
                 "
   ::= { r2TimerVariantsEntry 100 }

  -- Columnar:Address Complete Timeout

  r2TimerVariantsAddressCompleteTimeout OBJECT-TYPE
   SYNTAX        Integer32 ( 0..20000 )
   MAX-ACCESS    read-write
   STATUS        current
   DESCRIPTION " Address Complete Timeout

                 The Address Complete Timeout is the maximum time that the
                 caller waits for a reception of AddressComplete Tone after
                 sending all ANI or DNIS Digits.

                 This value is expressed in milliseconds (ms).


                 "
   DEFVAL        { 8000 }
   ::= { r2TimerVariantsEntry 1000 }

  -- Columnar:Wait Answer Timeout

  r2TimerVariantsWaitAnswerTimeout OBJECT-TYPE
   SYNTAX        Integer32 ( 0..600000 )
   MAX-ACCESS    read-write
   STATUS        current
   DESCRIPTION " Wait Answer Timeout

                 The maximal time that the caller waits for an Answer signal
                 (ANSW) after receiving a Group B Line Free Signal Tone. This
                 timer is effective only when the line is free.

                 This value is expressed in milliseconds (ms).


                 "
   DEFVAL        { 60000 }
   ::= { r2TimerVariantsEntry 1100 }

  -- Columnar:Digit Complete Timeout

  r2TimerVariantsDigitCompleteTimeout OBJECT-TYPE
   SYNTAX        Integer32 ( 0..10000 )
   MAX-ACCESS    read-write
   STATUS        current
   DESCRIPTION " Digit Complete Timeout

                 The maximal time that the caller waits for a Group I forward
                 tone after sending either a Group A next Dnis digit, next Ani
                 digit or next calling category Tone.

                 This value is expressed in milliseconds (ms).


                 "
   DEFVAL        { 4000 }
   ::= { r2TimerVariantsEntry 1200 }

  -- Columnar:Wait Group B Response Complete Timeout

  r2TimerVariantsWaitGroupBResponseCompleteTimeout OBJECT-TYPE
   SYNTAX        Integer32 ( 0..30000 )
   MAX-ACCESS    read-write
   STATUS        current
   DESCRIPTION " Wait Group B Response Complete Timeout

                 The maximal time that the caller waits for the confirmation
                 of the end of the compelled sequence after receiving a Group
                 B Signal Tone. The end of the compelled sequence is detected
                 by a transition of the backward tone to off.

                 This value is expressed in milliseconds (ms).


                 "
   DEFVAL        { 3000 }
   ::= { r2TimerVariantsEntry 1300 }

  -- Columnar:Wait Immediate Response Complete Timeout

  r2TimerVariantsWaitImmediateResponseCompleteTimeout OBJECT-TYPE
   SYNTAX        Integer32 ( 0..10000 )
   MAX-ACCESS    read-write
   STATUS        current
   DESCRIPTION " Wait Immediate Response Complete Timeout

                 The maximal time that the caller waits for the confirmation
                 of the end of the compelled sequence after receiving a Group
                 B Signal Tone. The end of the compelled sequence is detected
                 by a transition of the backward tone to off. This timer is
                 specific to the immediate accept Signal Tone.

                 This value is expressed in milliseconds (ms).


                 "
   DEFVAL        { 1000 }
   ::= { r2TimerVariantsEntry 1400 }

  -- Columnar:Play Tone guard Timeout

  r2TimerVariantsPlayToneGuardTimeout OBJECT-TYPE
   SYNTAX        Integer32 ( 0..2000 )
   MAX-ACCESS    read-write
   STATUS        current
   DESCRIPTION " Play Tone guard Timeout

                 The maximum time an incoming R2 registers waits after
                 receiving the confirmation of the reception of the Group B
                 Signal Tone before playing one of the calling tones in the
                 caller direction.

                 This value is expressed in milliseconds (ms).


                 "
   DEFVAL        { 70 }
   ::= { r2TimerVariantsEntry 1500 }

  -- Columnar:Accept Call Timeout

  r2TimerVariantsAcceptCallTimeout OBJECT-TYPE
   SYNTAX        Integer32 ( 0..10000 )
   MAX-ACCESS    read-write
   STATUS        current
   DESCRIPTION " Accept Call Timeout

                 Time that the unit waits to accept a R2 CAS call.

                 This value is expressed in milliseconds (ms).


                 "
   DEFVAL        { 2000 }
   ::= { r2TimerVariantsEntry 1600 }

  -- Columnar:Clear Forward Guard Timeout

  r2TimerVariantsClearForwardGuardTimeout OBJECT-TYPE
   SYNTAX        Integer32 ( 0..600000 )
   MAX-ACCESS    read-write
   STATUS        current
   DESCRIPTION " Clear Forward Guard Timeout

                 The maximum time an outgoing R2 register waits after sending
                 a clear forward line signal before transiting to the idle
                 state.

                 This value is expressed in milliseconds (ms).


                 "
   DEFVAL        { 1500 }
   ::= { r2TimerVariantsEntry 1700 }

  -- Columnar:Clear Backward Guard Timeout

  r2TimerVariantsClearBackwardGuardTimeout OBJECT-TYPE
   SYNTAX        Integer32 ( 0..600000 )
   MAX-ACCESS    read-write
   STATUS        current
   DESCRIPTION " Clear Backward Guard Timeout

                 The maximum time an incoming R2 register waits after sending
                 a clear backward line signal before sending the idle line
                 signal and transit in the idle state.

                 This value is expressed in milliseconds (ms).


                 "
   DEFVAL        { 1500 }
   ::= { r2TimerVariantsEntry 1800 }

  -- Columnar:Fault On Answered Guard Timeout

  r2TimerVariantsFaultOnAnsweredGuardTimeout OBJECT-TYPE
   SYNTAX        Integer32 ( 0..86400000 )
   MAX-ACCESS    read-write
   STATUS        current
   DESCRIPTION " Fault On Answered Guard Timeout

                 The maximum time an outgoing R2 register wait for the fault
                 to clear before sending the clear forward line signal. In the
                 case of recognition of bb = 0 while in the answered state, no
                 immediate action is taken. However, the clear forward signal
                 will be sent if bb = 1 is restored or the answered guard
                 timeout is reached.

                 This value is expressed in milliseconds (ms).


                 "
   DEFVAL        { 250 }
   ::= { r2TimerVariantsEntry 1900 }

  -- Columnar:Country Selection

  r2TimerVariantsCountrySelection OBJECT-TYPE
   SYNTAX        INTEGER { brazilR2(100) , mexicoR2(200) , argentinaR2(300) ,
                 saudiArabiaR2(400) , venezuelaR2(500) , philippinesR2(600) ,
                 iTUTR2(700) }
   MAX-ACCESS    read-only
   STATUS        current
   DESCRIPTION " Country Selection

                 Identifies the current country selected in the R2 table for
                 the specified interface.

                   * Brazil-R2: Brazil R2 setting.
                   * Mexico-R2: Mexico R2 setting.
                   * Argentina-R2: Argentina R2 setting.
                   * SaudiArabia-R2: SaudiArabia R2 setting.
                   * Venezuela-R2: Venezuela R2 setting.
                   * Philippines-R2: Philippines R2 setting.
                   * ITU-T-R2: ITU-T R2 setting.


                 "
   ::= { r2TimerVariantsEntry 200 }

  -- Columnar:Fault On Clear Backward Guard Timeout

  r2TimerVariantsFaultOnClearBackwardGuardTimeout OBJECT-TYPE
   SYNTAX        Integer32 ( 0..86400000 )
   MAX-ACCESS    read-write
   STATUS        current
   DESCRIPTION " Fault On Clear Backward Guard Timeout

                 The maximum time an outgoing R2 register wait for the fault
                 to clear before sending the clear forward line signal. In the
                 case of recognition of bb = 0 while in the clear backward
                 state, no immediate action is taken. However, the clear
                 forward signal will be sent if bb = 1 is restored or the
                 clear backward guard timeout is reached.

                 This value is expressed in milliseconds (ms).


                 "
   DEFVAL        { 250 }
   ::= { r2TimerVariantsEntry 2000 }

  -- Columnar:Fault On Seize Ack Guard Timeout

  r2TimerVariantsFaultOnSeizeAckGuardTimeout OBJECT-TYPE
   SYNTAX        Integer32 ( 0..86400000 )
   MAX-ACCESS    read-write
   STATUS        current
   DESCRIPTION " Fault On Seize Ack Guard Timeout

                 The maximum time an outgoing R2 register wait for the fault
                 to clear before sending the clear forward line signal. In the
                 case of recognition of bb = 0 while in the seize acknowledge
                 state prior to the answer signal, no immediate action is
                 taken. However, the clear forward signal will be sent if bb =
                 1 is restored or the seize acknowledge guard timeout is
                 reached.

                 This value is expressed in milliseconds (ms).


                 "
   DEFVAL        { 250 }
   ::= { r2TimerVariantsEntry 2100 }

  -- Columnar:Fault On Seize Guard Timeout

  r2TimerVariantsFaultOnSeizeGuardTimeout OBJECT-TYPE
   SYNTAX        Integer32 ( 0..86400000 )
   MAX-ACCESS    read-write
   STATUS        current
   DESCRIPTION " Fault On Seize Guard Timeout

                 The maximum time an outgoing R2 register wait for the fault
                 to clear before sending the clear forward line signal. In the
                 case of recognition of bb = 0 while in the seize state, no
                 immediate action is taken. However, when the seize
                 acknowledgement signal is recognized after the seize ack
                 timeout period has elapsed or the seize guard timeout, the
                 clear forward signal will be sent.

                 This value is expressed in milliseconds (ms).


                 "
   DEFVAL        { 250 }
   ::= { r2TimerVariantsEntry 2200 }

  -- Row command:Reset Specific

  r2TimerVariantsResetSpecific OBJECT-TYPE
   SYNTAX        INTEGER { noOp(0), resetSpecific(10) }
   MAX-ACCESS    read-write
   STATUS        current
   DESCRIPTION " Reset Specific

                 Resets specific settings of R2 Timers parameters with the
                 default country settings. This command is used to retrieve
                 the default country configuration set in the CountrySelection
                 variable.
                 "
   DEFVAL        { noOp }
   ::= { r2TimerVariantsEntry 2300 }

  -- Columnar:Override Default

  r2TimerVariantsOverrideDefault OBJECT-TYPE
   SYNTAX        MxEnableState
   MAX-ACCESS    read-write
   STATUS        current
   DESCRIPTION " Override Default

                 Overrides the default setting of R2 Timers for the
                 CountrySelection and InterfaceName.

                   * Disable: The interface uses the default country
                     configuration. The configuration set in the current row
                     has no effects on the default country configuration.
                     Refer to the technical documentation to get the default
                     country timers configuration.
                   * Enable: The interface uses the specific country
                     configuration as defined in the current row. To retrieve
                     the default configuration associated with the current
                     country, the variable reset MUST be enabled.


                 "
   DEFVAL        { disable }
   ::= { r2TimerVariantsEntry 300 }

  -- Columnar:Seizure Ack Timeout

  r2TimerVariantsSeizureAckTimeout OBJECT-TYPE
   SYNTAX        Integer32 ( 0..10000 )
   MAX-ACCESS    read-write
   STATUS        current
   DESCRIPTION " Seizure Ack Timeout

                 Maximum time an outgoing R2 register waits for the seizure
                 acknowledgement signal after sending a seizure signal.

                 This value is expressed in milliseconds (ms).


                 "
   DEFVAL        { 2000 }
   ::= { r2TimerVariantsEntry 400 }

  -- Columnar:Fault Seizure Ack Timeout

  r2TimerVariantsFaultSeizureAckTimeout OBJECT-TYPE
   SYNTAX        Integer32 ( 0..100000 )
   MAX-ACCESS    read-write
   STATUS        current
   DESCRIPTION " Fault Seizure Ack Timeout

                 Maximum time an incoming R2 register waits for a seizure
                 acknowledge failure condition to clear.

                 This value is expressed in milliseconds (ms).


                 "
   DEFVAL        { 60000 }
   ::= { r2TimerVariantsEntry 500 }

  -- Columnar:Double Seizure Timeout

  r2TimerVariantsDoubleSeizureTimeout OBJECT-TYPE
   SYNTAX        Integer32 ( 0..1000 )
   MAX-ACCESS    read-write
   STATUS        current
   DESCRIPTION " Double Seizure Timeout

                 Minimum time an outgoing R2 register waits after a double
                 seizure is recognized before releasing the connection.

                 This value is expressed in milliseconds (ms).


                 "
   DEFVAL        { 100 }
   ::= { r2TimerVariantsEntry 600 }

  -- Columnar:Double Answer Timeout

  r2TimerVariantsDoubleAnswerTimeout OBJECT-TYPE
   SYNTAX        Integer32 ( 0..8000 )
   MAX-ACCESS    read-write
   STATUS        current
   DESCRIPTION " Double Answer Timeout

                 Maximum time an outgoing R2 register waits after receiving a
                 clear-backward signal before releasing the connection.

                 This value is expressed in milliseconds (ms).


                 "
   DEFVAL        { 1000 }
   ::= { r2TimerVariantsEntry 700 }

  -- Columnar:Release Guard Timeout

  r2TimerVariantsReleaseGuardTimeout OBJECT-TYPE
   SYNTAX        Integer32 ( 0..4000 )
   MAX-ACCESS    read-write
   STATUS        current
   DESCRIPTION " Release Guard Timeout

                 Maximum time an incoming R2 register waits after sending an
                 idle line signal to prevent a new seizure of the line when a
                 clear forward line signal is received.

                 This value is expressed in milliseconds (ms).


                 "
   DEFVAL        { 100 }
   ::= { r2TimerVariantsEntry 800 }

  -- Columnar:Inter-call Guard Timeout

  r2TimerVariantsInterCallGuardTimeout OBJECT-TYPE
   SYNTAX        Integer32 ( 0..15000 )
   MAX-ACCESS    read-write
   STATUS        current
   DESCRIPTION " Inter-call Guard Timeout

                 Maximum time an outgoing R2 register waits after receiving an
                 idle line signal before attempting a new seizure of the line.

                 This value is expressed in milliseconds (ms).


                 "
   DEFVAL        { 100 }
   ::= { r2TimerVariantsEntry 820 }

  -- Columnar:Congestion Tone Guard Timeout

  r2TimerVariantsCongestionToneGuardTimeout OBJECT-TYPE
   SYNTAX        Integer32 ( 0..4000 )
   MAX-ACCESS    read-write
   STATUS        current
   DESCRIPTION " Congestion Tone Guard Timeout

                 Maximum time an incoming R2 register waits after sending a
                 congestion tone before sending a clear forward line signal
                 and transit to the idle state.

                 This value is expressed in milliseconds (ms).


                 "
   DEFVAL        { 1000 }
   ::= { r2TimerVariantsEntry 850 }

  -- Columnar:Unblocking Timeout

  r2TimerVariantsUnblockingTimeout OBJECT-TYPE
   SYNTAX        Integer32 ( 0..4000 )
   MAX-ACCESS    read-write
   STATUS        current
   DESCRIPTION " Unblocking Timeout

                 Maximum time a both-way trunk waits before assuming an idle
                 state when a blocking condition is removed. This will prevent
                 a too aggressive seizure of the trunk.

                 This value is expressed in milliseconds (ms).


                 "
   DEFVAL        { 100 }
   ::= { r2TimerVariantsEntry 900 }


 -- End of table:R2 Signaling Timer Variants

 -- ***************************************************************************
 
 -- Table:R2 Digit Timer Variants

 -- ***************************************************************************
 
 r2DigitTimerVariantsTable OBJECT-TYPE
  SYNTAX        SEQUENCE OF R2DigitTimerVariantsEntry
  MAX-ACCESS    not-accessible
  STATUS        current
  DESCRIPTION " R2 Digit Timer Variants

                This table allows to override or retrieve the default country
                setting for R2 Digit Timers.
                "
  ::= { r2Group 400 }
  r2DigitTimerVariantsEntry OBJECT-TYPE
   SYNTAX        R2DigitTimerVariantsEntry
   MAX-ACCESS    not-accessible
   STATUS        current
   DESCRIPTION " A row in table R2 Digit Timer Variants. "
   INDEX         {
                   r2DigitTimerVariantsInterfaceName
                 }

   ::= { r2DigitTimerVariantsTable 1 }

  R2DigitTimerVariantsEntry ::= SEQUENCE
  {
    r2DigitTimerVariantsInterfaceName             OCTET STRING,
    r2DigitTimerVariantsCountrySelection          INTEGER,
    r2DigitTimerVariantsOverrideDefault           MxEnableState,
    r2DigitTimerVariantsMfcPulseInterDigitTimeout Integer32,
    r2DigitTimerVariantsMfcPulseMinOnTimeout      Integer32,
    r2DigitTimerVariantsMfcMaxSequenceTimeout     Integer32,
    r2DigitTimerVariantsMfcMaxOnTimeout           Integer32,
    r2DigitTimerVariantsMfcMaxOffTimeout          Integer32,
    r2DigitTimerVariantsResetSpecific             INTEGER
  }

  -- Index:Interface Name

  r2DigitTimerVariantsInterfaceName OBJECT-TYPE
   SYNTAX         OCTET STRING
   MAX-ACCESS     read-only
   STATUS         current
   DESCRIPTION  " Interface Name

                  Identifies the interface.
                  "
   ::= { r2DigitTimerVariantsEntry 100 }

  -- Columnar:Country Selection

  r2DigitTimerVariantsCountrySelection OBJECT-TYPE
   SYNTAX        INTEGER { brazilR2(100) , mexicoR2(200) , argentinaR2(300) ,
                 saudiArabiaR2(400) , venezuelaR2(500) , philippinesR2(600) ,
                 iTUTR2(700) }
   MAX-ACCESS    read-only
   STATUS        current
   DESCRIPTION " Country Selection

                 Identifies the current country selected in the R2 table for
                 the specified interface.

                   * Brazil-R2: Brazil R2 setting.
                   * Mexico-R2: Mexico R2 setting.
                   * Argentina-R2: Argentina R2 setting.
                   * SaudiArabia-R2: SaudiArabia R2 setting.
                   * Venezuela-R2: Venezuela R2 setting.
                   * Philippines-R2: Philippines R2 setting.
                   * ITU-T-R2: ITU-T R2 setting.


                 "
   ::= { r2DigitTimerVariantsEntry 200 }

  -- Columnar:Override Default

  r2DigitTimerVariantsOverrideDefault OBJECT-TYPE
   SYNTAX        MxEnableState
   MAX-ACCESS    read-write
   STATUS        current
   DESCRIPTION " Override Default

                 Overrides the default setting of R2 Digit timers for the
                 CountrySelection and InterfaceName.

                   * Disable: The interface uses the default country
                     configuration. The configuration set in the current row
                     has no effects on the default country configuration.
                     Refer to the technical documentation to get the default
                     country timers configuration.
                   * Enable: The interface uses the specific country
                     configuration as defined in the current row. To retrieve
                     the default configuration associated with the current
                     country, the variable reset MUST be enabled.


                 "
   DEFVAL        { disable }
   ::= { r2DigitTimerVariantsEntry 300 }

  -- Columnar:MFC Pulse Inter Digit Timeout

  r2DigitTimerVariantsMfcPulseInterDigitTimeout OBJECT-TYPE
   SYNTAX        Integer32 ( 0..1000 )
   MAX-ACCESS    read-write
   STATUS        current
   DESCRIPTION " MFC Pulse Inter Digit Timeout

                 The minimum delay between the end of transmission of the last
                 signal of the compelled cycle and the start of the next one.

                 This value is expressed in milliseconds (ms).


                 "
   DEFVAL        { 100 }
   ::= { r2DigitTimerVariantsEntry 400 }

  -- Columnar:MFC Minimum Pulse OnTimeout

  r2DigitTimerVariantsMfcPulseMinOnTimeout OBJECT-TYPE
   SYNTAX        Integer32 ( 0..1000 )
   MAX-ACCESS    read-write
   STATUS        current
   DESCRIPTION " MFC Minimum Pulse OnTimeout

                 The minimum time a backward tone can be on from the backward
                 perspective.

                 This value is expressed in milliseconds (ms).


                 "
   DEFVAL        { 150 }
   ::= { r2DigitTimerVariantsEntry 500 }

  -- Columnar:MFC Maximum Sequence Timeout

  r2DigitTimerVariantsMfcMaxSequenceTimeout OBJECT-TYPE
   SYNTAX        Integer32 ( 0..70000 )
   MAX-ACCESS    read-write
   STATUS        current
   DESCRIPTION " MFC Maximum Sequence Timeout

                 The maximum time for a complete compelled signaling cycle
                 from the forward perspective.

                 This value is expressed in milliseconds (ms).


                 "
   DEFVAL        { 10000 }
   ::= { r2DigitTimerVariantsEntry 600 }

  -- Columnar:MFC Maximum On Timeout

  r2DigitTimerVariantsMfcMaxOnTimeout OBJECT-TYPE
   SYNTAX        Integer32 ( 0..35000 )
   MAX-ACCESS    read-write
   STATUS        current
   DESCRIPTION " MFC Maximum On Timeout

                 The maximum time a forward tone can be on from the forward
                 perspective.

                 This value is expressed in milliseconds (ms).


                 "
   DEFVAL        { 5000 }
   ::= { r2DigitTimerVariantsEntry 700 }

  -- Columnar:MFC Maximum Off Timeout

  r2DigitTimerVariantsMfcMaxOffTimeout OBJECT-TYPE
   SYNTAX        Integer32 ( 0..35000 )
   MAX-ACCESS    read-write
   STATUS        current
   DESCRIPTION " MFC Maximum Off Timeout

                 The maximum time a forward tone can be off from the forward
                 perspective.

                 This value is expressed in milliseconds (ms).


                 "
   DEFVAL        { 5000 }
   ::= { r2DigitTimerVariantsEntry 800 }

  -- Row command:Reset Specific

  r2DigitTimerVariantsResetSpecific OBJECT-TYPE
   SYNTAX        INTEGER { noOp(0), resetSpecific(10) }
   MAX-ACCESS    read-write
   STATUS        current
   DESCRIPTION " Reset Specific

                 Resets specific settings of R2 Digit Timers parameters with
                 the default country settings. This command is used to
                 retrieve the default country configuration set in the
                 CountrySelection variable.
                 "
   DEFVAL        { noOp }
   ::= { r2DigitTimerVariantsEntry 900 }


 -- End of table:R2 Digit Timer Variants

 -- ***************************************************************************
 
 -- Table:R2 Link Timer Variants

 -- ***************************************************************************
 
 r2LinkTimerVariantsTable OBJECT-TYPE
  SYNTAX        SEQUENCE OF R2LinkTimerVariantsEntry
  MAX-ACCESS    not-accessible
  STATUS        current
  DESCRIPTION " R2 Link Timer Variants

                This table allows to override or retrieve the default country
                setting for R2 Link Timers.
                "
  ::= { r2Group 500 }
  r2LinkTimerVariantsEntry OBJECT-TYPE
   SYNTAX        R2LinkTimerVariantsEntry
   MAX-ACCESS    not-accessible
   STATUS        current
   DESCRIPTION " A row in table R2 Link Timer Variants. "
   INDEX         {
                   r2LinkTimerVariantsInterfaceName
                 }

   ::= { r2LinkTimerVariantsTable 1 }

  R2LinkTimerVariantsEntry ::= SEQUENCE
  {
    r2LinkTimerVariantsInterfaceName              OCTET STRING,
    r2LinkTimerVariantsCountrySelection           INTEGER,
    r2LinkTimerVariantsOverrideDefault            MxEnableState,
    r2LinkTimerVariantsLinkActivationTimeout      Integer32,
    r2LinkTimerVariantsLinkActivationRetryTimeout Integer32,
    r2LinkTimerVariantsResetSpecific              INTEGER
  }

  -- Index:Interface Name

  r2LinkTimerVariantsInterfaceName OBJECT-TYPE
   SYNTAX         OCTET STRING
   MAX-ACCESS     read-only
   STATUS         current
   DESCRIPTION  " Interface Name

                  Identifies the interface.
                  "
   ::= { r2LinkTimerVariantsEntry 100 }

  -- Columnar:Country Selection

  r2LinkTimerVariantsCountrySelection OBJECT-TYPE
   SYNTAX        INTEGER { brazilR2(100) , mexicoR2(200) , argentinaR2(300) ,
                 saudiArabiaR2(400) , venezuelaR2(500) , philippinesR2(600) ,
                 iTUTR2(700) }
   MAX-ACCESS    read-only
   STATUS        current
   DESCRIPTION " Country Selection

                 Identifies the current country selected in the R2 table for
                 the specified interface.

                   * Brazil-R2: Brazil R2 setting.
                   * Mexico-R2: Mexico R2 setting.
                   * Argentina-R2: Argentina R2 setting.
                   * SaudiArabia-R2: SaudiArabia R2 setting.
                   * Venezuela-R2: Venezuela R2 setting.
                   * Philippines-R2: Philippines R2 setting.
                   * ITU-T-R2: ITU-T R2 setting.


                 "
   ::= { r2LinkTimerVariantsEntry 200 }

  -- Columnar:Override Default

  r2LinkTimerVariantsOverrideDefault OBJECT-TYPE
   SYNTAX        MxEnableState
   MAX-ACCESS    read-write
   STATUS        current
   DESCRIPTION " Override Default

                 Overrides the default setting of R2 Link timers for the
                 CountrySelection and InterfaceName.

                   * Disable: The interface uses the default country
                     configuration. The configuration set in the current row
                     has no effects on the default country configuration.
                     Refer to the technical documentation to get the default
                     country timers configuration.
                   * Enable: The interface uses the specific country
                     configuration as defined in the current row. To retrieve
                     the default configuration associated with the current
                     country, the variable reset MUST be enabled.


                 "
   DEFVAL        { disable }
   ::= { r2LinkTimerVariantsEntry 300 }

  -- Columnar:Link Activation Timeout

  r2LinkTimerVariantsLinkActivationTimeout OBJECT-TYPE
   SYNTAX        Integer32 ( 0..10000 )
   MAX-ACCESS    read-write
   STATUS        current
   DESCRIPTION " Link Activation Timeout

                 The maximum time the unit waits for an activation indication
                 coming from the physical link. The activation indication is
                 used to indicate that the physical layer connection has been
                 activated.

                 This value is expressed in milliseconds (ms).


                 "
   DEFVAL        { 1000 }
   ::= { r2LinkTimerVariantsEntry 400 }

  -- Columnar:Link Activation Retry Timeout

  r2LinkTimerVariantsLinkActivationRetryTimeout OBJECT-TYPE
   SYNTAX        Integer32 ( 0..10000 )
   MAX-ACCESS    read-write
   STATUS        current
   DESCRIPTION " Link Activation Retry Timeout

                 The maximum time the unit waits before attempting to
                 reestablish the physical link. The attempt is made when the
                 physical layer connection has been deactivated.

                 This value is expressed in milliseconds (ms).


                 "
   DEFVAL        { 3000 }
   ::= { r2LinkTimerVariantsEntry 500 }

  -- Row command:Reset Specific

  r2LinkTimerVariantsResetSpecific OBJECT-TYPE
   SYNTAX        INTEGER { noOp(0), resetSpecific(10) }
   MAX-ACCESS    read-write
   STATUS        current
   DESCRIPTION " Reset Specific

                 Resets specific settings of R2 Link Timers parameters with
                 the default country settings. This command is used to
                 retrieve the default country configuration set in the
                 CountrySelection variable.
                 "
   DEFVAL        { noOp }
   ::= { r2LinkTimerVariantsEntry 600 }


 -- End of table:R2 Link Timer Variants

 -- ***************************************************************************
 
 -- Table:R2 Signaling Tone Variants

 -- ***************************************************************************
 
 r2ToneVariantsTable OBJECT-TYPE
  SYNTAX        SEQUENCE OF R2ToneVariantsEntry
  MAX-ACCESS    not-accessible
  STATUS        current
  DESCRIPTION " R2 Signaling Tone Variants

                This table allows to override or retrieve the default country
                setting for R2 Tone variants in forward and backward group.
                "
  ::= { r2Group 600 }
  r2ToneVariantsEntry OBJECT-TYPE
   SYNTAX        R2ToneVariantsEntry
   MAX-ACCESS    not-accessible
   STATUS        current
   DESCRIPTION " A row in table R2 Signaling Tone Variants. "
   INDEX         {
                   r2ToneVariantsInterfaceName
                 }

   ::= { r2ToneVariantsTable 1 }

  R2ToneVariantsEntry ::= SEQUENCE
  {
    r2ToneVariantsInterfaceName                                 OCTET STRING,
    r2ToneVariantsCountrySelection                              INTEGER,
    r2ToneVariantsOverrideDefault                               MxEnableState,
    r2ToneVariantsFwdGroup1EndOfDnis                            INTEGER,
    r2ToneVariantsFwdGroup1EndOfAni                             INTEGER,
    r2ToneVariantsFwdGroup1RestrictedAni                        INTEGER,
    r2ToneVariantsBwdGroupASendNextDnisDigit                    INTEGER,
    r2ToneVariantsBwdGroupASendPreviousDnisDigit                INTEGER,
    r2ToneVariantsBwdGroupASwitchToGroupII                      INTEGER,
    r2ToneVariantsBwdGroupANetworkCongestion                    INTEGER,
    r2ToneVariantsBwdGroupASendCallingPartyCategory             INTEGER,
    r2ToneVariantsBwdGroupAImmediateAccept                      INTEGER,
    r2ToneVariantsBwdGroupASendDnisDigitNMinus2                 INTEGER,
    r2ToneVariantsBwdGroupASendDnisDigitNMinus3                 INTEGER,
    r2ToneVariantsBwdGroupARepeatAllDnis                        INTEGER,
    r2ToneVariantsBwdGroupASendNextAniDigit                     INTEGER,
    r2ToneVariantsBwdGroupASendCallingPartyCategorySwitchGroupC INTEGER,
    r2ToneVariantsBwdGroupBSendSit                              INTEGER,
    r2ToneVariantsBwdGroupBUserBusy                             INTEGER,
    r2ToneVariantsBwdGroupBNetworkCongestion                    INTEGER,
    r2ToneVariantsBwdGroupBUnassignedNumber                     INTEGER,
    r2ToneVariantsBwdGroupBLineFreeCharge                       INTEGER,
    r2ToneVariantsBwdGroupBSupplementaryLineFreeCharge          INTEGER,
    r2ToneVariantsBwdGroupBLineFreeNoCharge                     INTEGER,
    r2ToneVariantsBwdGroupBLineOutOfOrder                       INTEGER,
    r2ToneVariantsBwdGroupBChangedNumber                        INTEGER,
    r2ToneVariantsBwdGroupCSendNextAniDigit                     INTEGER,
    r2ToneVariantsBwdGroupCRepeatAllDnisSwitchGroupA            INTEGER,
    r2ToneVariantsBwdGroupCSendNextDnisDigitSwitchGroupA        INTEGER,
    r2ToneVariantsBwdGroupCNetworkCongestion                    INTEGER,
    r2ToneVariantsBwdGroupCSendPreviousDnisDigitSwitchGroupA    INTEGER,
    r2ToneVariantsBwdGroupCSwitchGroupII                        INTEGER,
    r2ToneVariantsResetSpecific                                 INTEGER
  }

  -- Index:Interface Name

  r2ToneVariantsInterfaceName OBJECT-TYPE
   SYNTAX        OCTET STRING
   MAX-ACCESS    read-only
   STATUS        current
   DESCRIPTION " Interface Name

                 Identifies the interface.
                 "
   ::= { r2ToneVariantsEntry 100 }

  -- Columnar:Backward Group A SendCallingPartyCategory Tone

  r2ToneVariantsBwdGroupASendCallingPartyCategory OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A SendCallingPartyCategory Tone

                 Specifies the backward Group A tone sent when the backward
                 group requests the calling party category.

                   * None : No tone used.
                   * A1..A15 : Group A backward signals MF Tone


                 "
   DEFVAL        { a15 }
   ::= { r2ToneVariantsEntry 1000 }

  -- Columnar:Backward Group A ImmediateAccept Tone

  r2ToneVariantsBwdGroupAImmediateAccept OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A ImmediateAccept Tone

                 Specifies the backward Group A tone sent when the backward
                 group accepts the call immediatly.

                   * None : No tone used.
                   * A1..A15 : Group A backward signals MF Tone


                 "
   DEFVAL        { a15 }
   ::= { r2ToneVariantsEntry 1100 }

  -- Columnar:Backward Group A BwdGroupASendDnisDigitNMinus2 Tone

  r2ToneVariantsBwdGroupASendDnisDigitNMinus2 OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A BwdGroupASendDnisDigitNMinus2 Tone

                 Specifies the backward Group A tone used to request the
                 previous - 1 DNIS digit.

                   * None : No tone used.
                   * A1..A15 : Group A backward signals MF Tone


                 "
   DEFVAL        { a15 }
   ::= { r2ToneVariantsEntry 1200 }

  -- Columnar:Backward Group A BwdGroupASendDnisDigitNMinus3 Tone

  r2ToneVariantsBwdGroupASendDnisDigitNMinus3 OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A BwdGroupASendDnisDigitNMinus3 Tone

                 Specifies the backward Group A tone used to request the
                 previous - 2 DNIS digit.

                   * None : No tone used.
                   * A1..A15 : Group A backward signals MF Tone


                 "
   DEFVAL        { a15 }
   ::= { r2ToneVariantsEntry 1300 }

  -- Columnar:Backward Group A BwdGroupARepeatAllDnis Tone

  r2ToneVariantsBwdGroupARepeatAllDnis OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A BwdGroupARepeatAllDnis Tone

                 Specifies the backward Group A tone used to request all DNIS
                 digits.

                   * None : No tone used.
                   * A1..A15 : Group A backward signals MF Tone


                 "
   DEFVAL        { a15 }
   ::= { r2ToneVariantsEntry 1400 }

  -- Columnar:Backward Group A BwdGroupASendNextAniDigit Tone

  r2ToneVariantsBwdGroupASendNextAniDigit OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A BwdGroupASendNextAniDigit Tone

                 Specifies the backward Group A tone used to request the next
                 ANI digit.

                   * None : No tone used.
                   * A1..A15 : Group A backward signals MF Tone


                 "
   DEFVAL        { a15 }
   ::= { r2ToneVariantsEntry 1500 }

  -- Columnar:Backward Group A BwdGroupASendCallingPartyCategorySwitchGroupC
  -- Tone

  r2ToneVariantsBwdGroupASendCallingPartyCategorySwitchGroupC OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A
                 BwdGroupASendCallingPartyCategorySwitchGroupC Tone

                 Specifies the backward Group A tone used to request the
                 calling party category and then switch to Group C signals.

                   * None : No tone used.
                   * A1..A15 : Group A backward signals MF Tone


                 "
   DEFVAL        { a15 }
   ::= { r2ToneVariantsEntry 1550 }

  -- Columnar:Backward Group B BwdGroupBSendSpecialToneInformation Tone

  r2ToneVariantsBwdGroupBSendSit OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBSendSpecialToneInformation Tone

                 Specifies the backward Group B tone used to send a special
                 information tone.

                   * None : No tone used.
                   * B1..B15 : Group B backward signals MF Tone


                 "
   DEFVAL        { b15 }
   ::= { r2ToneVariantsEntry 1600 }

  -- Columnar:Backward Group B BwdGroupBUserBusy Tone

  r2ToneVariantsBwdGroupBUserBusy OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBUserBusy Tone

                 Specifies the backward Group B tone used to signal a user
                 busy.

                   * None : No tone used.
                   * B1..B15 : Group B backward signals MF Tone


                 "
   DEFVAL        { b15 }
   ::= { r2ToneVariantsEntry 1700 }

  -- Columnar:Backward Group B BwdGroupBNetworkCongestion Tone

  r2ToneVariantsBwdGroupBNetworkCongestion OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBNetworkCongestion Tone

                 Specifies the backward Group B tone used to signal a network
                 congestion.

                   * None : No tone used.
                   * B1..B15 : Group B backward signals MF Tone


                 "
   DEFVAL        { b15 }
   ::= { r2ToneVariantsEntry 1800 }

  -- Columnar:Backward Group B BwdGroupBUnassignedNumber Tone

  r2ToneVariantsBwdGroupBUnassignedNumber OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBUnassignedNumber Tone

                 Specifies the backward Group B tone used to signal an
                 unassigned number.

                   * None : No tone used.
                   * B1..B15 : Group B backward signals MF Tone


                 "
   DEFVAL        { b15 }
   ::= { r2ToneVariantsEntry 1900 }

  -- Columnar:Country Selection

  r2ToneVariantsCountrySelection OBJECT-TYPE
   SYNTAX        INTEGER { brazilR2(100) , mexicoR2(200) , argentinaR2(300) ,
                 saudiArabiaR2(400) , venezuelaR2(500) , philippinesR2(600) ,
                 iTUTR2(700) }
   MAX-ACCESS    read-only
   STATUS        current
   DESCRIPTION " Country Selection

                 Identifies the current country selected in the R2 table for
                 the specified interface.

                   * Brazil-R2: Brazil R2 setting.
                   * Mexico-R2: Mexico R2 setting.
                   * Argentina-R2: Argentina R2 setting.
                   * SaudiArabia-R2: SaudiArabia R2 setting.
                   * Venezuela-R2: Venezuela R2 setting.
                   * Philippines-R2: Philippines R2 setting.
                   * ITU-T-R2: ITU-T R2 setting.


                 "
   ::= { r2ToneVariantsEntry 200 }

  -- Columnar:Backward Group B BwdGroupBLineFreeCharge Tone

  r2ToneVariantsBwdGroupBLineFreeCharge OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBLineFreeCharge Tone

                 Specifies the backward Group B tone used to signal that the
                 line is free and charge must be applied.

                   * None : No tone used.
                   * B1..B15 : Group B backward signals MF Tone


                 "
   DEFVAL        { b15 }
   ::= { r2ToneVariantsEntry 2000 }

  -- Columnar:Backward Group B BwdGroupBSupplementaryLineFreeCharge Tone

  r2ToneVariantsBwdGroupBSupplementaryLineFreeCharge OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBSupplementaryLineFreeCharge Tone

                 Specifies a supplementary backward Group B tone used to
                 detect that the line is free and charge must be applied. This
                 is a supplementary (optionnal) tone used on the reception
                 only.

                   * None : No tone used.
                   * B1..B15 : Group B backward signals MF Tone


                 "
   DEFVAL        { b15 }
   ::= { r2ToneVariantsEntry 2100 }

  -- Columnar:Backward Group B BwdGroupBLineFreeNoCharge Tone

  r2ToneVariantsBwdGroupBLineFreeNoCharge OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBLineFreeNoCharge Tone

                 Specifies the backward Group B tone used to signal that the
                 line is free and no charges must be applied.

                   * None : No tone used.
                   * B1..B15 : Group B backward signals MF Tone


                 "
   DEFVAL        { b15 }
   ::= { r2ToneVariantsEntry 2200 }

  -- Columnar:Backward Group B BwdGroupBLineOutOfOrder Tone

  r2ToneVariantsBwdGroupBLineOutOfOrder OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBLineOutOfOrder Tone

                 Specifies the backward Group B tone used to signal that the
                 line is out of order.

                   * None : No tone used.
                   * B1..B15 : Group B backward signals MF Tone


                 "
   DEFVAL        { b15 }
   ::= { r2ToneVariantsEntry 2300 }

  -- Columnar:Backward Group B BwdGroupBChangedNumber Tone

  r2ToneVariantsBwdGroupBChangedNumber OBJECT-TYPE
   SYNTAX        INTEGER { none(100) , b1(200) , b2(300) , b3(400) , b4(500) ,
                 b5(600) , b6(700) , b7(800) , b8(900) , b9(1000) , b10(1100)
                 , b11(1200) , b12(1300) , b13(1400) , b14(1500) , b15(1600) }
   MAX-ACCESS    read-write
   STATUS        current
   DESCRIPTION " Backward Group B BwdGroupBChangedNumber Tone

                 Specifies the backward Group B tone used to signal that the
                 subscriber has changed number.

                   * None : No tone used.
                   * B1..B15 : Group B backward signals MF Tone


                 "
   DEFVAL        { b15 }
   ::= { r2ToneVariantsEntry 2350 }

  -- Columnar:Backward Group C BwdGroupCSendNextAniDigit Tone

  r2ToneVariantsBwdGroupCSendNextAniDigit OBJECT-TYPE
   SYNTAX        INTEGER { none(100) , c1(200) , c2(300) , c3(400) , c4(500) ,
                 c5(600) , c6(700) , c7(800) , c8(900) , c9(1000) , c10(1100)
                 , c11(1200) , c12(1300) , c13(1400) , c14(1500) , c15(1600) }
   MAX-ACCESS    read-write
   STATUS        current
   DESCRIPTION " Backward Group C BwdGroupCSendNextAniDigit Tone

                 Specifies the backward Group C tone used to request the next
                 ANI digit.

                   * None : No tone used.
                   * C1..C15 : Group C backward signals MF Tone


                 "
   DEFVAL        { c15 }
   ::= { r2ToneVariantsEntry 2355 }

  -- Columnar:Backward Group C BwdCRepeatAllDnisSwitchGroupA Tone

  r2ToneVariantsBwdGroupCRepeatAllDnisSwitchGroupA OBJECT-TYPE
   SYNTAX        INTEGER { none(100) , c1(200) , c2(300) , c3(400) , c4(500) ,
                 c5(600) , c6(700) , c7(800) , c8(900) , c9(1000) , c10(1100)
                 , c11(1200) , c12(1300) , c13(1400) , c14(1500) , c15(1600) }
   MAX-ACCESS    read-write
   STATUS        current
   DESCRIPTION " Backward Group C BwdCRepeatAllDnisSwitchGroupA Tone

                 Specifies the backward Group C tone used to request all DNIS
                 digits and then switch to Group A signals.

                   * None : No tone used.
                   * C1..C15 : Group C backward signals MF Tone


                 "
   DEFVAL        { c15 }
   ::= { r2ToneVariantsEntry 2360 }

  -- Columnar:Backward Group C BwdCSendNextDnisDigitSwitchGroupA Tone

  r2ToneVariantsBwdGroupCSendNextDnisDigitSwitchGroupA OBJECT-TYPE
   SYNTAX        INTEGER { none(100) , c1(200) , c2(300) , c3(400) , c4(500) ,
                 c5(600) , c6(700) , c7(800) , c8(900) , c9(1000) , c10(1100)
                 , c11(1200) , c12(1300) , c13(1400) , c14(1500) , c15(1600) }
   MAX-ACCESS    read-write
   STATUS        current
   DESCRIPTION " Backward Group C BwdCSendNextDnisDigitSwitchGroupA Tone

                 Specifies the backward Group C tone used to request the next
                 DNIS digit and then switch to Group A signals.

                   * None : No tone used.
                   * C1..C15 : Group C backward signals MF Tone


                 "
   DEFVAL        { c15 }
   ::= { r2ToneVariantsEntry 2365 }

  -- Columnar:Backward Group C BwdGroupCNetworkCongestion Tone

  r2ToneVariantsBwdGroupCNetworkCongestion OBJECT-TYPE
   SYNTAX        INTEGER { none(100) , c1(200) , c2(300) , c3(400) , c4(500) ,
                 c5(600) , c6(700) , c7(800) , c8(900) , c9(1000) , c10(1100)
                 , c11(1200) , c12(1300) , c13(1400) , c14(1500) , c15(1600) }
   MAX-ACCESS    read-write
   STATUS        current
   DESCRIPTION " Backward Group C BwdGroupCNetworkCongestion Tone

                 Specifies the backward Group C tone used to signal a network
                 congestion.

                   * None : No tone used.
                   * C1..C15 : Group C backward signals MF Tone


                 "
   DEFVAL        { c15 }
   ::= { r2ToneVariantsEntry 2370 }

  -- Columnar:Backward Group C BwdCSendPreviousDnisDigitSwitchGroupA Tone

  r2ToneVariantsBwdGroupCSendPreviousDnisDigitSwitchGroupA OBJECT-TYPE
   SYNTAX        INTEGER { none(100) , c1(200) , c2(300) , c3(400) , c4(500) ,
                 c5(600) , c6(700) , c7(800) , c8(900) , c9(1000) , c10(1100)
                 , c11(1200) , c12(1300) , c13(1400) , c14(1500) , c15(1600) }
   MAX-ACCESS    read-write
   STATUS        current
   DESCRIPTION " Backward Group C BwdCSendPreviousDnisDigitSwitchGroupA Tone

                 Specifies the backward Group C tone used to request the
                 previous DNIS digit and then switch to Group A signals.

                   * None : No tone used.
                   * C1..C15 : Group C backward signals MF Tone


                 "
   DEFVAL        { c15 }
   ::= { r2ToneVariantsEntry 2375 }

  -- Columnar:Backward Group C BwdCSwitchGroupII Tone

  r2ToneVariantsBwdGroupCSwitchGroupII OBJECT-TYPE
   SYNTAX        INTEGER { none(100) , c1(200) , c2(300) , c3(400) , c4(500) ,
                 c5(600) , c6(700) , c7(800) , c8(900) , c9(1000) , c10(1100)
                 , c11(1200) , c12(1300) , c13(1400) , c14(1500) , c15(1600) }
   MAX-ACCESS    read-write
   STATUS        current
   DESCRIPTION " Backward Group C BwdCSwitchGroupII Tone

                 Specifies the backward Group C tone used to request to the
                 caller a switch of Group II signals.

                   * None : No tone used.
                   * C1..C15 : Group C backward signals MF Tone


                 "
   DEFVAL        { c15 }
   ::= { r2ToneVariantsEntry 2380 }

  -- Row command:Reset Specific

  r2ToneVariantsResetSpecific OBJECT-TYPE
   SYNTAX        INTEGER { noOp(0), resetSpecific(10) }
   MAX-ACCESS    read-write
   STATUS        current
   DESCRIPTION " Reset Specific

                 Resets specific settings of R2 Tones parameters with the
                 default country settings. This command is used to retrieve
                 the default country configuration set in the CountrySelection
                 variable.
                 "
   DEFVAL        { noOp }
   ::= { r2ToneVariantsEntry 2400 }

  -- Columnar:Override Default

  r2ToneVariantsOverrideDefault OBJECT-TYPE
   SYNTAX        MxEnableState
   MAX-ACCESS    read-write
   STATUS        current
   DESCRIPTION " Override Default

                 Overrides the default setting of R2 tone variants for the
                 CountrySelection and InterfaceName.

                   * Disable: The interface uses the default country
                     configuration. The configuration set in the current row
                     has no effects on the default country configuration.
                     Refer to the technical documentation to get the default
                     country tones configuration.
                   * Enable: The interface uses the specific country
                     configuration as defined in the current row. To retrieve
                     the default configuration associated with the current
                     country, the variable reset MUST be enabled.


                 "
   DEFVAL        { disable }
   ::= { r2ToneVariantsEntry 300 }

  -- Columnar:Forward Group 1 EndOfDnis Tone

  r2ToneVariantsFwdGroup1EndOfDnis OBJECT-TYPE
   SYNTAX        INTEGER { none(100) , i1(200) , i2(300) , i3(400) , i4(500) ,
                 i5(600) , i6(700) , i7(800) , i8(900) , i9(1000) , i10(1100)
                 , i11(1200) , i12(1300) , i13(1400) , i14(1500) , i15(1600) }
   MAX-ACCESS    read-write
   STATUS        current
   DESCRIPTION " Forward Group 1 EndOfDnis Tone

                 Specifies the forward Group 1 tone used to send after the
                 DNIS digits.

                   * None : No tone used.
                   * I1..I15 : Group 1 forward signals MF Tone


                 "
   DEFVAL        { i15 }
   ::= { r2ToneVariantsEntry 400 }

  -- Columnar:Forward Group 1 EndOfAni Tone

  r2ToneVariantsFwdGroup1EndOfAni OBJECT-TYPE
   SYNTAX        INTEGER { none(100) , i1(200) , i2(300) , i3(400) , i4(500) ,
                 i5(600) , i6(700) , i7(800) , i8(900) , i9(1000) , i10(1100)
                 , i11(1200) , i12(1300) , i13(1400) , i14(1500) , i15(1600) }
   MAX-ACCESS    read-write
   STATUS        current
   DESCRIPTION " Forward Group 1 EndOfAni Tone

                 Specifies the forward Group 1 tone used to send after the ANI
                 digits.

                   * None : No tone used.
                   * I1..I15 : Group 1 forward signals MF Tone


                 "
   DEFVAL        { i15 }
   ::= { r2ToneVariantsEntry 500 }

  -- Columnar:Forward Group 1 Restricted ANI Tone

  r2ToneVariantsFwdGroup1RestrictedAni OBJECT-TYPE
   SYNTAX        INTEGER { none(100) , i1(200) , i2(300) , i3(400) , i4(500) ,
                 i5(600) , i6(700) , i7(800) , i8(900) , i9(1000) , i10(1100)
                 , i11(1200) , i12(1300) , i13(1400) , i14(1500) , i15(1600) }
   MAX-ACCESS    read-write
   STATUS        current
   DESCRIPTION " Forward Group 1 Restricted ANI Tone

                 Specifies the forward Group 1 tone used to reject a send next
                 digit (ANI). This tone is generally used in response to the
                 identification request when the caller party is unable to
                 send his identification to the called party. If no tone is
                 defined, the FwdGroup1EndOfAni tone is sent to the caller.

                   * None : No tone used.
                   * I1..I15 : Group 1 forward signals MF Tone


                 "
   DEFVAL        { i12 }
   ::= { r2ToneVariantsEntry 520 }

  -- Columnar:Backward Group A SendNextDnisDigit Tone

  r2ToneVariantsBwdGroupASendNextDnisDigit OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A SendNextDnisDigit Tone

                 Specifies the backward Group A tone used to request the next
                 DNIS digit.

                   * None : No tone used.
                   * A1..A15 : Group A backward signals MF Tone


                 "
   DEFVAL        { a15 }
   ::= { r2ToneVariantsEntry 600 }

  -- Columnar:Backward Group A SendPreviousDnisDigit Tone

  r2ToneVariantsBwdGroupASendPreviousDnisDigit OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A SendPreviousDnisDigit Tone

                 Specifies the backward Group A tone used to request the
                 previous DNIS digit.

                   * None : No tone used.
                   * A1..A15 : Group A backward signals MF Tone


                 "
   DEFVAL        { a15 }
   ::= { r2ToneVariantsEntry 700 }

  -- Columnar:Backward Group A BwdGroupASwitchToGroupII Tone

  r2ToneVariantsBwdGroupASwitchToGroupII OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A BwdGroupASwitchToGroupII Tone

                 Specifies the backward Group A tone used to request to the
                 caller a switch of Group II signals.

                   * None : No tone used.
                   * A1..A15 : Group A backward signals MF Tone


                 "
   DEFVAL        { a15 }
   ::= { r2ToneVariantsEntry 800 }

  -- Columnar:Backward Group A NetworkCongestion Tone

  r2ToneVariantsBwdGroupANetworkCongestion OBJECT-TYPE
   SYNTAX        INTEGER { none(100) , a1(200) , a2(300) , a3(400) , a4(500) ,
                 a5(600) , a6(700) , a7(800) , a8(900) , a9(1000) , a10(1100)
                 , a11(1200) , a12(1300) , a13(1400) , a14(1500) , a15(1600) }
   MAX-ACCESS    read-write
   STATUS        current
   DESCRIPTION " Backward Group A NetworkCongestion Tone

                 Specifies the backward Group A tone to be sent when a
                 congestion network is detected.

                   * None : No tone used.
                   * A1..A15 : Group A backward signals MF Tone


                 "
   DEFVAL        { a15 }
   ::= { r2ToneVariantsEntry 900 }


 -- End of table:R2 Signaling Tone Variants

-- End of group:R2 Configuration

-- ****************************************************************************

-- Group:Bearer Channel Configuration

-- ****************************************************************************

bearerChannelGroup OBJECT IDENTIFIER
 ::= { r2MIBObjects 200 }
 -- ***************************************************************************
 
 -- Table:Bearer Channel Info

 -- ***************************************************************************
 
 bearerChannelInfoTable OBJECT-TYPE
  SYNTAX        SEQUENCE OF BearerChannelInfoEntry
  MAX-ACCESS    not-accessible
  STATUS        current
  DESCRIPTION " Bearer Channel Info

                Port-specific operational, statistics, and active call data
                for B channels.
                "
  ::= { bearerChannelGroup 100 }
  bearerChannelInfoEntry OBJECT-TYPE
   SYNTAX        BearerChannelInfoEntry
   MAX-ACCESS    not-accessible
   STATUS        current
   DESCRIPTION " A row in table Bearer Channel Info. "
   INDEX         {
                   bearerChannelInfoIndex
                 }

   ::= { bearerChannelInfoTable 1 }

  BearerChannelInfoEntry ::= SEQUENCE
  {
    bearerChannelInfoIndex OCTET STRING,
    bearerChannelInfoState INTEGER
  }

  -- Index:Index

  bearerChannelInfoIndex OBJECT-TYPE
   SYNTAX        OCTET STRING
   MAX-ACCESS    read-only
   STATUS        current
   DESCRIPTION " Index

                 Identifies the Bearer Channel..
                 "
   ::= { bearerChannelInfoEntry 100 }

  -- Columnar:State

  bearerChannelInfoState OBJECT-TYPE
   SYNTAX        INTEGER { idle(100) , inUse(200) , maintenance(300) , error
                 (400) , disabled(500) }
   MAX-ACCESS    read-only
   STATUS        current
   DESCRIPTION " State

                 The current call control state for this channel:

                   * Idle: The channel is available
                   * InUse: The channel is currently used
                   * Maintenance: Maintenance state, temporarily unavailable
                   * Error: Error on this channel
                   * Disabled: The channel is disabled


                 "
   ::= { bearerChannelInfoEntry 200 }


 -- End of table:Bearer Channel Info

-- End of group:Bearer Channel Configuration

-- ****************************************************************************

-- Group:Signaling Channel Configuration

-- ****************************************************************************

physicalGroup OBJECT IDENTIFIER
 ::= { r2MIBObjects 300 }
 -- ***************************************************************************
 
 -- Table:Physical Link Information

 -- ***************************************************************************
 
 physicalLinkInfoTable OBJECT-TYPE
  SYNTAX        SEQUENCE OF PhysicalLinkInfoEntry
  MAX-ACCESS    not-accessible
  STATUS        current
  DESCRIPTION " Physical Link Information

                The physical link information table contains status
                information for all interfaces on this managed device.
                "
  ::= { physicalGroup 100 }
  physicalLinkInfoEntry OBJECT-TYPE
   SYNTAX        PhysicalLinkInfoEntry
   MAX-ACCESS    not-accessible
   STATUS        current
   DESCRIPTION " A row in table Physical Link Information. "
   INDEX         {
                   physicalLinkInfoInterfaceName
                 }

   ::= { physicalLinkInfoTable 1 }

  PhysicalLinkInfoEntry ::= SEQUENCE
  {
    physicalLinkInfoInterfaceName OCTET STRING,
    physicalLinkInfoState         INTEGER
  }

  -- Index:Interface Name

  physicalLinkInfoInterfaceName OBJECT-TYPE
   SYNTAX        OCTET STRING
   MAX-ACCESS    read-only
   STATUS        current
   DESCRIPTION " Interface Name

                 Identifies the interface.
                 "
   ::= { physicalLinkInfoEntry 100 }

  -- Columnar:State

  physicalLinkInfoState OBJECT-TYPE
   SYNTAX        INTEGER { up(100) , down(200) }
   MAX-ACCESS    read-only
   STATUS        current
   DESCRIPTION " State

                 The layer 1 state for this interface:

                   * Up: Layer 1 connectivity.
                   * Down: No layer 1 connectivity. The interface might be in
                     this state because no cable is plugged in or a pinout
                     problem is detected.


                 "
   ::= { physicalLinkInfoEntry 200 }


 -- End of table:Physical Link Information

 -- ***************************************************************************
 
 -- Table:Physical Link

 -- ***************************************************************************
 
 physicalLinkTable OBJECT-TYPE
  SYNTAX        SEQUENCE OF PhysicalLinkEntry
  MAX-ACCESS    not-accessible
  STATUS        current
  DESCRIPTION " Physical Link

                The physical link table containing configuration and
                operational parameters for all interfaces on this managed
                device.
                "
  ::= { physicalGroup 200 }
  physicalLinkEntry OBJECT-TYPE
   SYNTAX        PhysicalLinkEntry
   MAX-ACCESS    not-accessible
   STATUS        current
   DESCRIPTION " A row in table Physical Link. "
   INDEX         {
                   physicalLinkInterfaceName
                 }

   ::= { physicalLinkTable 1 }

  PhysicalLinkEntry ::= SEQUENCE
  {
    physicalLinkInterfaceName          OCTET STRING,
    physicalLinkLineCoding             INTEGER,
    physicalLinkLineFraming            INTEGER,
    physicalLinkClockMode              INTEGER,
    physicalLinkMonitorLinkStateEnable MxEnableState,
    physicalLinkPortPinout             INTEGER
  }

  -- Index:Interface Name

  physicalLinkInterfaceName OBJECT-TYPE
   SYNTAX        OCTET STRING
   MAX-ACCESS    read-only
   STATUS        current
   DESCRIPTION " Interface Name

                 Identifies the interface.
                 "
   ::= { physicalLinkEntry 100 }

  -- Columnar:Line Coding

  physicalLinkLineCoding OBJECT-TYPE
   SYNTAX        INTEGER { b8zs(100) , hdb3(200) , ami(300) }
   MAX-ACCESS    read-write
   STATUS        current
   DESCRIPTION " Line Coding

                 Defines the transmission encoding of bits:

                   * B8ZS: Bipolar with 8-Zeros Substitution (T1 lines)
                   * HDB3: High-Density Bipolar with 3-zeros (E1 lines)
                   * AMI: Alternate Mark Inversion (E1 and T1 lines)

                 For further information, see ITU-T Recommendation G.703.
                 "
   DEFVAL        { hdb3 }
   ::= { physicalLinkEntry 200 }

  -- Columnar:Line Framing

  physicalLinkLineFraming OBJECT-TYPE
   SYNTAX        INTEGER { sf(100) , esf(200) , crc4(300) , noCrc4(400) }
   MAX-ACCESS    read-write
   STATUS        current
   DESCRIPTION " Line Framing

                 Defines the frame format:

                   * SF: Super frame. Sometimes known as D4 (T1 lines)
                   * ESF: Extended super frame (T1 lines)
                   * CRC4: Cyclic redundancy check 4 (E1 lines)
                   * NO-CRC4: No Cyclic redundancy check 4 (E1 lines)

                 For further information, see ITU-T Recommendation G.704.
                 "
   DEFVAL        { crc4 }
   ::= { physicalLinkEntry 300 }

  -- Columnar:Clock Mode

  physicalLinkClockMode OBJECT-TYPE
   SYNTAX        INTEGER { master(100) , slave(200) }
   MAX-ACCESS    read-write
   STATUS        current
   DESCRIPTION " Clock Mode

                 A port can either generate the clocking for the line or
                 accept the clock from the line. The options master or slave
                 determine the clocking method:

                   * Master: Generates clock
                   * Slave: Accepts clock


                 "
   DEFVAL        { slave }
   ::= { physicalLinkEntry 400 }

  -- Columnar:Monitor Link State Enable

  physicalLinkMonitorLinkStateEnable OBJECT-TYPE
   SYNTAX        MxEnableState
   MAX-ACCESS    read-write
   STATUS        current
   DESCRIPTION " Monitor Link State Enable

                 Monitors the physical link state of an R2 interface.

                 Enable: An R2 endpoint's operational state is affected by its
                 interface physical link state. When the link state of an R2
                 interface is down, the operational state of its matching
                 endpoint becomes 'disable'.

                 Disable: An R2 endpoint's operational state is not affected
                 by its interface physical link state.


                 "
   DEFVAL        { enable }
   ::= { physicalLinkEntry 500 }

  -- Columnar:Port Pinout

  physicalLinkPortPinout OBJECT-TYPE
   SYNTAX        INTEGER { auto(100) , master(200) , slave(300) }
   MAX-ACCESS    read-write
   STATUS        current
   DESCRIPTION " Port Pinout

                 Defines the port pinout:

                   * Auto: The pinout is set according to the clock mode.
                   * Master: Force the pinout to Master regardless of the
                     clock mode.
                   * Slave: Force the pinout to Slave regardless of the clock
                     mode.

                 See variable PhysicalLink.ClockMode for a description of the
                 clock mode.
                 "
   DEFVAL        { auto }
   ::= { physicalLinkEntry 600 }


 -- End of table:Physical Link

-- End of group:Signaling Channel Configuration

-- ****************************************************************************

-- Group:Notification Messages Configuration

-- ****************************************************************************

notificationsGroup OBJECT IDENTIFIER
 ::= { r2MIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { r2MIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
