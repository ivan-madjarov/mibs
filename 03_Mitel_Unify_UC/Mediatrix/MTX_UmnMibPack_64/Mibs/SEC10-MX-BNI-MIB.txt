-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************
  
SEC10-MX-BNI-MIB
DEFINITIONS ::= BEGIN

IMPORTS
        MODULE-IDENTITY,
        OBJECT-TYPE,
        Unsigned32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices       
    FROM MX-SMI2;

bniMIB MODULE-IDENTITY                                                         
    LAST-UPDATED   "0510310000Z"                                               
    ORGANIZATION " Mediatrix Telecom, Inc. "                                   
    CONTACT-INFO " Mediatrix Telecom, Inc.                                     
                   4229, Garlock Street                                        
                   Sherbrooke (Quebec)                                         
                   Canada                                                      
                   Phone: (819) 829-8749                                       
                   "                                                           
    DESCRIPTION  " Basic Network Interfaces                                    
                                                                               
                   The Basic Network Interfaces service allows the             
                   administrator to configure parameters for the network       
                   interfaces.                                                 
                   "                                                           
    -- *************************************************************************
                                                                               
    -- Revision history                                                        
                                                                               
    -- *************************************************************************
    REVISION       "0510310000Z"                                               
    DESCRIPTION  " Initial Revision "                                          
    ::= { mediatrixServices 200 }                                              

bniMIBObjects OBJECT IDENTIFIER ::= { bniMIB 1 }

-- *****************************************************************************
                                                                               
-- Group:  PPP Configuration                                                   
                                                                               
-- *****************************************************************************
                                                                               
pppIpcpGroup OBJECT IDENTIFIER                                                 
    ::= { bniMIBObjects 400 }                                                  
                                                                               
                                                                               
    -- Scalar:  Service Name                                                   
                                                                               
    pppServiceName OBJECT-TYPE                                                 
        SYNTAX        OCTET STRING ( SIZE(0..64) )                             
        MAX-ACCESS    read-write                                               
        STATUS        current                                                  
        DESCRIPTION " Service Name                                             
                                                                               
                      Name of the service requested to the access concentrator 
                      (AC) when establishing the next PPPoE connection.        
                                                                               
                      This string is used as the Service-Name field of the PADI
                      packet broadcasted to the access concentrators. See RFC  
                      2516 section 5.1 for details.                            
                                                                               
                                                                               
                      "                                                        
        DEFVAL        { "" }                                                   
        ::= { pppIpcpGroup 100 }                                               
                                                                               
    -- Scalar:  Retry Interval                                                 
                                                                               
    pppRetryInterval OBJECT-TYPE                                               
        SYNTAX        Unsigned32 ( 1..900 )                                    
        MAX-ACCESS    read-write                                               
        STATUS        current                                                  
        DESCRIPTION " Retry Interval                                           
                                                                               
                      Interval, in seconds, between connection attempts. A     
                      connection is automatically retried when it fails due to 
                      a transient error. The only error type considered        
                      non-transient is a configuration error.                  
                      "                                                        
        DEFVAL        { 10 }                                                   
        ::= { pppIpcpGroup 200 }                                               
                                                                               
    -- Scalar:  Authentication Protocol                                        
                                                                               
    pppAuthenticationProtocol OBJECT-TYPE                                      
        SYNTAX        INTEGER { pap(100) , chap(200) }                         
        MAX-ACCESS    read-write                                               
        STATUS        current                                                  
        DESCRIPTION " Authentication Protocol                                  
                                                                               
                      Authentication protocol to use for authenticating the    
                      system to the PPP peer.                                  
                                                                               
                        * Pap: Use the Password Authentication Protocol.       
                        * Chap: Use the Challenge Handshake Authentication     
                          Protocol.                                            
                                                                               
                                                                               
                      "                                                        
        DEFVAL        { chap }                                                 
        ::= { pppIpcpGroup 300 }                                               
                                                                               
    -- Scalar:  User Name                                                      
                                                                               
    pppIdentity OBJECT-TYPE                                                    
        SYNTAX        OCTET STRING ( SIZE(0..64) )                             
        MAX-ACCESS    read-write                                               
        STATUS        current                                                  
        DESCRIPTION " User Name                                                
                                                                               
                      Name that identifies the system to the PPP peer during   
                      the authentication process.                              
                      "                                                        
        DEFVAL        { "" }                                                   
        ::= { pppIpcpGroup 400 }                                               
                                                                               
    -- Scalar:  Password                                                       
                                                                               
    pppSecret OBJECT-TYPE                                                      
        SYNTAX        OCTET STRING ( SIZE(0..64) )                             
        MAX-ACCESS    read-write                                               
        STATUS        current                                                  
        DESCRIPTION " Password                                                 
                                                                               
                      Secret that identifies the system to the PPP peer during 
                      the authentication process.                              
                                                                               
                      Whatever the value defined, this variable always displays
                      '*****'.                                                 
                                                                               
                                                                               
                      "                                                        
        DEFVAL        { "" }                                                   
        ::= { pppIpcpGroup 500 }                                               
                                                                               
-- End of group:  PPP Configuration                                            

-- *****************************************************************************
                                                                               
-- Table:  Interfaces Configuration                                            
                                                                               
-- *****************************************************************************
                                                                               
networkInterfacesTable OBJECT-TYPE                                             
    SYNTAX               SEQUENCE OF NetworkInterfacesEntry                    
    MAX-ACCESS           not-accessible                                        
    STATUS               current                                               
    DESCRIPTION       "  Interfaces Configuration                              
                                                                               
                         This table configures the network interfaces.         
                         "                                                     
    ::= { bniMIBObjects 1000 }                                                 
                                                                               
                                                                               
    networkInterfacesEntry OBJECT-TYPE                                         
        SYNTAX         NetworkInterfacesEntry                                  
        MAX-ACCESS     not-accessible                                          
        STATUS         current                                                 
        DESCRIPTION  " A row in the Interfaces Configuration. "                
        INDEX          {                                                       
                           interfaceName                                       
                       }                                                       
                                                                               
        ::= { networkInterfacesTable 1 }                                       
                                                                               
    NetworkInterfacesEntry ::= SEQUENCE                                        
    {                                                                          
        interfaceName     OCTET STRING,                                        
        linkName          OCTET STRING,                                        
        connectionType    INTEGER,                                             
        staticIpAddr      MxIpAddrMask,                                        
        activationAttempt MxEnableState,                                       
        delete            INTEGER                                              
    }                                                                          
                                                                               
    -- Index:  Interface Name                                                  
                                                                               
    networkInterfacesInterfaceName OBJECT-TYPE                                 
        SYNTAX         OCTET STRING                                            
        MAX-ACCESS     read-only                                               
        STATUS         current                                                 
        DESCRIPTION  " Interface Name                                          
                                                                               
                       Network interface name.                                 
                       "                                                       
        ::= { networkInterfacesEntry 100 }                                     
                                                                               
    -- Columnar:  Link Interface                                               
                                                                               
    networkInterfacesLinkName OBJECT-TYPE                                      
        SYNTAX        OCTET STRING                                             
        MAX-ACCESS    read-write                                               
        STATUS        current                                                  
        DESCRIPTION " Link Interface                                           
                                                                               
                      Name of the link interface associated with the network   
                      interface.                                               
                      "                                                        
        ::= { networkInterfacesEntry 200 }                                     
                                                                               
    -- Columnar:  Connection Type                                              
                                                                               
    networkInterfacesConnectionType OBJECT-TYPE                                
        SYNTAX        INTEGER { ipDhcp(100) , ipStatic(200) , pppIpcp(300) }   
        MAX-ACCESS    read-write                                               
        STATUS        current                                                  
        DESCRIPTION " Connection Type                                          
                                                                               
                      Connection type of the network interface.                
                                                                               
                        * IpDhcp: IPv4 connection, address and network mask are
                          provided by a DHCP server.                           
                        * IpStatic: IPv4 connection, address and network mask  
                          are configured by the column 'StaticIpAddr'.         
                        * PppIpcp: IPv4 over PPP connection, address and       
                          network mask are provided by the PPP peer using IPCP.
                                                                               
                      Only one connection is allowed to have a type different  
                      than IpStatic. DHCP servers and PPP peers may provide a  
                      list of DNS to use. If that is the case, the DNS are     
                      forwarded to the Host Configuration service where they   
                      can be used.                                             
                      "                                                        
        DEFVAL        { ipStatic }                                             
        ::= { networkInterfacesEntry 250 }                                     
                                                                               
    -- Columnar:  Static IP Address                                            
                                                                               
    networkInterfacesStaticIpAddr OBJECT-TYPE                                  
        SYNTAX        MxIpAddrMask                                             
        MAX-ACCESS    read-write                                               
        STATUS        current                                                  
        DESCRIPTION " Static IP Address                                        
                                                                               
                      IPv4 address and network mask of the network interface   
                      when it is of type ipStatic                              
                      "                                                        
        DEFVAL        { "192.168.0.10/24" }                                    
        ::= { networkInterfacesEntry 300 }                                     
                                                                               
    -- Columnar:  ActivationAttempt                                            
                                                                               
    networkInterfacesActivationAttempt OBJECT-TYPE                             
        SYNTAX        MxEnableState                                            
        MAX-ACCESS    read-write                                               
        STATUS        current                                                  
        DESCRIPTION " ActivationAttempt                                        
                                                                               
                      Attempt to activate the network interface.               
                                                                               
                        * Enable: The system should attempt to activate the    
                          network interface.                                   
                        * Disable: The system should not attempt to activate   
                          the network interface.                               
                                                                               
                      Tells whether the system should attempt to activate the  
                      network interface or not. The actual status of network   
                      interfaces is shown in the NetworkInterfacesStatus table.
                      "                                                        
        DEFVAL        { disable }                                              
        ::= { networkInterfacesEntry 400 }                                     
                                                                               
    -- Row command:  Delete                                                    
                                                                               
    networkInterfacesDelete OBJECT-TYPE                                        
        SYNTAX        INTEGER { noOp(0), delete(10) }                          
        MAX-ACCESS    read-write                                               
        STATUS        current                                                  
        DESCRIPTION " Delete                                                   
                                                                               
                      Deletes the network interface and removes it from the    
                      system.                                                  
                      "                                                        
        DEFVAL        { noOp }                                                 
        ::= { networkInterfacesEntry 500 }                                     
                                                                               
                                                                               
-- End of table:  Interfaces Configuration                                     

-- *****************************************************************************
                                                                               
-- Table:  Interfaces Status                                                   
                                                                               
-- *****************************************************************************
                                                                               
networkInterfacesStatusTable OBJECT-TYPE                                       
    SYNTAX        SEQUENCE OF NetworkInterfacesStatusEntry                     
    MAX-ACCESS    not-accessible                                               
    STATUS        current                                                      
    DESCRIPTION " Interfaces Status                                            
                                                                               
                  This table displays all currently operationnal network       
                  interfaces.                                                  
                  "                                                            
    ::= { bniMIBObjects 2000 }                                                 
                                                                               
                                                                               
    networkInterfacesStatusEntry OBJECT-TYPE                                   
        SYNTAX         NetworkInterfacesStatusEntry                            
        MAX-ACCESS     not-accessible                                          
        STATUS         current                                                 
        DESCRIPTION  " A row in the Interfaces Status. "                       
        INDEX          {                                                       
                           interfaceName                                       
                       }                                                       
                                                                               
        ::= { networkInterfacesStatusTable 1 }                                 
                                                                               
    NetworkInterfacesStatusEntry ::= SEQUENCE                                  
    {                                                                          
         interfaceName       OCTET STRING,                                     
         interfaceStatus     INTEGER,                                          
         linkName            OCTET STRING,                                     
         ipAddr              MxIpAddrMask                                      
    }                                                                          
                                                                               
    -- Index:  Interface Name                                                  
                                                                               
    networkInterfacesStatusInterfaceName OBJECT-TYPE                           
        SYNTAX           OCTET STRING                                          
        MAX-ACCESS       read-only                                             
        STATUS           current                                               
        DESCRIPTION    " Interface Name                                        
                                                                               
                         Network interface name.                               
                         "                                                     
        ::= { networkInterfacesStatusEntry 100 }                               
                                                                               
    -- Columnar:  Network Interface Status                                     
                                                                               
    networkInterfacesStatusInterfaceStatus OBJECT-TYPE                         
        SYNTAX        INTEGER { disabled(100) , invalidConfig(200) ,           
                      waitingResponse(300) , ok(400) }                         
        MAX-ACCESS    read-only                                                
        STATUS        current                                                  
        DESCRIPTION " Network Interface Status                                 
                                                                               
                      Displays the operational status of the network interface.
                                                                               
                        * Disabled: The interface is not operational because it
                          is explicitly disabled or the link interface is      
                          unavailable.                                         
                        * InvalidConfig: The interface is not operational      
                          because its configuration is not valid.              
                        * WaitingResponse: The interface is not operational    
                          because a response from a peer or server is required.
                        * Ok: The interface is operational.                    
                                                                               
                                                                               
                      "                                                        
        ::= { networkInterfacesStatusEntry 150 }                               
                                                                               
    -- Columnar:  Link Interface                                               
                                                                               
    networkInterfacesStatusLinkName OBJECT-TYPE                                
        SYNTAX        OCTET STRING                                             
        MAX-ACCESS    read-only                                                
        STATUS        current                                                  
        DESCRIPTION " Link Interface                                           
                                                                               
                      Name of the link interface associated with the network   
                      interface.                                               
                      "                                                        
        ::= { networkInterfacesStatusEntry 200 }                               
                                                                               
    -- Columnar:  IP Address Status                                            
                                                                               
    networkInterfacesStatusIpAddr OBJECT-TYPE                                  
        SYNTAX        MxIpAddrMask                                             
        MAX-ACCESS    read-only                                                
        STATUS        current                                                  
        DESCRIPTION " IP Address Status                                        
                                                                               
                      Current IPv4 address and network mask of the network     
                      interface.                                               
                      "                                                        
        ::= { networkInterfacesStatusEntry 300 }                               
                                                                               
                                                                               
-- End of table:  Interfaces Status                                            

-- ***********************************************************************
                                                                         
-- Table:  Link Interfaces Status                                        
                                                                         
-- ***********************************************************************
                                                                         
linkInterfacesStatusTable OBJECT-TYPE                                    
    SYNTAX         SEQUENCE OF LinkInterfacesStatusEntry                 
    MAX-ACCESS     not-accessible                                        
    STATUS         current                                               
    DESCRIPTION  " Link Interfaces Status                                
                                                                         
                   This table displays all the available link interfaces.
                   "                                                     
    ::= { bniMIBObjects 2100 }                                           
                                                                         
                                                                         
    linkInterfacesStatusEntry OBJECT-TYPE                                
        SYNTAX         LinkInterfacesStatusEntry                         
        MAX-ACCESS     not-accessible                                    
        STATUS         current                                           
        DESCRIPTION  " A row in the Link Interfaces Status. "            
        INDEX          {                                                 
                           linkName                                      
                       }                                                 
                                                                         
        ::= { linkInterfacesStatusTable 1 }                              
                                                                         
    LinkInterfacesStatusEntry ::= SEQUENCE                               
    {                                                                    
          linkName      OCTET STRING,                                    
          linkType      OCTET STRING,                                    
          linkState     MxEnableState                                    
    }                                                                    
                                                                         
    -- Index:  Link Interface                                            
                                                                         
    linkInterfacesStatusLinkName OBJECT-TYPE                             
        SYNTAX         OCTET STRING                                      
        MAX-ACCESS     read-only                                         
        STATUS         current                                           
        DESCRIPTION  " Link Interface                                    
                                                                         
                       Name of the link interface.                       
                       "                                                 
        ::= { linkInterfacesStatusEntry 100 }                            
                                                                         
    -- Columnar:  Interface Type                                         
                                                                         
    linkInterfacesStatusLinkType OBJECT-TYPE                             
        SYNTAX         OCTET STRING                                      
        MAX-ACCESS     read-only                                         
        STATUS         current                                           
        DESCRIPTION  " Interface Type                                    
                                                                         
                       Type of link interface.                           
                       "                                                 
        ::= { linkInterfacesStatusEntry 200 }                            
                                                                         
    -- Columnar:  Interface Status                                       
                                                                         
    linkInterfacesStatusLinkState OBJECT-TYPE                            
        SYNTAX         MxEnableState                                     
        MAX-ACCESS     read-only                                         
        STATUS         current                                           
        DESCRIPTION  " Interface Status                                  
                                                                         
                       Administrative status of the link interface.      
                                                                         
                         * Enable: The link interface is enabled.        
                         * Disable: The link interface is disabled.      
                                                                         
                                                                         
                       "                                                 
        ::= { linkInterfacesStatusEntry 300 }                            
                                                                         
                                                                         
-- End of table:  Link Interfaces Status                                 

-- *****************************************************************************
                                                                               
-- Group:  Statistics                                                          
                                                                               
-- *****************************************************************************
                                                                               
statisticsGroup OBJECT IDENTIFIER                                              
    ::= { bniMIBObjects 10000 }                                                
                                                                               
                                                                               
    -- *************************************************************************
                                                                               
    -- Table:  Network Interfaces                                              
                                                                               
    -- *************************************************************************
                                                                               
    interfaceStatisticsTable OBJECT-TYPE                                       
        SYNTAX        SEQUENCE OF InterfaceStatisticsEntry                     
        MAX-ACCESS    not-accessible                                           
        STATUS        current                                                  
        DESCRIPTION " Network Interfaces                                       
                                                                               
                      This table contains the statistics for each network      
                      interface.                                               
                      "                                                        
        ::= { statisticsGroup 100 }                                            
                                                                               
                                                                               
        interfaceStatisticsEntry OBJECT-TYPE                                   
            SYNTAX         InterfaceStatisticsEntry                            
            MAX-ACCESS     not-accessible                                      
            STATUS         current                                             
            DESCRIPTION  " A row in the Network Interfaces. "                  
            INDEX          {                                                   
                               linkName                                        
                           }                                                   
                                                                               
            ::= { interfaceStatisticsTable 1 }                                 
                                                                               
        InterfaceStatisticsEntry ::= SEQUENCE                                  
        {                                                                      
            linkName        OCTET STRING,                                      
            txBytes         MxUInt64,                                          
            rxBytes         MxUInt64,                                          
            txPackets       MxUInt64,                                          
            rxPackets       MxUInt64,                                          
            rxErrors        MxUInt64,                                          
            collectTime     Unsigned32,                                        
            resetStat       INTEGER                                            
        }                                                                      
                                                                               
        -- Index:  Link Interface                                              
                                                                               
        interfaceStatisticsLinkName OBJECT-TYPE                                
            SYNTAX        OCTET STRING                                         
            MAX-ACCESS    read-only                                            
            STATUS        current                                              
            DESCRIPTION " Link Interface                                       
                                                                               
                          Name of the link interface associated with the       
                          network interface.                                   
                          "                                                    
            ::= { interfaceStatisticsEntry 100 }                               
                                                                               
        -- Columnar:  Statistics Collect Time                                  
                                                                               
        interfaceStatisticsCollectTime OBJECT-TYPE                             
            SYNTAX        Unsigned32                                           
            MAX-ACCESS    read-only                                            
            STATUS        current                                              
            DESCRIPTION " Statistics Collect Time                              
                                                                               
                          Time, in seconds, since the network statistics were  
                          last reset.                                          
                          "                                                    
            ::= { interfaceStatisticsEntry 10000 }                             
                                                                               
        -- Row command:  Reset                                                 
                                                                               
        interfaceStatisticsResetStat OBJECT-TYPE                               
            SYNTAX         INTEGER { noOp(0), resetStat(10) }                  
            MAX-ACCESS     read-write                                          
            STATUS         current                                             
            DESCRIPTION  " Reset                                               
                                                                               
                           Reset all statistics variables for this interface.  
                           "                                                   
            DEFVAL         { noOp }                                            
            ::= { interfaceStatisticsEntry 11000 }                             
                                                                               
        -- Columnar:  Bytes Transmitted                                        
                                                                               
        interfaceStatisticsTxBytes OBJECT-TYPE                                 
            SYNTAX        MxUInt64                                             
            MAX-ACCESS    read-only                                            
            STATUS        current                                              
            DESCRIPTION " Bytes Transmitted                                    
                                                                               
                          Total number of bytes transmitted on the interface at
                          the link level.                                      
                          "                                                    
            ::= { interfaceStatisticsEntry 200 }                               
                                                                               
        -- Columnar:  Bytes Received                                           
                                                                               
        interfaceStatisticsRxBytes OBJECT-TYPE                                 
            SYNTAX        MxUInt64                                             
            MAX-ACCESS    read-only                                            
            STATUS        current                                              
            DESCRIPTION " Bytes Received                                       
                                                                               
                          Total number of bytes received on this interface at  
                          the link level.                                      
                          "                                                    
            ::= { interfaceStatisticsEntry 300 }                               
                                                                               
        -- Columnar:  IP Packets Transmitted                                   
                                                                               
        interfaceStatisticsTxPackets OBJECT-TYPE                               
            SYNTAX        MxUInt64                                             
            MAX-ACCESS    read-only                                            
            STATUS        current                                              
            DESCRIPTION " IP Packets Transmitted                               
                                                                               
                          Total number of IP packets transmitted on this       
                          interface.                                           
                          "                                                    
            ::= { interfaceStatisticsEntry 400 }                               
                                                                               
        -- Columnar:  IP Packets Received                                      
                                                                               
        interfaceStatisticsRxPackets OBJECT-TYPE                               
            SYNTAX        MxUInt64                                             
            MAX-ACCESS    read-only                                            
            STATUS        current                                              
            DESCRIPTION " IP Packets Received                                  
                                                                               
                          Total number of IP packets received on this          
                          interface.                                           
                          "                                                    
            ::= { interfaceStatisticsEntry 500 }                               
                                                                               
        -- Columnar:  IP Packets Discarded                                     
                                                                               
        interfaceStatisticsRxErrors OBJECT-TYPE                                
            SYNTAX        MxUInt64                                             
            MAX-ACCESS    read-only                                            
            STATUS        current                                              
            DESCRIPTION " IP Packets Discarded                                 
                                                                               
                          Total number of IP packets discarded on this         
                          interface.                                           
                          "                                                    
            ::= { interfaceStatisticsEntry 600 }                               
                                                                               
                                                                               
    -- End of table:  Network Interfaces                                       
                                                                               
-- End of group:  Statistics                                                   

-- *****************************************************************************
                                                                               
-- Group:  Notification Messages Configuration                                 
                                                                               
-- *****************************************************************************
                                                                               
notificationsGroup OBJECT IDENTIFIER                                           
    ::= { bniMIBObjects 60010 }                                                
                                                                               
                                                                               
    -- Scalar:  Minimal Severity of Notification                               
                                                                               
    minSeverity OBJECT-TYPE                                                    
        SYNTAX        INTEGER { disable(0) , debug(100) , info(200) , warning  
                      (300) , error(400) , critical (500) }                    
        MAX-ACCESS    read-write                                               
        STATUS        current                                                  
        DESCRIPTION " Minimal Severity of Notification                         
                                                                               
                      Sets the minimal severity to issue a notification message
                      incoming from this service.                              
                                                                               
                        * Disable: No notification is issued.                  
                        * Debug: All notification messages are issued.         
                        * Info: Notification messages with severity            
                          'Informational' and higher are issued.               
                        * Warning: Notification messages with severity         
                          'Warning' and higher are issued.                     
                        * Error: Notification messages with severity 'Error'   
                          and higher are issued.                               
                        * Critical: Notification messages with severity        
                          'Critical' are issued.                               
                                                                               
                                                                               
                      "                                                        
        DEFVAL        { warning }                                              
        ::= { notificationsGroup 100 }                                         
                                                                               
-- End of group:  Notification Messages Configuration                          

-- ****************************************************************************
                                                                              
-- Group:  Configuration Settings                                             
                                                                              
-- ****************************************************************************
                                                                              
configurationGroup OBJECT IDENTIFIER                                          
    ::= { bniMIBObjects 60020 }                                               
                                                                              
                                                                              
    -- Scalar:  Need Restart                                                  
                                                                              
    needRestartInfo OBJECT-TYPE                                               
        SYNTAX        INTEGER { no(0) , yes(100) }                            
        MAX-ACCESS    read-only                                               
        STATUS        current                                                 
        DESCRIPTION " Need Restart                                            
                                                                              
                      Indicates if the service needs to be restarted for its  
                      configuration to fully take effect.                     
                                                                              
                        * Yes: Service needs to be restarted.                 
                        * No: Service does not need to be restarted.          
                                                                              
                      Services can be restarted by using the command          
                      Scm.ServiceCommands.Restart.                            
                                                                              
                                                                              
                      "                                                       
        ::= { configurationGroup 100 }                                        
                                                                              
-- End of group:  Configuration Settings                                      

END
