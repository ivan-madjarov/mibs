-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************

DGW20-MX-HARDWARE-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixHardware
    FROM MX-SMI2;

hardwareMIB MODULE-IDENTITY
 LAST-UPDATED   "1905090000Z"
 ORGANIZATION " Mediatrix Telecom, Inc. "
 CONTACT-INFO " Mediatrix Telecom, Inc.
                4229, Garlock Street
                Sherbrooke (Quebec)
                Canada
                Phone: (819) 829-8749
                "
 DESCRIPTION  " Hardware

                The Hardware component manages the mainboard and the extension
                cards.
                "
 ::= { mediatrixHardware 40000 }

hardwareMIBObjects OBJECT IDENTIFIER ::= { hardwareMIB 1 }

-- Scalar:Reset/Default Button Management

resetButtonManagement OBJECT-TYPE
 SYNTAX        INTEGER { all(100) , disablePartialReset(200) }
 MAX-ACCESS    read-write
 STATUS        current
 DESCRIPTION " Reset/Default Button Management

               Configures the actions allowed on the reset/default button.

                 * All: All the actions are allowed: reset, partial reset, and
                   factory reset.
                 * DisablePartialReset: All actions are allowed except the
                   partial reset.

               The reset action restarts the unit.

               The partial reset action provides a way to contact the unit in a
               known and static state while keeping most of the configuration
               unchanged.

               The factory reset action reverts the unit back to its default
               factory settings.

               For more details, search for the Partial Reset documentation in
               the Media5 Documentation Portal (https://
               documentation.media5corp.com).

               "
 DEFVAL        { all }
 ::= { hardwareMIBObjects 100 }

-- Scalar:Force DSP resynchronisation

interopForceDspResync OBJECT-TYPE
 SYNTAX        INTEGER { disable(100) , enable(200) }
 MAX-ACCESS    read-write
 STATUS        current
 DESCRIPTION " Force DSP resynchronisation

               Force DSP resynchronisation for 3XXX PRI cards and 4108-16-24
               platforms.
               "
 DEFVAL        { disable }
 ::= { hardwareMIBObjects 200 }

-- ****************************************************************************

-- Group:Fxs

-- ****************************************************************************

fxs OBJECT IDENTIFIER
 ::= { hardwareMIBObjects 1000 }
 -- Scalar:Ring Management

 ringManagement OBJECT-TYPE
  SYNTAX        INTEGER { cascade(100) , simultaneous(200) }
  MAX-ACCESS    read-write
  STATUS        current
  DESCRIPTION " Ring Management

                Configures how the ring pulse is sent on FXS ports.

                  * Cascade: FXS ports are prevented from ringing at the same
                    time in order to reduce the peak power usage of the
                    device.
                  * Simultaneous: All ports ring at the same time.

                Note: This parameter is only used by the Mx4102 platform.

                "
  DEFVAL        { cascade }
  ::= { fxs 100 }

-- End of group:Fxs

-- ****************************************************************************

-- Group:Pri

-- ****************************************************************************

pri OBJECT IDENTIFIER
 ::= { hardwareMIBObjects 2000 }
 -- ***************************************************************
 
 -- Table:PRI Ports Status

 -- ***************************************************************
 
 portsStatusTable OBJECT-TYPE
  SYNTAX        SEQUENCE OF PortsStatusEntry
  MAX-ACCESS    not-accessible
  STATUS        current
  DESCRIPTION " PRI Ports Status

                This table displays the status of each PRI port.
                "
  ::= { pri 100 }
  portsStatusEntry OBJECT-TYPE
   SYNTAX        PortsStatusEntry
   MAX-ACCESS    not-accessible
   STATUS        current
   DESCRIPTION " A row in table PRI Ports Status. "
   INDEX         {
                   portsStatusPort
                 }

   ::= { portsStatusTable 1 }

  PortsStatusEntry ::= SEQUENCE
  {
    portsStatusPort      OCTET STRING,
    portsStatusLineType  INTEGER,
    portsStatusSignaling INTEGER
  }

  -- Index:Port

  portsStatusPort OBJECT-TYPE
   SYNTAX        OCTET STRING
   MAX-ACCESS    read-only
   STATUS        current
   DESCRIPTION " Port

                 Indicates the name of the port.
                 "
   ::= { portsStatusEntry 100 }

  -- Columnar:Line Type

  portsStatusLineType OBJECT-TYPE
   SYNTAX        INTEGER { e1(100) , t1(200) }
   MAX-ACCESS    read-only
   STATUS        current
   DESCRIPTION " Line Type

                 Defines the line type.
                 "
   ::= { portsStatusEntry 300 }

  -- Columnar:Signaling

  portsStatusSignaling OBJECT-TYPE
   SYNTAX        INTEGER { isdn(100) , r2(200) , eam(300) }
   MAX-ACCESS    read-only
   STATUS        current
   DESCRIPTION " Signaling

                 Defines the signaling protocol used by this port.
                 "
   ::= { portsStatusEntry 400 }

 -- End of table:PRI Ports Status

 -- ***************************************************************************
 
 -- Table:PRI Ports Configuration

 -- ***************************************************************************
 
 portsTable OBJECT-TYPE
  SYNTAX        SEQUENCE OF PortsEntry
  MAX-ACCESS    not-accessible
  STATUS        current
  DESCRIPTION " PRI Ports Configuration

                The settings of each PRI port are configured in this table.
                "
  ::= { pri 200 }
  portsEntry OBJECT-TYPE
   SYNTAX        PortsEntry
   MAX-ACCESS    not-accessible
   STATUS        current
   DESCRIPTION " A row in table PRI Ports Configuration. "
   INDEX         {
                   portsPort
                 }

   ::= { portsTable 1 }

  PortsEntry ::= SEQUENCE
  {
    portsPort       OCTET STRING,
    portsLineType   INTEGER,
    portsSignaling  INTEGER
  }

  -- Index:Port

  portsPort OBJECT-TYPE
   SYNTAX        OCTET STRING
   MAX-ACCESS    read-only
   STATUS        current
   DESCRIPTION " Port

                 Indicates the name of the port.
                 "
   ::= { portsEntry 100 }

  -- Columnar:Line Type

  portsLineType OBJECT-TYPE
   SYNTAX        INTEGER { e1(100) , t1(200) }
   MAX-ACCESS    read-write
   STATUS        current
   DESCRIPTION " Line Type

                 Defines the line type.

                   * T1: DS1 T-Carrier Signaling
                   * E1: E1 E-Carrier Signaling

                 Note: The value T1 is not valid when the Ports.Signaling
                 parameter is set to R2.

                 "
   DEFVAL        { e1 }
   ::= { portsEntry 300 }

  -- Columnar:Signaling

  portsSignaling OBJECT-TYPE
   SYNTAX        INTEGER { isdn(100) , r2(200) , eam(300) }
   MAX-ACCESS    read-write
   STATUS        current
   DESCRIPTION " Signaling

                 Defines the signaling protocol used by this port.

                   * Isdn: Integrated Services Digital Network
                   * R2: E1-R2 CAS signaling protocol.
                   * Eam: E&M CAS signaling protocol.

                 Note: The value R2 is not valid when the Ports.LineType
                 parameter is set to T1.

                 "
   DEFVAL        { isdn }
   ::= { portsEntry 400 }

 -- End of table:PRI Ports Configuration

 -- ***************************************************************************
 
 -- Group:PRI Statistics Group

 -- ***************************************************************************
 
 statisticsGroup OBJECT IDENTIFIER
  ::= { pri 1000 }
  -- ***************************************************************************
  
  -- Table:

  -- ***************************************************************************
  
  statsInfoTable OBJECT-TYPE
   SYNTAX                   SEQUENCE OF StatsInfoEntry
   MAX-ACCESS               not-accessible
   STATUS                   current
   DESCRIPTION           "

                            Statistics table of each PRI port.
                            "
   ::= { statisticsGroup 100 }
   statsInfoEntry OBJECT-TYPE
    SYNTAX        StatsInfoEntry
    MAX-ACCESS    not-accessible
    STATUS        current
    DESCRIPTION " A row in table . "
    INDEX         {
                    statsInfoPort
                  }

    ::= { statsInfoTable 1 }

   StatsInfoEntry ::= SEQUENCE
   {
     statsInfoPort                          OCTET STRING,
     statsInfoFramesTransmitted             Unsigned32,
     statsInfoFramesReceived                Unsigned32,
     statsInfoOctetsTransmitted             Unsigned32,
     statsInfoOctetsReceived                Unsigned32,
     statsInfoFcsErrors                     Unsigned32,
     statsInfoFramesDropped                 Unsigned32,
     statsInfoOctetsDropped                 Unsigned32,
     statsInfoNegativeFrameSlipsTransmitted Unsigned32,
     statsInfoNegativeFrameSlipsReceived    Unsigned32,
     statsInfoPositiveFrameSlipsTransmitted Unsigned32,
     statsInfoPositiveFrameSlipsReceived    Unsigned32,
     statsInfoFramingErrors                 Unsigned32,
     statsInfoCodeViolations                Unsigned32,
     statsInfoCRCErrors                     Unsigned32,
     statsInfoEBitErrors                    Unsigned32,
     statsInfoBlockErrors                   Unsigned32,
     statsInfoResetStats                    INTEGER
   }

   -- Index:Port

   statsInfoPort OBJECT-TYPE
    SYNTAX        OCTET STRING
    MAX-ACCESS    read-only
    STATUS        current
    DESCRIPTION " Port

                  The name of the port.
                  "
    ::= { statsInfoEntry 100 }

   -- Columnar:Negative Frame Slips Received

   statsInfoNegativeFrameSlipsReceived OBJECT-TYPE
    SYNTAX        Unsigned32
    MAX-ACCESS    read-only
    STATUS        current
    DESCRIPTION " Negative Frame Slips Received

                  A frame is skipped when the frequency of the received route
                  clock is greater than the frequency of the receive system
                  interface working clock (2.048 MHz on E1 or 1.544 MHz on T1).

                  This value is available on E1 and T1.

                  "
    ::= { statsInfoEntry 1000 }

   -- Row command:Reset Stats

   statsInfoResetStats OBJECT-TYPE
    SYNTAX        INTEGER { noOp(0), resetStats(10) }
    MAX-ACCESS    read-write
    STATUS        current
    DESCRIPTION " Reset Stats

                  Resets all statistics for the specified interface.
                  "
    DEFVAL        { noOp }
    ::= { statsInfoEntry 10000 }

   -- Columnar:Positive Frame Slips Transmitted

   statsInfoPositiveFrameSlipsTransmitted OBJECT-TYPE
    SYNTAX        Unsigned32
    MAX-ACCESS    read-only
    STATUS        current
    DESCRIPTION " Positive Frame Slips Transmitted

                  A frame is repeated when the frequency of the transmit clock
                  is less than the frequency of the transmit system interface
                  working clock (2.048 MHz on E1 or 1.544 MHz on T1).

                  This value is available on E1 and T1.

                  "
    ::= { statsInfoEntry 1100 }

   -- Columnar:Positive Frame Slips Received

   statsInfoPositiveFrameSlipsReceived OBJECT-TYPE
    SYNTAX        Unsigned32
    MAX-ACCESS    read-only
    STATUS        current
    DESCRIPTION " Positive Frame Slips Received

                  A frame is repeated when the frequency of the receive route
                  clock is less than the frequency of the receive system
                  interface working clock (2.048 MHz on E1 or 1.544 MHz on T1).

                  This value is available on E1 and T1.

                  "
    ::= { statsInfoEntry 1200 }

   -- Columnar:Framing Error

   statsInfoFramingErrors OBJECT-TYPE
    SYNTAX        Unsigned32
    MAX-ACCESS    read-only
    STATUS        current
    DESCRIPTION " Framing Error

                  The framing error count indicates that a FAS (Frame Alignment
                  Signal) word has been received with an error.

                  The FAS-bits are present in every even frame of timeslot 0 on
                  E1.

                  The FAS-bits are present in ESF format on T1.

                  This value is available on E1 and T1.

                  "
    ::= { statsInfoEntry 1300 }

   -- Columnar:Code Violations

   statsInfoCodeViolations OBJECT-TYPE
    SYNTAX        Unsigned32
    MAX-ACCESS    read-only
    STATUS        current
    DESCRIPTION " Code Violations

                  The code violations count indicates that an encoding error on
                  the PCM line has been detected.

                  This value is available on E1 and T1.

                  "
    ::= { statsInfoEntry 1400 }

   -- Columnar:CRC Errors

   statsInfoCRCErrors OBJECT-TYPE
    SYNTAX        Unsigned32
    MAX-ACCESS    read-only
    STATUS        current
    DESCRIPTION " CRC Errors

                  The CRC errors count is incremented when a multiframe has
                  been received with a CRC error.

                  On E1, this counter is only available with the CRC line
                  framing format.

                  On T1, this counter is only available with the ESF line
                  framing format.

                  "
    ::= { statsInfoEntry 1500 }

   -- Columnar:E-Bit Error

   statsInfoEBitErrors OBJECT-TYPE
    SYNTAX        Unsigned32
    MAX-ACCESS    read-only
    STATUS        current
    DESCRIPTION " E-Bit Error

                  The E-Bit error count gives information about the outgoing
                  transmit PCM line if the E-bits are used by the remote end
                  for submultiframe error indication. Incrementing is only
                  possible in the multiframe synchronous state.

                  Due to signaling requirements, the E-bits of frame 13 and
                  frame 15 of the CRC multiframe can be used to indicate an
                  error in a received submultiframes:

                    * Submultiframe I status E-bit located in frame 13
                    * Submultiframe II status E-bit located in frame 15
                    * no CRC error: E = 1
                    * CRC error: E = 0

                  This value is only available in E1.

                  "
    ::= { statsInfoEntry 1600 }

   -- Columnar:Block Error

   statsInfoBlockErrors OBJECT-TYPE
    SYNTAX        Unsigned32
    MAX-ACCESS    read-only
    STATUS        current
    DESCRIPTION " Block Error

                  The Block Error count is incremented once per multiframe if a
                  multiframe has been received with a CRC error or if a bad
                  frame alignment has been detected.

                  This value is only available for ESF format on T1 only.

                  "
    ::= { statsInfoEntry 1700 }

   -- Columnar:Frames Transmitted

   statsInfoFramesTransmitted OBJECT-TYPE
    SYNTAX        Unsigned32
    MAX-ACCESS    read-only
    STATUS        current
    DESCRIPTION " Frames Transmitted

                  Number of HDLC frames transmitted.

                  Note: Frames do not refer to the structure defined in I.431.

                  "
    ::= { statsInfoEntry 200 }

   -- Columnar:Frames Received

   statsInfoFramesReceived OBJECT-TYPE
    SYNTAX        Unsigned32
    MAX-ACCESS    read-only
    STATUS        current
    DESCRIPTION " Frames Received

                  Number of HDLC frames received.

                  Note: Frames do not refer to the structure defined in I.431.

                  "
    ::= { statsInfoEntry 300 }

   -- Columnar:Octets Transmitted

   statsInfoOctetsTransmitted OBJECT-TYPE
    SYNTAX        Unsigned32
    MAX-ACCESS    read-only
    STATUS        current
    DESCRIPTION " Octets Transmitted

                  Number of octets transmitted. This value is obtained by
                  cumulating the octets transmitted in the HDLC frames.

                  Note: Frames do not refer to the structure defined in I.431.

                  "
    ::= { statsInfoEntry 400 }

   -- Columnar:Octets Received

   statsInfoOctetsReceived OBJECT-TYPE
    SYNTAX        Unsigned32
    MAX-ACCESS    read-only
    STATUS        current
    DESCRIPTION " Octets Received

                  Number of octets received. This value is obtained by
                  cumulating the octets received in the HDLC frames.

                  Note: Frames do not refer to the structure defined in I.431.

                  "
    ::= { statsInfoEntry 500 }

   -- Columnar:FCS Errors

   statsInfoFcsErrors OBJECT-TYPE
    SYNTAX        Unsigned32
    MAX-ACCESS    read-only
    STATUS        current
    DESCRIPTION " FCS Errors

                  Frame check sequence (FCS) errors indicate that frames of
                  data are being corrupted during transmission. FCS error count
                  is the number of frames that were received with a bad
                  checksum (CRC value) in the HDLC frame. These frames are
                  dropped and not propagated to the upper layers.

                  This value is available on E1 and T1.

                  "
    ::= { statsInfoEntry 600 }

   -- Columnar:Frames Dropped

   statsInfoFramesDropped OBJECT-TYPE
    SYNTAX        Unsigned32
    MAX-ACCESS    read-only
    STATUS        current
    DESCRIPTION " Frames Dropped

                  Number of frames dropped. This value is obtained by
                  cumulating the number of frames dropped when transferring
                  data from the framer chip to the device internal buffer.

                  This value is available on E1 and T1.

                  "
    ::= { statsInfoEntry 700 }

   -- Columnar:Octets Dropped

   statsInfoOctetsDropped OBJECT-TYPE
    SYNTAX        Unsigned32
    MAX-ACCESS    read-only
    STATUS        current
    DESCRIPTION " Octets Dropped

                  Number of octets dropped. This value is obtained by
                  cumulating the number of octets dropped when transferring
                  data from the framer chip to the device internal buffer.

                  This value is available on E1 and T1.

                  "
    ::= { statsInfoEntry 800 }

   -- Columnar:Negative Frame Slips Transmitted

   statsInfoNegativeFrameSlipsTransmitted OBJECT-TYPE
    SYNTAX        Unsigned32
    MAX-ACCESS    read-only
    STATUS        current
    DESCRIPTION " Negative Frame Slips Transmitted

                  A frame is skipped when the frequency of the transmit clock
                  is greater than the frequency of the transmit system
                  interface working clock (2.048 MHz on E1 or 1.544 MHz on T1).

                  This value is available on E1 and T1.

                  "
    ::= { statsInfoEntry 900 }

  -- End of table:

 -- End of group:PRI Statistics Group

-- End of group:Pri

-- ****************************************************************************

-- Group:Bri

-- ****************************************************************************

bri OBJECT IDENTIFIER
 ::= { hardwareMIBObjects 3000 }
 -- ***************************************************************************
 
 -- Table:BRI Ports Status

 -- ***************************************************************************
 
 briPortsStatusTable OBJECT-TYPE
  SYNTAX          SEQUENCE OF BriPortsStatusEntry
  MAX-ACCESS      not-accessible
  STATUS          current
  DESCRIPTION   " BRI Ports Status

                  This table displays the status of each BRI port.
                  "
  ::= { bri 100 }
  briPortsStatusEntry OBJECT-TYPE
   SYNTAX        BriPortsStatusEntry
   MAX-ACCESS    not-accessible
   STATUS        current
   DESCRIPTION " A row in table BRI Ports Status. "
   INDEX         {
                   briPortsStatusPort
                 }

   ::= { briPortsStatusTable 1 }

  BriPortsStatusEntry ::= SEQUENCE
  {
    briPortsStatusPort         OCTET STRING,
    briPortsStatusPowerFeeding INTEGER
  }

  -- Index:Port

  briPortsStatusPort OBJECT-TYPE
   SYNTAX        OCTET STRING
   MAX-ACCESS    read-only
   STATUS        current
   DESCRIPTION " Port

                 Indicates the name of the port.
                 "
   ::= { briPortsStatusEntry 100 }

  -- Columnar:Power Feeding State

  briPortsStatusPowerFeeding OBJECT-TYPE
   SYNTAX        INTEGER { on(100) , off(200) , unavailable(300) , unsupported
                 (400) }
   MAX-ACCESS    read-only
   STATUS        current
   DESCRIPTION " Power Feeding State

                 Indicates the state of the power feeding for the port.

                   * On: Power is fed to the line.
                   * Off: Power is not fed to the line.
                   * Unavailable: The power feeding feature is unavailable on
                     TE endpoints.
                   * Unsupported: The power feeding feature is not physically
                     supported on this port.

                 "
   ::= { briPortsStatusEntry 200 }

 -- End of table:BRI Ports Status

 -- ************************************************************************
 
 -- Table:BRI Ports Configuration

 -- ************************************************************************
 
 briPortsTable OBJECT-TYPE
  SYNTAX        SEQUENCE OF BriPortsEntry
  MAX-ACCESS    not-accessible
  STATUS        current
  DESCRIPTION " BRI Ports Configuration

                The settings of each BRI port are configured in this table.
                "
  ::= { bri 200 }
  briPortsEntry OBJECT-TYPE
   SYNTAX        BriPortsEntry
   MAX-ACCESS    not-accessible
   STATUS        current
   DESCRIPTION " A row in table BRI Ports Configuration. "
   INDEX         {
                   briPortsPort
                 }

   ::= { briPortsTable 1 }

  BriPortsEntry ::= SEQUENCE
  {
    briPortsPort               OCTET STRING,
    briPortsPowerFeedingEnable MxEnableState
  }

  -- Index:Port

  briPortsPort OBJECT-TYPE
   SYNTAX        OCTET STRING
   MAX-ACCESS    read-only
   STATUS        current
   DESCRIPTION " Port

                 Indicates the name of the port.
                 "
   ::= { briPortsEntry 100 }

  -- Columnar:Power Feeding Enable

  briPortsPowerFeedingEnable OBJECT-TYPE
   SYNTAX        MxEnableState
   MAX-ACCESS    read-write
   STATUS        current
   DESCRIPTION " Power Feeding Enable

                 Enables or disables the power feeding for the port.
                 "
   DEFVAL        { disable }
   ::= { briPortsEntry 200 }

 -- End of table:BRI Ports Configuration

-- End of group:Bri

-- ****************************************************************************

-- Group:Clock Reference

-- ****************************************************************************

clockReference OBJECT IDENTIFIER
 ::= { hardwareMIBObjects 5000 }
 -- Scalar:Clock Reference List

 clockReferenceList OBJECT-TYPE
  SYNTAX        OCTET STRING
  MAX-ACCESS    read-only
  STATUS        current
  DESCRIPTION " Clock Reference List

                List of available clock references.

                The SYNCIN value means the internal clock is synchronised with
                the SYNC IN port (on platforms equipped with this port).

                "
  ::= { clockReference 100 }

 -- Scalar:Clock Reference Source

 clockReferenceSource OBJECT-TYPE
  SYNTAX        OCTET STRING ( SIZE(0..255) )
  MAX-ACCESS    read-write
  STATUS        current
  DESCRIPTION " Clock Reference Source

                Indicates the preferred synchronisation source(s) to use for
                the internal clock. Refer to the ClockReferenceList parameter
                for a list of available clock references for the platform.

                When the value is empty, the platform will automatically
                choose the synchronisation source.

                When a source or a list of sources are specified, the internal
                clock is synchronised with the first source that offers a
                valid signal. The only exception is the SYNCIN port (not
                present on all platforms), which is always used when
                encountered in the list.

                Depending on the platform, two string separators may be used:

                  * ',' (comma): List synchronisation sources, per priority
                    (Sentinel and G7 platforms only).
                  * ';' (semicolon): Adding a second synchronisation source
                    (3xxx platform only)

                Examples:

                  * For 44xx: 'Bri1'
                  * For C7xx: 'BRI1, BRI2'
                  * For 3xxx: 'Slot2/E1T1'
                  * For 3xxx: 'Slot2/Bri0; Slot3/Bri2'
                  * For Sentinel 400: 'Slot1/E1T1, Slot2/BRI1, Slot2/BRI2,
                    SYNCIN'
                  * For Sentinel 100 and G7: 'BRI1, BRI2, PRI1, PRI2, SYNCIN'
                  * Any platform: ''

                "
  DEFVAL        { "" }
  ::= { clockReference 200 }

 -- Scalar:Current synchronisation Reference

 clockReferenceStatus OBJECT-TYPE
  SYNTAX        OCTET STRING
  MAX-ACCESS    read-only
  STATUS        current
  DESCRIPTION " Current synchronisation Reference

                Indicates the synchronisation source currently in use.

                On the 3xxx platform, up to two clock reference statuses can
                be displayed.

                On all other platforms, only one clock reference status is
                displayed.

                The 'None' value means the internal clock is not synchronised.

                "
  ::= { clockReference 300 }

-- End of group:Clock Reference

-- ****************************************************************************

-- Group:Eth

-- ****************************************************************************

eth OBJECT IDENTIFIER
 ::= { hardwareMIBObjects 10000 }
 -- Scalar:Ports Configuration

 portsConfiguration OBJECT-TYPE
  SYNTAX        INTEGER { separate(100) , bridge(200) }
  MAX-ACCESS    read-write
  STATUS        current
  DESCRIPTION " Ports Configuration

                Configures how each port provides a link interface.

                  * Separate: Each Ethernet port provides an independent link
                    interface. This is the required configuration for IP
                    Routing.
                  * Bridge: Both Ethernet ports are bridged together and
                    provide a single link interface.

                Note: This feature is only available on units with a total of
                2 Ethernet ports.

                "
  DEFVAL        { separate }
  ::= { eth 100 }

 -- Scalar:Kernel Network Priority

 kernelNetworkPriority OBJECT-TYPE
  SYNTAX        Unsigned32 ( 0..100 )
  MAX-ACCESS    read-write
  STATUS        current
  DESCRIPTION " Kernel Network Priority

                Controls the network priority in the kernel. The default value
                is platform-dependent. This parameter should not be
                altered, unless advised otherwise by a technical support
                specialist.
                "
  DEFVAL        { 10 }
  ::= { eth 200 }

-- End of group:Eth

-- **************************************

-- Group:Debug Group

-- **************************************

debugGroup OBJECT IDENTIFIER
        ::= { hardwareMIBObjects 50000 }
-- End of group:Debug Group

-- ****************************************************************************

-- Group:Notification Messages Configuration

-- ****************************************************************************

notificationsGroup OBJECT IDENTIFIER
 ::= { hardwareMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with a 'Informational' and
                    higher severity are issued.
                  * Warning: Notification messages with a 'Warning' and higher
                    severity are issued.
                  * Error: Notification messages with an 'Error' and higher
                    severity are issued.
                  * Critical: Notification messages with a 'Critical' severity
                    are issued.

                "
  DEFVAL        { warning }
  ::= { notificationsGroup 100 }

-- End of group:Notification Messages Configuration

-- ****************************************************************************

-- Group:Configuration Settings

-- ****************************************************************************

configurationGroup OBJECT IDENTIFIER
 ::= { hardwareMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for the
                configuration to fully take effect.

                  * Yes: Service needs to be restarted.
                  * No: Service does not need to be restarted.

                Services can be restarted by using the
                Scm.ServiceCommands.Restart command.

                "
  ::= { configurationGroup 100 }

-- End of group:Configuration Settings

END
