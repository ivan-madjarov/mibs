-- ****************************************************************************
--
--             Copyright(c) 2001-2005 Mediatrix Telecom, Inc.
--
--  NOTICE:
--   This document contains information that is confidential and proprietary
--   to Mediatrix Telecom, Inc.
--
--   Mediatrix Telecom, Inc. reserves all rights to this document as well as
--   to the Intellectual Property of the document and the technology and
--   know how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

H32340-MX-FXS-MIB
DEFINITIONS ::= BEGIN

IMPORTS
        MODULE-IDENTITY,
        OBJECT-TYPE,
        Unsigned32
    FROM SNMPv2-SMI
        MODULE-COMPLIANCE,
        OBJECT-GROUP
    FROM SNMPv2-CONF
        mediatrixConfig
    FROM MX-SMI
        MxEnableState,
        MxDigitMap
    FROM MX-TC;

fxsMIB MODULE-IDENTITY
    LAST-UPDATED "200503300000Z"
    ORGANIZATION "Mediatrix Telecom, Inc."
    CONTACT-INFO "Mediatrix Telecom, Inc.
                  4229, Garlock Street
                  Sherbrooke (Quebec)
                  Canada
                  Phone: (819) 829-8749
                  "
    DESCRIPTION  "This MIB provides Foreign eXchange Station (FXS) parameters."
    -- ************************************************************************
    -- Revision history
    -- ************************************************************************
    REVISION    "200503300000Z"
    DESCRIPTION "Modified the description of fxsEmergencyBypassEnable and
                 fxsEmergencyBypassDialDelay."
    REVISION    "200501270000Z"
    DESCRIPTION "Added range to fxsEmergencyBypassTimeout."
    REVISION    "200411240000Z"
    DESCRIPTION "Added fxsEmergencyBypassDialDelay"
    REVISION    "200409270000Z"
    DESCRIPTION "Added fxsEmergencyBypassEnable, fxsEmergencyBypassTimeout and
                 fxsEmergencyBypassDialMap"
    REVISION    "200208300000Z"
    DESCRIPTION "Updated fxsLoopCurrent DESCRIPTION to remove reference to
                 explicit hardware platform."
    REVISION    "200208220000Z"
    DESCRIPTION "Updated range of fxsLoopCurrent and augmented description."
    REVISION    "200111050000Z"
    DESCRIPTION "Added fxsFlashHookDetectionDelayMin and fxsFlashHookDetectionDelayMax."
    REVISION    "200108290000Z"
    DESCRIPTION "Creation"
    ::= { mediatrixConfig 40 }

fxsMIBObjects     OBJECT IDENTIFIER ::= { fxsMIB 1 }
fxsConformance    OBJECT IDENTIFIER ::= { fxsMIB 2 }


    fxsByPassEnable OBJECT-TYPE
        SYNTAX      INTEGER {
                             disable(0),
                             enable(1)
                            }
        MAX-ACCESS  read-write
        STATUS      current
        DESCRIPTION "Enable the bypass service.

                     disable : The port with the bypass service is never
                               redirected on the bypass line.

                     enable : When the port with the bypass service is unusable
                              (ifAdminUsageState is idle-unusable), it will be
                              redirected to the bypass line. When this port
                              becomes usable again (ifAdminUsageState is idle),
                              the redirection is stopped within 10 seconds if
                              the bypass line is unused or 10 seconds after
                              the termination of the call.

                     NOTE: The control of the bypass service is only possible
                           when the unit is powered on. When power is off, the
                           bypass service is always enabled."
        DEFVAL      { enable }
        ::= { fxsMIBObjects 1 }

    fxsLoopCurrent OBJECT-TYPE
        SYNTAX Unsigned32 (20..50)
        MAX-ACCESS read-write
        STATUS current
        DESCRIPTION "Current flowing through the current detector that
                     permits the detection of the on-hook and off-hook states.
                     The loop current is in mA.

                     Some hardware platforms may support less than the available
                     range.

                     Please refer to the documentation shipped with your device
                     for more details."
        DEFVAL { 30 }
        ::= { fxsMIBObjects 2 }

    fxsFlashHookDetectionDelayMin OBJECT-TYPE
        SYNTAX Unsigned32 (10..1200)
        MAX-ACCESS read-write
        STATUS current
        DESCRIPTION "Minimum time in ms the hook switch must remain pressed
                     to perform a flash hook."
        DEFVAL { 100 }
        ::= { fxsMIBObjects 3 }

    fxsFlashHookDetectionDelayMax OBJECT-TYPE
        SYNTAX Unsigned32 (10..1200)
        MAX-ACCESS read-write
        STATUS current
        DESCRIPTION "Maximum time in ms the hook switch can remain pressed
                     to perform a flash hook."
        DEFVAL { 1200 }
        ::= { fxsMIBObjects 4 }

    -- *************************************************************************
    -- fxsEmergencyBypass
    -- *************************************************************************
    fxsEmergencyBypass    OBJECT IDENTIFIER ::= { fxsMIBObjects 200 }

    fxsEmergencyBypassEnable OBJECT-TYPE
        SYNTAX      MxEnableState
        MAX-ACCESS  read-write
        STATUS      current
        DESCRIPTION "Enables/Disables bypass for emergency calls.

                     disable: Bypass for emergency calls is disabled.

                     enable : Bypass for emergency calls is enabled. If dialed digits
                              match those defined in the fxsEmergencyBypassDialMap
                              variable, the unit switches to bypass mode and makes
                              the call on the PSTN side.

                     Note that the bypass functionality only applies for
                     digits dialed on FXS port 1

                     This variable's semantics are different depending on protocol and/or
                     hardware platforms.
                     Please refer to the documentation shipped with your device for more details."

        DEFVAL { disable }
        ::= { fxsEmergencyBypass 50 }

    fxsEmergencyBypassTimeout OBJECT-TYPE
        SYNTAX      Unsigned32 (1..3600)
        MAX-ACCESS  read-write
        STATUS      current
        DESCRIPTION "Indicates how long the unit will stay in bypass mode
                     waiting for an incoming call after the outgoing call on
                     the PSTN side is finished.

                     This value is expressed in seconds (s)."

        DEFVAL { 120 }
        ::= { fxsEmergencyBypass 100 }

    fxsEmergencyBypassDialMap OBJECT-TYPE
        SYNTAX  MxDigitMap
        MAX-ACCESS  read-write
        STATUS      current
        DESCRIPTION "A string composing a digit map that will be
                     considered valid to make the unit switch to bypass mode.

                     The string must follow the syntax described in
                     the digitMapMIB entry description."

        DEFVAL      { "" }
        ::= { fxsEmergencyBypass 150 }

    fxsEmergencyBypassDialDelay OBJECT-TYPE
        SYNTAX      Unsigned32 (1..10)
        MAX-ACCESS  read-write
        STATUS      current
        DESCRIPTION "Indicates how long the unit will wait before playing
                     emergency digits on the PSTN side once in bypass mode.

                     This value is expressed in seconds (s).

                     This variable's semantics are different depending on protocol and/or
                     hardware platforms.
                     Please refer to the documentation shipped with your device for more details."

        DEFVAL { 3 }
        ::= { fxsEmergencyBypass 200 }



    -- ************************************************************************
    -- Conformance information
    -- ************************************************************************
    fxsCompliances OBJECT IDENTIFIER ::= { fxsConformance 1 }

    fxsComplVer1 MODULE-COMPLIANCE
        STATUS      current
        DESCRIPTION
            "This is the list of conformance groups to support FXS parameters."
        MODULE -- This Module
            MANDATORY-GROUPS {
                                fxsGroupVer1,
                                fxsEmergencyBypassGroupVer1
                             }
        ::= { fxsCompliances 1 }

    -- ************************************************************************
    -- MIB variable grouping
    -- ************************************************************************
    fxsGroups OBJECT IDENTIFIER ::= { fxsConformance 5 }

    fxsGroupVer1 OBJECT-GROUP
        OBJECTS {
                    fxsByPassEnable,
                    fxsLoopCurrent,
                    fxsFlashHookDetectionDelayMin,
                    fxsFlashHookDetectionDelayMax
                }
        STATUS      current
        DESCRIPTION "This group holds the objects to define FXS specific parameters."
        ::= { fxsGroups 5 }


    fxsEmergencyBypassGroupVer1 OBJECT-GROUP
        OBJECTS {
                    fxsEmergencyBypassEnable,
                    fxsEmergencyBypassTimeout,
                    fxsEmergencyBypassDialMap
                }
        STATUS      current
        DESCRIPTION "This group holds the objects to define emergency bypass specific parameters."
        ::= { fxsGroups 10 }
END
