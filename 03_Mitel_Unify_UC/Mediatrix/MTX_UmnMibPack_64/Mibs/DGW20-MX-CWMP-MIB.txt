-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************

DGW20-MX-CWMP-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

cwmpMIB MODULE-IDENTITY
 LAST-UPDATED   "1905090000Z"
 ORGANIZATION " Mediatrix Telecom, Inc. "
 CONTACT-INFO " Mediatrix Telecom, Inc.
                4229, Garlock Street
                Sherbrooke (Quebec)
                Canada
                Phone: (819) 829-8749
                "
 DESCRIPTION  " CPE WAN Management Protocol

                The CPE WAN Management Protocol (Cwmp) service allows the
                administrator to manage the unit using the TR-069 protocol.
                "
 ::= { mediatrixServices 3900 }

cwmpMIBObjects OBJECT IDENTIFIER ::= { cwmpMIB 1 }

-- Scalar:Root Element

rootElement OBJECT-TYPE
 SYNTAX        INTEGER { device(100) , internetGatewayDevice(200) }
 MAX-ACCESS    read-write
 STATUS        current
 DESCRIPTION " Root Element

               Determines the data model used for the configuration.

                 * Device: Uses the Device data model as defined in TR-106.
                 * InternetGatewayDevice: Uses the Internet Gateway Device data
                   model as defined in TR-098.

               "
 DEFVAL        { device }
 ::= { cwmpMIBObjects 100 }

-- Scalar:Network Interface

networkInterface OBJECT-TYPE
 SYNTAX        OCTET STRING ( SIZE(0..50) )
 MAX-ACCESS    read-write
 STATUS        current
 DESCRIPTION " Network Interface

               Specifies to which network interface the Cwmp service is bound.
               The name specified here must match an existing InterfaceName of
               the NetworkInterfaces table of the Bni service. The DHCP options
               for the automatic configuration are retrieved from this network
               interface.

               The possible values are:

                 * Empty: Use the network interface configured in the
                   Hoc.ManagementInterface parameter.
                 * 'All': Use any network interface.
                 * A valid IPv4 network interface name.

               Note that this parameter is case-sensitive.

               Note that Advance IP Routing could be required to forward the
               packet over the correct network.

               "
 DEFVAL        { "" }
 ::= { cwmpMIBObjects 190 }

-- Scalar:Listening Port

listeningPort OBJECT-TYPE
 SYNTAX        MxAdvancedIpPort
 MAX-ACCESS    read-write
 STATUS        current
 DESCRIPTION " Listening Port

               Port on which the unit listens for incoming TR-069 connections.

               Note: If set to 0, the unit uses the default TR-069 port 7547.

               "
 DEFVAL        { 0 }
 ::= { cwmpMIBObjects 200 }

-- ****************************************************************************

-- Group:ACS Group

-- ****************************************************************************

acsGroup OBJECT IDENTIFIER
 ::= { cwmpMIBObjects 1000 }
 -- Scalar:ACS URL Config Source

 acsUrlConfigSource OBJECT-TYPE
  SYNTAX        INTEGER { dhcp(100) , static(200) , dhcpWithFailover(300) }
  MAX-ACCESS    read-write
  STATUS        current
  DESCRIPTION " ACS URL Config Source

                Determines the method to obtain the URL of the ACS.

                  * Dhcp: Uses the DHCP protocol to find the URL as defined in
                    TR-106 section 3.1.
                  * Static: Uses the URL defined in the AcsStaticUrl
                    parameter.
                  * DhcpWithFailover: Uses the DHCP protocol to find the URL
                    or the URL defined in the AcsStaticUrl parameter if the
                    DHCP method fails.

                "
  DEFVAL        { dhcp }
  ::= { acsGroup 100 }

 -- Scalar:ACS Static URL

 acsStaticUrl OBJECT-TYPE
  SYNTAX        OCTET STRING ( SIZE(0..256) )
  MAX-ACCESS    read-write
  STATUS        current
  DESCRIPTION " ACS Static URL

                URL used by the unit to connect to the ACS using the CPE WAN
                Management Protocol if the AcsUrlConfigSource parameter is set
                to 'Static'.

                This parameter must be a valid HTTP or HTTPS URL.

                Example:

                  * 'http://somewhere.com'.
                  * 'https://somewhere.secure.com'.

                "
  DEFVAL        { "" }
  ::= { acsGroup 200 }

 -- Scalar:Username

 username OBJECT-TYPE
  SYNTAX        OCTET STRING ( SIZE(0..256) )
  MAX-ACCESS    read-write
  STATUS        current
  DESCRIPTION " Username

                Username used to authenticate the unit when making a
                connection to the ACS using the CPE WAN Management Protocol.
                "
  DEFVAL        { "" }
  ::= { acsGroup 300 }

 -- Scalar:Password

 password OBJECT-TYPE
  SYNTAX        OCTET STRING ( SIZE(0..256) )
  MAX-ACCESS    read-write
  STATUS        current
  DESCRIPTION " Password

                Password used to authenticate the unit when making a
                connection to the ACS the CPE WAN Management Protocol.
                "
  DEFVAL        { "" }
  ::= { acsGroup 600 }

 -- Scalar:ACS Status

 acsStatus OBJECT-TYPE
  SYNTAX        INTEGER { starting(100) , connected(200) , noUrl(300) ,
                errorCannotResolve(400) , errorNotResponding(500) ,
                errorAuthFailure(600) , errorOther(700) }
  MAX-ACCESS    read-only
  STATUS        current
  DESCRIPTION " ACS Status

                Indicates the status of the connection with the ACS.

                  * Starting: Cwmp service is starting and no connection
                    attempt have been made so far.
                  * Connected: The Cwmp service is connected to the ACS.
                  * NoUrl: The Cwmp service cannot connect with the ACS
                    because no ACS URL is configured.
                  * ErrorCannotResolve: The Cwmp service cannot connect with
                    the ACS because the FQDN cannot be resolved.
                  * ErrorNotResponding: The Cwmp service cannot connect with
                    the ACS because the ACS is not responding.
                  * ErrorAuthFailure: The Cwmp service failed authenticating
                    to the ACS.
                  * ErrorOther: The Cwmp service cannot connect to the ACS for
                    unspecified reason. See device and ACS logs.

                "
  ::= { acsGroup 700 }

 -- Scalar:ACS URL

 acsUrl OBJECT-TYPE
  SYNTAX        OCTET STRING
  MAX-ACCESS    read-only
  STATUS        current
  DESCRIPTION " ACS URL

                Current ACS URL used by the unit.
                "
  ::= { acsGroup 750 }

 -- Scalar:Connection Request Username

 connectionRequestUsername OBJECT-TYPE
  SYNTAX        OCTET STRING ( SIZE(0..256) )
  MAX-ACCESS    read-write
  STATUS        current
  DESCRIPTION " Connection Request Username

                Username used to authenticate an ACS making a Connection
                Request to the CPE.
                "
  DEFVAL        { "admin" }
  ::= { acsGroup 800 }

 -- Scalar:Connection Request Password

 connectionRequestPassword OBJECT-TYPE
  SYNTAX        OCTET STRING ( SIZE(0..256) )
  MAX-ACCESS    read-write
  STATUS        current
  DESCRIPTION " Connection Request Password

                Password used to authenticate an ACS making a Connection
                Request to the CPE.
                "
  DEFVAL        { "administrator" }
  ::= { acsGroup 900 }

-- End of group:ACS Group

-- ****************************************************************************

-- Group:Periodic Inform Group

-- ****************************************************************************

periodicInformGroup OBJECT IDENTIFIER
 ::= { cwmpMIBObjects 2000 }
 -- Scalar:Periodic Inform Enable

 periodicInformEnable OBJECT-TYPE
  SYNTAX        MxEnableState
  MAX-ACCESS    read-write
  STATUS        current
  DESCRIPTION " Periodic Inform Enable

                Defines whether or not the unit needs to periodically send CPE
                information to the ACS using the Inform method call.

                  * Disable: The unit does not send periodic inform.
                  * Enable: The unit sends periodic inform.

                "
  DEFVAL        { disable }
  ::= { periodicInformGroup 100 }

 -- Scalar:Periodic Inform Interval

 periodicInformInterval OBJECT-TYPE
  SYNTAX        Unsigned32 ( 1..31536000 )
  MAX-ACCESS    read-write
  STATUS        current
  DESCRIPTION " Periodic Inform Interval

                The duration, in seconds, of the interval for which the unit
                will attempt to connect with the ACS and call the Inform
                method if the PeriodicInformEnable parameter is set to
                'Enable'.

                "
  DEFVAL        { 3600 }
  ::= { periodicInformGroup 200 }

 -- Scalar:Periodic Inform Time

 periodicInformTime OBJECT-TYPE
  SYNTAX        OCTET STRING ( SIZE(20..20) )
  MAX-ACCESS    read-write
  STATUS        current
  DESCRIPTION " Periodic Inform Time

                An absolute time reference in UTC to determine when the unit
                initiates the periodic Inform method calls. Each Inform call
                MUST occur at this reference time plus or minus an integer
                multiple of the PeriodicInformInterval parameter.

                The PeriodicInformTime parameter is used only to set the
                'phase' of the periodic Informs. The actual value of
                PeriodicInformTime can be arbitrarily far into the past or
                future.

                For example, if the PeriodicInformInterval parameter is 86400
                (a day) and if the PeriodicInformTime parameter is set to UTC
                midnight on some day (in the past, present, or future), then
                periodic Informs will occur every day at UTC midnight. These
                MUST begin on the very next midnight, even if the
                PeriodicInformTime parameter refers to a day in the future.

                The Unknown Time value indicates that no particular time
                reference is specified. That is, the unit locally chooses the
                time reference and needs only to follow the specified
                PeriodicInformInterval.

                If absolute time is not available to the unit, its periodic
                Inform behavior is the same as if the PeriodicInformTime
                parameter was set to the Unknown Time value.

                The format of the value is 'CCYY-MM-DDThh:mm:ssZ' where:

                  * CCYY: Year number.
                  * MM: Month number in the year.
                  * DD: Day number in the month.
                  * hh: Hour number in the day.
                  * mm: Minute number in the hour.
                  * ss: Second number in the minute.

                Example: 1969-07-21T02:28:00Z.

                The Unknown Time value is defined at '0001-01-01T00:00:00Z'.

                "
  DEFVAL        { "0001-01-01T00:00:00Z" }
  ::= { periodicInformGroup 300 }

-- End of group:Periodic Inform Group

-- ****************************************************************************

-- Group:TR069 Group

-- ****************************************************************************

tr069Group OBJECT IDENTIFIER
 ::= { cwmpMIBObjects 2100 }
 -- Scalar:TR-069 Annex F Enable

 tr069AnnexFEnable OBJECT-TYPE
  SYNTAX        MxEnableState
  MAX-ACCESS    read-write
  STATUS        current
  DESCRIPTION " TR-069 Annex F Enable

                Enables/disables the support of parameters under the TR-069
                Device.GatewayInfo tree.

                "
  DEFVAL        { disable }
  ::= { tr069Group 100 }

-- End of group:TR069 Group

-- ****************************************************************************

-- Group:TR104 Group

-- ****************************************************************************

tr104Group OBJECT IDENTIFIER
 ::= { cwmpMIBObjects 2900 }
 -- Scalar:TR-104 Enable

 tr104Enable OBJECT-TYPE
  SYNTAX        MxEnableState
  MAX-ACCESS    read-write
  STATUS        current
  DESCRIPTION " TR-104 Enable

                Enables/disables the support of parameters under the TR-069
                Device.Services.VoiceService tree.

                "
  DEFVAL        { disable }
  ::= { tr104Group 100 }

-- End of group:TR104 Group

-- ****************************************************************************

-- Group:TR106 Group

-- ****************************************************************************

tr106Group OBJECT IDENTIFIER
 ::= { cwmpMIBObjects 3000 }
 -- Scalar:TR-106 Lan Profile Network Interface Override

 tr106LanNetworkInterface OBJECT-TYPE
  SYNTAX        OCTET STRING ( SIZE(0..50) )
  MAX-ACCESS    read-write
  STATUS        current
  DESCRIPTION " TR-106 Lan Profile Network Interface Override

                Network interface referred by the TR-106 LAN profile.

                  * If empty, use the network interface configured in the
                    Hoc.ManagementInterface parameter.
                  * If the Hoc.ManagementInterface parameter is set to 'All',
                    use the network interface used for contacting the ACS.

                "
  DEFVAL        { "" }
  ::= { tr106Group 100 }

-- End of group:TR106 Group

-- ****************************************************************************

-- Group:TR-111 Group

-- ****************************************************************************

tr111Group OBJECT IDENTIFIER
 ::= { cwmpMIBObjects 4000 }
 -- Scalar:TR-111 STUN Enable

 tr111StunEnable OBJECT-TYPE
  SYNTAX        MxEnableState
  MAX-ACCESS    read-write
  STATUS        current
  DESCRIPTION " TR-111 STUN Enable

                Enables/disables the use of STUN binding requests to discover
                the unit's external IP address and port and to set the
                ManagementServer.UDPConnectionRequestAddress parameter
                accordingly. The ACS can then send UDP connection requests to
                the unit at that IP address and port.

                  * Enable: Enables the use of STUN by the unit.
                  * Disable: Disables the use of STUN by the unit.

                "
  DEFVAL        { disable }
  ::= { tr111Group 100 }

 -- Scalar:TR-111 NAT Detected

 tr111NatDetected OBJECT-TYPE
  SYNTAX        INTEGER { no(100) , yes(200) }
  MAX-ACCESS    read-only
  STATUS        current
  DESCRIPTION " TR-111 NAT Detected

                When the Tr111StunEnable parameter is enabled, this parameter
                indicates whether or not the unit has detected the address and
                /or port mapping in use.

                  * Yes: the Tr111StunEnable parameter is enabled and the unit
                    has detected the address and/or port mapping.
                  * No: the Tr111StunEnable parameter is disabled or the unit
                    has not detected the address and/or port mapping.

                "
  ::= { tr111Group 200 }

 -- Scalar:TR-111 STUN Server Host

 tr111StunServerHost OBJECT-TYPE
  SYNTAX        MxIpHostNamePort
  MAX-ACCESS    read-write
  STATUS        current
  DESCRIPTION " TR-111 STUN Server Host

                Host name or IP address of the STUN server for the unit to
                send Binding Requests if the Tr111StunEnable parameter is
                enabled.

                If the Tr111StunServerHost parameter is empty and the
                Tr111StunEnable parameter is enabled, the unit uses the
                address of the ACS extracted from the host portion of the ACS
                URL.

                If the port is not specified or set to 0, the default STUN
                port (3478) is used.

                "
  DEFVAL        { "" }
  ::= { tr111Group 300 }

 -- Scalar:TR-111 STUN Keep Alive Period

 tr111StunKeepAlivePeriod OBJECT-TYPE
  SYNTAX        OCTET STRING ( SIZE(0..256) )
  MAX-ACCESS    read-write
  STATUS        current
  DESCRIPTION " TR-111 STUN Keep Alive Period

                If the Tr111StunEnable parameter is enabled, this is the
                period, in seconds, at which STUN Binding Requests must be
                sent by the unit for the purpose of maintaining the STUN
                connection. The timeouts must be entered in the
                'minimum-maximum' format.

                The value must be less than or equal to 3600 seconds.

                Note: The current implementation does not allow a range. The
                minimum and maximum values must be the same.

                "
  DEFVAL        { "60-60" }
  ::= { tr111Group 400 }

 -- Scalar:TR-111 STUN Username

 tr111StunUsername OBJECT-TYPE
  SYNTAX        OCTET STRING ( SIZE(0..256) )
  MAX-ACCESS    read-write
  STATUS        current
  DESCRIPTION " TR-111 STUN Username

                If non-empty, the value of the STUN username attribute to be
                used in Binding Requests when the Tr111StunEnable parameter is
                enabled.

                "
  DEFVAL        { "" }
  ::= { tr111Group 500 }

 -- Scalar:TR-111 STUN Status

 tr111StunStatus OBJECT-TYPE
  SYNTAX        INTEGER { disabled(0) , starting(100) , connected(200) ,
                errorCannotResolve(400) , errorNotResponding(500) , errorOther
                (700) }
  MAX-ACCESS    read-only
  STATUS        current
  DESCRIPTION " TR-111 STUN Status

                Indicates the status of the connection with the STUN server.

                  * Disabled: TR-111 is disabled.
                  * Starting: Cwmp service is starting and no connection
                    attempt have been made so far.
                  * Connected: The Cwmp service is connected to the STUN
                    server.
                  * ErrorCannotResolve: The Cwmp service cannot connect with
                    the STUN server because the FQDN cannot be resolved.
                  * ErrorNotResponding: The Cwmp service cannot connect with
                    the STUN server because the server is not responding.
                  * ErrorOther: The Cwmp service cannot connect to the STUN
                    server for unspecified reason or because no ACS URL is
                    configured. See device and ACS logs.

                "
  ::= { tr111Group 600 }

-- End of group:TR-111 Group

-- ****************************************************************************

-- Group:Data Model Group

-- ****************************************************************************

dataModelGroup OBJECT IDENTIFIER
 ::= { cwmpMIBObjects 4500 }
 -- Scalar:Enable Nlm.LocalLog.Log

 nlmLocalLogLogEnable OBJECT-TYPE
  SYNTAX        MxEnableState
  MAX-ACCESS    read-write
  STATUS        current
  DESCRIPTION " Enable Nlm.LocalLog.Log

                Add the object .X_0090F8_Nlm.LocalLog.Log{i}. to the data
                model.

                This object contains the notifications stored locally on the
                device.

                Making this object accessible requires significant CPU
                resources when notifications are frequently sent to the local
                log.

                "
  DEFVAL        { disable }
  ::= { dataModelGroup 100 }

-- End of group:Data Model Group

-- ****************************************************************************

-- Group:Transport Group

-- ****************************************************************************

transportGroup OBJECT IDENTIFIER
 ::= { cwmpMIBObjects 5000 }
 -- Scalar:HTTPS Cipher Suite

 transportHttpsCipherSuite OBJECT-TYPE
  SYNTAX        INTEGER { cS1(100) , cS2(200) , cS3(300) }
  MAX-ACCESS    read-write
  STATUS        current
  DESCRIPTION " HTTPS Cipher Suite

                Defines the allowed cipher suites for the network security
                settings when using the HTTPS protocol to connect to the ACS.
                When the device initiates an HTTPS connection to the ACS, it
                will negotiate the cipher suite according to its
                configuration.

                  * CS1:
                      + TLS_DHE_RSA_WITH_AES_256_CBC_SHA
                      + TLS_DHE_DSS_WITH_AES_256_CBC_SHA
                      + TLS_RSA_WITH_AES_256_CBC_SHA
                      + TLS_DHE_RSA_WITH_3DES_EDE_CBC_SHA
                      + TLS_DHE_DSS_WITH_3DES_EDE_CBC_SHA
                      + TLS_RSA_WITH_3DES_EDE_CBC_SHA
                      + TLS_DHE_RSA_WITH_AES_128_CBC_SHA
                      + TLS_DHE_DSS_WITH_AES_128_CBC_SHA
                      + TLS_RSA_WITH_AES_128_CBC_SHA
                      + TLS_RSA_WITH_RC4_128_SHA
                      + TLS_RSA_WITH_RC4_128_MD5
                  * CS2:
                      + TLS_RSA_WITH_AES_128_CBC_SHA
                      + TLS_RSA_WITH_AES_256_CBC_SHA
                      + TLS_RSA_WITH_3DES_EDE_CBC_SHA
                      + TLS_DHE_RSA_WITH_AES_128_CBC_SHA
                      + TLS_DHE_RSA_WITH_AES_256_CBC_SHA
                      + TLS_DHE_RSA_WITH_3DES_EDE_CBC_SHA
                  * CS3:
                      + TLS_ECDHE_RSA_WITH_AES_256_GCM_SHA384
                      + TLS_ECDHE_RSA_WITH_AES_256_CBC_SHA384
                      + TLS_DHE_RSA_WITH_AES_256_GCM_SHA384
                      + TLS_DHE_RSA_WITH_AES_256_CBC_SHA256
                      + TLS_ECDHE_RSA_WITH_AES_128_CBC_SHA256
                      + TLS_ECDH_RSA_WITH_AES_256_GCM_SHA384
                      + TLS_ECDH_RSA_WITH_AES_256_CBC_SHA384
                      + TLS_RSA_WITH_AES_256_GCM_SHA384
                      + TLS_RSA_WITH_AES_256_CBC_SHA256
                      + TLS_ECDHE_RSA_WITH_AES_128_GCM_SHA256
                      + TLS_DHE_RSA_WITH_AES_128_GCM_SHA256
                      + TLS_DHE_RSA_WITH_AES_128_CBC_SHA256
                      + TLS_ECDH_RSA_WITH_AES_128_GCM_SHA256
                      + TLS_ECDH_RSA_WITH_AES_128_CBC_SHA256
                      + TLS_RSA_WITH_AES_128_GCM_SHA256
                      + TLS_RSA_WITH_AES_128_CBC_SHA256

                "
  DEFVAL        { cS1 }
  ::= { transportGroup 100 }

 -- Scalar:TLS Version

 transportHttpsTlsVersion OBJECT-TYPE
  SYNTAX        INTEGER { sSLv3(100) , tLSv1(200) , tLSv1-1(300) , tLSv1-2
                (400) }
  MAX-ACCESS    read-write
  STATUS        current
  DESCRIPTION " TLS Version

                Defines the allowed TLS versions for the network security
                settings when using the HTTPS protocol to connect to the ACS.
                When the device initiates an HTTPS connection to the ACS, it
                will negotiate the TLS version according to its configuration.

                  * SSLv3: Allow SSL version 3 and all TLS versions.
                  * TLSv1: Allow TLS versions 1 and up.
                  * TLSv1_1: Allow TLS versions 1.1 and up.
                  * TLSv1_2: Allow TLS versions 1.2 and up.

                The device will always send its highest supported TLS version
                in the ClientHello message. The server will select the highest
                supported TLS version it supports from the ClientHello
                message. The device will then validate that the selected
                version is allowed. If the version is not allowed the device
                will close the connection.

                "
  DEFVAL        { tLSv1 }
  ::= { transportGroup 150 }

 -- Scalar:Level of security for HTTPS certificate validation.

 transportCertificateValidation OBJECT-TYPE
  SYNTAX        INTEGER { noValidation(100) , hostName(200) }
  MAX-ACCESS    read-write
  STATUS        current
  DESCRIPTION " Level of security for HTTPS certificate validation.

                When connecting to the ACS using HTTPS, this parameter defines
                the level of security to use when validating the server's
                certificate.

                  * NoValidation: Allow a connection to the server without
                    validating its certificate. The only condition is to
                    receive a certificate from the server. This option
                    provides partial security and should be selected with
                    care.
                  * HostName: Allow a connection to the server by validating
                    its certificate is trusted and valid. The validations
                    performed on the certificate include the expiration date
                    and that the Subject Alternate Name (SAN) or Common Name
                    (CN) matches the FQDN or IP address of the server.

                "
  DEFVAL        { hostName }
  ::= { transportGroup 200 }

-- End of group:Transport Group

-- ****************************************************************************

-- Group:Interop Group

-- ****************************************************************************

interopGroup OBJECT IDENTIFIER
 ::= { cwmpMIBObjects 50000 }
 -- Scalar:Allow Unauthenticated UDP Connection Requests

 interopAllowUnauthenticatedUDPConnectionRequests OBJECT-TYPE
  SYNTAX        MxEnableState
  MAX-ACCESS    read-write
  STATUS        current
  DESCRIPTION " Allow Unauthenticated UDP Connection Requests

                Determines the CPE behavior when receiving a UDP connection
                request message.

                  * Enable: Allow any UDP connection request without
                    authentication. This behavior goes against the UDP
                    Connection Request described by TR-069 Amendment-2
                    specification.
                  * Disable: Force the authentication of a UDP connection
                    request.

                "
  DEFVAL        { disable }
  ::= { interopGroup 100 }

 -- Scalar:Parameter Type Validation

 interopParameterTypeValidation OBJECT-TYPE
  SYNTAX        INTEGER { tolerant(100) , strict(200) }
  MAX-ACCESS    read-write
  STATUS        current
  DESCRIPTION " Parameter Type Validation

                Defines the parameter type validation when the ACS assigns a
                value to a parameter.

                  * Tolerant: The client target type is evaluated and
                    conversion is done (if possible): i.e., string to boolean,
                    string to int, string to unsigned int, string to datetime,
                    etc.
                  * Strict: The ACS and the client must have matching xsd:type
                    otherwise the client rejects the parameter value.

                "
  DEFVAL        { tolerant }
  ::= { interopGroup 200 }

 -- Scalar:MAC Address Format

 interopMacAddressFormat OBJECT-TYPE
  SYNTAX        INTEGER { lowerCase(100) , upperCaseWithColon(200) }
  MAX-ACCESS    read-write
  STATUS        current
  DESCRIPTION " MAC Address Format

                LAN.MACAddress Display Format

                  * LowerCase: MAC address is in lower case format. Ex.:
                    0090f80d5b4a
                  * UpperCaseWithColon: MAC address is in upper case format,
                    each octet separated by colons. Ex.: 00:90:F8:0D:5B:4A

                "
  DEFVAL        { lowerCase }
  ::= { interopGroup 300 }

-- End of group:Interop Group

-- ****************************************************************************

-- Group:Notification Messages Configuration

-- ****************************************************************************

notificationsGroup OBJECT IDENTIFIER
 ::= { cwmpMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with a 'Informational' and
                    higher severity are issued.
                  * Warning: Notification messages with a 'Warning' and higher
                    severity are issued.
                  * Error: Notification messages with an 'Error' and higher
                    severity are issued.
                  * Critical: Notification messages with a 'Critical' severity
                    are issued.

                "
  DEFVAL        { warning }
  ::= { notificationsGroup 100 }

-- End of group:Notification Messages Configuration

-- ****************************************************************************

-- Group:Configuration Settings

-- ****************************************************************************

configurationGroup OBJECT IDENTIFIER
 ::= { cwmpMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for the
                configuration to fully take effect.

                  * Yes: Service needs to be restarted.
                  * No: Service does not need to be restarted.

                Services can be restarted by using the
                Scm.ServiceCommands.Restart command.

                "
  ::= { configurationGroup 100 }

-- End of group:Configuration Settings

END
