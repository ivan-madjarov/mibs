OPENBRANCH-MIB DEFINITIONS ::= BEGIN

	-- ==================================================================
	--  Copyright © 1999 - 2006 Siemens Network Convergence LLC
	--
	--  All Rights Reserved.
	--
	--  Reproduction of this document is authorized on condition that
	--  this copyright notice is included.
	--
	--  This MIB document embodies proprietary intellectual property. 
	--  of Siemens Network Convergence LLC, which retains all title and
	--  ownership in this MIB, including any revisions.
	--
	--  This module will be extended, as required.	
	--
	--  Siemens Network Convergence LLC reserves the right to make 
	--  changes in specification and other information contained in this 
	--  document without prior notice. The reader should consult 
	--  Siemens Network Convergence LLC to determine whether any such
	--  changes have been made.
	--
	--  Copyright © 1999 - 2006 Siemens Network Convergence LLC
	-- ==================================================================


	-- ==================================================================
	-- Revision History V1R0
	--  08/26/08      Uwe Grothe		initial issue
	--  08/29/08      Jijo Jose             Integrated with NET-SNMP module.
	--  09/25/08	  Uwe Grothe		added official openBranch OID
	--  10/01/08      Antonio Fernandes     merge
	--  02/05/09      Evandro Hauenstein    CQ00095099
	--  02/10/09      Evandro Hauenstein    CQ00095495        
	-- Revision History V1R1
	--  08/26/09      Jose Macedo           Merge from v1.1.4.10
	-- Revision History V1R2
	--  09/29/09      Jose Macedo           CQ00115262
	--  06/10/09      Evandro Hauenstein    CQ00113298
	-- Revision History V1R3
	--  12/10/09      Jose Macedo           merge
	--  02/22/10      Evandro Hauenstein    CQ00124486        
	--  03/24/10      Jose Macedo           CQ00122337        
    --  04/26/10	  William Bley		add some spare traps
	--  04/30/09      Jose Macedo           CQ00132480
	--  06/09/10      Evandro Hauenstein    CQ00134813        
	-- Revision History V1R3 PGA
	--  11/18/10      William Bley          Correct  History of Changes
	--  12/03/10      Evandro Hauenstein    CQ00152265
	-- ==================================================================


IMPORTS
    MODULE-IDENTITY, OBJECT-TYPE,NOTIFICATION-TYPE,enterprises	FROM SNMPv2-SMI
    DisplayString               			        FROM SNMPv2-TC;


	siemens			OBJECT IDENTIFIER ::= { enterprises 4329 }
				-- The authoritative identity of the enterprise Siemens AG

	iandcAdmin		OBJECT IDENTIFIER ::= { siemens 2 }
				-- The Siemens I&C product-specific MIBs

	openBranch	        OBJECT IDENTIFIER ::= { iandcAdmin 55 }
				-- HiPath OpenBranch, registered with Myriam Rosshuber SEN CTO IM 2


	openBranchAlarms	MODULE-IDENTITY
	LAST-UPDATED		"201007161500Z"
	ORGANIZATION		"Siemens Enterprise"
	CONTACT-INFO		"Technical Support
				Postal: TBD
					TBD
					TBD
				Tel: TBD
	                	E-mail: TBD"

	DESCRIPTION		"This MIB module implements the SNMP Alarms, 	
				which are reported by the OpenBranch product
				An alarm is uniquely identified by the trap name
				(mainly the last two numbers of trap OID) and
				the neName and the FaultyObject parameter.
				An alarm trap is a trap with a non-cleared severity.
				It is cleared by the same trap
				with the same neName and a severiy of clear."

	::= { openBranch 1 }


	trapParameters		OBJECT IDENTIFIER ::= { openBranchAlarms 1 }
	eventCommon		OBJECT IDENTIFIER ::= { openBranchAlarms 2 }
	eventGroups		OBJECT IDENTIFIER ::= { openBranchAlarms 3 }

	eventGroup01		OBJECT IDENTIFIER ::= { eventGroups 1 }  
	eventGroup02		OBJECT IDENTIFIER ::= { eventGroups 2 }  
	eventGroup03		OBJECT IDENTIFIER ::= { eventGroups 3 }
	eventGroup04		OBJECT IDENTIFIER ::= { eventGroups 4 }
	eventGroup05		OBJECT IDENTIFIER ::= { eventGroups 5 }
	eventGroup06		OBJECT IDENTIFIER ::= { eventGroups 6 }
	eventGroup07		OBJECT IDENTIFIER ::= { eventGroups 7 }
	eventGroup08		OBJECT IDENTIFIER ::= { eventGroups 8 }
	eventGroup09		OBJECT IDENTIFIER ::= { eventGroups 9 }
	eventGroup10		OBJECT IDENTIFIER ::= { eventGroups 10 }


	--********************************************************************
	-- Alarm Trap Parameters:
	--********************************************************************


	neName			OBJECT-TYPE                              
	SYNTAX			DisplayString
	MAX-ACCESS		not-accessible
	STATUS			current
	DESCRIPTION		"name of the network element sending the alarm"
	::= { trapParameters 1 }

   
	eventGroupName		OBJECT-TYPE
	SYNTAX			DisplayString
	MAX-ACCESS		not-accessible
	STATUS			current
	DESCRIPTION		"corresponds to the eventGroup, 
				the second last number of the trap OID."
	::= { trapParameters 2 }


	eventName		OBJECT-TYPE
	SYNTAX			DisplayString
	MAX-ACCESS		not-accessible
	STATUS			current
	DESCRIPTION		"corresponds to the event within the eventGroup
				reported by the trap, the last number of the trap OID."
	::= { trapParameters 3 }


	severity		OBJECT-TYPE
	SYNTAX			INTEGER	{indeterminate(0),
					critical(1),
					major(2),
					minor(3),	
					warning(4),
					cleared(5) }
	MAX-ACCESS		not-accessible
	STATUS			current
	DESCRIPTION		"corresponds to X.721/X.733:PerceivedSeverity.
				indeterminate is not used.
				critical, major, minor and warning correspond to an alarm.
				cleared corresponds to an alarm clearance event, which clears
				all alarms of the network element that had been reported by this trap."
	::= { trapParameters 4 }


	eventType OBJECT-TYPE         
        SYNTAX  INTEGER     {	indeterminate(0),
			 	communicationsAlarm(2),
				enviromentalAlarm(3),
				equipmentAlarm(4),
				processingErrorAlarm(10),
				qualityOfServiceAlarm(11)  }
	MAX-ACCESS	  	not-accessible
	STATUS		  	current
	DESCRIPTION		"The event type categorizes the alarms."
        ::= { trapParameters 5 }

     
	eventTime		OBJECT-TYPE
        SYNTAX			DisplayString
        MAX-ACCESS		not-accessible
        STATUS			current
        DESCRIPTION		"An element of X.710: Parameter contains
				the time of generation of the event,
				The EventTime is a GeneralizedTime (defined in X.208),
		                format is YYYYMMDDhhmmss.f+hhmm where 
		                Y year 
		                M month in year
		                D day in month
		                h hour in day (0-23)
		                m minute in hour
		                s second in minute
		                f tenth part of second
				+hhmm	local time offset(+-) to UTC time. 
				Time represents the local time (t1), and the time 
				differential (t2) enables UTC time to be determined as follows:
				UTC time = t1 - t2"
        ::= { trapParameters 6 } 


	faultyObject		OBJECT-TYPE          
	SYNTAX			DisplayString
	MAX-ACCESS		not-accessible
	STATUS			current
	DESCRIPTION		"Specifies the component of the network element at fault."
	::= { trapParameters 7 }
  
    	monitoredValue		OBJECT-TYPE          
	SYNTAX			DisplayString
	MAX-ACCESS		not-accessible
	STATUS			current
	DESCRIPTION		"Specifies the value shows the current condition of the system for this particular alarm"
	::= { trapParameters 8 }

	thresholdValue		OBJECT-TYPE          
	SYNTAX			DisplayString
	MAX-ACCESS		not-accessible
	STATUS			current
	DESCRIPTION		"Specifies the value that needs to be crossed by monitored-value for an alarm to be generated"
	::= { trapParameters 9 }

	neType			OBJECT-TYPE         
	SYNTAX			DisplayString
	MAX-ACCESS	  	not-accessible
	STATUS		  	current
	DESCRIPTION		"Indicate the network element type"
        ::= { trapParameters 10 }

	
	--********************************************************************
	-- Common Trap Definitions
	--********************************************************************


	networkElementStarting NOTIFICATION-TYPE                 
	OBJECTS {	neName,
			eventTime,
			neType  }
	STATUS		current
	DESCRIPTION	"This trap reports that the network element is starting up.
			All alarms of this network element shall be deleted."       
	::= { eventCommon 1 }                                                        



	--********************************************************************
	-- Alarm Trap Definitions for event group 01
	--********************************************************************


	openBranchAlarm0101 NOTIFICATION-TYPE
	OBJECTS {	neName,
			eventGroupName,			-- 01
			eventName,			-- 01
			severity,
			eventType,
			eventTime,
			faultyObject,
			monitoredValue,
			thresholdValue,
			neType }
	STATUS		current
	DESCRIPTION	"Spontaneous Alarm from the managed network element."
	::= { eventGroup01 1 }

	openBranchAlarm0102 NOTIFICATION-TYPE
	OBJECTS {	neName,
			eventGroupName,			-- 01
			eventName,			-- 02
			severity,
			eventType,
			eventTime,
			faultyObject,
			monitoredValue,
			thresholdValue,
			neType }
	STATUS		current
	DESCRIPTION	"Spontaneous Alarm from the managed network element."
	::= { eventGroup01 2 }

	openBranchAlarm0103 NOTIFICATION-TYPE
	OBJECTS {	neName,
			eventGroupName,			-- 01
			eventName,			-- 03
			severity,
			eventType,
			eventTime,
			faultyObject,
			monitoredValue,
			thresholdValue,
			neType }
	STATUS		current
	DESCRIPTION	"Spontaneous Alarm from the managed network element."
	::= { eventGroup01 3 }

	openBranchAlarm0104 NOTIFICATION-TYPE
	OBJECTS {	neName,
			eventGroupName,			-- 01
			eventName,			-- 04
			severity,
			eventType,
			eventTime,
			faultyObject,
			monitoredValue,
			thresholdValue,
			neType }
	STATUS		current
	DESCRIPTION	"Spontaneous Alarm from the managed network element."
	::= { eventGroup01 4 }

	openBranchAlarm0105 NOTIFICATION-TYPE
	OBJECTS {	neName,
			eventGroupName,			-- 01
			eventName,			-- 05
			severity,
			eventType,
			eventTime,
			faultyObject,
			monitoredValue,
			thresholdValue,
			neType }
	STATUS		current
	DESCRIPTION	"Spontaneous Alarm from the managed network element."
	::= { eventGroup01 5 }

	openBranchAlarm0106 NOTIFICATION-TYPE
	OBJECTS {	neName,
			eventGroupName,			-- 01
			eventName,			-- 06
			severity,
			eventType,
			eventTime,
			faultyObject,
			monitoredValue,
			thresholdValue,
			neType }
	STATUS		current
	DESCRIPTION	"Spontaneous Alarm from the managed network element."
	::= { eventGroup01 6 }

	openBranchAlarm0107 NOTIFICATION-TYPE
	OBJECTS {	neName,
			eventGroupName,			-- 01
			eventName,			-- 07
			severity,
			eventType,
			eventTime,
			faultyObject,
			monitoredValue,
			thresholdValue,
			neType }
	STATUS		current
	DESCRIPTION	"Spontaneous Alarm from the managed network element."
	::= { eventGroup01 7 }

	openBranchAlarm0108 NOTIFICATION-TYPE
	OBJECTS {	neName,
			eventGroupName,			-- 01
			eventName,			-- 08
			severity,
			eventType,
			eventTime,
			faultyObject,
			monitoredValue,
			thresholdValue,
			neType }
	STATUS		current
	DESCRIPTION	"Spontaneous Alarm from the managed network element."
	::= { eventGroup01 8 }

	openBranchAlarm0109 NOTIFICATION-TYPE
	OBJECTS {	neName,
			eventGroupName,			-- 01
			eventName,			-- 09
			severity,
			eventType,
			eventTime,
			faultyObject,
			monitoredValue,
			thresholdValue,
			neType }
	STATUS		current
	DESCRIPTION	"Spontaneous Alarm from the managed network element."
	::= { eventGroup01 9 }

	openBranchAlarm0110 NOTIFICATION-TYPE
	OBJECTS {	neName,
			eventGroupName,			-- 01
			eventName,			-- 10
			severity,
			eventType,
			eventTime,
			faultyObject,
			monitoredValue,
			thresholdValue,
			neType }
	STATUS		current
	DESCRIPTION	"Spontaneous Alarm from the managed network element."
	::= { eventGroup01 10 }

	openBranchAlarm0111 NOTIFICATION-TYPE
	OBJECTS {	neName,
			eventGroupName,			-- 01
			eventName,			-- 11
			severity,
			eventType,
			eventTime,
			faultyObject,
			monitoredValue,
			thresholdValue,
			neType }
	STATUS		current
	DESCRIPTION	"Spontaneous Alarm from the managed network element."
	::= { eventGroup01 11 }

	openBranchAlarm0112 NOTIFICATION-TYPE
	OBJECTS {	neName,
			eventGroupName,			-- 01
			eventName,			-- 12
			severity,
			eventType,
			eventTime,
			faultyObject,
			monitoredValue,
			thresholdValue,
			neType }
	STATUS		current
	DESCRIPTION	"Spontaneous Alarm from the managed network element."
	::= { eventGroup01 12 }

	openBranchAlarm0113 NOTIFICATION-TYPE
	OBJECTS {	neName,
			eventGroupName,			-- 01
			eventName,			-- 13
			severity,
			eventType,
			eventTime,
			faultyObject,
			monitoredValue,
			thresholdValue,
			neType }
	STATUS		current
	DESCRIPTION	"Spontaneous Alarm from the managed network element."
	::= { eventGroup01 13 }

	openBranchAlarm0114 NOTIFICATION-TYPE
	OBJECTS {	neName,
			eventGroupName,			-- 01
			eventName,			-- 14
			severity,
			eventType,
			eventTime,
			faultyObject,
			monitoredValue,
			thresholdValue,
			neType }
	STATUS		current
	DESCRIPTION	"Spontaneous Alarm from the managed network element."
	::= { eventGroup01 14 }

	openBranchAlarm0115 NOTIFICATION-TYPE
	OBJECTS {	neName,
			eventGroupName,			-- 01
			eventName,			-- 15
			severity,
			eventType,
			eventTime,
			faultyObject,
			monitoredValue,
			thresholdValue,
			neType }
	STATUS		current
	DESCRIPTION	"Spontaneous Alarm from the managed network element."
	::= { eventGroup01 15 }

	openBranchAlarm0116 NOTIFICATION-TYPE
	OBJECTS {	neName,
			eventGroupName,			-- 01
			eventName,			-- 16
			severity,
			eventType,
			eventTime,
			faultyObject,
			monitoredValue,
			thresholdValue,
			neType }
	STATUS		current
	DESCRIPTION	"Spontaneous Alarm from the managed network element."
	::= { eventGroup01 16 }

	openBranchAlarm0117 NOTIFICATION-TYPE
	OBJECTS {	neName,
			eventGroupName,			-- 01
			eventName,			-- 17
			severity,
			eventType,
			eventTime,
			faultyObject,
			monitoredValue,
			thresholdValue,
			neType }
	STATUS		current
	DESCRIPTION	"Spontaneous Alarm from the managed network element."
	::= { eventGroup01 17 }

	openBranchAlarm0118 NOTIFICATION-TYPE
	OBJECTS {	neName,
			eventGroupName,			-- 01
			eventName,			-- 18
			severity,
			eventType,
			eventTime,
			faultyObject,
			monitoredValue,
			thresholdValue,
			neType }
	STATUS		current
	DESCRIPTION	"Spontaneous Alarm from the managed network element."
	::= { eventGroup01 18 }

	openBranchAlarm0119 NOTIFICATION-TYPE
	OBJECTS {	neName,
			eventGroupName,			-- 01
			eventName,			-- 19
			severity,
			eventType,
			eventTime,
			faultyObject,
			monitoredValue,
			thresholdValue,
			neType }
	STATUS		current
	DESCRIPTION	"Spontaneous Alarm from the managed network element."
	::= { eventGroup01 19 }

	openBranchAlarm0120 NOTIFICATION-TYPE
	OBJECTS {	neName,
			eventGroupName,			-- 01
			eventName,			-- 20
			severity,
			eventType,
			eventTime,
			faultyObject,
			monitoredValue,
			thresholdValue,
			neType }
	STATUS		current
	DESCRIPTION	"Spontaneous Alarm from the managed network element."
	::= { eventGroup01 20 }

	openBranchAlarm0121 NOTIFICATION-TYPE
	OBJECTS {	neName,
			eventGroupName,			-- 01
			eventName,			-- 21
			severity,
			eventType,
			eventTime,
			faultyObject,
			monitoredValue,
			thresholdValue,
			neType }
	STATUS		current
	DESCRIPTION	"Spontaneous Alarm from the managed network element."
	::= { eventGroup01 21 }

	openBranchAlarm0122 NOTIFICATION-TYPE
	OBJECTS {	neName,
			eventGroupName,			-- 01
			eventName,			-- 22
			severity,
			eventType,
			eventTime,
			faultyObject,
			monitoredValue,
			thresholdValue,
			neType }
	STATUS		current
	DESCRIPTION	"Spontaneous Alarm from the managed network element."
	::= { eventGroup01 22 }

	openBranchAlarm0123 NOTIFICATION-TYPE
	OBJECTS {	neName,
			eventGroupName,			-- 01
			eventName,			-- 23
			severity,
			eventType,
			eventTime,
			faultyObject,
			monitoredValue,
			thresholdValue,
			neType }
	STATUS		current
	DESCRIPTION	"Spontaneous Alarm from the managed network element."
	::= { eventGroup01 23 }

	openBranchAlarm0124 NOTIFICATION-TYPE
	OBJECTS {	neName,
			eventGroupName,			-- 01
			eventName,			-- 24
			severity,
			eventType,
			eventTime,
			faultyObject,
			monitoredValue,
			thresholdValue,
			neType }
	STATUS		current
	DESCRIPTION	"Spontaneous Alarm from the managed network element."
	::= { eventGroup01 24 }

	openBranchAlarm0125 NOTIFICATION-TYPE
	OBJECTS {	neName,
			eventGroupName,			-- 01
			eventName,			-- 25
			severity,
			eventType,
			eventTime,
			faultyObject,
			monitoredValue,
			thresholdValue,
			neType }
	STATUS		current
	DESCRIPTION	"Spontaneous Alarm from the managed network element."
	::= { eventGroup01 25 }

	openBranchAlarm0126 NOTIFICATION-TYPE
	OBJECTS {	neName,
			eventGroupName,			-- 01
			eventName,			-- 26
			severity,
			eventType,
			eventTime,
			faultyObject,
			monitoredValue,
			thresholdValue,
			neType }
	STATUS		current
	DESCRIPTION	"Spontaneous Alarm from the managed network element."
	::= { eventGroup01 26 }

	openBranchAlarm0127 NOTIFICATION-TYPE
	OBJECTS {	neName,
			eventGroupName,			-- 01
			eventName,			-- 27
			severity,
			eventType,
			eventTime,
			faultyObject,
			monitoredValue,
			thresholdValue,
			neType }
	STATUS		current
	DESCRIPTION	"Spontaneous Alarm from the managed network element."
	::= { eventGroup01 27 }

	openBranchAlarm0128 NOTIFICATION-TYPE
	OBJECTS {	neName,
			eventGroupName,			-- 01
			eventName,			-- 28
			severity,
			eventType,
			eventTime,
			faultyObject,
			monitoredValue,
			thresholdValue,
			neType }
	STATUS		current
	DESCRIPTION	"Spontaneous Alarm from the managed network element."
	::= { eventGroup01 28 }

	openBranchAlarm0129 NOTIFICATION-TYPE
	OBJECTS {	neName,
			eventGroupName,			-- 01
			eventName,			-- 29
			severity,
			eventType,
			eventTime,
			faultyObject,
			monitoredValue,
			thresholdValue,
			neType }
	STATUS		current
	DESCRIPTION	"Spontaneous Alarm from the managed network element."
	::= { eventGroup01 29 }

	openBranchAlarm0130 NOTIFICATION-TYPE
	OBJECTS {	neName,
			eventGroupName,			-- 01
			eventName,			-- 30
			severity,
			eventType,
			eventTime,
			faultyObject,
			monitoredValue,
			thresholdValue,
			neType }
	STATUS		current
	DESCRIPTION	"Spontaneous Alarm from the managed network element."
	::= { eventGroup01 30 }

	openBranchAlarm0131 NOTIFICATION-TYPE
	OBJECTS {	neName,
			eventGroupName,			-- 01
			eventName,			-- 31
			severity,
			eventType,
			eventTime,
			faultyObject,
			monitoredValue,
			thresholdValue,
			neType }
	STATUS		current
	DESCRIPTION	"Spontaneous Alarm from the managed network element."
	::= { eventGroup01 31 }

	openBranchAlarm0132 NOTIFICATION-TYPE
	OBJECTS {	neName,
			eventGroupName,			-- 01
			eventName,			-- 32
			severity,
			eventType,
			eventTime,
			faultyObject,
			monitoredValue,
			thresholdValue,
			neType }
	STATUS		current
	DESCRIPTION	"Spontaneous Alarm from the managed network element."
	::= { eventGroup01 32 }

	openBranchAlarm0133 NOTIFICATION-TYPE
	OBJECTS {	neName,
			eventGroupName,			-- 01
			eventName,			-- 33
			severity,
			eventType,
			eventTime,
			faultyObject,
			monitoredValue,
			thresholdValue,
			neType }
	STATUS		current
	DESCRIPTION	"Spontaneous Alarm from the managed network element."
	::= { eventGroup01 33 }

	openBranchAlarm0134 NOTIFICATION-TYPE
	OBJECTS {	neName,
			eventGroupName,			-- 01
			eventName,			-- 34
			severity,
			eventType,
			eventTime,
			faultyObject,
			monitoredValue,
			thresholdValue,
			neType }
	STATUS		current
	DESCRIPTION	"Spontaneous Alarm from the managed network element."
	::= { eventGroup01 34 }

	openBranchAlarm0135 NOTIFICATION-TYPE
	OBJECTS {	neName,
			eventGroupName,			-- 01
			eventName,			-- 35
			severity,
			eventType,
			eventTime,
			faultyObject,
			monitoredValue,
			thresholdValue,
			neType }
	STATUS		current
	DESCRIPTION	"Spontaneous Alarm from the managed network element."
	::= { eventGroup01 35 }

	openBranchAlarm0136 NOTIFICATION-TYPE
	OBJECTS {	neName,
			eventGroupName,			-- 01
			eventName,			-- 36
			severity,
			eventType,
			eventTime,
			faultyObject,
			monitoredValue,
			thresholdValue,
			neType }
	STATUS		current
	DESCRIPTION	"Spontaneous Alarm from the managed network element."
	::= { eventGroup01 36 }

	openBranchAlarm0137 NOTIFICATION-TYPE
	OBJECTS {	neName,
			eventGroupName,			-- 01
			eventName,			-- 37
			severity,
			eventType,
			eventTime,
			faultyObject,
			monitoredValue,
			thresholdValue,
			neType }
	STATUS		current
	DESCRIPTION	"Spontaneous Alarm from the managed network element."
	::= { eventGroup01 37 }

	openBranchAlarm0138 NOTIFICATION-TYPE
	OBJECTS {	neName,
			eventGroupName,			-- 01
			eventName,			-- 38
			severity,
			eventType,
			eventTime,
			faultyObject,
			monitoredValue,
			thresholdValue,
			neType }
	STATUS		current
	DESCRIPTION	"Spontaneous Alarm from the managed network element."
	::= { eventGroup01 38 }

	openBranchAlarm0139 NOTIFICATION-TYPE
	OBJECTS {	neName,
			eventGroupName,			-- 01
			eventName,			-- 39
			severity,
			eventType,
			eventTime,
			faultyObject,
			monitoredValue,
			thresholdValue,
			neType }
	STATUS		current
	DESCRIPTION	"Spontaneous Alarm from the managed network element."
	::= { eventGroup01 39 }

	openBranchAlarm0140 NOTIFICATION-TYPE
	OBJECTS {	neName,
			eventGroupName,			-- 01
			eventName,			-- 40
			severity,
			eventType,
			eventTime,
			faultyObject,
			monitoredValue,
			thresholdValue,
			neType }
	STATUS		current
	DESCRIPTION	"Spontaneous Alarm from the managed network element."
	::= { eventGroup01 40 }

	openBranchAlarm0141 NOTIFICATION-TYPE
	OBJECTS {	neName,
			eventGroupName,			-- 01
			eventName,			-- 41
			severity,
			eventType,
			eventTime,
			faultyObject,
			monitoredValue,
			thresholdValue,
			neType }
	STATUS		current
	DESCRIPTION	"Spontaneous Alarm from the managed network element."
	::= { eventGroup01 41 }

	openBranchAlarm0142 NOTIFICATION-TYPE
	OBJECTS {	neName,
			eventGroupName,			-- 01
			eventName,			-- 42
			severity,
			eventType,
			eventTime,
			faultyObject,
			monitoredValue,
			thresholdValue,
			neType }
	STATUS		current
	DESCRIPTION	"Spontaneous Alarm from the managed network element."
	::= { eventGroup01 42 }

	openBranchAlarm0143 NOTIFICATION-TYPE
	OBJECTS {	neName,
			eventGroupName,			-- 01
			eventName,			-- 43
			severity,
			eventType,
			eventTime,
			faultyObject,
			monitoredValue,
			thresholdValue,
			neType }
	STATUS		current
	DESCRIPTION	"Spontaneous Alarm from the managed network element."
	::= { eventGroup01 43 }

	openBranchAlarm0144 NOTIFICATION-TYPE
	OBJECTS {	neName,
			eventGroupName,			-- 01
			eventName,			-- 44
			severity,
			eventType,
			eventTime,
			faultyObject,
			monitoredValue,
			thresholdValue,
			neType }
	STATUS		current
	DESCRIPTION	"Spontaneous Alarm from the managed network element."
	::= { eventGroup01 44 }

	openBranchAlarm0145 NOTIFICATION-TYPE
	OBJECTS {	neName,
			eventGroupName,			-- 01
			eventName,			-- 45
			severity,
			eventType,
			eventTime,
			faultyObject,
			monitoredValue,
			thresholdValue,
			neType }
	STATUS		current
	DESCRIPTION	"Spontaneous Alarm from the managed network element."
	::= { eventGroup01 45 }

	openBranchAlarm0146 NOTIFICATION-TYPE
	OBJECTS {	neName,
			eventGroupName,			-- 01
			eventName,			-- 46
			severity,
			eventType,
			eventTime,
			faultyObject,
			monitoredValue,
			thresholdValue,
			neType }
	STATUS		current
	DESCRIPTION	"Spontaneous Alarm from the managed network element."
	::= { eventGroup01 46 }

	openBranchAlarm0147 NOTIFICATION-TYPE
	OBJECTS {	neName,
			eventGroupName,			-- 01
			eventName,			-- 47
			severity,
			eventType,
			eventTime,
			faultyObject,
			monitoredValue,
			thresholdValue,
			neType }
	STATUS		current
	DESCRIPTION	"Spontaneous Alarm from the managed network element."
	::= { eventGroup01 47 }

	openBranchAlarm0148 NOTIFICATION-TYPE
	OBJECTS {	neName,
			eventGroupName,			-- 01
			eventName,			-- 48
			severity,
			eventType,
			eventTime,
			faultyObject,
			monitoredValue,
			thresholdValue,
			neType }
	STATUS		current
	DESCRIPTION	"Spontaneous Alarm from the managed network element."
	::= { eventGroup01 48 }

	openBranchAlarm0149 NOTIFICATION-TYPE
	OBJECTS {	neName,
			eventGroupName,			-- 01
			eventName,			-- 49
			severity,
			eventType,
			eventTime,
			faultyObject,
			monitoredValue,
			thresholdValue,
			neType }
	STATUS		current
	DESCRIPTION	"Spontaneous Alarm from the managed network element."
	::= { eventGroup01 49 }

	openBranchAlarm0150 NOTIFICATION-TYPE
	OBJECTS {	neName,
			eventGroupName,			-- 01
			eventName,			-- 50
			severity,
			eventType,
			eventTime,
			faultyObject,
			monitoredValue,
			thresholdValue,
			neType }
	STATUS		current
	DESCRIPTION	"Spontaneous Alarm from the managed network element."
	::= { eventGroup01 50 }

	openBranchAlarm0151 NOTIFICATION-TYPE
	OBJECTS {	neName,
			eventGroupName,			-- 01
			eventName,			-- 51
			severity,
			eventType,
			eventTime,
			faultyObject,
			monitoredValue,
			thresholdValue,
			neType }
	STATUS		current
	DESCRIPTION	"Spontaneous Alarm from the managed network element."
	::= { eventGroup01 51 }

	openBranchAlarm0152 NOTIFICATION-TYPE
	OBJECTS {	neName,
			eventGroupName,			-- 01
			eventName,			-- 52
			severity,
			eventType,
			eventTime,
			faultyObject,
			monitoredValue,
			thresholdValue,
			neType }
	STATUS		current
	DESCRIPTION	"Spontaneous Alarm from the managed network element."
	::= { eventGroup01 52 }

	openBranchAlarm0153 NOTIFICATION-TYPE
	OBJECTS {	neName,
			eventGroupName,			-- 01
			eventName,			-- 53
			severity,
			eventType,
			eventTime,
			faultyObject,
			monitoredValue,
			thresholdValue,
			neType }
	STATUS		current
	DESCRIPTION	"Spontaneous Alarm from the managed network element."
	::= { eventGroup01 53 }

	openBranchAlarm0154 NOTIFICATION-TYPE
	OBJECTS {	neName,
			eventGroupName,			-- 01
			eventName,			-- 54
			severity,
			eventType,
			eventTime,
			faultyObject,
			monitoredValue,
			thresholdValue,
			neType }
	STATUS		current
	DESCRIPTION	"Spontaneous Alarm from the managed network element."
	::= { eventGroup01 54 }

	openBranchAlarm0155 NOTIFICATION-TYPE
	OBJECTS {	neName,
			eventGroupName,			-- 01
			eventName,			-- 55
			severity,
			eventType,
			eventTime,
			faultyObject,
			monitoredValue,
			thresholdValue,
			neType }
	STATUS		current
	DESCRIPTION	"Spontaneous Alarm from the managed network element."
	::= { eventGroup01 55 }

	openBranchAlarm0156 NOTIFICATION-TYPE
	OBJECTS {	neName,
			eventGroupName,			-- 01
			eventName,			-- 56
			severity,
			eventType,
			eventTime,
			faultyObject,
			monitoredValue,
			thresholdValue,
			neType }
	STATUS		current
	DESCRIPTION	"Spontaneous Alarm from the managed network element."
	::= { eventGroup01 56 }

	openBranchAlarm0157 NOTIFICATION-TYPE
	OBJECTS {	neName,
			eventGroupName,			-- 01
			eventName,			-- 57
			severity,
			eventType,
			eventTime,
			faultyObject,
			monitoredValue,
			thresholdValue,
			neType }
	STATUS		current
	DESCRIPTION	"Spontaneous Alarm from the managed network element."
	::= { eventGroup01 57 }

	openBranchAlarm0158 NOTIFICATION-TYPE
	OBJECTS {	neName,
			eventGroupName,			-- 01
			eventName,			-- 58
			severity,
			eventType,
			eventTime,
			faultyObject,
			monitoredValue,
			thresholdValue,
			neType }
	STATUS		current
	DESCRIPTION	"Spontaneous Alarm from the managed network element."
	::= { eventGroup01 58 }

	openBranchAlarm0159 NOTIFICATION-TYPE
	OBJECTS {	neName,
			eventGroupName,			-- 01
			eventName,			-- 59
			severity,
			eventType,
			eventTime,
			faultyObject,
			monitoredValue,
			thresholdValue,
			neType }
	STATUS		current
	DESCRIPTION	"Spontaneous Alarm from the managed network element."
	::= { eventGroup01 59 }

	openBranchAlarm0160 NOTIFICATION-TYPE
	OBJECTS {	neName,
			eventGroupName,			-- 01
			eventName,			-- 60
			severity,
			eventType,
			eventTime,
			faultyObject,
			monitoredValue,
			thresholdValue,
			neType }
	STATUS		current
	DESCRIPTION	"Spontaneous Alarm from the managed network element."
	::= { eventGroup01 60 }

	openBranchAlarm0161 NOTIFICATION-TYPE
	OBJECTS {	neName,
			eventGroupName,			-- 01
			eventName,			-- 61
			severity,
			eventType,
			eventTime,
			faultyObject,
			monitoredValue,
			thresholdValue,
			neType }
	STATUS		current
	DESCRIPTION	"Spontaneous Alarm from the managed network element."
	::= { eventGroup01 61 }

	openBranchAlarm0162 NOTIFICATION-TYPE
	OBJECTS {	neName,
			eventGroupName,			-- 01
			eventName,			-- 62
			severity,
			eventType,
			eventTime,
			faultyObject,
			monitoredValue,
			thresholdValue,
			neType }
	STATUS		current
	DESCRIPTION	"Spontaneous Alarm from the managed network element."
	::= { eventGroup01 62 }

	openBranchAlarm0163 NOTIFICATION-TYPE
	OBJECTS {	neName,
			eventGroupName,			-- 01
			eventName,			-- 63
			severity,
			eventType,
			eventTime,
			faultyObject,
			monitoredValue,
			thresholdValue,
			neType }
	STATUS		current
	DESCRIPTION	"Spontaneous Alarm from the managed network element."
	::= { eventGroup01 63 }

	openBranchAlarm0164 NOTIFICATION-TYPE
	OBJECTS {	neName,
			eventGroupName,			-- 01
			eventName,			-- 64
			severity,
			eventType,
			eventTime,
			faultyObject,
			monitoredValue,
			thresholdValue,
			neType }
	STATUS		current
	DESCRIPTION	"Spontaneous Alarm from the managed network element."
	::= { eventGroup01 64 }

	openBranchAlarm0165 NOTIFICATION-TYPE
	OBJECTS {	neName,
			eventGroupName,			-- 01
			eventName,			-- 65
			severity,
			eventType,
			eventTime,
			faultyObject,
			monitoredValue,
			thresholdValue,
			neType }
	STATUS		current
	DESCRIPTION	"Spontaneous Alarm from the managed network element."
	::= { eventGroup01 65 }

	openBranchAlarm0166 NOTIFICATION-TYPE
	OBJECTS {	neName,
			eventGroupName,			-- 01
			eventName,			-- 66
			severity,
			eventType,
			eventTime,
			faultyObject,
			monitoredValue,
			thresholdValue,
			neType }
	STATUS		current
	DESCRIPTION	"Spontaneous Alarm from the managed network element."
	::= { eventGroup01 66 }

	openBranchAlarm0167 NOTIFICATION-TYPE
	OBJECTS {	neName,
			eventGroupName,			-- 01
			eventName,			-- 67
			severity,
			eventType,
			eventTime,
			faultyObject,
			monitoredValue,
			thresholdValue,
			neType }
	STATUS		current
	DESCRIPTION	"Spontaneous Alarm from the managed network element."
	::= { eventGroup01 67 }

	openBranchAlarm0168 NOTIFICATION-TYPE
	OBJECTS {	neName,
			eventGroupName,			-- 01
			eventName,			-- 68
			severity,
			eventType,
			eventTime,
			faultyObject,
			monitoredValue,
			thresholdValue,
			neType }
	STATUS		current
	DESCRIPTION	"Spontaneous Alarm from the managed network element."
	::= { eventGroup01 68 }

	openBranchAlarm0169 NOTIFICATION-TYPE
	OBJECTS {	neName,
			eventGroupName,			-- 01
			eventName,			-- 69
			severity,
			eventType,
			eventTime,
			faultyObject,
			monitoredValue,
			thresholdValue,
			neType }
	STATUS		current
	DESCRIPTION	"Spontaneous Alarm from the managed network element."
	::= { eventGroup01 69 }

	openBranchAlarm0170 NOTIFICATION-TYPE
	OBJECTS {	neName,
			eventGroupName,			-- 01
			eventName,			-- 70
			severity,
			eventType,
			eventTime,
			faultyObject,
			monitoredValue,
			thresholdValue,
			neType }
	STATUS		current
	DESCRIPTION	"Spontaneous Alarm from the managed network element."
	::= { eventGroup01 70 }

	openBranchAlarm0171 NOTIFICATION-TYPE
	OBJECTS {	neName,
			eventGroupName,			-- 01
			eventName,			-- 71
			severity,
			eventType,
			eventTime,
			faultyObject,
			monitoredValue,
			thresholdValue,
			neType }
	STATUS		current
	DESCRIPTION	"Spontaneous Alarm from the managed network element."
	::= { eventGroup01 71 }

	openBranchAlarm0172 NOTIFICATION-TYPE
	OBJECTS {	neName,
			eventGroupName,			-- 01
			eventName,			-- 72
			severity,
			eventType,
			eventTime,
			faultyObject,
			monitoredValue,
			thresholdValue,
			neType }
	STATUS		current
	DESCRIPTION	"Spontaneous Alarm from the managed network element."
	::= { eventGroup01 72 }

	openBranchAlarm0173 NOTIFICATION-TYPE
	OBJECTS {	neName,
			eventGroupName,			-- 01
			eventName,			-- 73
			severity,
			eventType,
			eventTime,
			faultyObject,
			monitoredValue,
			thresholdValue,
			neType }
	STATUS		current
	DESCRIPTION	"Spontaneous Alarm from the managed network element."
	::= { eventGroup01 73 }

	openBranchAlarm0174 NOTIFICATION-TYPE
	OBJECTS {	neName,
			eventGroupName,			-- 01
			eventName,			-- 74
			severity,
			eventType,
			eventTime,
			faultyObject,
			monitoredValue,
			thresholdValue,
			neType }
	STATUS		current
	DESCRIPTION	"Spontaneous Alarm from the managed network element."
	::= { eventGroup01 74 }

	openBranchAlarm0175 NOTIFICATION-TYPE
	OBJECTS {	neName,
			eventGroupName,			-- 01
			eventName,			-- 75
			severity,
			eventType,
			eventTime,
			faultyObject,
			monitoredValue,
			thresholdValue,
			neType }
	STATUS		current
	DESCRIPTION	"Spontaneous Alarm from the managed network element."
	::= { eventGroup01 75 }

	openBranchAlarm0176 NOTIFICATION-TYPE
	OBJECTS {	neName,
			eventGroupName,			-- 01
			eventName,			-- 76
			severity,
			eventType,
			eventTime,
			faultyObject,
			monitoredValue,
			thresholdValue,
			neType }
	STATUS		current
	DESCRIPTION	"Spontaneous Alarm from the managed network element."
	::= { eventGroup01 76 }

	openBranchAlarm0177 NOTIFICATION-TYPE
	OBJECTS {	neName,
			eventGroupName,			-- 01
			eventName,			-- 77
			severity,
			eventType,
			eventTime,
			faultyObject,
			monitoredValue,
			thresholdValue,
			neType }
	STATUS		current
	DESCRIPTION	"Spontaneous Alarm from the managed network element."
	::= { eventGroup01 77 }

	openBranchAlarm0178 NOTIFICATION-TYPE
	OBJECTS {	neName,
			eventGroupName,			-- 01
			eventName,			-- 78
			severity,
			eventType,
			eventTime,
			faultyObject,
			monitoredValue,
			thresholdValue,
			neType }
	STATUS		current
	DESCRIPTION	"Spontaneous Alarm from the managed network element."
	::= { eventGroup01 78 }

	openBranchAlarm0179 NOTIFICATION-TYPE
	OBJECTS {	neName,
			eventGroupName,			-- 01
			eventName,			-- 79
			severity,
			eventType,
			eventTime,
			faultyObject,
			monitoredValue,
			thresholdValue,
			neType }
	STATUS		current
	DESCRIPTION	"Spontaneous Alarm from the managed network element."
	::= { eventGroup01 79 }

	openBranchAlarm0180 NOTIFICATION-TYPE
	OBJECTS {	neName,
			eventGroupName,			-- 01
			eventName,			-- 80
			severity,
			eventType,
			eventTime,
			faultyObject,
			monitoredValue,
			thresholdValue,
			neType }
	STATUS		current
	DESCRIPTION	"Spontaneous Alarm from the managed network element."
	::= { eventGroup01 80 }

	openBranchAlarm0181 NOTIFICATION-TYPE
	OBJECTS {	neName,
			eventGroupName,			-- 01
			eventName,			-- 81
			severity,
			eventType,
			eventTime,
			faultyObject,
			monitoredValue,
			thresholdValue,
			neType }
	STATUS		current
	DESCRIPTION	"Spontaneous Alarm from the managed network element."
	::= { eventGroup01 81 }

	openBranchAlarm0182 NOTIFICATION-TYPE
	OBJECTS {	neName,
			eventGroupName,			-- 01
			eventName,			-- 82
			severity,
			eventType,
			eventTime,
			faultyObject,
			monitoredValue,
			thresholdValue,
			neType }
	STATUS		current
	DESCRIPTION	"Spontaneous Alarm from the managed network element."
	::= { eventGroup01 82 }

	openBranchAlarm0183 NOTIFICATION-TYPE
	OBJECTS {	neName,
			eventGroupName,			-- 01
			eventName,			-- 83
			severity,
			eventType,
			eventTime,
			faultyObject,
			monitoredValue,
			thresholdValue,
			neType }
	STATUS		current
	DESCRIPTION	"Spontaneous Alarm from the managed network element."
	::= { eventGroup01 83 }

	openBranchAlarm0184 NOTIFICATION-TYPE
	OBJECTS {	neName,
			eventGroupName,			-- 01
			eventName,			-- 84
			severity,
			eventType,
			eventTime,
			faultyObject,
			monitoredValue,
			thresholdValue,
			neType }
	STATUS		current
	DESCRIPTION	"Spontaneous Alarm from the managed network element."
	::= { eventGroup01 84 }

	openBranchAlarm0185 NOTIFICATION-TYPE
	OBJECTS {	neName,
			eventGroupName,			-- 01
			eventName,			-- 85
			severity,
			eventType,
			eventTime,
			faultyObject,
			monitoredValue,
			thresholdValue,
			neType }
	STATUS		current
	DESCRIPTION	"Spontaneous Alarm from the managed network element."
	::= { eventGroup01 85 }

	openBranchAlarm0186 NOTIFICATION-TYPE
	OBJECTS {	neName,
			eventGroupName,			-- 01
			eventName,			-- 86
			severity,
			eventType,
			eventTime,
			faultyObject,
			monitoredValue,
			thresholdValue,
			neType }
	STATUS		current
	DESCRIPTION	"Spontaneous Alarm from the managed network element."
	::= { eventGroup01 86 }

	openBranchAlarm0187 NOTIFICATION-TYPE
	OBJECTS {	neName,
			eventGroupName,			-- 01
			eventName,			-- 87
			severity,
			eventType,
			eventTime,
			faultyObject,
			monitoredValue,
			thresholdValue,
			neType }
	STATUS		current
	DESCRIPTION	"Spontaneous Alarm from the managed network element."
	::= { eventGroup01 87 }

	openBranchAlarm0188 NOTIFICATION-TYPE
	OBJECTS {	neName,
			eventGroupName,			-- 01
			eventName,			-- 88
			severity,
			eventType,
			eventTime,
			faultyObject,
			monitoredValue,
			thresholdValue,
			neType }
	STATUS		current
	DESCRIPTION	"Spontaneous Alarm from the managed network element."
	::= { eventGroup01 88 }

	openBranchAlarm0189 NOTIFICATION-TYPE
	OBJECTS {	neName,
			eventGroupName,			-- 01
			eventName,			-- 89
			severity,
			eventType,
			eventTime,
			faultyObject,
			monitoredValue,
			thresholdValue,
			neType }
	STATUS		current
	DESCRIPTION	"Spontaneous Alarm from the managed network element."
	::= { eventGroup01 89 }

	openBranchAlarm0190 NOTIFICATION-TYPE
	OBJECTS {	neName,
			eventGroupName,			-- 01
			eventName,			-- 90
			severity,
			eventType,
			eventTime,
			faultyObject,
			monitoredValue,
			thresholdValue,
			neType }
	STATUS		current
	DESCRIPTION	"Spontaneous Alarm from the managed network element."
	::= { eventGroup01 90 }

	openBranchAlarm0191 NOTIFICATION-TYPE
	OBJECTS {	neName,
			eventGroupName,			-- 01
			eventName,			-- 91
			severity,
			eventType,
			eventTime,
			faultyObject,
			monitoredValue,
			thresholdValue,
			neType }
	STATUS		current
	DESCRIPTION	"Spontaneous Alarm from the managed network element."
	::= { eventGroup01 91 }

	openBranchAlarm0192 NOTIFICATION-TYPE
	OBJECTS {	neName,
			eventGroupName,			-- 01
			eventName,			-- 92
			severity,
			eventType,
			eventTime,
			faultyObject,
			monitoredValue,
			thresholdValue,
			neType }
	STATUS		current
	DESCRIPTION	"Spontaneous Alarm from the managed network element."
	::= { eventGroup01 92 }

	openBranchAlarm0193 NOTIFICATION-TYPE
	OBJECTS {	neName,
			eventGroupName,			-- 01
			eventName,			-- 93
			severity,
			eventType,
			eventTime,
			faultyObject,
			monitoredValue,
			thresholdValue,
			neType }
	STATUS		current
	DESCRIPTION	"Spontaneous Alarm from the managed network element."
	::= { eventGroup01 93 }

	openBranchAlarm0194 NOTIFICATION-TYPE
	OBJECTS {	neName,
			eventGroupName,			-- 01
			eventName,			-- 94
			severity,
			eventType,
			eventTime,
			faultyObject,
			monitoredValue,
			thresholdValue,
			neType }
	STATUS		current
	DESCRIPTION	"Spontaneous Alarm from the managed network element."
	::= { eventGroup01 94 }

	openBranchAlarm0195 NOTIFICATION-TYPE
	OBJECTS {	neName,
			eventGroupName,			-- 01
			eventName,			-- 95
			severity,
			eventType,
			eventTime,
			faultyObject,
			monitoredValue,
			thresholdValue,
			neType }
	STATUS		current
	DESCRIPTION	"Spontaneous Alarm from the managed network element."
	::= { eventGroup01 95 }

	openBranchAlarm0196 NOTIFICATION-TYPE
	OBJECTS {	neName,
			eventGroupName,			-- 01
			eventName,			-- 96
			severity,
			eventType,
			eventTime,
			faultyObject,
			monitoredValue,
			thresholdValue,
			neType }
	STATUS		current
	DESCRIPTION	"Spontaneous Alarm from the managed network element."
	::= { eventGroup01 96 }

	openBranchAlarm0197 NOTIFICATION-TYPE
	OBJECTS {	neName,
			eventGroupName,			-- 01
			eventName,			-- 97
			severity,
			eventType,
			eventTime,
			faultyObject,
			monitoredValue,
			thresholdValue,
			neType }
	STATUS		current
	DESCRIPTION	"Spontaneous Alarm from the managed network element."
	::= { eventGroup01 97 }

	openBranchAlarm0198 NOTIFICATION-TYPE
	OBJECTS {	neName,
			eventGroupName,			-- 01
			eventName,			-- 98
			severity,
			eventType,
			eventTime,
			faultyObject,
			monitoredValue,
			thresholdValue,
			neType }
	STATUS		current
	DESCRIPTION	"Spontaneous Alarm from the managed network element."
	::= { eventGroup01 98 }

	openBranchAlarm0199 NOTIFICATION-TYPE
	OBJECTS {	neName,
			eventGroupName,			-- 01
			eventName,			-- 99
			severity,
			eventType,
			eventTime,
			faultyObject,
			monitoredValue,
			thresholdValue,
			neType }
	STATUS		current
	DESCRIPTION	"Spontaneous Alarm from the managed network element."
	::= { eventGroup01 99 }

	openBranchAlarm01100 NOTIFICATION-TYPE
	OBJECTS {	neName,
			eventGroupName,			-- 01
			eventName,			-- 100
			severity,
			eventType,
			eventTime,
			faultyObject,
			monitoredValue,
			thresholdValue,
			neType }
	STATUS		current
	DESCRIPTION	"Spontaneous Alarm from the managed network element."
	::= { eventGroup01 100 }

	openBranchAlarm01101 NOTIFICATION-TYPE
	OBJECTS {	neName,
			eventGroupName,			-- 01
			eventName,			-- 101
			severity,
			eventType,
			eventTime,
			faultyObject,
			monitoredValue,
			thresholdValue,
			neType }
	STATUS		current
	DESCRIPTION	"Spontaneous Alarm from the managed network element."
	::= { eventGroup01 101 }

	openBranchAlarm01102 NOTIFICATION-TYPE
	OBJECTS {	neName,
			eventGroupName,			-- 01
			eventName,			-- 102
			severity,
			eventType,
			eventTime,
			faultyObject,
			monitoredValue,
			thresholdValue,
			neType }
	STATUS		current
	DESCRIPTION	"Spontaneous Alarm from the managed network element."
	::= { eventGroup01 102 }

	openBranchAlarm01103 NOTIFICATION-TYPE
	OBJECTS {	neName,
			eventGroupName,			-- 01
			eventName,			-- 103
			severity,
			eventType,
			eventTime,
			faultyObject,
			monitoredValue,
			thresholdValue,
			neType }
	STATUS		current
	DESCRIPTION	"Spontaneous Alarm from the managed network element."
	::= { eventGroup01 103 }

	openBranchAlarm01104 NOTIFICATION-TYPE
	OBJECTS {	neName,
			eventGroupName,			-- 01
			eventName,			-- 104
			severity,
			eventType,
			eventTime,
			faultyObject,
			monitoredValue,
			thresholdValue,
			neType }
	STATUS		current
	DESCRIPTION	"Spontaneous Alarm from the managed network element."
	::= { eventGroup01 104 }

	openBranchAlarm01105 NOTIFICATION-TYPE
	OBJECTS {	neName,
			eventGroupName,			-- 01
			eventName,			-- 105
			severity,
			eventType,
			eventTime,
			faultyObject,
			monitoredValue,
			thresholdValue,
			neType }
	STATUS		current
	DESCRIPTION	"Spontaneous Alarm from the managed network element."
	::= { eventGroup01 105 }

	openBranchAlarm01106 NOTIFICATION-TYPE
	OBJECTS {	neName,
			eventGroupName,			-- 01
			eventName,			-- 106
			severity,
			eventType,
			eventTime,
			faultyObject,
			monitoredValue,
			thresholdValue,
			neType }
	STATUS		current
	DESCRIPTION	"Spontaneous Alarm from the managed network element."
	::= { eventGroup01 106 }

	openBranchAlarm01107 NOTIFICATION-TYPE
	OBJECTS {	neName,
			eventGroupName,			-- 01
			eventName,			-- 107
			severity,
			eventType,
			eventTime,
			faultyObject,
			monitoredValue,
			thresholdValue,
			neType }
	STATUS		current
	DESCRIPTION	"Spontaneous Alarm from the managed network element."
	::= { eventGroup01 107 }

	openBranchAlarm01108 NOTIFICATION-TYPE
	OBJECTS {	neName,
			eventGroupName,			-- 01
			eventName,			-- 108
			severity,
			eventType,
			eventTime,
			faultyObject,
			monitoredValue,
			thresholdValue,
			neType }
	STATUS		current
	DESCRIPTION	"Spontaneous Alarm from the managed network element."
	::= { eventGroup01 108 }

	openBranchAlarm01109 NOTIFICATION-TYPE
	OBJECTS {	neName,
			eventGroupName,			-- 01
			eventName,			-- 109
			severity,
			eventType,
			eventTime,
			faultyObject,
			monitoredValue,
			thresholdValue,
			neType }
	STATUS		current
	DESCRIPTION	"Spontaneous Alarm from the managed network element."
	::= { eventGroup01 109 }

	openBranchAlarm01110 NOTIFICATION-TYPE
	OBJECTS {	neName,
			eventGroupName,			-- 01
			eventName,			-- 110
			severity,
			eventType,
			eventTime,
			faultyObject,
			monitoredValue,
			thresholdValue,
			neType }
	STATUS		current
	DESCRIPTION	"Spontaneous Alarm from the managed network element."
	::= { eventGroup01 110 }

	openBranchAlarm01111 NOTIFICATION-TYPE
	OBJECTS {	neName,
			eventGroupName,			-- 01
			eventName,			-- 111
			severity,
			eventType,
			eventTime,
			faultyObject,
			monitoredValue,
			thresholdValue,
			neType }
	STATUS		current
	DESCRIPTION	"Spontaneous Alarm from the managed network element."
	::= { eventGroup01 111 }

	openBranchAlarm01112 NOTIFICATION-TYPE
	OBJECTS {	neName,
			eventGroupName,			-- 01
			eventName,			-- 112
			severity,
			eventType,
			eventTime,
			faultyObject,
			monitoredValue,
			thresholdValue,
			neType }
	STATUS		current
	DESCRIPTION	"Spontaneous Alarm from the managed network element."
	::= { eventGroup01 112 }

	openBranchAlarm01113 NOTIFICATION-TYPE
	OBJECTS {	neName,
			eventGroupName,			-- 01
			eventName,			-- 113
			severity,
			eventType,
			eventTime,
			faultyObject,
			monitoredValue,
			thresholdValue,
			neType }
	STATUS		current
	DESCRIPTION	"Spontaneous Alarm from the managed network element."
	::= { eventGroup01 113 }

	openBranchAlarm01114 NOTIFICATION-TYPE
	OBJECTS {	neName,
			eventGroupName,			-- 01
			eventName,			-- 114
			severity,
			eventType,
			eventTime,
			faultyObject,
			monitoredValue,
			thresholdValue,
			neType }
	STATUS		current
	DESCRIPTION	"Spontaneous Alarm from the managed network element."
	::= { eventGroup01 114 }

	openBranchAlarm01115 NOTIFICATION-TYPE
	OBJECTS {	neName,
			eventGroupName,			-- 01
			eventName,			-- 115
			severity,
			eventType,
			eventTime,
			faultyObject,
			monitoredValue,
			thresholdValue,
			neType }
	STATUS		current
	DESCRIPTION	"Spontaneous Alarm from the managed network element."
	::= { eventGroup01 115 }

	openBranchAlarm01116 NOTIFICATION-TYPE
	OBJECTS {	neName,
			eventGroupName,			-- 01
			eventName,			-- 116
			severity,
			eventType,
			eventTime,
			faultyObject,
			monitoredValue,
			thresholdValue,
			neType }
	STATUS		current
	DESCRIPTION	"Spontaneous Alarm from the managed network element."
	::= { eventGroup01 116 }

	openBranchAlarm01117 NOTIFICATION-TYPE
	OBJECTS {	neName,
			eventGroupName,			-- 01
			eventName,			-- 117
			severity,
			eventType,
			eventTime,
			faultyObject,
			monitoredValue,
			thresholdValue,
			neType }
	STATUS		current
	DESCRIPTION	"Spontaneous Alarm from the managed network element."
	::= { eventGroup01 117 }

	openBranchAlarm01118 NOTIFICATION-TYPE
	OBJECTS {	neName,
			eventGroupName,			-- 01
			eventName,			-- 118
			severity,
			eventType,
			eventTime,
			faultyObject,
			monitoredValue,
			thresholdValue,
			neType }
	STATUS		current
	DESCRIPTION	"Spontaneous Alarm from the managed network element."
	::= { eventGroup01 118 }

	openBranchAlarm01119 NOTIFICATION-TYPE
	OBJECTS {	neName,
			eventGroupName,			-- 01
			eventName,			-- 119
			severity,
			eventType,
			eventTime,
			faultyObject,
			monitoredValue,
			thresholdValue,
			neType }
	STATUS		current
	DESCRIPTION	"Spontaneous Alarm from the managed network element."
	::= { eventGroup01 119 }

	openBranchAlarm01120 NOTIFICATION-TYPE
	OBJECTS {	neName,
			eventGroupName,			-- 01
			eventName,			-- 120
			severity,
			eventType,
			eventTime,
			faultyObject,
			monitoredValue,
			thresholdValue,
			neType }
	STATUS		current
	DESCRIPTION	"Spontaneous Alarm from the managed network element."
	::= { eventGroup01 120 }

	openBranchAlarm01121 NOTIFICATION-TYPE
	OBJECTS {	neName,
			eventGroupName,			-- 01
			eventName,			-- 121
			severity,
			eventType,
			eventTime,
			faultyObject,
			monitoredValue,
			thresholdValue,
			neType }
	STATUS		current
	DESCRIPTION	"Spontaneous Alarm from the managed network element."
	::= { eventGroup01 121 }

	openBranchAlarm01122 NOTIFICATION-TYPE
	OBJECTS {	neName,
			eventGroupName,			-- 01
			eventName,			-- 122
			severity,
			eventType,
			eventTime,
			faultyObject,
			monitoredValue,
			thresholdValue,
			neType }
	STATUS		current
	DESCRIPTION	"Spontaneous Alarm from the managed network element."
	::= { eventGroup01 122 }

	openBranchAlarm01123 NOTIFICATION-TYPE
	OBJECTS {	neName,
			eventGroupName,			-- 01
			eventName,			-- 123
			severity,
			eventType,
			eventTime,
			faultyObject,
			monitoredValue,
			thresholdValue,
			neType }
	STATUS		current
	DESCRIPTION	"Spontaneous Alarm from the managed network element."
	::= { eventGroup01 123 }

	openBranchAlarm01124 NOTIFICATION-TYPE
	OBJECTS {	neName,
			eventGroupName,			-- 01
			eventName,			-- 124
			severity,
			eventType,
			eventTime,
			faultyObject,
			monitoredValue,
			thresholdValue,
			neType }
	STATUS		current
	DESCRIPTION	"Spontaneous Alarm from the managed network element."
	::= { eventGroup01 124 }

	openBranchAlarm01125 NOTIFICATION-TYPE
	OBJECTS {	neName,
			eventGroupName,			-- 01
			eventName,			-- 125
			severity,
			eventType,
			eventTime,
			faultyObject,
			monitoredValue,
			thresholdValue,
			neType }
	STATUS		current
	DESCRIPTION	"Spontaneous Alarm from the managed network element."
	::= { eventGroup01 125 }

	openBranchAlarm01126 NOTIFICATION-TYPE
	OBJECTS {	neName,
			eventGroupName,			-- 01
			eventName,			-- 126
			severity,
			eventType,
			eventTime,
			faultyObject,
			monitoredValue,
			thresholdValue,
			neType }
	STATUS		current
	DESCRIPTION	"Spontaneous Alarm from the managed network element."
	::= { eventGroup01 126 }

	openBranchAlarm01127 NOTIFICATION-TYPE
	OBJECTS {	neName,
			eventGroupName,			-- 01
			eventName,			-- 127
			severity,
			eventType,
			eventTime,
			faultyObject,
			monitoredValue,
			thresholdValue,
			neType }
	STATUS		current
	DESCRIPTION	"Spontaneous Alarm from the managed network element."
	::= { eventGroup01 127 }

	openBranchAlarm01128 NOTIFICATION-TYPE
	OBJECTS {	neName,
			eventGroupName,			-- 01
			eventName,			-- 128
			severity,
			eventType,
			eventTime,
			faultyObject,
			monitoredValue,
			thresholdValue,
			neType }
	STATUS		current
	DESCRIPTION	"Spontaneous Alarm from the managed network element."
	::= { eventGroup01 128 }

	openBranchAlarm01129 NOTIFICATION-TYPE
	OBJECTS {	neName,
			eventGroupName,			-- 01
			eventName,			-- 129
			severity,
			eventType,
			eventTime,
			faultyObject,
			monitoredValue,
			thresholdValue,
			neType }
	STATUS		current
	DESCRIPTION	"Spontaneous Alarm from the managed network element."
	::= { eventGroup01 129 }

	openBranchAlarm01130 NOTIFICATION-TYPE
	OBJECTS {	neName,
			eventGroupName,			-- 01
			eventName,			-- 130
			severity,
			eventType,
			eventTime,
			faultyObject,
			monitoredValue,
			thresholdValue,
			neType }
	STATUS		current
	DESCRIPTION	"Spontaneous Alarm from the managed network element."
	::= { eventGroup01 130 }

	openBranchAlarm01131 NOTIFICATION-TYPE
	OBJECTS {	neName,
			eventGroupName,			-- 01
			eventName,			-- 131
			severity,
			eventType,
			eventTime,
			faultyObject,
			monitoredValue,
			thresholdValue,
			neType }
	STATUS		current
	DESCRIPTION	"Spontaneous Alarm from the managed network element."
	::= { eventGroup01 131 }

	openBranchAlarm01132 NOTIFICATION-TYPE
	OBJECTS {	neName,
			eventGroupName,			-- 01
			eventName,			-- 132
			severity,
			eventType,
			eventTime,
			faultyObject,
			monitoredValue,
			thresholdValue,
			neType }
	STATUS		current
	DESCRIPTION	"Spontaneous Alarm from the managed network element."
	::= { eventGroup01 132 }

	openBranchAlarm01133 NOTIFICATION-TYPE
	OBJECTS {	neName,
			eventGroupName,			-- 01
			eventName,			-- 133
			severity,
			eventType,
			eventTime,
			faultyObject,
			monitoredValue,
			thresholdValue,
			neType }
	STATUS		current
	DESCRIPTION	"Spontaneous Alarm from the managed network element."
	::= { eventGroup01 133 }

	openBranchAlarm01134 NOTIFICATION-TYPE
	OBJECTS {	neName,
			eventGroupName,			-- 01
			eventName,			-- 134
			severity,
			eventType,
			eventTime,
			faultyObject,
			monitoredValue,
			thresholdValue,
			neType }
	STATUS		current
	DESCRIPTION	"Spontaneous Alarm from the managed network element."
	::= { eventGroup01 134 }

	openBranchAlarm01135 NOTIFICATION-TYPE
	OBJECTS {	neName,
			eventGroupName,			-- 01
			eventName,			-- 135
			severity,
			eventType,
			eventTime,
			faultyObject,
			monitoredValue,
			thresholdValue,
			neType }
	STATUS		current
	DESCRIPTION	"Spontaneous Alarm from the managed network element."
	::= { eventGroup01 135 }

	openBranchAlarm01136 NOTIFICATION-TYPE
	OBJECTS {	neName,
			eventGroupName,			-- 01
			eventName,			-- 136
			severity,
			eventType,
			eventTime,
			faultyObject,
			monitoredValue,
			thresholdValue,
			neType }
	STATUS		current
	DESCRIPTION	"Spontaneous Alarm from the managed network element."
	::= { eventGroup01 136 }

	openBranchAlarm01137 NOTIFICATION-TYPE
	OBJECTS {	neName,
			eventGroupName,			-- 01
			eventName,			-- 137
			severity,
			eventType,
			eventTime,
			faultyObject,
			monitoredValue,
			thresholdValue,
			neType }
	STATUS		current
	DESCRIPTION	"Spontaneous Alarm from the managed network element."
	::= { eventGroup01 137 }

	openBranchAlarm01138 NOTIFICATION-TYPE
	OBJECTS {	neName,
			eventGroupName,			-- 01
			eventName,			-- 138
			severity,
			eventType,
			eventTime,
			faultyObject,
			monitoredValue,
			thresholdValue,
			neType }
	STATUS		current
	DESCRIPTION	"Spontaneous Alarm from the managed network element."
	::= { eventGroup01 138 }

	openBranchAlarm01139 NOTIFICATION-TYPE
	OBJECTS {	neName,
			eventGroupName,			-- 01
			eventName,			-- 139
			severity,
			eventType,
			eventTime,
			faultyObject,
			monitoredValue,
			thresholdValue,
			neType }
	STATUS		current
	DESCRIPTION	"Spontaneous Alarm from the managed network element."
	::= { eventGroup01 139 }

	openBranchAlarm01140 NOTIFICATION-TYPE
	OBJECTS {	neName,
			eventGroupName,			-- 01
			eventName,			-- 140
			severity,
			eventType,
			eventTime,
			faultyObject,
			monitoredValue,
			thresholdValue,
			neType }
	STATUS		current
	DESCRIPTION	"Spontaneous Alarm from the managed network element."
	::= { eventGroup01 140 }

	openBranchAlarm01141 NOTIFICATION-TYPE
	OBJECTS {	neName,
			eventGroupName,			-- 01
			eventName,			-- 141
			severity,
			eventType,
			eventTime,
			faultyObject,
			monitoredValue,
			thresholdValue,
			neType }
	STATUS		current
	DESCRIPTION	"Spontaneous Alarm from the managed network element."
	::= { eventGroup01 141 }

	openBranchAlarm01142 NOTIFICATION-TYPE
	OBJECTS {	neName,
			eventGroupName,			-- 01
			eventName,			-- 142
			severity,
			eventType,
			eventTime,
			faultyObject,
			monitoredValue,
			thresholdValue,
			neType }
	STATUS		current
	DESCRIPTION	"Spontaneous Alarm from the managed network element."
	::= { eventGroup01 142 }

	openBranchAlarm01143 NOTIFICATION-TYPE
	OBJECTS {	neName,
			eventGroupName,			-- 01
			eventName,			-- 143
			severity,
			eventType,
			eventTime,
			faultyObject,
			monitoredValue,
			thresholdValue,
			neType }
	STATUS		current
	DESCRIPTION	"Spontaneous Alarm from the managed network element."
	::= { eventGroup01 143 }

	openBranchAlarm01144 NOTIFICATION-TYPE
	OBJECTS {	neName,
			eventGroupName,			-- 01
			eventName,			-- 144
			severity,
			eventType,
			eventTime,
			faultyObject,
			monitoredValue,
			thresholdValue,
			neType }
	STATUS		current
	DESCRIPTION	"Spontaneous Alarm from the managed network element."
	::= { eventGroup01 144 }

	openBranchAlarm01145 NOTIFICATION-TYPE
	OBJECTS {	neName,
			eventGroupName,			-- 01
			eventName,			-- 145
			severity,
			eventType,
			eventTime,
			faultyObject,
			monitoredValue,
			thresholdValue,
			neType }
	STATUS		current
	DESCRIPTION	"Spontaneous Alarm from the managed network element."
	::= { eventGroup01 145 }

	openBranchAlarm01146 NOTIFICATION-TYPE
	OBJECTS {	neName,
			eventGroupName,			-- 01
			eventName,			-- 146
			severity,
			eventType,
			eventTime,
			faultyObject,
			monitoredValue,
			thresholdValue,
			neType }
	STATUS		current
	DESCRIPTION	"Spontaneous Alarm from the managed network element."
	::= { eventGroup01 146 }

	openBranchAlarm01147 NOTIFICATION-TYPE
	OBJECTS {	neName,
			eventGroupName,			-- 01
			eventName,			-- 147
			severity,
			eventType,
			eventTime,
			faultyObject,
			monitoredValue,
			thresholdValue,
			neType }
	STATUS		current
	DESCRIPTION	"Spontaneous Alarm from the managed network element."
	::= { eventGroup01 147 }

	openBranchAlarm01148 NOTIFICATION-TYPE
	OBJECTS {	neName,
			eventGroupName,			-- 01
			eventName,			-- 148
			severity,
			eventType,
			eventTime,
			faultyObject,
			monitoredValue,
			thresholdValue,
			neType }
	STATUS		current
	DESCRIPTION	"Spontaneous Alarm from the managed network element."
	::= { eventGroup01 148 }

	openBranchAlarm01149 NOTIFICATION-TYPE
	OBJECTS {	neName,
			eventGroupName,			-- 01
			eventName,			-- 149
			severity,
			eventType,
			eventTime,
			faultyObject,
			monitoredValue,
			thresholdValue,
			neType }
	STATUS		current
	DESCRIPTION	"Spontaneous Alarm from the managed network element."
	::= { eventGroup01 149 }

	openBranchAlarm01150 NOTIFICATION-TYPE
	OBJECTS {	neName,
			eventGroupName,			-- 01
			eventName,			-- 150
			severity,
			eventType,
			eventTime,
			faultyObject,
			monitoredValue,
			thresholdValue,
			neType }
	STATUS		current
	DESCRIPTION	"Spontaneous Alarm from the managed network element."
	::= { eventGroup01 150 }

	openBranchAlarm01151 NOTIFICATION-TYPE
	OBJECTS {	neName,
			eventGroupName,			-- 01
			eventName,			-- 151
			severity,
			eventType,
			eventTime,
			faultyObject,
			monitoredValue,
			thresholdValue,
			neType }
	STATUS		current
	DESCRIPTION	"Spontaneous Alarm from the managed network element."
	::= { eventGroup01 151 }

	openBranchAlarm01152 NOTIFICATION-TYPE
	OBJECTS {	neName,
			eventGroupName,			-- 01
			eventName,			-- 152
			severity,
			eventType,
			eventTime,
			faultyObject,
			monitoredValue,
			thresholdValue,
			neType }
	STATUS		current
	DESCRIPTION	"Spontaneous Alarm from the managed network element."
	::= { eventGroup01 152 }

	openBranchAlarm01153 NOTIFICATION-TYPE
	OBJECTS {	neName,
			eventGroupName,			-- 01
			eventName,			-- 153
			severity,
			eventType,
			eventTime,
			faultyObject,
			monitoredValue,
			thresholdValue,
			neType }
	STATUS		current
	DESCRIPTION	"Spontaneous Alarm from the managed network element."
	::= { eventGroup01 153 }

	openBranchAlarm01154 NOTIFICATION-TYPE
	OBJECTS {	neName,
			eventGroupName,			-- 01
			eventName,			-- 154
			severity,
			eventType,
			eventTime,
			faultyObject,
			monitoredValue,
			thresholdValue,
			neType }
	STATUS		current
	DESCRIPTION	"Spontaneous Alarm from the managed network element."
	::= { eventGroup01 154 }

	openBranchAlarm01155 NOTIFICATION-TYPE
	OBJECTS {	neName,
			eventGroupName,			-- 01
			eventName,			-- 155
			severity,
			eventType,
			eventTime,
			faultyObject,
			monitoredValue,
			thresholdValue,
			neType }
	STATUS		current
	DESCRIPTION	"Spontaneous Alarm from the managed network element."
	::= { eventGroup01 155 }

	openBranchAlarm01156 NOTIFICATION-TYPE
	OBJECTS {	neName,
			eventGroupName,			-- 01
			eventName,			-- 156
			severity,
			eventType,
			eventTime,
			faultyObject,
			monitoredValue,
			thresholdValue,
			neType }
	STATUS		current
	DESCRIPTION	"Spontaneous Alarm from the managed network element."
	::= { eventGroup01 156 }

	openBranchAlarm01157 NOTIFICATION-TYPE
	OBJECTS {	neName,
			eventGroupName,			-- 01
			eventName,			-- 157
			severity,
			eventType,
			eventTime,
			faultyObject,
			monitoredValue,
			thresholdValue,
			neType }
	STATUS		current
	DESCRIPTION	"Spontaneous Alarm from the managed network element."
	::= { eventGroup01 157 }

	openBranchAlarm01158 NOTIFICATION-TYPE
	OBJECTS {	neName,
			eventGroupName,			-- 01
			eventName,			-- 158
			severity,
			eventType,
			eventTime,
			faultyObject,
			monitoredValue,
			thresholdValue,
			neType }
	STATUS		current
	DESCRIPTION	"Spontaneous Alarm from the managed network element."
	::= { eventGroup01 158 }

	openBranchAlarm01159 NOTIFICATION-TYPE
	OBJECTS {	neName,
			eventGroupName,			-- 01
			eventName,			-- 159
			severity,
			eventType,
			eventTime,
			faultyObject,
			monitoredValue,
			thresholdValue,
			neType }
	STATUS		current
	DESCRIPTION	"Spontaneous Alarm from the managed network element."
	::= { eventGroup01 159 }

	openBranchAlarm01160 NOTIFICATION-TYPE
	OBJECTS {	neName,
			eventGroupName,			-- 01
			eventName,			-- 160
			severity,
			eventType,
			eventTime,
			faultyObject,
			monitoredValue,
			thresholdValue,
			neType }
	STATUS		current
	DESCRIPTION	"Spontaneous Alarm from the managed network element."
	::= { eventGroup01 160 }

	openBranchAlarm01161 NOTIFICATION-TYPE
	OBJECTS {	neName,
			eventGroupName,			-- 01
			eventName,			-- 161
			severity,
			eventType,
			eventTime,
			faultyObject,
			monitoredValue,
			thresholdValue,
			neType }
	STATUS		current
	DESCRIPTION	"Spontaneous Alarm from the managed network element."
	::= { eventGroup01 161 }

	openBranchAlarm01162 NOTIFICATION-TYPE
	OBJECTS {	neName,
			eventGroupName,			-- 01
			eventName,			-- 162
			severity,
			eventType,
			eventTime,
			faultyObject,
			monitoredValue,
			thresholdValue,
			neType }
	STATUS		current
	DESCRIPTION	"Spontaneous Alarm from the managed network element."
	::= { eventGroup01 162 }

	openBranchAlarm01163 NOTIFICATION-TYPE
	OBJECTS {	neName,
			eventGroupName,			-- 01
			eventName,			-- 163
			severity,
			eventType,
			eventTime,
			faultyObject,
			monitoredValue,
			thresholdValue,
			neType }
	STATUS		current
	DESCRIPTION	"Spontaneous Alarm from the managed network element."
	::= { eventGroup01 163 }

	openBranchAlarm01164 NOTIFICATION-TYPE
	OBJECTS {	neName,
			eventGroupName,			-- 01
			eventName,			-- 164
			severity,
			eventType,
			eventTime,
			faultyObject,
			monitoredValue,
			thresholdValue,
			neType }
	STATUS		current
	DESCRIPTION	"Spontaneous Alarm from the managed network element."
	::= { eventGroup01 164 }

	openBranchAlarm01165 NOTIFICATION-TYPE
	OBJECTS {	neName,
			eventGroupName,			-- 01
			eventName,			-- 165
			severity,
			eventType,
			eventTime,
			faultyObject,
			monitoredValue,
			thresholdValue,
			neType }
	STATUS		current
	DESCRIPTION	"Spontaneous Alarm from the managed network element."
	::= { eventGroup01 165 }

	openBranchAlarm01166 NOTIFICATION-TYPE
	OBJECTS {	neName,
			eventGroupName,			-- 01
			eventName,			-- 166
			severity,
			eventType,
			eventTime,
			faultyObject,
			monitoredValue,
			thresholdValue,
			neType }
	STATUS		current
	DESCRIPTION	"Spontaneous Alarm from the managed network element."
	::= { eventGroup01 166 }

	openBranchAlarm01167 NOTIFICATION-TYPE
	OBJECTS {	neName,
			eventGroupName,			-- 01
			eventName,			-- 167
			severity,
			eventType,
			eventTime,
			faultyObject,
			monitoredValue,
			thresholdValue,
			neType }
	STATUS		current
	DESCRIPTION	"Spontaneous Alarm from the managed network element."
	::= { eventGroup01 167 }

	openBranchAlarm01168 NOTIFICATION-TYPE
	OBJECTS {	neName,
			eventGroupName,			-- 01
			eventName,			-- 168
			severity,
			eventType,
			eventTime,
			faultyObject,
			monitoredValue,
			thresholdValue,
			neType }
	STATUS		current
	DESCRIPTION	"Spontaneous Alarm from the managed network element."
	::= { eventGroup01 168 }

	openBranchAlarm01169 NOTIFICATION-TYPE
	OBJECTS {	neName,
			eventGroupName,			-- 01
			eventName,			-- 169
			severity,
			eventType,
			eventTime,
			faultyObject,
			monitoredValue,
			thresholdValue,
			neType }
	STATUS		current
	DESCRIPTION	"Spontaneous Alarm from the managed network element."
	::= { eventGroup01 169 }

	openBranchAlarm01170 NOTIFICATION-TYPE
	OBJECTS {	neName,
			eventGroupName,			-- 01
			eventName,			-- 170
			severity,
			eventType,
			eventTime,
			faultyObject,
			monitoredValue,
			thresholdValue,
			neType }
	STATUS		current
	DESCRIPTION	"Spontaneous Alarm from the managed network element."
	::= { eventGroup01 170 }

	openBranchAlarm01171 NOTIFICATION-TYPE
	OBJECTS {	neName,
			eventGroupName,			-- 01
			eventName,			-- 171
			severity,
			eventType,
			eventTime,
			faultyObject,
			monitoredValue,
			thresholdValue,
			neType }
	STATUS		current
	DESCRIPTION	"Spontaneous Alarm from the managed network element."
	::= { eventGroup01 171 }

	openBranchAlarm01172 NOTIFICATION-TYPE
	OBJECTS {	neName,
			eventGroupName,			-- 01
			eventName,			-- 172
			severity,
			eventType,
			eventTime,
			faultyObject,
			monitoredValue,
			thresholdValue,
			neType }
	STATUS		current
	DESCRIPTION	"Spontaneous Alarm from the managed network element."
	::= { eventGroup01 172 }

	openBranchAlarm01173 NOTIFICATION-TYPE
	OBJECTS {	neName,
			eventGroupName,			-- 01
			eventName,			-- 173
			severity,
			eventType,
			eventTime,
			faultyObject,
			monitoredValue,
			thresholdValue,
			neType }
	STATUS		current
	DESCRIPTION	"Spontaneous Alarm from the managed network element."
	::= { eventGroup01 173 }

	openBranchAlarm01174 NOTIFICATION-TYPE
	OBJECTS {	neName,
			eventGroupName,			-- 01
			eventName,			-- 174
			severity,
			eventType,
			eventTime,
			faultyObject,
			monitoredValue,
			thresholdValue,
			neType }
	STATUS		current
	DESCRIPTION	"Spontaneous Alarm from the managed network element."
	::= { eventGroup01 174 }

	openBranchAlarm01175 NOTIFICATION-TYPE
	OBJECTS {	neName,
			eventGroupName,			-- 01
			eventName,			-- 175
			severity,
			eventType,
			eventTime,
			faultyObject,
			monitoredValue,
			thresholdValue,
			neType }
	STATUS		current
	DESCRIPTION	"Spontaneous Alarm from the managed network element."
	::= { eventGroup01 175 }

	openBranchAlarm01176 NOTIFICATION-TYPE
	OBJECTS {	neName,
			eventGroupName,			-- 01
			eventName,			-- 176
			severity,
			eventType,
			eventTime,
			faultyObject,
			monitoredValue,
			thresholdValue,
			neType }
	STATUS		current
	DESCRIPTION	"Spontaneous Alarm from the managed network element."
	::= { eventGroup01 176 }

	openBranchAlarm01177 NOTIFICATION-TYPE
	OBJECTS {	neName,
			eventGroupName,			-- 01
			eventName,			-- 177
			severity,
			eventType,
			eventTime,
			faultyObject,
			monitoredValue,
			thresholdValue,
			neType }
	STATUS		current
	DESCRIPTION	"Spontaneous Alarm from the managed network element."
	::= { eventGroup01 177 }

	openBranchAlarm01178 NOTIFICATION-TYPE
	OBJECTS {	neName,
			eventGroupName,			-- 01
			eventName,			-- 178
			severity,
			eventType,
			eventTime,
			faultyObject,
			monitoredValue,
			thresholdValue,
			neType }
	STATUS		current
	DESCRIPTION	"Spontaneous Alarm from the managed network element."
	::= { eventGroup01 178 }

	openBranchAlarm01179 NOTIFICATION-TYPE
	OBJECTS {	neName,
			eventGroupName,			-- 01
			eventName,			-- 179
			severity,
			eventType,
			eventTime,
			faultyObject,
			monitoredValue,
			thresholdValue,
			neType }
	STATUS		current
	DESCRIPTION	"Spontaneous Alarm from the managed network element."
	::= { eventGroup01 179 }

	openBranchAlarm01180 NOTIFICATION-TYPE
	OBJECTS {	neName,
			eventGroupName,			-- 01
			eventName,			-- 180
			severity,
			eventType,
			eventTime,
			faultyObject,
			monitoredValue,
			thresholdValue,
			neType }
	STATUS		current
	DESCRIPTION	"Spontaneous Alarm from the managed network element."
	::= { eventGroup01 180 }

	openBranchAlarm01181 NOTIFICATION-TYPE
	OBJECTS {	neName,
			eventGroupName,			-- 01
			eventName,			-- 181
			severity,
			eventType,
			eventTime,
			faultyObject,
			monitoredValue,
			thresholdValue,
			neType }
	STATUS		current
	DESCRIPTION	"Spontaneous Alarm from the managed network element."
	::= { eventGroup01 181 }

	openBranchAlarm01182 NOTIFICATION-TYPE
	OBJECTS {	neName,
			eventGroupName,			-- 01
			eventName,			-- 182
			severity,
			eventType,
			eventTime,
			faultyObject,
			monitoredValue,
			thresholdValue,
			neType }
	STATUS		current
	DESCRIPTION	"Spontaneous Alarm from the managed network element."
	::= { eventGroup01 182 }

	openBranchAlarm01183 NOTIFICATION-TYPE
	OBJECTS {	neName,
			eventGroupName,			-- 01
			eventName,			-- 183
			severity,
			eventType,
			eventTime,
			faultyObject,
			monitoredValue,
			thresholdValue,
			neType }
	STATUS		current
	DESCRIPTION	"Spontaneous Alarm from the managed network element."
	::= { eventGroup01 183 }

	openBranchAlarm01184 NOTIFICATION-TYPE
	OBJECTS {	neName,
			eventGroupName,			-- 01
			eventName,			-- 184
			severity,
			eventType,
			eventTime,
			faultyObject,
			monitoredValue,
			thresholdValue,
			neType }
	STATUS		current
	DESCRIPTION	"Spontaneous Alarm from the managed network element."
	::= { eventGroup01 184 }

	openBranchAlarm01185 NOTIFICATION-TYPE
	OBJECTS {	neName,
			eventGroupName,			-- 01
			eventName,			-- 185
			severity,
			eventType,
			eventTime,
			faultyObject,
			monitoredValue,
			thresholdValue,
			neType }
	STATUS		current
	DESCRIPTION	"Spontaneous Alarm from the managed network element."
	::= { eventGroup01 185 }

	openBranchAlarm01186 NOTIFICATION-TYPE
	OBJECTS {	neName,
			eventGroupName,			-- 01
			eventName,			-- 186
			severity,
			eventType,
			eventTime,
			faultyObject,
			monitoredValue,
			thresholdValue,
			neType }
	STATUS		current
	DESCRIPTION	"Spontaneous Alarm from the managed network element."
	::= { eventGroup01 186 }

	openBranchAlarm01187 NOTIFICATION-TYPE
	OBJECTS {	neName,
			eventGroupName,			-- 01
			eventName,			-- 187
			severity,
			eventType,
			eventTime,
			faultyObject,
			monitoredValue,
			thresholdValue,
			neType }
	STATUS		current
	DESCRIPTION	"Spontaneous Alarm from the managed network element."
	::= { eventGroup01 187 }

	openBranchAlarm01188 NOTIFICATION-TYPE
	OBJECTS {	neName,
			eventGroupName,			-- 01
			eventName,			-- 188
			severity,
			eventType,
			eventTime,
			faultyObject,
			monitoredValue,
			thresholdValue,
			neType }
	STATUS		current
	DESCRIPTION	"Spontaneous Alarm from the managed network element."
	::= { eventGroup01 188 }

	openBranchAlarm01189 NOTIFICATION-TYPE
	OBJECTS {	neName,
			eventGroupName,			-- 01
			eventName,			-- 189
			severity,
			eventType,
			eventTime,
			faultyObject,
			monitoredValue,
			thresholdValue,
			neType }
	STATUS		current
	DESCRIPTION	"Spontaneous Alarm from the managed network element."
	::= { eventGroup01 189 }

	openBranchAlarm01190 NOTIFICATION-TYPE
	OBJECTS {	neName,
			eventGroupName,			-- 01
			eventName,			-- 190
			severity,
			eventType,
			eventTime,
			faultyObject,
			monitoredValue,
			thresholdValue,
			neType }
	STATUS		current
	DESCRIPTION	"Spontaneous Alarm from the managed network element."
	::= { eventGroup01 190 }

	openBranchAlarm01191 NOTIFICATION-TYPE
	OBJECTS {	neName,
			eventGroupName,			-- 01
			eventName,			-- 191
			severity,
			eventType,
			eventTime,
			faultyObject,
			monitoredValue,
			thresholdValue,
			neType }
	STATUS		current
	DESCRIPTION	"Spontaneous Alarm from the managed network element."
	::= { eventGroup01 191 }

	openBranchAlarm01192 NOTIFICATION-TYPE
	OBJECTS {	neName,
			eventGroupName,			-- 01
			eventName,			-- 192
			severity,
			eventType,
			eventTime,
			faultyObject,
			monitoredValue,
			thresholdValue,
			neType }
	STATUS		current
	DESCRIPTION	"Spontaneous Alarm from the managed network element."
	::= { eventGroup01 192 }


	--********************************************************************
	-- Alarm Trap Definitions for event group 02
	--********************************************************************


	openBranchAlarm0201 NOTIFICATION-TYPE
	OBJECTS {	neName,
			eventGroupName,			-- 02
			eventName,			-- 01
			severity,
			eventType,
			eventTime,
			faultyObject,
			monitoredValue,
			thresholdValue,
			neType }
	STATUS		current
	DESCRIPTION	"Spontaneous Alarm from the managed network element."
	::= { eventGroup02 1 }

	openBranchAlarm0202 NOTIFICATION-TYPE
	OBJECTS {	neName,
			eventGroupName,			-- 02
			eventName,			-- 02
			severity,
			eventType,
			eventTime,
			faultyObject,
			monitoredValue,
			thresholdValue,
			neType }
	STATUS		current
	DESCRIPTION	"Spontaneous Alarm from the managed network element."
	::= { eventGroup02 2 }

	openBranchAlarm0203 NOTIFICATION-TYPE
	OBJECTS {	neName,
			eventGroupName,			-- 02
			eventName,			-- 03
			severity,
			eventType,
			eventTime,
			faultyObject,
			monitoredValue,
			thresholdValue,
			neType }
	STATUS		current
	DESCRIPTION	"Spontaneous Alarm from the managed network element."
	::= { eventGroup02 3 }

	openBranchAlarm0204 NOTIFICATION-TYPE
	OBJECTS {	neName,
			eventGroupName,			-- 02
			eventName,			-- 04
			severity,
			eventType,
			eventTime,
			faultyObject,
			monitoredValue,
			thresholdValue,
			neType }
	STATUS		current
	DESCRIPTION	"Spontaneous Alarm from the managed network element."
	::= { eventGroup02 4 }

	openBranchAlarm0205 NOTIFICATION-TYPE
	OBJECTS {	neName,
			eventGroupName,			-- 02
			eventName,			-- 05
			severity,
			eventType,
			eventTime,
			faultyObject,
			monitoredValue,
			thresholdValue,
			neType }
	STATUS		current
	DESCRIPTION	"Spontaneous Alarm from the managed network element."
	::= { eventGroup02 5 }

	openBranchAlarm0206 NOTIFICATION-TYPE
	OBJECTS {	neName,
			eventGroupName,			-- 02
			eventName,			-- 06
			severity,
			eventType,
			eventTime,
			faultyObject,
			monitoredValue,
			thresholdValue,
			neType }
	STATUS		current
	DESCRIPTION	"Spontaneous Alarm from the managed network element."
	::= { eventGroup02 6 }

	openBranchAlarm0207 NOTIFICATION-TYPE
	OBJECTS {	neName,
			eventGroupName,			-- 02
			eventName,			-- 07
			severity,
			eventType,
			eventTime,
			faultyObject,
			monitoredValue,
			thresholdValue,
			neType }
	STATUS		current
	DESCRIPTION	"Spontaneous Alarm from the managed network element."
	::= { eventGroup02 7 }

	openBranchAlarm0208 NOTIFICATION-TYPE
	OBJECTS {	neName,
			eventGroupName,			-- 02
			eventName,			-- 08
			severity,
			eventType,
			eventTime,
			faultyObject,
			monitoredValue,
			thresholdValue,
			neType }
	STATUS		current
	DESCRIPTION	"Spontaneous Alarm from the managed network element."
	::= { eventGroup02 8 }

	openBranchAlarm0209 NOTIFICATION-TYPE
	OBJECTS {	neName,
			eventGroupName,			-- 02
			eventName,			-- 09
			severity,
			eventType,
			eventTime,
			faultyObject,
			monitoredValue,
			thresholdValue,
			neType }
	STATUS		current
	DESCRIPTION	"Spontaneous Alarm from the managed network element."
	::= { eventGroup02 9 }

	openBranchAlarm0210 NOTIFICATION-TYPE
	OBJECTS {	neName,
			eventGroupName,			-- 02
			eventName,			-- 10
			severity,
			eventType,
			eventTime,
			faultyObject,
			monitoredValue,
			thresholdValue,
			neType }
	STATUS		current
	DESCRIPTION	"Spontaneous Alarm from the managed network element."
	::= { eventGroup02 10 }

	openBranchAlarm0211 NOTIFICATION-TYPE
	OBJECTS {	neName,
			eventGroupName,			-- 02
			eventName,			-- 11
			severity,
			eventType,
			eventTime,
			faultyObject,
			monitoredValue,
			thresholdValue,
			neType }
	STATUS		current
	DESCRIPTION	"Spontaneous Alarm from the managed network element."
	::= { eventGroup02 11 }

	openBranchAlarm0212 NOTIFICATION-TYPE
	OBJECTS {	neName,
			eventGroupName,			-- 02
			eventName,			-- 12
			severity,
			eventType,
			eventTime,
			faultyObject,
			monitoredValue,
			thresholdValue,
			neType }
	STATUS		current
	DESCRIPTION	"Spontaneous Alarm from the managed network element."
	::= { eventGroup02 12 }

	openBranchAlarm0213 NOTIFICATION-TYPE
	OBJECTS {	neName,
			eventGroupName,			-- 02
			eventName,			-- 13
			severity,
			eventType,
			eventTime,
			faultyObject,
			monitoredValue,
			thresholdValue,
			neType }
	STATUS		current
	DESCRIPTION	"Spontaneous Alarm from the managed network element."
	::= { eventGroup02 13 }

	openBranchAlarm0214 NOTIFICATION-TYPE
	OBJECTS {	neName,
			eventGroupName,			-- 02
			eventName,			-- 14
			severity,
			eventType,
			eventTime,
			faultyObject,
			monitoredValue,
			thresholdValue,
			neType }
	STATUS		current
	DESCRIPTION	"Spontaneous Alarm from the managed network element."
	::= { eventGroup02 14 }

	openBranchAlarm0215 NOTIFICATION-TYPE
	OBJECTS {	neName,
			eventGroupName,			-- 02
			eventName,			-- 15
			severity,
			eventType,
			eventTime,
			faultyObject,
			monitoredValue,
			thresholdValue,
			neType }
	STATUS		current
	DESCRIPTION	"Spontaneous Alarm from the managed network element."
	::= { eventGroup02 15 }

	openBranchAlarm0216 NOTIFICATION-TYPE
	OBJECTS {	neName,
			eventGroupName,			-- 02
			eventName,			-- 16
			severity,
			eventType,
			eventTime,
			faultyObject,
			monitoredValue,
			thresholdValue,
			neType }
	STATUS		current
	DESCRIPTION	"Spontaneous Alarm from the managed network element."
	::= { eventGroup02 16 }

	openBranchAlarm0217 NOTIFICATION-TYPE
	OBJECTS {	neName,
			eventGroupName,			-- 02
			eventName,			-- 17
			severity,
			eventType,
			eventTime,
			faultyObject,
			monitoredValue,
			thresholdValue,
			neType }
	STATUS		current
	DESCRIPTION	"Spontaneous Alarm from the managed network element."
	::= { eventGroup02 17 }

	openBranchAlarm0218 NOTIFICATION-TYPE
	OBJECTS {	neName,
			eventGroupName,			-- 02
			eventName,			-- 18
			severity,
			eventType,
			eventTime,
			faultyObject,
			monitoredValue,
			thresholdValue,
			neType }
	STATUS		current
	DESCRIPTION	"Spontaneous Alarm from the managed network element."
	::= { eventGroup02 18 }

	openBranchAlarm0219 NOTIFICATION-TYPE
	OBJECTS {	neName,
			eventGroupName,			-- 02
			eventName,			-- 19
			severity,
			eventType,
			eventTime,
			faultyObject,
			monitoredValue,
			thresholdValue,
			neType }
	STATUS		current
	DESCRIPTION	"Spontaneous Alarm from the managed network element."
	::= { eventGroup02 19 }

	openBranchAlarm0220 NOTIFICATION-TYPE
	OBJECTS {	neName,
			eventGroupName,			-- 02
			eventName,			-- 20
			severity,
			eventType,
			eventTime,
			faultyObject,
			monitoredValue,
			thresholdValue,
			neType }
	STATUS		current
	DESCRIPTION	"Spontaneous Alarm from the managed network element."
	::= { eventGroup02 20 }

	openBranchAlarm0221 NOTIFICATION-TYPE
	OBJECTS {	neName,
			eventGroupName,			-- 02
			eventName,			-- 21
			severity,
			eventType,
			eventTime,
			faultyObject,
			monitoredValue,
			thresholdValue,
			neType }
	STATUS		current
	DESCRIPTION	"Spontaneous Alarm from the managed network element."
	::= { eventGroup02 21 }

	openBranchAlarm0222 NOTIFICATION-TYPE
	OBJECTS {	neName,
			eventGroupName,			-- 02
			eventName,			-- 22
			severity,
			eventType,
			eventTime,
			faultyObject,
			monitoredValue,
			thresholdValue,
			neType }
	STATUS		current
	DESCRIPTION	"Spontaneous Alarm from the managed network element."
	::= { eventGroup02 22 }

	openBranchAlarm0223 NOTIFICATION-TYPE
	OBJECTS {	neName,
			eventGroupName,			-- 02
			eventName,			-- 23
			severity,
			eventType,
			eventTime,
			faultyObject,
			monitoredValue,
			thresholdValue,
			neType }
	STATUS		current
	DESCRIPTION	"Spontaneous Alarm from the managed network element."
	::= { eventGroup02 23 }

	openBranchAlarm0224 NOTIFICATION-TYPE
	OBJECTS {	neName,
			eventGroupName,			-- 02
			eventName,			-- 24
			severity,
			eventType,
			eventTime,
			faultyObject,
			monitoredValue,
			thresholdValue,
			neType }
	STATUS		current
	DESCRIPTION	"Spontaneous Alarm from the managed network element."
	::= { eventGroup02 24 }

	openBranchAlarm0225 NOTIFICATION-TYPE
	OBJECTS {	neName,
			eventGroupName,			-- 02
			eventName,			-- 25
			severity,
			eventType,
			eventTime,
			faultyObject,
			monitoredValue,
			thresholdValue,
			neType }
	STATUS		current
	DESCRIPTION	"Spontaneous Alarm from the managed network element."
	::= { eventGroup02 25 }

	openBranchAlarm0226 NOTIFICATION-TYPE
	OBJECTS {	neName,
			eventGroupName,			-- 02
			eventName,			-- 26
			severity,
			eventType,
			eventTime,
			faultyObject,
			monitoredValue,
			thresholdValue,
			neType }
	STATUS		current
	DESCRIPTION	"Spontaneous Alarm from the managed network element."
	::= { eventGroup02 26 }

	openBranchAlarm0227 NOTIFICATION-TYPE
	OBJECTS {	neName,
			eventGroupName,			-- 02
			eventName,			-- 27
			severity,
			eventType,
			eventTime,
			faultyObject,
			monitoredValue,
			thresholdValue,
			neType }
	STATUS		current
	DESCRIPTION	"Spontaneous Alarm from the managed network element."
	::= { eventGroup02 27 }

	openBranchAlarm0228 NOTIFICATION-TYPE
	OBJECTS {	neName,
			eventGroupName,			-- 02
			eventName,			-- 28
			severity,
			eventType,
			eventTime,
			faultyObject,
			monitoredValue,
			thresholdValue,
			neType }
	STATUS		current
	DESCRIPTION	"Spontaneous Alarm from the managed network element."
	::= { eventGroup02 28 }

	openBranchAlarm0229 NOTIFICATION-TYPE
	OBJECTS {	neName,
			eventGroupName,			-- 02
			eventName,			-- 29
			severity,
			eventType,
			eventTime,
			faultyObject,
			monitoredValue,
			thresholdValue,
			neType }
	STATUS		current
	DESCRIPTION	"Spontaneous Alarm from the managed network element."
	::= { eventGroup02 29 }

	openBranchAlarm0230 NOTIFICATION-TYPE
	OBJECTS {	neName,
			eventGroupName,			-- 02
			eventName,			-- 30
			severity,
			eventType,
			eventTime,
			faultyObject,
			monitoredValue,
			thresholdValue,
			neType }
	STATUS		current
	DESCRIPTION	"Spontaneous Alarm from the managed network element."
	::= { eventGroup02 30 }

	openBranchAlarm0231 NOTIFICATION-TYPE
	OBJECTS {	neName,
			eventGroupName,			-- 02
			eventName,			-- 31
			severity,
			eventType,
			eventTime,
			faultyObject,
			monitoredValue,
			thresholdValue,
			neType }
	STATUS		current
	DESCRIPTION	"Spontaneous Alarm from the managed network element."
	::= { eventGroup02 31 }

	openBranchAlarm0232 NOTIFICATION-TYPE
	OBJECTS {	neName,
			eventGroupName,			-- 02
			eventName,			-- 32
			severity,
			eventType,
			eventTime,
			faultyObject,
			monitoredValue,
			thresholdValue,
			neType }
	STATUS		current
	DESCRIPTION	"Spontaneous Alarm from the managed network element."
	::= { eventGroup02 32 }


	--********************************************************************
	-- Alarm Trap Definitions for event group 03
	--********************************************************************


	openBranchAlarm0301 NOTIFICATION-TYPE
	OBJECTS {	neName,
			eventGroupName,			-- 03
			eventName,			-- 01
			severity,
			eventType,
			eventTime,
			faultyObject,
			monitoredValue,
			thresholdValue,
			neType }
	STATUS		current
	DESCRIPTION	"Spontaneous Alarm from the managed network element."
	::= { eventGroup03 1 }

	openBranchAlarm0302 NOTIFICATION-TYPE
	OBJECTS {	neName,
			eventGroupName,			-- 03
			eventName,			-- 02
			severity,
			eventType,
			eventTime,
			faultyObject,
			monitoredValue,
			thresholdValue,
			neType }
	STATUS		current
	DESCRIPTION	"Spontaneous Alarm from the managed network element."
	::= { eventGroup03 2 }

	openBranchAlarm0303 NOTIFICATION-TYPE
	OBJECTS {	neName,
			eventGroupName,			-- 03
			eventName,			-- 03
			severity,
			eventType,
			eventTime,
			faultyObject,
			monitoredValue,
			thresholdValue,
			neType }
	STATUS		current
	DESCRIPTION	"Spontaneous Alarm from the managed network element."
	::= { eventGroup03 3 }

	openBranchAlarm0304 NOTIFICATION-TYPE
	OBJECTS {	neName,
			eventGroupName,			-- 03
			eventName,			-- 04
			severity,
			eventType,
			eventTime,
			faultyObject,
			monitoredValue,
			thresholdValue,
			neType }
	STATUS		current
	DESCRIPTION	"Spontaneous Alarm from the managed network element."
	::= { eventGroup03 4 }

	openBranchAlarm0305 NOTIFICATION-TYPE
	OBJECTS {	neName,
			eventGroupName,			-- 03
			eventName,			-- 05
			severity,
			eventType,
			eventTime,
			faultyObject,
			monitoredValue,
			thresholdValue,
			neType }
	STATUS		current
	DESCRIPTION	"Spontaneous Alarm from the managed network element."
	::= { eventGroup03 5 }

	openBranchAlarm0306 NOTIFICATION-TYPE
	OBJECTS {	neName,
			eventGroupName,			-- 03
			eventName,			-- 06
			severity,
			eventType,
			eventTime,
			faultyObject,
			monitoredValue,
			thresholdValue,
			neType }
	STATUS		current
	DESCRIPTION	"Spontaneous Alarm from the managed network element."
	::= { eventGroup03 6 }

	openBranchAlarm0307 NOTIFICATION-TYPE
	OBJECTS {	neName,
			eventGroupName,			-- 03
			eventName,			-- 07
			severity,
			eventType,
			eventTime,
			faultyObject,
			monitoredValue,
			thresholdValue,
			neType }
	STATUS		current
	DESCRIPTION	"Spontaneous Alarm from the managed network element."
	::= { eventGroup03 7 }

	openBranchAlarm0308 NOTIFICATION-TYPE
	OBJECTS {	neName,
			eventGroupName,			-- 03
			eventName,			-- 08
			severity,
			eventType,
			eventTime,
			faultyObject,
			monitoredValue,
			thresholdValue,
			neType }
	STATUS		current
	DESCRIPTION	"Spontaneous Alarm from the managed network element."
	::= { eventGroup03 8 }

	openBranchAlarm0309 NOTIFICATION-TYPE
	OBJECTS {	neName,
			eventGroupName,			-- 03
			eventName,			-- 09
			severity,
			eventType,
			eventTime,
			faultyObject,
			monitoredValue,
			thresholdValue,
			neType }
	STATUS		current
	DESCRIPTION	"Spontaneous Alarm from the managed network element."
	::= { eventGroup03 9 }

	openBranchAlarm0310 NOTIFICATION-TYPE
	OBJECTS {	neName,
			eventGroupName,			-- 03
			eventName,			-- 10
			severity,
			eventType,
			eventTime,
			faultyObject,
			monitoredValue,
			thresholdValue,
			neType }
	STATUS		current
	DESCRIPTION	"Spontaneous Alarm from the managed network element."
	::= { eventGroup03 10 }

	openBranchAlarm0311 NOTIFICATION-TYPE
	OBJECTS {	neName,
			eventGroupName,			-- 03
			eventName,			-- 11
			severity,
			eventType,
			eventTime,
			faultyObject,
			monitoredValue,
			thresholdValue,
			neType }
	STATUS		current
	DESCRIPTION	"Spontaneous Alarm from the managed network element."
	::= { eventGroup03 11 }

	openBranchAlarm0312 NOTIFICATION-TYPE
	OBJECTS {	neName,
			eventGroupName,			-- 03
			eventName,			-- 12
			severity,
			eventType,
			eventTime,
			faultyObject,
			monitoredValue,
			thresholdValue,
			neType }
	STATUS		current
	DESCRIPTION	"Spontaneous Alarm from the managed network element."
	::= { eventGroup03 12 }

	openBranchAlarm0313 NOTIFICATION-TYPE
	OBJECTS {	neName,
			eventGroupName,			-- 03
			eventName,			-- 13
			severity,
			eventType,
			eventTime,
			faultyObject,
			monitoredValue,
			thresholdValue,
			neType }
	STATUS		current
	DESCRIPTION	"Spontaneous Alarm from the managed network element."
	::= { eventGroup03 13 }

	openBranchAlarm0314 NOTIFICATION-TYPE
	OBJECTS {	neName,
			eventGroupName,			-- 03
			eventName,			-- 14
			severity,
			eventType,
			eventTime,
			faultyObject,
			monitoredValue,
			thresholdValue,
			neType }
	STATUS		current
	DESCRIPTION	"Spontaneous Alarm from the managed network element."
	::= { eventGroup03 14 }

	openBranchAlarm0315 NOTIFICATION-TYPE
	OBJECTS {	neName,
			eventGroupName,			-- 03
			eventName,			-- 15
			severity,
			eventType,
			eventTime,
			faultyObject,
			monitoredValue,
			thresholdValue,
			neType }
	STATUS		current
	DESCRIPTION	"Spontaneous Alarm from the managed network element."
	::= { eventGroup03 15 }

	openBranchAlarm0316 NOTIFICATION-TYPE
	OBJECTS {	neName,
			eventGroupName,			-- 03
			eventName,			-- 16
			severity,
			eventType,
			eventTime,
			faultyObject,
			monitoredValue,
			thresholdValue,
			neType }
	STATUS		current
	DESCRIPTION	"Spontaneous Alarm from the managed network element."
	::= { eventGroup03 16 }

	openBranchAlarm0317 NOTIFICATION-TYPE
	OBJECTS {	neName,
			eventGroupName,			-- 03
			eventName,			-- 17
			severity,
			eventType,
			eventTime,
			faultyObject,
			monitoredValue,
			thresholdValue,
			neType }
	STATUS		current
	DESCRIPTION	"Spontaneous Alarm from the managed network element."
	::= { eventGroup03 17 }

	openBranchAlarm0318 NOTIFICATION-TYPE
	OBJECTS {	neName,
			eventGroupName,			-- 03
			eventName,			-- 18
			severity,
			eventType,
			eventTime,
			faultyObject,
			monitoredValue,
			thresholdValue,
			neType }
	STATUS		current
	DESCRIPTION	"Spontaneous Alarm from the managed network element."
	::= { eventGroup03 18 }

	openBranchAlarm0319 NOTIFICATION-TYPE
	OBJECTS {	neName,
			eventGroupName,			-- 03
			eventName,			-- 19
			severity,
			eventType,
			eventTime,
			faultyObject,
			monitoredValue,
			thresholdValue,
			neType }
	STATUS		current
	DESCRIPTION	"Spontaneous Alarm from the managed network element."
	::= { eventGroup03 19 }

	openBranchAlarm0320 NOTIFICATION-TYPE
	OBJECTS {	neName,
			eventGroupName,			-- 03
			eventName,			-- 20
			severity,
			eventType,
			eventTime,
			faultyObject,
			monitoredValue,
			thresholdValue,
			neType }
	STATUS		current
	DESCRIPTION	"Spontaneous Alarm from the managed network element."
	::= { eventGroup03 20 }

	openBranchAlarm0321 NOTIFICATION-TYPE
	OBJECTS {	neName,
			eventGroupName,			-- 03
			eventName,			-- 21
			severity,
			eventType,
			eventTime,
			faultyObject,
			monitoredValue,
			thresholdValue,
			neType }
	STATUS		current
	DESCRIPTION	"Spontaneous Alarm from the managed network element."
	::= { eventGroup03 21 }

	openBranchAlarm0322 NOTIFICATION-TYPE
	OBJECTS {	neName,
			eventGroupName,			-- 03
			eventName,			-- 22
			severity,
			eventType,
			eventTime,
			faultyObject,
			monitoredValue,
			thresholdValue,
			neType }
	STATUS		current
	DESCRIPTION	"Spontaneous Alarm from the managed network element."
	::= { eventGroup03 22 }

	openBranchAlarm0323 NOTIFICATION-TYPE
	OBJECTS {	neName,
			eventGroupName,			-- 03
			eventName,			-- 23
			severity,
			eventType,
			eventTime,
			faultyObject,
			monitoredValue,
			thresholdValue,
			neType }
	STATUS		current
	DESCRIPTION	"Spontaneous Alarm from the managed network element."
	::= { eventGroup03 23 }

	openBranchAlarm0324 NOTIFICATION-TYPE
	OBJECTS {	neName,
			eventGroupName,			-- 03
			eventName,			-- 24
			severity,
			eventType,
			eventTime,
			faultyObject,
			monitoredValue,
			thresholdValue,
			neType }
	STATUS		current
	DESCRIPTION	"Spontaneous Alarm from the managed network element."
	::= { eventGroup03 24 }

	openBranchAlarm0325 NOTIFICATION-TYPE
	OBJECTS {	neName,
			eventGroupName,			-- 03
			eventName,			-- 25
			severity,
			eventType,
			eventTime,
			faultyObject,
			monitoredValue,
			thresholdValue,
			neType }
	STATUS		current
	DESCRIPTION	"Spontaneous Alarm from the managed network element."
	::= { eventGroup03 25 }

	openBranchAlarm0326 NOTIFICATION-TYPE
	OBJECTS {	neName,
			eventGroupName,			-- 03
			eventName,			-- 26
			severity,
			eventType,
			eventTime,
			faultyObject,
			monitoredValue,
			thresholdValue,
			neType }
	STATUS		current
	DESCRIPTION	"Spontaneous Alarm from the managed network element."
	::= { eventGroup03 26 }

	openBranchAlarm0327 NOTIFICATION-TYPE
	OBJECTS {	neName,
			eventGroupName,			-- 03
			eventName,			-- 27
			severity,
			eventType,
			eventTime,
			faultyObject,
			monitoredValue,
			thresholdValue,
			neType }
	STATUS		current
	DESCRIPTION	"Spontaneous Alarm from the managed network element."
	::= { eventGroup03 27 }

	openBranchAlarm0328 NOTIFICATION-TYPE
	OBJECTS {	neName,
			eventGroupName,			-- 03
			eventName,			-- 28
			severity,
			eventType,
			eventTime,
			faultyObject,
			monitoredValue,
			thresholdValue,
			neType }
	STATUS		current
	DESCRIPTION	"Spontaneous Alarm from the managed network element."
	::= { eventGroup03 28 }

	openBranchAlarm0329 NOTIFICATION-TYPE
	OBJECTS {	neName,
			eventGroupName,			-- 03
			eventName,			-- 29
			severity,
			eventType,
			eventTime,
			faultyObject,
			monitoredValue,
			thresholdValue,
			neType }
	STATUS		current
	DESCRIPTION	"Spontaneous Alarm from the managed network element."
	::= { eventGroup03 29 }

	openBranchAlarm0330 NOTIFICATION-TYPE
	OBJECTS {	neName,
			eventGroupName,			-- 03
			eventName,			-- 30
			severity,
			eventType,
			eventTime,
			faultyObject,
			monitoredValue,
			thresholdValue,
			neType }
	STATUS		current
	DESCRIPTION	"Spontaneous Alarm from the managed network element."
	::= { eventGroup03 30 }

	openBranchAlarm0331 NOTIFICATION-TYPE
	OBJECTS {	neName,
			eventGroupName,			-- 03
			eventName,			-- 31
			severity,
			eventType,
			eventTime,
			faultyObject,
			monitoredValue,
			thresholdValue,
			neType }
	STATUS		current
	DESCRIPTION	"Spontaneous Alarm from the managed network element."
	::= { eventGroup03 31 }

	openBranchAlarm0332 NOTIFICATION-TYPE
	OBJECTS {	neName,
			eventGroupName,			-- 03
			eventName,			-- 32
			severity,
			eventType,
			eventTime,
			faultyObject,
			monitoredValue,
			thresholdValue,
			neType }
	STATUS		current
	DESCRIPTION	"Spontaneous Alarm from the managed network element."
	::= { eventGroup03 32 }


	--********************************************************************
	-- Alarm Trap Definitions for event group 04
	--********************************************************************


	openBranchAlarm0401 NOTIFICATION-TYPE
	OBJECTS {	neName,
			eventGroupName,			-- 04
			eventName,			-- 01
			severity,
			eventType,
			eventTime,
			faultyObject,
			monitoredValue,
			thresholdValue,
			neType }
	STATUS		current
	DESCRIPTION	"Spontaneous Alarm from the managed network element."
	::= { eventGroup04 1 }

	openBranchAlarm0402 NOTIFICATION-TYPE
	OBJECTS {	neName,
			eventGroupName,			-- 04
			eventName,			-- 02
			severity,
			eventType,
			eventTime,
			faultyObject,
			monitoredValue,
			thresholdValue,
			neType }
	STATUS		current
	DESCRIPTION	"Spontaneous Alarm from the managed network element."
	::= { eventGroup04 2 }

	openBranchAlarm0403 NOTIFICATION-TYPE
	OBJECTS {	neName,
			eventGroupName,			-- 04
			eventName,			-- 03
			severity,
			eventType,
			eventTime,
			faultyObject,
			monitoredValue,
			thresholdValue,
			neType }
	STATUS		current
	DESCRIPTION	"Spontaneous Alarm from the managed network element."
	::= { eventGroup04 3 }

	openBranchAlarm0404 NOTIFICATION-TYPE
	OBJECTS {	neName,
			eventGroupName,			-- 04
			eventName,			-- 04
			severity,
			eventType,
			eventTime,
			faultyObject,
			monitoredValue,
			thresholdValue,
			neType }
	STATUS		current
	DESCRIPTION	"Spontaneous Alarm from the managed network element."
	::= { eventGroup04 4 }

	openBranchAlarm0405 NOTIFICATION-TYPE
	OBJECTS {	neName,
			eventGroupName,			-- 04
			eventName,			-- 05
			severity,
			eventType,
			eventTime,
			faultyObject,
			monitoredValue,
			thresholdValue,
			neType }
	STATUS		current
	DESCRIPTION	"Spontaneous Alarm from the managed network element."
	::= { eventGroup04 5 }

	openBranchAlarm0406 NOTIFICATION-TYPE
	OBJECTS {	neName,
			eventGroupName,			-- 04
			eventName,			-- 06
			severity,
			eventType,
			eventTime,
			faultyObject,
			monitoredValue,
			thresholdValue,
			neType }
	STATUS		current
	DESCRIPTION	"Spontaneous Alarm from the managed network element."
	::= { eventGroup04 6 }

	openBranchAlarm0407 NOTIFICATION-TYPE
	OBJECTS {	neName,
			eventGroupName,			-- 04
			eventName,			-- 07
			severity,
			eventType,
			eventTime,
			faultyObject,
			monitoredValue,
			thresholdValue,
			neType }
	STATUS		current
	DESCRIPTION	"Spontaneous Alarm from the managed network element."
	::= { eventGroup04 7 }

	openBranchAlarm0408 NOTIFICATION-TYPE
	OBJECTS {	neName,
			eventGroupName,			-- 04
			eventName,			-- 08
			severity,
			eventType,
			eventTime,
			faultyObject,
			monitoredValue,
			thresholdValue,
			neType }
	STATUS		current
	DESCRIPTION	"Spontaneous Alarm from the managed network element."
	::= { eventGroup04 8 }

	openBranchAlarm0409 NOTIFICATION-TYPE
	OBJECTS {	neName,
			eventGroupName,			-- 04
			eventName,			-- 09
			severity,
			eventType,
			eventTime,
			faultyObject,
			monitoredValue,
			thresholdValue,
			neType }
	STATUS		current
	DESCRIPTION	"Spontaneous Alarm from the managed network element."
	::= { eventGroup04 9 }

	openBranchAlarm0410 NOTIFICATION-TYPE
	OBJECTS {	neName,
			eventGroupName,			-- 04
			eventName,			-- 10
			severity,
			eventType,
			eventTime,
			faultyObject,
			monitoredValue,
			thresholdValue,
			neType }
	STATUS		current
	DESCRIPTION	"Spontaneous Alarm from the managed network element."
	::= { eventGroup04 10 }

	openBranchAlarm0411 NOTIFICATION-TYPE
	OBJECTS {	neName,
			eventGroupName,			-- 04
			eventName,			-- 11
			severity,
			eventType,
			eventTime,
			faultyObject,
			monitoredValue,
			thresholdValue,
			neType }
	STATUS		current
	DESCRIPTION	"Spontaneous Alarm from the managed network element."
	::= { eventGroup04 11 }

	openBranchAlarm0412 NOTIFICATION-TYPE
	OBJECTS {	neName,
			eventGroupName,			-- 04
			eventName,			-- 12
			severity,
			eventType,
			eventTime,
			faultyObject,
			monitoredValue,
			thresholdValue,
			neType }
	STATUS		current
	DESCRIPTION	"Spontaneous Alarm from the managed network element."
	::= { eventGroup04 12 }

	openBranchAlarm0413 NOTIFICATION-TYPE
	OBJECTS {	neName,
			eventGroupName,			-- 04
			eventName,			-- 13
			severity,
			eventType,
			eventTime,
			faultyObject,
			monitoredValue,
			thresholdValue,
			neType }
	STATUS		current
	DESCRIPTION	"Spontaneous Alarm from the managed network element."
	::= { eventGroup04 13 }

	openBranchAlarm0414 NOTIFICATION-TYPE
	OBJECTS {	neName,
			eventGroupName,			-- 04
			eventName,			-- 14
			severity,
			eventType,
			eventTime,
			faultyObject,
			monitoredValue,
			thresholdValue,
			neType }
	STATUS		current
	DESCRIPTION	"Spontaneous Alarm from the managed network element."
	::= { eventGroup04 14 }

	openBranchAlarm0415 NOTIFICATION-TYPE
	OBJECTS {	neName,
			eventGroupName,			-- 04
			eventName,			-- 15
			severity,
			eventType,
			eventTime,
			faultyObject,
			monitoredValue,
			thresholdValue,
			neType }
	STATUS		current
	DESCRIPTION	"Spontaneous Alarm from the managed network element."
	::= { eventGroup04 15 }

	openBranchAlarm0416 NOTIFICATION-TYPE
	OBJECTS {	neName,
			eventGroupName,			-- 04
			eventName,			-- 16
			severity,
			eventType,
			eventTime,
			faultyObject,
			monitoredValue,
			thresholdValue,
			neType }
	STATUS		current
	DESCRIPTION	"Spontaneous Alarm from the managed network element."
	::= { eventGroup04 16 }

	openBranchAlarm0417 NOTIFICATION-TYPE
	OBJECTS {	neName,
			eventGroupName,			-- 04
			eventName,			-- 17
			severity,
			eventType,
			eventTime,
			faultyObject,
			monitoredValue,
			thresholdValue,
			neType }
	STATUS		current
	DESCRIPTION	"Spontaneous Alarm from the managed network element."
	::= { eventGroup04 17 }

	openBranchAlarm0418 NOTIFICATION-TYPE
	OBJECTS {	neName,
			eventGroupName,			-- 04
			eventName,			-- 18
			severity,
			eventType,
			eventTime,
			faultyObject,
			monitoredValue,
			thresholdValue,
			neType }
	STATUS		current
	DESCRIPTION	"Spontaneous Alarm from the managed network element."
	::= { eventGroup04 18 }

	openBranchAlarm0419 NOTIFICATION-TYPE
	OBJECTS {	neName,
			eventGroupName,			-- 04
			eventName,			-- 19
			severity,
			eventType,
			eventTime,
			faultyObject,
			monitoredValue,
			thresholdValue,
			neType }
	STATUS		current
	DESCRIPTION	"Spontaneous Alarm from the managed network element."
	::= { eventGroup04 19 }

	openBranchAlarm0420 NOTIFICATION-TYPE
	OBJECTS {	neName,
			eventGroupName,			-- 04
			eventName,			-- 20
			severity,
			eventType,
			eventTime,
			faultyObject,
			monitoredValue,
			thresholdValue,
			neType }
	STATUS		current
	DESCRIPTION	"Spontaneous Alarm from the managed network element."
	::= { eventGroup04 20 }

	openBranchAlarm0421 NOTIFICATION-TYPE
	OBJECTS {	neName,
			eventGroupName,			-- 04
			eventName,			-- 21
			severity,
			eventType,
			eventTime,
			faultyObject,
			monitoredValue,
			thresholdValue,
			neType }
	STATUS		current
	DESCRIPTION	"Spontaneous Alarm from the managed network element."
	::= { eventGroup04 21 }

	openBranchAlarm0422 NOTIFICATION-TYPE
	OBJECTS {	neName,
			eventGroupName,			-- 04
			eventName,			-- 22
			severity,
			eventType,
			eventTime,
			faultyObject,
			monitoredValue,
			thresholdValue,
			neType }
	STATUS		current
	DESCRIPTION	"Spontaneous Alarm from the managed network element."
	::= { eventGroup04 22 }

	openBranchAlarm0423 NOTIFICATION-TYPE
	OBJECTS {	neName,
			eventGroupName,			-- 04
			eventName,			-- 23
			severity,
			eventType,
			eventTime,
			faultyObject,
			monitoredValue,
			thresholdValue,
			neType }
	STATUS		current
	DESCRIPTION	"Spontaneous Alarm from the managed network element."
	::= { eventGroup04 23 }

	openBranchAlarm0424 NOTIFICATION-TYPE
	OBJECTS {	neName,
			eventGroupName,			-- 04
			eventName,			-- 24
			severity,
			eventType,
			eventTime,
			faultyObject,
			monitoredValue,
			thresholdValue,
			neType }
	STATUS		current
	DESCRIPTION	"Spontaneous Alarm from the managed network element."
	::= { eventGroup04 24 }

	openBranchAlarm0425 NOTIFICATION-TYPE
	OBJECTS {	neName,
			eventGroupName,			-- 04
			eventName,			-- 25
			severity,
			eventType,
			eventTime,
			faultyObject,
			monitoredValue,
			thresholdValue,
			neType }
	STATUS		current
	DESCRIPTION	"Spontaneous Alarm from the managed network element."
	::= { eventGroup04 25 }

	openBranchAlarm0426 NOTIFICATION-TYPE
	OBJECTS {	neName,
			eventGroupName,			-- 04
			eventName,			-- 26
			severity,
			eventType,
			eventTime,
			faultyObject,
			monitoredValue,
			thresholdValue,
			neType }
	STATUS		current
	DESCRIPTION	"Spontaneous Alarm from the managed network element."
	::= { eventGroup04 26 }

	openBranchAlarm0427 NOTIFICATION-TYPE
	OBJECTS {	neName,
			eventGroupName,			-- 04
			eventName,			-- 27
			severity,
			eventType,
			eventTime,
			faultyObject,
			monitoredValue,
			thresholdValue,
			neType }
	STATUS		current
	DESCRIPTION	"Spontaneous Alarm from the managed network element."
	::= { eventGroup04 27 }

	openBranchAlarm0428 NOTIFICATION-TYPE
	OBJECTS {	neName,
			eventGroupName,			-- 04
			eventName,			-- 28
			severity,
			eventType,
			eventTime,
			faultyObject,
			monitoredValue,
			thresholdValue,
			neType }
	STATUS		current
	DESCRIPTION	"Spontaneous Alarm from the managed network element."
	::= { eventGroup04 28 }

	openBranchAlarm0429 NOTIFICATION-TYPE
	OBJECTS {	neName,
			eventGroupName,			-- 04
			eventName,			-- 29
			severity,
			eventType,
			eventTime,
			faultyObject,
			monitoredValue,
			thresholdValue,
			neType }
	STATUS		current
	DESCRIPTION	"Spontaneous Alarm from the managed network element."
	::= { eventGroup04 29 }

	openBranchAlarm0430 NOTIFICATION-TYPE
	OBJECTS {	neName,
			eventGroupName,			-- 04
			eventName,			-- 30
			severity,
			eventType,
			eventTime,
			faultyObject,
			monitoredValue,
			thresholdValue,
			neType }
	STATUS		current
	DESCRIPTION	"Spontaneous Alarm from the managed network element."
	::= { eventGroup04 30 }

	openBranchAlarm0431 NOTIFICATION-TYPE
	OBJECTS {	neName,
			eventGroupName,			-- 04
			eventName,			-- 31
			severity,
			eventType,
			eventTime,
			faultyObject,
			monitoredValue,
			thresholdValue,
			neType }
	STATUS		current
	DESCRIPTION	"Spontaneous Alarm from the managed network element."
	::= { eventGroup04 31 }

	openBranchAlarm0432 NOTIFICATION-TYPE
	OBJECTS {	neName,
			eventGroupName,			-- 04
			eventName,			-- 32
			severity,
			eventType,
			eventTime,
			faultyObject,
			monitoredValue,
			thresholdValue,
			neType }
	STATUS		current
	DESCRIPTION	"Spontaneous Alarm from the managed network element."
	::= { eventGroup04 32 }


	--********************************************************************
	-- Alarm Trap Definitions for event group 05
	--********************************************************************


	openBranchAlarm0501 NOTIFICATION-TYPE
	OBJECTS {	neName,
			eventGroupName,			-- 05
			eventName,			-- 01
			severity,
			eventType,
			eventTime,
			faultyObject,
			monitoredValue,
			thresholdValue,
			neType }
	STATUS		current
	DESCRIPTION	"Spontaneous Alarm from the managed network element."
	::= { eventGroup05 1 }

	openBranchAlarm0502 NOTIFICATION-TYPE
	OBJECTS {	neName,
			eventGroupName,			-- 05
			eventName,			-- 02
			severity,
			eventType,
			eventTime,
			faultyObject,
			monitoredValue,
			thresholdValue,
			neType }
	STATUS		current
	DESCRIPTION	"Spontaneous Alarm from the managed network element."
	::= { eventGroup05 2 }

	openBranchAlarm0503 NOTIFICATION-TYPE
	OBJECTS {	neName,
			eventGroupName,			-- 05
			eventName,			-- 03
			severity,
			eventType,
			eventTime,
			faultyObject,
			monitoredValue,
			thresholdValue,
			neType }
	STATUS		current
	DESCRIPTION	"Spontaneous Alarm from the managed network element."
	::= { eventGroup05 3 }

	openBranchAlarm0504 NOTIFICATION-TYPE
	OBJECTS {	neName,
			eventGroupName,			-- 05
			eventName,			-- 04
			severity,
			eventType,
			eventTime,
			faultyObject,
			monitoredValue,
			thresholdValue,
			neType }
	STATUS		current
	DESCRIPTION	"Spontaneous Alarm from the managed network element."
	::= { eventGroup05 4 }

	openBranchAlarm0505 NOTIFICATION-TYPE
	OBJECTS {	neName,
			eventGroupName,			-- 05
			eventName,			-- 05
			severity,
			eventType,
			eventTime,
			faultyObject,
			monitoredValue,
			thresholdValue,
			neType }
	STATUS		current
	DESCRIPTION	"Spontaneous Alarm from the managed network element."
	::= { eventGroup05 5 }

	openBranchAlarm0506 NOTIFICATION-TYPE
	OBJECTS {	neName,
			eventGroupName,			-- 05
			eventName,			-- 06
			severity,
			eventType,
			eventTime,
			faultyObject,
			monitoredValue,
			thresholdValue,
			neType }
	STATUS		current
	DESCRIPTION	"Spontaneous Alarm from the managed network element."
	::= { eventGroup05 6 }

	openBranchAlarm0507 NOTIFICATION-TYPE
	OBJECTS {	neName,
			eventGroupName,			-- 05
			eventName,			-- 07
			severity,
			eventType,
			eventTime,
			faultyObject,
			monitoredValue,
			thresholdValue,
			neType }
	STATUS		current
	DESCRIPTION	"Spontaneous Alarm from the managed network element."
	::= { eventGroup05 7 }

	openBranchAlarm0508 NOTIFICATION-TYPE
	OBJECTS {	neName,
			eventGroupName,			-- 05
			eventName,			-- 08
			severity,
			eventType,
			eventTime,
			faultyObject,
			monitoredValue,
			thresholdValue,
			neType }
	STATUS		current
	DESCRIPTION	"Spontaneous Alarm from the managed network element."
	::= { eventGroup05 8 }

	openBranchAlarm0509 NOTIFICATION-TYPE
	OBJECTS {	neName,
			eventGroupName,			-- 05
			eventName,			-- 09
			severity,
			eventType,
			eventTime,
			faultyObject,
			monitoredValue,
			thresholdValue,
			neType }
	STATUS		current
	DESCRIPTION	"Spontaneous Alarm from the managed network element."
	::= { eventGroup05 9 }

	openBranchAlarm0510 NOTIFICATION-TYPE
	OBJECTS {	neName,
			eventGroupName,			-- 05
			eventName,			-- 10
			severity,
			eventType,
			eventTime,
			faultyObject,
			monitoredValue,
			thresholdValue,
			neType }
	STATUS		current
	DESCRIPTION	"Spontaneous Alarm from the managed network element."
	::= { eventGroup05 10 }

	openBranchAlarm0511 NOTIFICATION-TYPE
	OBJECTS {	neName,
			eventGroupName,			-- 05
			eventName,			-- 11
			severity,
			eventType,
			eventTime,
			faultyObject,
			monitoredValue,
			thresholdValue,
			neType }
	STATUS		current
	DESCRIPTION	"Spontaneous Alarm from the managed network element."
	::= { eventGroup05 11 }

	openBranchAlarm0512 NOTIFICATION-TYPE
	OBJECTS {	neName,
			eventGroupName,			-- 05
			eventName,			-- 12
			severity,
			eventType,
			eventTime,
			faultyObject,
			monitoredValue,
			thresholdValue,
			neType }
	STATUS		current
	DESCRIPTION	"Spontaneous Alarm from the managed network element."
	::= { eventGroup05 12 }

	openBranchAlarm0513 NOTIFICATION-TYPE
	OBJECTS {	neName,
			eventGroupName,			-- 05
			eventName,			-- 13
			severity,
			eventType,
			eventTime,
			faultyObject,
			monitoredValue,
			thresholdValue,
			neType }
	STATUS		current
	DESCRIPTION	"Spontaneous Alarm from the managed network element."
	::= { eventGroup05 13 }

	openBranchAlarm0514 NOTIFICATION-TYPE
	OBJECTS {	neName,
			eventGroupName,			-- 05
			eventName,			-- 14
			severity,
			eventType,
			eventTime,
			faultyObject,
			monitoredValue,
			thresholdValue,
			neType }
	STATUS		current
	DESCRIPTION	"Spontaneous Alarm from the managed network element."
	::= { eventGroup05 14 }

	openBranchAlarm0515 NOTIFICATION-TYPE
	OBJECTS {	neName,
			eventGroupName,			-- 05
			eventName,			-- 15
			severity,
			eventType,
			eventTime,
			faultyObject,
			monitoredValue,
			thresholdValue,
			neType }
	STATUS		current
	DESCRIPTION	"Spontaneous Alarm from the managed network element."
	::= { eventGroup05 15 }

	openBranchAlarm0516 NOTIFICATION-TYPE
	OBJECTS {	neName,
			eventGroupName,			-- 05
			eventName,			-- 16
			severity,
			eventType,
			eventTime,
			faultyObject,
			monitoredValue,
			thresholdValue,
			neType }
	STATUS		current
	DESCRIPTION	"Spontaneous Alarm from the managed network element."
	::= { eventGroup05 16 }

	openBranchAlarm0517 NOTIFICATION-TYPE
	OBJECTS {	neName,
			eventGroupName,			-- 05
			eventName,			-- 17
			severity,
			eventType,
			eventTime,
			faultyObject,
			monitoredValue,
			thresholdValue,
			neType }
	STATUS		current
	DESCRIPTION	"Spontaneous Alarm from the managed network element."
	::= { eventGroup05 17 }

	openBranchAlarm0518 NOTIFICATION-TYPE
	OBJECTS {	neName,
			eventGroupName,			-- 05
			eventName,			-- 18
			severity,
			eventType,
			eventTime,
			faultyObject,
			monitoredValue,
			thresholdValue,
			neType }
	STATUS		current
	DESCRIPTION	"Spontaneous Alarm from the managed network element."
	::= { eventGroup05 18 }

	openBranchAlarm0519 NOTIFICATION-TYPE
	OBJECTS {	neName,
			eventGroupName,			-- 05
			eventName,			-- 19
			severity,
			eventType,
			eventTime,
			faultyObject,
			monitoredValue,
			thresholdValue,
			neType }
	STATUS		current
	DESCRIPTION	"Spontaneous Alarm from the managed network element."
	::= { eventGroup05 19 }

	openBranchAlarm0520 NOTIFICATION-TYPE
	OBJECTS {	neName,
			eventGroupName,			-- 05
			eventName,			-- 20
			severity,
			eventType,
			eventTime,
			faultyObject,
			monitoredValue,
			thresholdValue,
			neType }
	STATUS		current
	DESCRIPTION	"Spontaneous Alarm from the managed network element."
	::= { eventGroup05 20 }

	openBranchAlarm0521 NOTIFICATION-TYPE
	OBJECTS {	neName,
			eventGroupName,			-- 05
			eventName,			-- 21
			severity,
			eventType,
			eventTime,
			faultyObject,
			monitoredValue,
			thresholdValue,
			neType }
	STATUS		current
	DESCRIPTION	"Spontaneous Alarm from the managed network element."
	::= { eventGroup05 21 }

	openBranchAlarm0522 NOTIFICATION-TYPE
	OBJECTS {	neName,
			eventGroupName,			-- 05
			eventName,			-- 22
			severity,
			eventType,
			eventTime,
			faultyObject,
			monitoredValue,
			thresholdValue,
			neType }
	STATUS		current
	DESCRIPTION	"Spontaneous Alarm from the managed network element."
	::= { eventGroup05 22 }

	openBranchAlarm0523 NOTIFICATION-TYPE
	OBJECTS {	neName,
			eventGroupName,			-- 05
			eventName,			-- 23
			severity,
			eventType,
			eventTime,
			faultyObject,
			monitoredValue,
			thresholdValue,
			neType }
	STATUS		current
	DESCRIPTION	"Spontaneous Alarm from the managed network element."
	::= { eventGroup05 23 }

	openBranchAlarm0524 NOTIFICATION-TYPE
	OBJECTS {	neName,
			eventGroupName,			-- 05
			eventName,			-- 24
			severity,
			eventType,
			eventTime,
			faultyObject,
			monitoredValue,
			thresholdValue,
			neType }
	STATUS		current
	DESCRIPTION	"Spontaneous Alarm from the managed network element."
	::= { eventGroup05 24 }

	openBranchAlarm0525 NOTIFICATION-TYPE
	OBJECTS {	neName,
			eventGroupName,			-- 05
			eventName,			-- 25
			severity,
			eventType,
			eventTime,
			faultyObject,
			monitoredValue,
			thresholdValue,
			neType }
	STATUS		current
	DESCRIPTION	"Spontaneous Alarm from the managed network element."
	::= { eventGroup05 25 }

	openBranchAlarm0526 NOTIFICATION-TYPE
	OBJECTS {	neName,
			eventGroupName,			-- 05
			eventName,			-- 26
			severity,
			eventType,
			eventTime,
			faultyObject,
			monitoredValue,
			thresholdValue,
			neType }
	STATUS		current
	DESCRIPTION	"Spontaneous Alarm from the managed network element."
	::= { eventGroup05 26 }

	openBranchAlarm0527 NOTIFICATION-TYPE
	OBJECTS {	neName,
			eventGroupName,			-- 05
			eventName,			-- 27
			severity,
			eventType,
			eventTime,
			faultyObject,
			monitoredValue,
			thresholdValue,
			neType }
	STATUS		current
	DESCRIPTION	"Spontaneous Alarm from the managed network element."
	::= { eventGroup05 27 }

	openBranchAlarm0528 NOTIFICATION-TYPE
	OBJECTS {	neName,
			eventGroupName,			-- 05
			eventName,			-- 28
			severity,
			eventType,
			eventTime,
			faultyObject,
			monitoredValue,
			thresholdValue,
			neType }
	STATUS		current
	DESCRIPTION	"Spontaneous Alarm from the managed network element."
	::= { eventGroup05 28 }

	openBranchAlarm0529 NOTIFICATION-TYPE
	OBJECTS {	neName,
			eventGroupName,			-- 05
			eventName,			-- 29
			severity,
			eventType,
			eventTime,
			faultyObject,
			monitoredValue,
			thresholdValue,
			neType }
	STATUS		current
	DESCRIPTION	"Spontaneous Alarm from the managed network element."
	::= { eventGroup05 29 }

	openBranchAlarm0530 NOTIFICATION-TYPE
	OBJECTS {	neName,
			eventGroupName,			-- 05
			eventName,			-- 30
			severity,
			eventType,
			eventTime,
			faultyObject,
			monitoredValue,
			thresholdValue,
			neType }
	STATUS		current
	DESCRIPTION	"Spontaneous Alarm from the managed network element."
	::= { eventGroup05 30 }

	openBranchAlarm0531 NOTIFICATION-TYPE
	OBJECTS {	neName,
			eventGroupName,			-- 05
			eventName,			-- 31
			severity,
			eventType,
			eventTime,
			faultyObject,
			monitoredValue,
			thresholdValue,
			neType }
	STATUS		current
	DESCRIPTION	"Spontaneous Alarm from the managed network element."
	::= { eventGroup05 31 }

	openBranchAlarm0532 NOTIFICATION-TYPE
	OBJECTS {	neName,
			eventGroupName,			-- 05
			eventName,			-- 32
			severity,
			eventType,
			eventTime,
			faultyObject,
			monitoredValue,
			thresholdValue,
			neType }
	STATUS		current
	DESCRIPTION	"Spontaneous Alarm from the managed network element."
	::= { eventGroup05 32 }

openBranchAlarm0535 NOTIFICATION-TYPE
	OBJECTS {	neName,
			eventGroupName,			-- 05
			eventName,			-- 36
			severity,
			eventType,
			eventTime,
			faultyObject,
			monitoredValue,
			thresholdValue,
			neType }
	STATUS		current
	DESCRIPTION	"Spontaneous Alarm from the managed network element."
	::= { eventGroup05 36 }

openBranchAlarm0537 NOTIFICATION-TYPE
	OBJECTS {	neName,
			eventGroupName,			-- 05
			eventName,			-- 37
			severity,
			eventType,
			eventTime,
			faultyObject,
			monitoredValue,
			thresholdValue,
			neType }
	STATUS		current
	DESCRIPTION	"Spontaneous Alarm from the managed network element."
	::= { eventGroup05 37 }

openBranchAlarm0538 NOTIFICATION-TYPE
	OBJECTS {	neName,
			eventGroupName,			-- 05
			eventName,			-- 38
			severity,
			eventType,
			eventTime,
			faultyObject,
			monitoredValue,
			thresholdValue,
			neType }
	STATUS		current
	DESCRIPTION	"Spontaneous Alarm from the managed network element."
	::= { eventGroup05 38 }

openBranchAlarm0539 NOTIFICATION-TYPE
	OBJECTS {	neName,
			eventGroupName,			-- 05
			eventName,			-- 39
			severity,
			eventType,
			eventTime,
			faultyObject,
			monitoredValue,
			thresholdValue,
			neType }
	STATUS		current
	DESCRIPTION	"Spontaneous Alarm from the managed network element."
	::= { eventGroup05 39 }


	--********************************************************************
	-- Alarm Trap Definitions for event group 06
	--********************************************************************


	openBranchAlarm0601 NOTIFICATION-TYPE
	OBJECTS {	neName,
			eventGroupName,			-- 06
			eventName,			-- 01
			severity,
			eventType,
			eventTime,
			faultyObject,
			monitoredValue,
			thresholdValue,
			neType }
	STATUS		current
	DESCRIPTION	"Spontaneous Alarm from the managed network element."
	::= { eventGroup06 1 }

	openBranchAlarm0602 NOTIFICATION-TYPE
	OBJECTS {	neName,
			eventGroupName,			-- 06
			eventName,			-- 02
			severity,
			eventType,
			eventTime,
			faultyObject,
			monitoredValue,
			thresholdValue,
			neType }
	STATUS		current
	DESCRIPTION	"Spontaneous Alarm from the managed network element."
	::= { eventGroup06 2 }

	openBranchAlarm0603 NOTIFICATION-TYPE
	OBJECTS {	neName,
			eventGroupName,			-- 06
			eventName,			-- 03
			severity,
			eventType,
			eventTime,
			faultyObject,
			monitoredValue,
			thresholdValue,
			neType }
	STATUS		current
	DESCRIPTION	"Spontaneous Alarm from the managed network element."
	::= { eventGroup06 3 }

	openBranchAlarm0604 NOTIFICATION-TYPE
	OBJECTS {	neName,
			eventGroupName,			-- 06
			eventName,			-- 04
			severity,
			eventType,
			eventTime,
			faultyObject,
			monitoredValue,
			thresholdValue,
			neType }
	STATUS		current
	DESCRIPTION	"Spontaneous Alarm from the managed network element."
	::= { eventGroup06 4 }

	openBranchAlarm0605 NOTIFICATION-TYPE
	OBJECTS {	neName,
			eventGroupName,			-- 06
			eventName,			-- 05
			severity,
			eventType,
			eventTime,
			faultyObject,
			monitoredValue,
			thresholdValue,
			neType }
	STATUS		current
	DESCRIPTION	"Spontaneous Alarm from the managed network element."
	::= { eventGroup06 5 }

	openBranchAlarm0606 NOTIFICATION-TYPE
	OBJECTS {	neName,
			eventGroupName,			-- 06
			eventName,			-- 06
			severity,
			eventType,
			eventTime,
			faultyObject,
			monitoredValue,
			thresholdValue,
			neType }
	STATUS		current
	DESCRIPTION	"Spontaneous Alarm from the managed network element."
	::= { eventGroup06 6 }

	openBranchAlarm0607 NOTIFICATION-TYPE
	OBJECTS {	neName,
			eventGroupName,			-- 06
			eventName,			-- 07
			severity,
			eventType,
			eventTime,
			faultyObject,
			monitoredValue,
			thresholdValue,
			neType }
	STATUS		current
	DESCRIPTION	"Spontaneous Alarm from the managed network element."
	::= { eventGroup06 7 }

	openBranchAlarm0608 NOTIFICATION-TYPE
	OBJECTS {	neName,
			eventGroupName,			-- 06
			eventName,			-- 08
			severity,
			eventType,
			eventTime,
			faultyObject,
			monitoredValue,
			thresholdValue,
			neType }
	STATUS		current
	DESCRIPTION	"Spontaneous Alarm from the managed network element."
	::= { eventGroup06 8 }

	openBranchAlarm0609 NOTIFICATION-TYPE
	OBJECTS {	neName,
			eventGroupName,			-- 06
			eventName,			-- 09
			severity,
			eventType,
			eventTime,
			faultyObject,
			monitoredValue,
			thresholdValue,
			neType }
	STATUS		current
	DESCRIPTION	"Spontaneous Alarm from the managed network element."
	::= { eventGroup06 9 }

	openBranchAlarm0610 NOTIFICATION-TYPE
	OBJECTS {	neName,
			eventGroupName,			-- 06
			eventName,			-- 10
			severity,
			eventType,
			eventTime,
			faultyObject,
			monitoredValue,
			thresholdValue,
			neType }
	STATUS		current
	DESCRIPTION	"Spontaneous Alarm from the managed network element."
	::= { eventGroup06 10 }

	openBranchAlarm0611 NOTIFICATION-TYPE
	OBJECTS {	neName,
			eventGroupName,			-- 06
			eventName,			-- 11
			severity,
			eventType,
			eventTime,
			faultyObject,
			monitoredValue,
			thresholdValue,
			neType }
	STATUS		current
	DESCRIPTION	"Spontaneous Alarm from the managed network element."
	::= { eventGroup06 11 }

	openBranchAlarm0612 NOTIFICATION-TYPE
	OBJECTS {	neName,
			eventGroupName,			-- 06
			eventName,			-- 12
			severity,
			eventType,
			eventTime,
			faultyObject,
			monitoredValue,
			thresholdValue,
			neType }
	STATUS		current
	DESCRIPTION	"Spontaneous Alarm from the managed network element."
	::= { eventGroup06 12 }

	openBranchAlarm0613 NOTIFICATION-TYPE
	OBJECTS {	neName,
			eventGroupName,			-- 06
			eventName,			-- 13
			severity,
			eventType,
			eventTime,
			faultyObject,
			monitoredValue,
			thresholdValue,
			neType }
	STATUS		current
	DESCRIPTION	"Spontaneous Alarm from the managed network element."
	::= { eventGroup06 13 }

	openBranchAlarm0614 NOTIFICATION-TYPE
	OBJECTS {	neName,
			eventGroupName,			-- 06
			eventName,			-- 14
			severity,
			eventType,
			eventTime,
			faultyObject,
			monitoredValue,
			thresholdValue,
			neType }
	STATUS		current
	DESCRIPTION	"Spontaneous Alarm from the managed network element."
	::= { eventGroup06 14 }

	openBranchAlarm0615 NOTIFICATION-TYPE
	OBJECTS {	neName,
			eventGroupName,			-- 06
			eventName,			-- 15
			severity,
			eventType,
			eventTime,
			faultyObject,
			monitoredValue,
			thresholdValue,
			neType }
	STATUS		current
	DESCRIPTION	"Spontaneous Alarm from the managed network element."
	::= { eventGroup06 15 }

	openBranchAlarm0616 NOTIFICATION-TYPE
	OBJECTS {	neName,
			eventGroupName,			-- 06
			eventName,			-- 16
			severity,
			eventType,
			eventTime,
			faultyObject,
			monitoredValue,
			thresholdValue,
			neType }
	STATUS		current
	DESCRIPTION	"Spontaneous Alarm from the managed network element."
	::= { eventGroup06 16 }

	openBranchAlarm0617 NOTIFICATION-TYPE
	OBJECTS {	neName,
			eventGroupName,			-- 06
			eventName,			-- 17
			severity,
			eventType,
			eventTime,
			faultyObject,
			monitoredValue,
			thresholdValue,
			neType }
	STATUS		current
	DESCRIPTION	"Spontaneous Alarm from the managed network element."
	::= { eventGroup06 17 }

	openBranchAlarm0618 NOTIFICATION-TYPE
	OBJECTS {	neName,
			eventGroupName,			-- 06
			eventName,			-- 18
			severity,
			eventType,
			eventTime,
			faultyObject,
			monitoredValue,
			thresholdValue,
			neType }
	STATUS		current
	DESCRIPTION	"Spontaneous Alarm from the managed network element."
	::= { eventGroup06 18 }

	openBranchAlarm0619 NOTIFICATION-TYPE
	OBJECTS {	neName,
			eventGroupName,			-- 06
			eventName,			-- 19
			severity,
			eventType,
			eventTime,
			faultyObject,
			monitoredValue,
			thresholdValue,
			neType }
	STATUS		current
	DESCRIPTION	"Spontaneous Alarm from the managed network element."
	::= { eventGroup06 19 }

	openBranchAlarm0620 NOTIFICATION-TYPE
	OBJECTS {	neName,
			eventGroupName,			-- 06
			eventName,			-- 20
			severity,
			eventType,
			eventTime,
			faultyObject,
			monitoredValue,
			thresholdValue,
			neType }
	STATUS		current
	DESCRIPTION	"Spontaneous Alarm from the managed network element."
	::= { eventGroup06 20 }

	openBranchAlarm0621 NOTIFICATION-TYPE
	OBJECTS {	neName,
			eventGroupName,			-- 06
			eventName,			-- 21
			severity,
			eventType,
			eventTime,
			faultyObject,
			monitoredValue,
			thresholdValue,
			neType }
	STATUS		current
	DESCRIPTION	"Spontaneous Alarm from the managed network element."
	::= { eventGroup06 21 }

	openBranchAlarm0622 NOTIFICATION-TYPE
	OBJECTS {	neName,
			eventGroupName,			-- 06
			eventName,			-- 22
			severity,
			eventType,
			eventTime,
			faultyObject,
			monitoredValue,
			thresholdValue,
			neType }
	STATUS		current
	DESCRIPTION	"Spontaneous Alarm from the managed network element."
	::= { eventGroup06 22 }

	openBranchAlarm0623 NOTIFICATION-TYPE
	OBJECTS {	neName,
			eventGroupName,			-- 06
			eventName,			-- 23
			severity,
			eventType,
			eventTime,
			faultyObject,
			monitoredValue,
			thresholdValue,
			neType }
	STATUS		current
	DESCRIPTION	"Spontaneous Alarm from the managed network element."
	::= { eventGroup06 23 }

	openBranchAlarm0624 NOTIFICATION-TYPE
	OBJECTS {	neName,
			eventGroupName,			-- 06
			eventName,			-- 24
			severity,
			eventType,
			eventTime,
			faultyObject,
			monitoredValue,
			thresholdValue,
			neType }
	STATUS		current
	DESCRIPTION	"Spontaneous Alarm from the managed network element."
	::= { eventGroup06 24 }

	openBranchAlarm0625 NOTIFICATION-TYPE
	OBJECTS {	neName,
			eventGroupName,			-- 06
			eventName,			-- 25
			severity,
			eventType,
			eventTime,
			faultyObject,
			monitoredValue,
			thresholdValue,
			neType }
	STATUS		current
	DESCRIPTION	"Spontaneous Alarm from the managed network element."
	::= { eventGroup06 25 }

	openBranchAlarm0626 NOTIFICATION-TYPE
	OBJECTS {	neName,
			eventGroupName,			-- 06
			eventName,			-- 26
			severity,
			eventType,
			eventTime,
			faultyObject,
			monitoredValue,
			thresholdValue,
			neType }
	STATUS		current
	DESCRIPTION	"Spontaneous Alarm from the managed network element."
	::= { eventGroup06 26 }

	openBranchAlarm0627 NOTIFICATION-TYPE
	OBJECTS {	neName,
			eventGroupName,			-- 06
			eventName,			-- 27
			severity,
			eventType,
			eventTime,
			faultyObject,
			monitoredValue,
			thresholdValue,
			neType }
	STATUS		current
	DESCRIPTION	"Spontaneous Alarm from the managed network element."
	::= { eventGroup06 27 }

	openBranchAlarm0628 NOTIFICATION-TYPE
	OBJECTS {	neName,
			eventGroupName,			-- 06
			eventName,			-- 28
			severity,
			eventType,
			eventTime,
			faultyObject,
			monitoredValue,
			thresholdValue,
			neType }
	STATUS		current
	DESCRIPTION	"Spontaneous Alarm from the managed network element."
	::= { eventGroup06 28 }

	openBranchAlarm0629 NOTIFICATION-TYPE
	OBJECTS {	neName,
			eventGroupName,			-- 06
			eventName,			-- 29
			severity,
			eventType,
			eventTime,
			faultyObject,
			monitoredValue,
			thresholdValue,
			neType }
	STATUS		current
	DESCRIPTION	"Spontaneous Alarm from the managed network element."
	::= { eventGroup06 29 }

	openBranchAlarm0630 NOTIFICATION-TYPE
	OBJECTS {	neName,
			eventGroupName,			-- 06
			eventName,			-- 30
			severity,
			eventType,
			eventTime,
			faultyObject,
			monitoredValue,
			thresholdValue,
			neType }
	STATUS		current
	DESCRIPTION	"Spontaneous Alarm from the managed network element."
	::= { eventGroup06 30 }

	openBranchAlarm0631 NOTIFICATION-TYPE
	OBJECTS {	neName,
			eventGroupName,			-- 06
			eventName,			-- 31
			severity,
			eventType,
			eventTime,
			faultyObject,
			monitoredValue,
			thresholdValue,
			neType }
	STATUS		current
	DESCRIPTION	"Spontaneous Alarm from the managed network element."
	::= { eventGroup06 31 }

	openBranchAlarm0632 NOTIFICATION-TYPE
	OBJECTS {	neName,
			eventGroupName,			-- 06
			eventName,			-- 32
			severity,
			eventType,
			eventTime,
			faultyObject,
			monitoredValue,
			thresholdValue,
			neType }
	STATUS		current
	DESCRIPTION	"Spontaneous Alarm from the managed network element."
	::= { eventGroup06 32 }


	--********************************************************************
	-- Alarm Trap Definitions for event group 07
	--********************************************************************


	openBranchAlarm0701 NOTIFICATION-TYPE
	OBJECTS {	neName,
			eventGroupName,			-- 07
			eventName,			-- 01
			severity,
			eventType,
			eventTime,
			faultyObject,
			monitoredValue,
			thresholdValue,
			neType }
	STATUS		current
	DESCRIPTION	"Spontaneous Alarm from the managed network element."
	::= { eventGroup07 1 }

	openBranchAlarm0702 NOTIFICATION-TYPE
	OBJECTS {	neName,
			eventGroupName,			-- 07
			eventName,			-- 02
			severity,
			eventType,
			eventTime,
			faultyObject,
			monitoredValue,
			thresholdValue,
			neType }
	STATUS		current
	DESCRIPTION	"Spontaneous Alarm from the managed network element."
	::= { eventGroup07 2 }

	openBranchAlarm0703 NOTIFICATION-TYPE
	OBJECTS {	neName,
			eventGroupName,			-- 07
			eventName,			-- 03
			severity,
			eventType,
			eventTime,
			faultyObject,
			monitoredValue,
			thresholdValue,
			neType }
	STATUS		current
	DESCRIPTION	"Spontaneous Alarm from the managed network element."
	::= { eventGroup07 3 }

	openBranchAlarm0704 NOTIFICATION-TYPE
	OBJECTS {	neName,
			eventGroupName,			-- 07
			eventName,			-- 04
			severity,
			eventType,
			eventTime,
			faultyObject,
			monitoredValue,
			thresholdValue,
			neType }
	STATUS		current
	DESCRIPTION	"Spontaneous Alarm from the managed network element."
	::= { eventGroup07 4 }

	openBranchAlarm0705 NOTIFICATION-TYPE
	OBJECTS {	neName,
			eventGroupName,			-- 07
			eventName,			-- 05
			severity,
			eventType,
			eventTime,
			faultyObject,
			monitoredValue,
			thresholdValue,
			neType }
	STATUS		current
	DESCRIPTION	"Spontaneous Alarm from the managed network element."
	::= { eventGroup07 5 }

	openBranchAlarm0706 NOTIFICATION-TYPE
	OBJECTS {	neName,
			eventGroupName,			-- 07
			eventName,			-- 06
			severity,
			eventType,
			eventTime,
			faultyObject,
			monitoredValue,
			thresholdValue,
			neType }
	STATUS		current
	DESCRIPTION	"Spontaneous Alarm from the managed network element."
	::= { eventGroup07 6 }

	openBranchAlarm0707 NOTIFICATION-TYPE
	OBJECTS {	neName,
			eventGroupName,			-- 07
			eventName,			-- 07
			severity,
			eventType,
			eventTime,
			faultyObject,
			monitoredValue,
			thresholdValue,
			neType }
	STATUS		current
	DESCRIPTION	"Spontaneous Alarm from the managed network element."
	::= { eventGroup07 7 }

	openBranchAlarm0708 NOTIFICATION-TYPE
	OBJECTS {	neName,
			eventGroupName,			-- 07
			eventName,			-- 08
			severity,
			eventType,
			eventTime,
			faultyObject,
			monitoredValue,
			thresholdValue,
			neType }
	STATUS		current
	DESCRIPTION	"Spontaneous Alarm from the managed network element."
	::= { eventGroup07 8 }

	openBranchAlarm0709 NOTIFICATION-TYPE
	OBJECTS {	neName,
			eventGroupName,			-- 07
			eventName,			-- 09
			severity,
			eventType,
			eventTime,
			faultyObject,
			monitoredValue,
			thresholdValue,
			neType }
	STATUS		current
	DESCRIPTION	"Spontaneous Alarm from the managed network element."
	::= { eventGroup07 9 }

	openBranchAlarm0710 NOTIFICATION-TYPE
	OBJECTS {	neName,
			eventGroupName,			-- 07
			eventName,			-- 10
			severity,
			eventType,
			eventTime,
			faultyObject,
			monitoredValue,
			thresholdValue,
			neType }
	STATUS		current
	DESCRIPTION	"Spontaneous Alarm from the managed network element."
	::= { eventGroup07 10 }

	openBranchAlarm0711 NOTIFICATION-TYPE
	OBJECTS {	neName,
			eventGroupName,			-- 07
			eventName,			-- 11
			severity,
			eventType,
			eventTime,
			faultyObject,
			monitoredValue,
			thresholdValue,
			neType }
	STATUS		current
	DESCRIPTION	"Spontaneous Alarm from the managed network element."
	::= { eventGroup07 11 }

	openBranchAlarm0712 NOTIFICATION-TYPE
	OBJECTS {	neName,
			eventGroupName,			-- 07
			eventName,			-- 12
			severity,
			eventType,
			eventTime,
			faultyObject,
			monitoredValue,
			thresholdValue,
			neType }
	STATUS		current
	DESCRIPTION	"Spontaneous Alarm from the managed network element."
	::= { eventGroup07 12 }

	openBranchAlarm0713 NOTIFICATION-TYPE
	OBJECTS {	neName,
			eventGroupName,			-- 07
			eventName,			-- 13
			severity,
			eventType,
			eventTime,
			faultyObject,
			monitoredValue,
			thresholdValue,
			neType }
	STATUS		current
	DESCRIPTION	"Spontaneous Alarm from the managed network element."
	::= { eventGroup07 13 }

	openBranchAlarm0714 NOTIFICATION-TYPE
	OBJECTS {	neName,
			eventGroupName,			-- 07
			eventName,			-- 14
			severity,
			eventType,
			eventTime,
			faultyObject,
			monitoredValue,
			thresholdValue,
			neType }
	STATUS		current
	DESCRIPTION	"Spontaneous Alarm from the managed network element."
	::= { eventGroup07 14 }

	openBranchAlarm0715 NOTIFICATION-TYPE
	OBJECTS {	neName,
			eventGroupName,			-- 07
			eventName,			-- 15
			severity,
			eventType,
			eventTime,
			faultyObject,
			monitoredValue,
			thresholdValue,
			neType }
	STATUS		current
	DESCRIPTION	"Spontaneous Alarm from the managed network element."
	::= { eventGroup07 15 }

	openBranchAlarm0716 NOTIFICATION-TYPE
	OBJECTS {	neName,
			eventGroupName,			-- 07
			eventName,			-- 16
			severity,
			eventType,
			eventTime,
			faultyObject,
			monitoredValue,
			thresholdValue,
			neType }
	STATUS		current
	DESCRIPTION	"Spontaneous Alarm from the managed network element."
	::= { eventGroup07 16 }

	openBranchAlarm0717 NOTIFICATION-TYPE
	OBJECTS {	neName,
			eventGroupName,			-- 07
			eventName,			-- 17
			severity,
			eventType,
			eventTime,
			faultyObject,
			monitoredValue,
			thresholdValue,
			neType }
	STATUS		current
	DESCRIPTION	"Spontaneous Alarm from the managed network element."
	::= { eventGroup07 17 }

	openBranchAlarm0718 NOTIFICATION-TYPE
	OBJECTS {	neName,
			eventGroupName,			-- 07
			eventName,			-- 18
			severity,
			eventType,
			eventTime,
			faultyObject,
			monitoredValue,
			thresholdValue,
			neType }
	STATUS		current
	DESCRIPTION	"Spontaneous Alarm from the managed network element."
	::= { eventGroup07 18 }

	openBranchAlarm0719 NOTIFICATION-TYPE
	OBJECTS {	neName,
			eventGroupName,			-- 07
			eventName,			-- 19
			severity,
			eventType,
			eventTime,
			faultyObject,
			monitoredValue,
			thresholdValue,
			neType }
	STATUS		current
	DESCRIPTION	"Spontaneous Alarm from the managed network element."
	::= { eventGroup07 19 }

	openBranchAlarm0720 NOTIFICATION-TYPE
	OBJECTS {	neName,
			eventGroupName,			-- 07
			eventName,			-- 20
			severity,
			eventType,
			eventTime,
			faultyObject,
			monitoredValue,
			thresholdValue,
			neType }
	STATUS		current
	DESCRIPTION	"Spontaneous Alarm from the managed network element."
	::= { eventGroup07 20 }

	openBranchAlarm0721 NOTIFICATION-TYPE
	OBJECTS {	neName,
			eventGroupName,			-- 07
			eventName,			-- 21
			severity,
			eventType,
			eventTime,
			faultyObject,
			monitoredValue,
			thresholdValue,
			neType }
	STATUS		current
	DESCRIPTION	"Spontaneous Alarm from the managed network element."
	::= { eventGroup07 21 }

	openBranchAlarm0722 NOTIFICATION-TYPE
	OBJECTS {	neName,
			eventGroupName,			-- 07
			eventName,			-- 22
			severity,
			eventType,
			eventTime,
			faultyObject,
			monitoredValue,
			thresholdValue,
			neType }
	STATUS		current
	DESCRIPTION	"Spontaneous Alarm from the managed network element."
	::= { eventGroup07 22 }

	openBranchAlarm0723 NOTIFICATION-TYPE
	OBJECTS {	neName,
			eventGroupName,			-- 07
			eventName,			-- 23
			severity,
			eventType,
			eventTime,
			faultyObject,
			monitoredValue,
			thresholdValue,
			neType }
	STATUS		current
	DESCRIPTION	"Spontaneous Alarm from the managed network element."
	::= { eventGroup07 23 }

	openBranchAlarm0724 NOTIFICATION-TYPE
	OBJECTS {	neName,
			eventGroupName,			-- 07
			eventName,			-- 24
			severity,
			eventType,
			eventTime,
			faultyObject,
			monitoredValue,
			thresholdValue,
			neType }
	STATUS		current
	DESCRIPTION	"Spontaneous Alarm from the managed network element."
	::= { eventGroup07 24 }

	openBranchAlarm0725 NOTIFICATION-TYPE
	OBJECTS {	neName,
			eventGroupName,			-- 07
			eventName,			-- 25
			severity,
			eventType,
			eventTime,
			faultyObject,
			monitoredValue,
			thresholdValue,
			neType }
	STATUS		current
	DESCRIPTION	"Spontaneous Alarm from the managed network element."
	::= { eventGroup07 25 }

	openBranchAlarm0726 NOTIFICATION-TYPE
	OBJECTS {	neName,
			eventGroupName,			-- 07
			eventName,			-- 26
			severity,
			eventType,
			eventTime,
			faultyObject,
			monitoredValue,
			thresholdValue,
			neType }
	STATUS		current
	DESCRIPTION	"Spontaneous Alarm from the managed network element."
	::= { eventGroup07 26 }

	openBranchAlarm0727 NOTIFICATION-TYPE
	OBJECTS {	neName,
			eventGroupName,			-- 07
			eventName,			-- 27
			severity,
			eventType,
			eventTime,
			faultyObject,
			monitoredValue,
			thresholdValue,
			neType }
	STATUS		current
	DESCRIPTION	"Spontaneous Alarm from the managed network element."
	::= { eventGroup07 27 }

	openBranchAlarm0728 NOTIFICATION-TYPE
	OBJECTS {	neName,
			eventGroupName,			-- 07
			eventName,			-- 28
			severity,
			eventType,
			eventTime,
			faultyObject,
			monitoredValue,
			thresholdValue,
			neType }
	STATUS		current
	DESCRIPTION	"Spontaneous Alarm from the managed network element."
	::= { eventGroup07 28 }

	openBranchAlarm0729 NOTIFICATION-TYPE
	OBJECTS {	neName,
			eventGroupName,			-- 07
			eventName,			-- 29
			severity,
			eventType,
			eventTime,
			faultyObject,
			monitoredValue,
			thresholdValue,
			neType }
	STATUS		current
	DESCRIPTION	"Spontaneous Alarm from the managed network element."
	::= { eventGroup07 29 }

	openBranchAlarm0730 NOTIFICATION-TYPE
	OBJECTS {	neName,
			eventGroupName,			-- 07
			eventName,			-- 30
			severity,
			eventType,
			eventTime,
			faultyObject,
			monitoredValue,
			thresholdValue,
			neType }
	STATUS		current
	DESCRIPTION	"Spontaneous Alarm from the managed network element."
	::= { eventGroup07 30 }

	openBranchAlarm0731 NOTIFICATION-TYPE
	OBJECTS {	neName,
			eventGroupName,			-- 07
			eventName,			-- 31
			severity,
			eventType,
			eventTime,
			faultyObject,
			monitoredValue,
			thresholdValue,
			neType }
	STATUS		current
	DESCRIPTION	"Spontaneous Alarm from the managed network element."
	::= { eventGroup07 31 }

	openBranchAlarm0732 NOTIFICATION-TYPE
	OBJECTS {	neName,
			eventGroupName,			-- 07
			eventName,			-- 32
			severity,
			eventType,
			eventTime,
			faultyObject,
			monitoredValue,
			thresholdValue,
			neType }
	STATUS		current
	DESCRIPTION	"Spontaneous Alarm from the managed network element."
	::= { eventGroup07 32 }


	--********************************************************************
	-- Alarm Trap Definitions for event group 08
	--********************************************************************


	openBranchAlarm0801 NOTIFICATION-TYPE
	OBJECTS {	neName,
			eventGroupName,			-- 08
			eventName,			-- 01
			severity,
			eventType,
			eventTime,
			faultyObject,
			monitoredValue,
			thresholdValue,
			neType }
	STATUS		current
	DESCRIPTION	"Spontaneous Alarm from the managed network element."
	::= { eventGroup08 1 }

	openBranchAlarm0802 NOTIFICATION-TYPE
	OBJECTS {	neName,
			eventGroupName,			-- 08
			eventName,			-- 02
			severity,
			eventType,
			eventTime,
			faultyObject,
			monitoredValue,
			thresholdValue,
			neType }
	STATUS		current
	DESCRIPTION	"Spontaneous Alarm from the managed network element."
	::= { eventGroup08 2 }

	openBranchAlarm0803 NOTIFICATION-TYPE
	OBJECTS {	neName,
			eventGroupName,			-- 08
			eventName,			-- 03
			severity,
			eventType,
			eventTime,
			faultyObject,
			monitoredValue,
			thresholdValue,
			neType }
	STATUS		current
	DESCRIPTION	"Spontaneous Alarm from the managed network element."
	::= { eventGroup08 3 }

	openBranchAlarm0804 NOTIFICATION-TYPE
	OBJECTS {	neName,
			eventGroupName,			-- 08
			eventName,			-- 04
			severity,
			eventType,
			eventTime,
			faultyObject,
			monitoredValue,
			thresholdValue,
			neType }
	STATUS		current
	DESCRIPTION	"Spontaneous Alarm from the managed network element."
	::= { eventGroup08 4 }

	openBranchAlarm0805 NOTIFICATION-TYPE
	OBJECTS {	neName,
			eventGroupName,			-- 08
			eventName,			-- 05
			severity,
			eventType,
			eventTime,
			faultyObject,
			monitoredValue,
			thresholdValue,
			neType }
	STATUS		current
	DESCRIPTION	"Spontaneous Alarm from the managed network element."
	::= { eventGroup08 5 }

	openBranchAlarm0806 NOTIFICATION-TYPE
	OBJECTS {	neName,
			eventGroupName,			-- 08
			eventName,			-- 06
			severity,
			eventType,
			eventTime,
			faultyObject,
			monitoredValue,
			thresholdValue,
			neType }
	STATUS		current
	DESCRIPTION	"Spontaneous Alarm from the managed network element."
	::= { eventGroup08 6 }

	openBranchAlarm0807 NOTIFICATION-TYPE
	OBJECTS {	neName,
			eventGroupName,			-- 08
			eventName,			-- 07
			severity,
			eventType,
			eventTime,
			faultyObject,
			monitoredValue,
			thresholdValue,
			neType }
	STATUS		current
	DESCRIPTION	"Spontaneous Alarm from the managed network element."
	::= { eventGroup08 7 }

	openBranchAlarm0808 NOTIFICATION-TYPE
	OBJECTS {	neName,
			eventGroupName,			-- 08
			eventName,			-- 08
			severity,
			eventType,
			eventTime,
			faultyObject,
			monitoredValue,
			thresholdValue,
			neType }
	STATUS		current
	DESCRIPTION	"Spontaneous Alarm from the managed network element."
	::= { eventGroup08 8 }

	openBranchAlarm0809 NOTIFICATION-TYPE
	OBJECTS {	neName,
			eventGroupName,			-- 08
			eventName,			-- 09
			severity,
			eventType,
			eventTime,
			faultyObject,
			monitoredValue,
			thresholdValue,
			neType }
	STATUS		current
	DESCRIPTION	"Spontaneous Alarm from the managed network element."
	::= { eventGroup08 9 }

	openBranchAlarm0810 NOTIFICATION-TYPE
	OBJECTS {	neName,
			eventGroupName,			-- 08
			eventName,			-- 10
			severity,
			eventType,
			eventTime,
			faultyObject,
			monitoredValue,
			thresholdValue,
			neType }
	STATUS		current
	DESCRIPTION	"Spontaneous Alarm from the managed network element."
	::= { eventGroup08 10 }

	openBranchAlarm0811 NOTIFICATION-TYPE
	OBJECTS {	neName,
			eventGroupName,			-- 08
			eventName,			-- 11
			severity,
			eventType,
			eventTime,
			faultyObject,
			monitoredValue,
			thresholdValue,
			neType }
	STATUS		current
	DESCRIPTION	"Spontaneous Alarm from the managed network element."
	::= { eventGroup08 11 }

	openBranchAlarm0812 NOTIFICATION-TYPE
	OBJECTS {	neName,
			eventGroupName,			-- 08
			eventName,			-- 12
			severity,
			eventType,
			eventTime,
			faultyObject,
			monitoredValue,
			thresholdValue,
			neType }
	STATUS		current
	DESCRIPTION	"Spontaneous Alarm from the managed network element."
	::= { eventGroup08 12 }

	openBranchAlarm0813 NOTIFICATION-TYPE
	OBJECTS {	neName,
			eventGroupName,			-- 08
			eventName,			-- 13
			severity,
			eventType,
			eventTime,
			faultyObject,
			monitoredValue,
			thresholdValue,
			neType }
	STATUS		current
	DESCRIPTION	"Spontaneous Alarm from the managed network element."
	::= { eventGroup08 13 }

	openBranchAlarm0814 NOTIFICATION-TYPE
	OBJECTS {	neName,
			eventGroupName,			-- 08
			eventName,			-- 14
			severity,
			eventType,
			eventTime,
			faultyObject,
			monitoredValue,
			thresholdValue,
			neType }
	STATUS		current
	DESCRIPTION	"Spontaneous Alarm from the managed network element."
	::= { eventGroup08 14 }

	openBranchAlarm0815 NOTIFICATION-TYPE
	OBJECTS {	neName,
			eventGroupName,			-- 08
			eventName,			-- 15
			severity,
			eventType,
			eventTime,
			faultyObject,
			monitoredValue,
			thresholdValue,
			neType }
	STATUS		current
	DESCRIPTION	"Spontaneous Alarm from the managed network element."
	::= { eventGroup08 15 }

	openBranchAlarm0816 NOTIFICATION-TYPE
	OBJECTS {	neName,
			eventGroupName,			-- 08
			eventName,			-- 16
			severity,
			eventType,
			eventTime,
			faultyObject,
			monitoredValue,
			thresholdValue,
			neType }
	STATUS		current
	DESCRIPTION	"Spontaneous Alarm from the managed network element."
	::= { eventGroup08 16 }

	openBranchAlarm0817 NOTIFICATION-TYPE
	OBJECTS {	neName,
			eventGroupName,			-- 08
			eventName,			-- 17
			severity,
			eventType,
			eventTime,
			faultyObject,
			monitoredValue,
			thresholdValue,
			neType }
	STATUS		current
	DESCRIPTION	"Spontaneous Alarm from the managed network element."
	::= { eventGroup08 17 }

	openBranchAlarm0818 NOTIFICATION-TYPE
	OBJECTS {	neName,
			eventGroupName,			-- 08
			eventName,			-- 18
			severity,
			eventType,
			eventTime,
			faultyObject,
			monitoredValue,
			thresholdValue,
			neType }
	STATUS		current
	DESCRIPTION	"Spontaneous Alarm from the managed network element."
	::= { eventGroup08 18 }

	openBranchAlarm0819 NOTIFICATION-TYPE
	OBJECTS {	neName,
			eventGroupName,			-- 08
			eventName,			-- 19
			severity,
			eventType,
			eventTime,
			faultyObject,
			monitoredValue,
			thresholdValue,
			neType }
	STATUS		current
	DESCRIPTION	"Spontaneous Alarm from the managed network element."
	::= { eventGroup08 19 }

	openBranchAlarm0820 NOTIFICATION-TYPE
	OBJECTS {	neName,
			eventGroupName,			-- 08
			eventName,			-- 20
			severity,
			eventType,
			eventTime,
			faultyObject,
			monitoredValue,
			thresholdValue,
			neType }
	STATUS		current
	DESCRIPTION	"Spontaneous Alarm from the managed network element."
	::= { eventGroup08 20 }

	openBranchAlarm0821 NOTIFICATION-TYPE
	OBJECTS {	neName,
			eventGroupName,			-- 08
			eventName,			-- 21
			severity,
			eventType,
			eventTime,
			faultyObject,
			monitoredValue,
			thresholdValue,
			neType }
	STATUS		current
	DESCRIPTION	"Spontaneous Alarm from the managed network element."
	::= { eventGroup08 21 }

	openBranchAlarm0822 NOTIFICATION-TYPE
	OBJECTS {	neName,
			eventGroupName,			-- 08
			eventName,			-- 22
			severity,
			eventType,
			eventTime,
			faultyObject,
			monitoredValue,
			thresholdValue,
			neType }
	STATUS		current
	DESCRIPTION	"Spontaneous Alarm from the managed network element."
	::= { eventGroup08 22 }

	openBranchAlarm0823 NOTIFICATION-TYPE
	OBJECTS {	neName,
			eventGroupName,			-- 08
			eventName,			-- 23
			severity,
			eventType,
			eventTime,
			faultyObject,
			monitoredValue,
			thresholdValue,
			neType }
	STATUS		current
	DESCRIPTION	"Spontaneous Alarm from the managed network element."
	::= { eventGroup08 23 }

	openBranchAlarm0824 NOTIFICATION-TYPE
	OBJECTS {	neName,
			eventGroupName,			-- 08
			eventName,			-- 24
			severity,
			eventType,
			eventTime,
			faultyObject,
			monitoredValue,
			thresholdValue,
			neType }
	STATUS		current
	DESCRIPTION	"Spontaneous Alarm from the managed network element."
	::= { eventGroup08 24 }

	openBranchAlarm0825 NOTIFICATION-TYPE
	OBJECTS {	neName,
			eventGroupName,			-- 08
			eventName,			-- 25
			severity,
			eventType,
			eventTime,
			faultyObject,
			monitoredValue,
			thresholdValue,
			neType }
	STATUS		current
	DESCRIPTION	"Spontaneous Alarm from the managed network element."
	::= { eventGroup08 25 }

	openBranchAlarm0826 NOTIFICATION-TYPE
	OBJECTS {	neName,
			eventGroupName,			-- 08
			eventName,			-- 26
			severity,
			eventType,
			eventTime,
			faultyObject,
			monitoredValue,
			thresholdValue,
			neType }
	STATUS		current
	DESCRIPTION	"Spontaneous Alarm from the managed network element."
	::= { eventGroup08 26 }

	openBranchAlarm0827 NOTIFICATION-TYPE
	OBJECTS {	neName,
			eventGroupName,			-- 08
			eventName,			-- 27
			severity,
			eventType,
			eventTime,
			faultyObject,
			monitoredValue,
			thresholdValue,
			neType }
	STATUS		current
	DESCRIPTION	"Spontaneous Alarm from the managed network element."
	::= { eventGroup08 27 }

	openBranchAlarm0828 NOTIFICATION-TYPE
	OBJECTS {	neName,
			eventGroupName,			-- 08
			eventName,			-- 28
			severity,
			eventType,
			eventTime,
			faultyObject,
			monitoredValue,
			thresholdValue,
			neType }
	STATUS		current
	DESCRIPTION	"Spontaneous Alarm from the managed network element."
	::= { eventGroup08 28 }

	openBranchAlarm0829 NOTIFICATION-TYPE
	OBJECTS {	neName,
			eventGroupName,			-- 08
			eventName,			-- 29
			severity,
			eventType,
			eventTime,
			faultyObject,
			monitoredValue,
			thresholdValue,
			neType }
	STATUS		current
	DESCRIPTION	"Spontaneous Alarm from the managed network element."
	::= { eventGroup08 29 }

	openBranchAlarm0830 NOTIFICATION-TYPE
	OBJECTS {	neName,
			eventGroupName,			-- 08
			eventName,			-- 30
			severity,
			eventType,
			eventTime,
			faultyObject,
			monitoredValue,
			thresholdValue,
			neType }
	STATUS		current
	DESCRIPTION	"Spontaneous Alarm from the managed network element."
	::= { eventGroup08 30 }

	openBranchAlarm0831 NOTIFICATION-TYPE
	OBJECTS {	neName,
			eventGroupName,			-- 08
			eventName,			-- 31
			severity,
			eventType,
			eventTime,
			faultyObject,
			monitoredValue,
			thresholdValue,
			neType }
	STATUS		current
	DESCRIPTION	"Spontaneous Alarm from the managed network element."
	::= { eventGroup08 31 }

	openBranchAlarm0832 NOTIFICATION-TYPE
	OBJECTS {	neName,
			eventGroupName,			-- 08
			eventName,			-- 32
			severity,
			eventType,
			eventTime,
			faultyObject,
			monitoredValue,
			thresholdValue,
			neType }
	STATUS		current
	DESCRIPTION	"Spontaneous Alarm from the managed network element."
	::= { eventGroup08 32 }


	--********************************************************************
	-- Alarm Trap Definitions for event group 09
	--********************************************************************


	openBranchAlarm0901 NOTIFICATION-TYPE
	OBJECTS {	neName,
			eventGroupName,			-- 09
			eventName,			-- 01
			severity,
			eventType,
			eventTime,
			faultyObject,
			monitoredValue,
			thresholdValue,
			neType }
	STATUS		current
	DESCRIPTION	"Spontaneous Alarm from the managed network element."
	::= { eventGroup09 1 }

	openBranchAlarm0902 NOTIFICATION-TYPE
	OBJECTS {	neName,
			eventGroupName,			-- 09
			eventName,			-- 02
			severity,
			eventType,
			eventTime,
			faultyObject,
			monitoredValue,
			thresholdValue,
			neType }
	STATUS		current
	DESCRIPTION	"Spontaneous Alarm from the managed network element."
	::= { eventGroup09 2 }

	openBranchAlarm0903 NOTIFICATION-TYPE
	OBJECTS {	neName,
			eventGroupName,			-- 09
			eventName,			-- 03
			severity,
			eventType,
			eventTime,
			faultyObject,
			monitoredValue,
			thresholdValue,
			neType }
	STATUS		current
	DESCRIPTION	"Spontaneous Alarm from the managed network element."
	::= { eventGroup09 3 }

	openBranchAlarm0904 NOTIFICATION-TYPE
	OBJECTS {	neName,
			eventGroupName,			-- 09
			eventName,			-- 04
			severity,
			eventType,
			eventTime,
			faultyObject,
			monitoredValue,
			thresholdValue,
			neType }
	STATUS		current
	DESCRIPTION	"Spontaneous Alarm from the managed network element."
	::= { eventGroup09 4 }

	openBranchAlarm0905 NOTIFICATION-TYPE
	OBJECTS {	neName,
			eventGroupName,			-- 09
			eventName,			-- 05
			severity,
			eventType,
			eventTime,
			faultyObject,
			monitoredValue,
			thresholdValue,
			neType }
	STATUS		current
	DESCRIPTION	"Spontaneous Alarm from the managed network element."
	::= { eventGroup09 5 }

	openBranchAlarm0906 NOTIFICATION-TYPE
	OBJECTS {	neName,
			eventGroupName,			-- 09
			eventName,			-- 06
			severity,
			eventType,
			eventTime,
			faultyObject,
			monitoredValue,
			thresholdValue,
			neType }
	STATUS		current
	DESCRIPTION	"Spontaneous Alarm from the managed network element."
	::= { eventGroup09 6 }

	openBranchAlarm0907 NOTIFICATION-TYPE
	OBJECTS {	neName,
			eventGroupName,			-- 09
			eventName,			-- 07
			severity,
			eventType,
			eventTime,
			faultyObject,
			monitoredValue,
			thresholdValue,
			neType }
	STATUS		current
	DESCRIPTION	"Spontaneous Alarm from the managed network element."
	::= { eventGroup09 7 }

	openBranchAlarm0908 NOTIFICATION-TYPE
	OBJECTS {	neName,
			eventGroupName,			-- 09
			eventName,			-- 08
			severity,
			eventType,
			eventTime,
			faultyObject,
			monitoredValue,
			thresholdValue,
			neType }
	STATUS		current
	DESCRIPTION	"Spontaneous Alarm from the managed network element."
	::= { eventGroup09 8 }

	openBranchAlarm0909 NOTIFICATION-TYPE
	OBJECTS {	neName,
			eventGroupName,			-- 09
			eventName,			-- 09
			severity,
			eventType,
			eventTime,
			faultyObject,
			monitoredValue,
			thresholdValue,
			neType }
	STATUS		current
	DESCRIPTION	"Spontaneous Alarm from the managed network element."
	::= { eventGroup09 9 }

	openBranchAlarm0910 NOTIFICATION-TYPE
	OBJECTS {	neName,
			eventGroupName,			-- 09
			eventName,			-- 10
			severity,
			eventType,
			eventTime,
			faultyObject,
			monitoredValue,
			thresholdValue,
			neType }
	STATUS		current
	DESCRIPTION	"Spontaneous Alarm from the managed network element."
	::= { eventGroup09 10 }

	openBranchAlarm0911 NOTIFICATION-TYPE
	OBJECTS {	neName,
			eventGroupName,			-- 09
			eventName,			-- 11
			severity,
			eventType,
			eventTime,
			faultyObject,
			monitoredValue,
			thresholdValue,
			neType }
	STATUS		current
	DESCRIPTION	"Spontaneous Alarm from the managed network element."
	::= { eventGroup09 11 }

	openBranchAlarm0912 NOTIFICATION-TYPE
	OBJECTS {	neName,
			eventGroupName,			-- 09
			eventName,			-- 12
			severity,
			eventType,
			eventTime,
			faultyObject,
			monitoredValue,
			thresholdValue,
			neType }
	STATUS		current
	DESCRIPTION	"Spontaneous Alarm from the managed network element."
	::= { eventGroup09 12 }

	openBranchAlarm0913 NOTIFICATION-TYPE
	OBJECTS {	neName,
			eventGroupName,			-- 09
			eventName,			-- 13
			severity,
			eventType,
			eventTime,
			faultyObject,
			monitoredValue,
			thresholdValue,
			neType }
	STATUS		current
	DESCRIPTION	"Spontaneous Alarm from the managed network element."
	::= { eventGroup09 13 }

	openBranchAlarm0914 NOTIFICATION-TYPE
	OBJECTS {	neName,
			eventGroupName,			-- 09
			eventName,			-- 14
			severity,
			eventType,
			eventTime,
			faultyObject,
			monitoredValue,
			thresholdValue,
			neType }
	STATUS		current
	DESCRIPTION	"Spontaneous Alarm from the managed network element."
	::= { eventGroup09 14 }

	openBranchAlarm0915 NOTIFICATION-TYPE
	OBJECTS {	neName,
			eventGroupName,			-- 09
			eventName,			-- 15
			severity,
			eventType,
			eventTime,
			faultyObject,
			monitoredValue,
			thresholdValue,
			neType }
	STATUS		current
	DESCRIPTION	"Spontaneous Alarm from the managed network element."
	::= { eventGroup09 15 }

	openBranchAlarm0916 NOTIFICATION-TYPE
	OBJECTS {	neName,
			eventGroupName,			-- 09
			eventName,			-- 16
			severity,
			eventType,
			eventTime,
			faultyObject,
			monitoredValue,
			thresholdValue,
			neType }
	STATUS		current
	DESCRIPTION	"Spontaneous Alarm from the managed network element."
	::= { eventGroup09 16 }

	openBranchAlarm0917 NOTIFICATION-TYPE
	OBJECTS {	neName,
			eventGroupName,			-- 09
			eventName,			-- 17
			severity,
			eventType,
			eventTime,
			faultyObject,
			monitoredValue,
			thresholdValue,
			neType }
	STATUS		current
	DESCRIPTION	"Spontaneous Alarm from the managed network element."
	::= { eventGroup09 17 }

	openBranchAlarm0918 NOTIFICATION-TYPE
	OBJECTS {	neName,
			eventGroupName,			-- 09
			eventName,			-- 18
			severity,
			eventType,
			eventTime,
			faultyObject,
			monitoredValue,
			thresholdValue,
			neType }
	STATUS		current
	DESCRIPTION	"Spontaneous Alarm from the managed network element."
	::= { eventGroup09 18 }

	openBranchAlarm0919 NOTIFICATION-TYPE
	OBJECTS {	neName,
			eventGroupName,			-- 09
			eventName,			-- 19
			severity,
			eventType,
			eventTime,
			faultyObject,
			monitoredValue,
			thresholdValue,
			neType }
	STATUS		current
	DESCRIPTION	"Spontaneous Alarm from the managed network element."
	::= { eventGroup09 19 }

	openBranchAlarm0920 NOTIFICATION-TYPE
	OBJECTS {	neName,
			eventGroupName,			-- 09
			eventName,			-- 20
			severity,
			eventType,
			eventTime,
			faultyObject,
			monitoredValue,
			thresholdValue,
			neType }
	STATUS		current
	DESCRIPTION	"Spontaneous Alarm from the managed network element."
	::= { eventGroup09 20 }

	openBranchAlarm0921 NOTIFICATION-TYPE
	OBJECTS {	neName,
			eventGroupName,			-- 09
			eventName,			-- 21
			severity,
			eventType,
			eventTime,
			faultyObject,
			monitoredValue,
			thresholdValue,
			neType }
	STATUS		current
	DESCRIPTION	"Spontaneous Alarm from the managed network element."
	::= { eventGroup09 21 }

	openBranchAlarm0922 NOTIFICATION-TYPE
	OBJECTS {	neName,
			eventGroupName,			-- 09
			eventName,			-- 22
			severity,
			eventType,
			eventTime,
			faultyObject,
			monitoredValue,
			thresholdValue,
			neType }
	STATUS		current
	DESCRIPTION	"Spontaneous Alarm from the managed network element."
	::= { eventGroup09 22 }

	openBranchAlarm0923 NOTIFICATION-TYPE
	OBJECTS {	neName,
			eventGroupName,			-- 09
			eventName,			-- 23
			severity,
			eventType,
			eventTime,
			faultyObject,
			monitoredValue,
			thresholdValue,
			neType }
	STATUS		current
	DESCRIPTION	"Spontaneous Alarm from the managed network element."
	::= { eventGroup09 23 }

	openBranchAlarm0924 NOTIFICATION-TYPE
	OBJECTS {	neName,
			eventGroupName,			-- 09
			eventName,			-- 24
			severity,
			eventType,
			eventTime,
			faultyObject,
			monitoredValue,
			thresholdValue,
			neType }
	STATUS		current
	DESCRIPTION	"Spontaneous Alarm from the managed network element."
	::= { eventGroup09 24 }

	openBranchAlarm0925 NOTIFICATION-TYPE
	OBJECTS {	neName,
			eventGroupName,			-- 09
			eventName,			-- 25
			severity,
			eventType,
			eventTime,
			faultyObject,
			monitoredValue,
			thresholdValue,
			neType }
	STATUS		current
	DESCRIPTION	"Spontaneous Alarm from the managed network element."
	::= { eventGroup09 25 }

	openBranchAlarm0926 NOTIFICATION-TYPE
	OBJECTS {	neName,
			eventGroupName,			-- 09
			eventName,			-- 26
			severity,
			eventType,
			eventTime,
			faultyObject,
			monitoredValue,
			thresholdValue,
			neType }
	STATUS		current
	DESCRIPTION	"Spontaneous Alarm from the managed network element."
	::= { eventGroup09 26 }

	openBranchAlarm0927 NOTIFICATION-TYPE
	OBJECTS {	neName,
			eventGroupName,			-- 09
			eventName,			-- 27
			severity,
			eventType,
			eventTime,
			faultyObject,
			monitoredValue,
			thresholdValue,
			neType }
	STATUS		current
	DESCRIPTION	"Spontaneous Alarm from the managed network element."
	::= { eventGroup09 27 }

	openBranchAlarm0928 NOTIFICATION-TYPE
	OBJECTS {	neName,
			eventGroupName,			-- 09
			eventName,			-- 28
			severity,
			eventType,
			eventTime,
			faultyObject,
			monitoredValue,
			thresholdValue,
			neType }
	STATUS		current
	DESCRIPTION	"Spontaneous Alarm from the managed network element."
	::= { eventGroup09 28 }

	openBranchAlarm0929 NOTIFICATION-TYPE
	OBJECTS {	neName,
			eventGroupName,			-- 09
			eventName,			-- 29
			severity,
			eventType,
			eventTime,
			faultyObject,
			monitoredValue,
			thresholdValue,
			neType }
	STATUS		current
	DESCRIPTION	"Spontaneous Alarm from the managed network element."
	::= { eventGroup09 29 }

	openBranchAlarm0930 NOTIFICATION-TYPE
	OBJECTS {	neName,
			eventGroupName,			-- 09
			eventName,			-- 30
			severity,
			eventType,
			eventTime,
			faultyObject,
			monitoredValue,
			thresholdValue,
			neType }
	STATUS		current
	DESCRIPTION	"Spontaneous Alarm from the managed network element."
	::= { eventGroup09 30 }

	openBranchAlarm0931 NOTIFICATION-TYPE
	OBJECTS {	neName,
			eventGroupName,			-- 09
			eventName,			-- 31
			severity,
			eventType,
			eventTime,
			faultyObject,
			monitoredValue,
			thresholdValue,
			neType }
	STATUS		current
	DESCRIPTION	"Spontaneous Alarm from the managed network element."
	::= { eventGroup09 31 }

	openBranchAlarm0932 NOTIFICATION-TYPE
	OBJECTS {	neName,
			eventGroupName,			-- 09
			eventName,			-- 32
			severity,
			eventType,
			eventTime,
			faultyObject,
			monitoredValue,
			thresholdValue,
			neType }
	STATUS		current
	DESCRIPTION	"Spontaneous Alarm from the managed network element."
	::= { eventGroup09 32 }


	--********************************************************************
	-- Alarm Trap Definitions for event group 10
	--********************************************************************


	openBranchAlarm1001 NOTIFICATION-TYPE
	OBJECTS {	neName,
			eventGroupName,			-- 10
			eventName,			-- 01
			severity,
			eventType,
			eventTime,
			faultyObject,
			monitoredValue,
			thresholdValue,
			neType }
	STATUS		current
	DESCRIPTION	"Spontaneous Alarm from the managed network element."
	::= { eventGroup10 1 }

	openBranchAlarm1002 NOTIFICATION-TYPE
	OBJECTS {	neName,
			eventGroupName,			-- 10
			eventName,			-- 02
			severity,
			eventType,
			eventTime,
			faultyObject,
			monitoredValue,
			thresholdValue,
			neType }
	STATUS		current
	DESCRIPTION	"Spontaneous Alarm from the managed network element."
	::= { eventGroup10 2 }

	openBranchAlarm1003 NOTIFICATION-TYPE
	OBJECTS {	neName,
			eventGroupName,			-- 10
			eventName,			-- 03
			severity,
			eventType,
			eventTime,
			faultyObject,
			monitoredValue,
			thresholdValue,
			neType }
	STATUS		current
	DESCRIPTION	"Spontaneous Alarm from the managed network element."
	::= { eventGroup10 3 }

	openBranchAlarm1004 NOTIFICATION-TYPE
	OBJECTS {	neName,
			eventGroupName,			-- 10
			eventName,			-- 04
			severity,
			eventType,
			eventTime,
			faultyObject,
			monitoredValue,
			thresholdValue,
			neType }
	STATUS		current
	DESCRIPTION	"Spontaneous Alarm from the managed network element."
	::= { eventGroup10 4 }

	openBranchAlarm1005 NOTIFICATION-TYPE
	OBJECTS {	neName,
			eventGroupName,			-- 10
			eventName,			-- 05
			severity,
			eventType,
			eventTime,
			faultyObject,
			monitoredValue,
			thresholdValue,
			neType }
	STATUS		current
	DESCRIPTION	"Spontaneous Alarm from the managed network element."
	::= { eventGroup10 5 }

	openBranchAlarm1006 NOTIFICATION-TYPE
	OBJECTS {	neName,
			eventGroupName,			-- 10
			eventName,			-- 06
			severity,
			eventType,
			eventTime,
			faultyObject,
			monitoredValue,
			thresholdValue,
			neType }
	STATUS		current
	DESCRIPTION	"Spontaneous Alarm from the managed network element."
	::= { eventGroup10 6 }

	openBranchAlarm1007 NOTIFICATION-TYPE
	OBJECTS {	neName,
			eventGroupName,			-- 10
			eventName,			-- 07
			severity,
			eventType,
			eventTime,
			faultyObject,
			monitoredValue,
			thresholdValue,
			neType }
	STATUS		current
	DESCRIPTION	"Spontaneous Alarm from the managed network element."
	::= { eventGroup10 7 }

	openBranchAlarm1008 NOTIFICATION-TYPE
	OBJECTS {	neName,
			eventGroupName,			-- 10
			eventName,			-- 08
			severity,
			eventType,
			eventTime,
			faultyObject,
			monitoredValue,
			thresholdValue,
			neType }
	STATUS		current
	DESCRIPTION	"Spontaneous Alarm from the managed network element."
	::= { eventGroup10 8 }

	openBranchAlarm1009 NOTIFICATION-TYPE
	OBJECTS {	neName,
			eventGroupName,			-- 10
			eventName,			-- 09
			severity,
			eventType,
			eventTime,
			faultyObject,
			monitoredValue,
			thresholdValue,
			neType }
	STATUS		current
	DESCRIPTION	"Spontaneous Alarm from the managed network element."
	::= { eventGroup10 9 }

	openBranchAlarm1010 NOTIFICATION-TYPE
	OBJECTS {	neName,
			eventGroupName,			-- 10
			eventName,			-- 10
			severity,
			eventType,
			eventTime,
			faultyObject,
			monitoredValue,
			thresholdValue,
			neType }
	STATUS		current
	DESCRIPTION	"Spontaneous Alarm from the managed network element."
	::= { eventGroup10 10 }

	openBranchAlarm1011 NOTIFICATION-TYPE
	OBJECTS {	neName,
			eventGroupName,			-- 10
			eventName,			-- 11
			severity,
			eventType,
			eventTime,
			faultyObject,
			monitoredValue,
			thresholdValue,
			neType }
	STATUS		current
	DESCRIPTION	"Spontaneous Alarm from the managed network element."
	::= { eventGroup10 11 }

	openBranchAlarm1012 NOTIFICATION-TYPE
	OBJECTS {	neName,
			eventGroupName,			-- 10
			eventName,			-- 12
			severity,
			eventType,
			eventTime,
			faultyObject,
			monitoredValue,
			thresholdValue,
			neType }
	STATUS		current
	DESCRIPTION	"Spontaneous Alarm from the managed network element."
	::= { eventGroup10 12 }

	openBranchAlarm1013 NOTIFICATION-TYPE
	OBJECTS {	neName,
			eventGroupName,			-- 10
			eventName,			-- 13
			severity,
			eventType,
			eventTime,
			faultyObject,
			monitoredValue,
			thresholdValue,
			neType }
	STATUS		current
	DESCRIPTION	"Spontaneous Alarm from the managed network element."
	::= { eventGroup10 13 }

	openBranchAlarm1014 NOTIFICATION-TYPE
	OBJECTS {	neName,
			eventGroupName,			-- 10
			eventName,			-- 14
			severity,
			eventType,
			eventTime,
			faultyObject,
			monitoredValue,
			thresholdValue,
			neType }
	STATUS		current
	DESCRIPTION	"Spontaneous Alarm from the managed network element."
	::= { eventGroup10 14 }

	openBranchAlarm1015 NOTIFICATION-TYPE
	OBJECTS {	neName,
			eventGroupName,			-- 10
			eventName,			-- 15
			severity,
			eventType,
			eventTime,
			faultyObject,
			monitoredValue,
			thresholdValue,
			neType }
	STATUS		current
	DESCRIPTION	"Spontaneous Alarm from the managed network element."
	::= { eventGroup10 15 }

	openBranchAlarm1016 NOTIFICATION-TYPE
	OBJECTS {	neName,
			eventGroupName,			-- 10
			eventName,			-- 16
			severity,
			eventType,
			eventTime,
			faultyObject,
			monitoredValue,
			thresholdValue,
			neType }
	STATUS		current
	DESCRIPTION	"Spontaneous Alarm from the managed network element."
	::= { eventGroup10 16 }

	openBranchAlarm1017 NOTIFICATION-TYPE
	OBJECTS {	neName,
			eventGroupName,			-- 10
			eventName,			-- 17
			severity,
			eventType,
			eventTime,
			faultyObject,
			monitoredValue,
			thresholdValue,
			neType }
	STATUS		current
	DESCRIPTION	"Spontaneous Alarm from the managed network element."
	::= { eventGroup10 17 }

	openBranchAlarm1018 NOTIFICATION-TYPE
	OBJECTS {	neName,
			eventGroupName,			-- 10
			eventName,			-- 18
			severity,
			eventType,
			eventTime,
			faultyObject,
			monitoredValue,
			thresholdValue,
			neType }
	STATUS		current
	DESCRIPTION	"Spontaneous Alarm from the managed network element."
	::= { eventGroup10 18 }

	openBranchAlarm1019 NOTIFICATION-TYPE
	OBJECTS {	neName,
			eventGroupName,			-- 10
			eventName,			-- 19
			severity,
			eventType,
			eventTime,
			faultyObject,
			monitoredValue,
			thresholdValue,
			neType }
	STATUS		current
	DESCRIPTION	"Spontaneous Alarm from the managed network element."
	::= { eventGroup10 19 }

	openBranchAlarm1020 NOTIFICATION-TYPE
	OBJECTS {	neName,
			eventGroupName,			-- 10
			eventName,			-- 20
			severity,
			eventType,
			eventTime,
			faultyObject,
			monitoredValue,
			thresholdValue,
			neType }
	STATUS		current
	DESCRIPTION	"Spontaneous Alarm from the managed network element."
	::= { eventGroup10 20 }

	openBranchAlarm1021 NOTIFICATION-TYPE
	OBJECTS {	neName,
			eventGroupName,			-- 10
			eventName,			-- 21
			severity,
			eventType,
			eventTime,
			faultyObject,
			monitoredValue,
			thresholdValue,
			neType }
	STATUS		current
	DESCRIPTION	"Spontaneous Alarm from the managed network element."
	::= { eventGroup10 21 }

	openBranchAlarm1022 NOTIFICATION-TYPE
	OBJECTS {	neName,
			eventGroupName,			-- 10
			eventName,			-- 22
			severity,
			eventType,
			eventTime,
			faultyObject,
			monitoredValue,
			thresholdValue,
			neType }
	STATUS		current
	DESCRIPTION	"Spontaneous Alarm from the managed network element."
	::= { eventGroup10 22 }

	openBranchAlarm1023 NOTIFICATION-TYPE
	OBJECTS {	neName,
			eventGroupName,			-- 10
			eventName,			-- 23
			severity,
			eventType,
			eventTime,
			faultyObject,
			monitoredValue,
			thresholdValue,
			neType }
	STATUS		current
	DESCRIPTION	"Spontaneous Alarm from the managed network element."
	::= { eventGroup10 23 }

	openBranchAlarm1024 NOTIFICATION-TYPE
	OBJECTS {	neName,
			eventGroupName,			-- 10
			eventName,			-- 24
			severity,
			eventType,
			eventTime,
			faultyObject,
			monitoredValue,
			thresholdValue,
			neType }
	STATUS		current
	DESCRIPTION	"Spontaneous Alarm from the managed network element."
	::= { eventGroup10 24 }

	openBranchAlarm1025 NOTIFICATION-TYPE
	OBJECTS {	neName,
			eventGroupName,			-- 10
			eventName,			-- 25
			severity,
			eventType,
			eventTime,
			faultyObject,
			monitoredValue,
			thresholdValue,
			neType }
	STATUS		current
	DESCRIPTION	"Spontaneous Alarm from the managed network element."
	::= { eventGroup10 25 }

	openBranchAlarm1026 NOTIFICATION-TYPE
	OBJECTS {	neName,
			eventGroupName,			-- 10
			eventName,			-- 26
			severity,
			eventType,
			eventTime,
			faultyObject,
			monitoredValue,
			thresholdValue,
			neType }
	STATUS		current
	DESCRIPTION	"Spontaneous Alarm from the managed network element."
	::= { eventGroup10 26 }

	openBranchAlarm1027 NOTIFICATION-TYPE
	OBJECTS {	neName,
			eventGroupName,			-- 10
			eventName,			-- 27
			severity,
			eventType,
			eventTime,
			faultyObject,
			monitoredValue,
			thresholdValue,
			neType }
	STATUS		current
	DESCRIPTION	"Spontaneous Alarm from the managed network element."
	::= { eventGroup10 27 }

	openBranchAlarm1028 NOTIFICATION-TYPE
	OBJECTS {	neName,
			eventGroupName,			-- 10
			eventName,			-- 28
			severity,
			eventType,
			eventTime,
			faultyObject,
			monitoredValue,
			thresholdValue,
			neType }
	STATUS		current
	DESCRIPTION	"Spontaneous Alarm from the managed network element."
	::= { eventGroup10 28 }

	openBranchAlarm1029 NOTIFICATION-TYPE
	OBJECTS {	neName,
			eventGroupName,			-- 10
			eventName,			-- 29
			severity,
			eventType,
			eventTime,
			faultyObject,
			monitoredValue,
			thresholdValue,
			neType }
	STATUS		current
	DESCRIPTION	"Spontaneous Alarm from the managed network element."
	::= { eventGroup10 29 }

	openBranchAlarm1030 NOTIFICATION-TYPE
	OBJECTS {	neName,
			eventGroupName,			-- 10
			eventName,			-- 30
			severity,
			eventType,
			eventTime,
			faultyObject,
			monitoredValue,
			thresholdValue,
			neType }
	STATUS		current
	DESCRIPTION	"Spontaneous Alarm from the managed network element."
	::= { eventGroup10 30 }

	openBranchAlarm1031 NOTIFICATION-TYPE
	OBJECTS {	neName,
			eventGroupName,			-- 10
			eventName,			-- 31
			severity,
			eventType,
			eventTime,
			faultyObject,
			monitoredValue,
			thresholdValue,
			neType }
	STATUS		current
	DESCRIPTION	"Spontaneous Alarm from the managed network element."
	::= { eventGroup10 31 }

	openBranchAlarm1032 NOTIFICATION-TYPE
	OBJECTS {	neName,
			eventGroupName,			-- 10
			eventName,			-- 32
			severity,
			eventType,
			eventTime,
			faultyObject,
			monitoredValue,
			thresholdValue,
			neType }
	STATUS		current
	DESCRIPTION	"Spontaneous Alarm from the managed network element."
	::= { eventGroup10 32 }


-- repeat trap definitions for all evenGroups and events


END
