EXTREME-VRRP-MIB DEFINITIONS ::= BEGIN
    IMPORTS
        MODULE-IDENTITY         FROM SNMPv2-SMI
        OBJECT-TYPE             FROM SNMPv2-SMI
        TruthValue              FROM SNMPv2-TC
        RowStatus               FROM SNMPv2-TC
        extremeAgent            FROM EXTREME-BASE-MIB
        IpAddress               FROM SNMPv2-SMI
        ifIndex                 FROM IF-MIB
        vrrpOperVrId            FROM VRRP-MIB;

   extremeVrrpMIB MODULE-IDENTITY
        LAST-UPDATED "201601040000Z"
        ORGANIZATION "Extreme Networks, Inc."
        CONTACT-INFO "www.extremenetworks.com"
        DESCRIPTION "This MIB describes objects used for managing 
                     Extreme Networks propreitary VRRP controls"
        REVISION     "201601040000Z"
        DESCRIPTION "Initial version of this MIB module"
    ::= { extremeAgent 49 }


-- *******************************************************************
--  VRRP MIB Groups
-- *******************************************************************

 extremeVrrpOperations      OBJECT IDENTIFIER ::= { extremeVrrpMIB 1 }
 extremeVrrpConformance     OBJECT IDENTIFIER ::= { extremeVrrpMIB 2 }


-- *******************************************************************
--  VRRP Operations Table
-- *******************************************************************

 extremeVrrpOperTable OBJECT-TYPE
     SYNTAX       SEQUENCE OF ExtremeVrrpOperEntry
     MAX-ACCESS   not-accessible
     STATUS       current
     DESCRIPTION
         "Operations table for a VRRP router which consists of a
          sequence (i.e., one or more conceptual rows) of
          'extremeVrrpOperEntry' items. This table is extension of 
          IETF tables, vrrpOperTable & vrrpv3OperationsTable "

        ::= { extremeVrrpOperations 1 }

 extremeVrrpOperEntry OBJECT-TYPE
     SYNTAX       ExtremeVrrpOperEntry
     MAX-ACCESS   not-accessible
     STATUS       current
     DESCRIPTION
         "An entry in the extremeVrrpOperTable containing the operational
          characteristics of a virtual router. On a VRRP router,
          a given virtual router is identified by a combination
          of the IF index and VRID."

    INDEX    { ifIndex, vrrpOperVrId }
     ::= { extremeVrrpOperTable 1 }

 ExtremeVrrpOperEntry ::=
     SEQUENCE {
         extremeVrrpFabricRoutingMode
             INTEGER
     }

  extremeVrrpFabricRoutingMode OBJECT-TYPE
     SYNTAX       INTEGER {
         enable     (1),
         disable    (2)
     }
     MAX-ACCESS   read-write
     STATUS       current
     DESCRIPTION
         "This object controls whether VRRP Backup node should assume L3 
          forwarding responsibility. Default is False"
     DEFVAL { disable }
     ::= { extremeVrrpOperEntry 1 }

-- *******************************************************************
--  Conformance Information
-- *******************************************************************

 extremeVrrpMIBCompliances  OBJECT IDENTIFIER ::= { extremeVrrpConformance 1 }
 extremeVrrpMIBGroups       OBJECT IDENTIFIER ::= { extremeVrrpConformance 2 }

-- ...................................................................
-- Compliance Statements
-- ...................................................................
 extremeVrrpMIBCompliance MODULE-COMPLIANCE
     STATUS current
     DESCRIPTION
        "The core compliance statement for Extreme's VRRP Extensions implementations."
     MODULE -- this module
     MANDATORY-GROUPS  {
         extremeVrrpOperGroup
     }
     ::= { extremeVrrpMIBCompliances 1 }

-- ...................................................................
-- Conformance Groups
-- ...................................................................
 
 extremeVrrpOperGroup OBJECT-GROUP
     OBJECTS {
         extremeVrrpFabricRoutingMode 
         }
     STATUS current
     DESCRIPTION
         "Conformance group for extreme VRRP operations."
     ::= { extremeVrrpMIBGroups 1 }  
END
