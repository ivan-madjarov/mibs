INFORMANT-STD DEFINITIONS ::= BEGIN

IMPORTS
    MODULE-IDENTITY, OBJECT-TYPE, OBJECT-IDENTITY, Gauge32
        FROM SNMPv2-SMI
    InstanceName, informant
        FROM WTCS;

standard MODULE-IDENTITY
    LAST-UPDATED "200507191826Z"
    ORGANIZATION "Informant Systems, Inc."
    CONTACT-INFO
            "Garth Williams
             11135-23A Ave
             Edmonton, AB  T6J4W5  Canada
             Tel: +1 780 434 4113
             E-mail: garth.williams@wtcs.org"
    DESCRIPTION
	    "The MIB module for SNMP Informant Standard
             performance counter entries."
    REVISION      "200507191826Z"
    DESCRIPTION
	    "Added the systemSystemUpTime OID to provide
	     access how long the computer has been up in
	     seconds."
    REVISION      "200402290627Z"
    DESCRIPTION
	    "Changed the syntax of the datapoints from
	     integer to gauge."
    REVISION      "200401171602Z"
    DESCRIPTION
            "The initial revision of this MIB module."
    ::= { informant 1 }

logicalDiskTable OBJECT-TYPE
    SYNTAX     SEQUENCE OF LogicalDiskEntry
    MAX-ACCESS not-accessible
    STATUS     current
    DESCRIPTION
	    "The Logical Disk performance object consists
	    of counters that monitor logical partitions of
	    hard or fixed disk drives. System Monitor
	    identifies logical disks by their drive letter,
	    such as 'C.' To monitor Logical Disk object
	    counters, you must activate them by typing the
	    following at the command prompt: diskperf -yv"
    ::= { standard 1 }

logicalDiskEntry OBJECT-TYPE
    SYNTAX     LogicalDiskEntry
    MAX-ACCESS not-accessible
    STATUS     current
    DESCRIPTION
	    "Performance information for one particular
	    instance of 'LogicalDisk' object."
    INDEX      { lDiskInstance }
    ::= { logicalDiskTable 1 }

LogicalDiskEntry ::= SEQUENCE {
    lDiskInstance InstanceName,
    lDiskPercentDiskReadTime Gauge32,
    lDiskPercentDiskTime Gauge32,
    lDiskPercentDiskWriteTime Gauge32,
    lDiskPercentFreeSpace Gauge32,
    lDiskPercentIdleTime Gauge32,
    lDiskAvgDiskQueueLength Gauge32,
    lDiskAvgDiskReadQueueLength Gauge32,
    lDiskAvgDiskWriteQueueLength Gauge32,
    lDiskAvgDiskSecPerRead Gauge32,
    lDiskAvgDiskSecPerTransfer Gauge32,
    lDiskAvgDiskSecPerWrite Gauge32,
    lDiskCurrentDiskQueueLength Gauge32,
    lDiskDiskBytesPerSec Gauge32,
    lDiskDiskReadBytesPerSec Gauge32,
    lDiskDiskReadsPerSec Gauge32,
    lDiskDiskTransfersPerSec Gauge32,
    lDiskDiskWriteBytesPerSec Gauge32,
    lDiskDiskWritesPerSec Gauge32,
    lDiskFreeMegabytes Gauge32,
    lDiskSplitIOPerSec Gauge32
}

lDiskInstance OBJECT-TYPE
    SYNTAX     InstanceName
    MAX-ACCESS read-only
    STATUS     current
    DESCRIPTION
	    "Instance name."
    ::= { logicalDiskEntry 1 }

lDiskPercentDiskReadTime OBJECT-TYPE
    SYNTAX     Gauge32
    MAX-ACCESS read-only
    STATUS     current
    DESCRIPTION
	    "% Disk Read Time is the percentage of elapsed
	    time that the selected disk drive is busy
	    servicing read requests."
    ::= { logicalDiskEntry 2 }

lDiskPercentDiskTime OBJECT-TYPE
    SYNTAX     Gauge32
    MAX-ACCESS read-only
    STATUS     current
    DESCRIPTION
	    "% Disk Time is the percentage of elapsed time
	    that the selected disk drive is busy servicing
	    read or write requests."
    ::= { logicalDiskEntry 3 }

lDiskPercentDiskWriteTime OBJECT-TYPE
    SYNTAX     Gauge32
    MAX-ACCESS read-only
    STATUS     current
    DESCRIPTION
	    "% Disk Write Time is the percentage of elapsed
	    time that the selected disk drive is busy
	    servicing write requests."
    ::= { logicalDiskEntry 4 }

lDiskPercentFreeSpace OBJECT-TYPE
    SYNTAX     Gauge32
    MAX-ACCESS read-only
    STATUS     current
    DESCRIPTION
	    "% Free Space is the ratio of the free space
	    available on the logical disk unit to the total
	    usable space provided by the selected logical
	    disk drive."
    ::= { logicalDiskEntry 5 }

lDiskPercentIdleTime OBJECT-TYPE
    SYNTAX     Gauge32
    MAX-ACCESS read-only
    STATUS     current
    DESCRIPTION
	    "% Idle Time reports the percentage of time
	    during the sample interval that the disk was
	    idle."
    ::= { logicalDiskEntry 6 }

lDiskAvgDiskQueueLength OBJECT-TYPE
    SYNTAX     Gauge32
    MAX-ACCESS read-only
    STATUS     current
    DESCRIPTION
	    "Avg. Disk Queue Length is the average number
	    of both read and write requests that were
	    queued for the selected disk during the sample
	    interval."
    ::= { logicalDiskEntry 7 }

lDiskAvgDiskReadQueueLength OBJECT-TYPE
    SYNTAX     Gauge32
    MAX-ACCESS read-only
    STATUS     current
    DESCRIPTION
	    "Avg. Disk Read Queue Length is the average
	    number of read requests that were queued for
	    the selected disk during the sample interval."
    ::= { logicalDiskEntry 8 }

lDiskAvgDiskWriteQueueLength OBJECT-TYPE
    SYNTAX     Gauge32
    MAX-ACCESS read-only
    STATUS     current
    DESCRIPTION
	    "Avg. Disk Write Queue Length is the average
	    number of write requests that were queued for
	    the selected disk during the sample interval."
    ::= { logicalDiskEntry 9 }

lDiskAvgDiskSecPerRead OBJECT-TYPE
    SYNTAX     Gauge32
    MAX-ACCESS read-only
    STATUS     current
    DESCRIPTION
	    "Avg. Disk sec/Read is the average time in
	    seconds of a read of data from the disk."
    ::= { logicalDiskEntry 10 }

lDiskAvgDiskSecPerTransfer OBJECT-TYPE
    SYNTAX     Gauge32
    MAX-ACCESS read-only
    STATUS     current
    DESCRIPTION
	    "Avg. Disk sec/Transfer is the time in seconds
	    of the average disk transfer."
    ::= { logicalDiskEntry 11 }

lDiskAvgDiskSecPerWrite OBJECT-TYPE
    SYNTAX     Gauge32
    MAX-ACCESS read-only
    STATUS     current
    DESCRIPTION
	    "Avg. Disk sec/Write is the average time in
	    seconds of a write of data to the disk."
    ::= { logicalDiskEntry 12 }

lDiskCurrentDiskQueueLength OBJECT-TYPE
    SYNTAX     Gauge32
    MAX-ACCESS read-only
    STATUS     current
    DESCRIPTION
	    "Current Disk Queue Length is the number of
	    requests outstanding on the disk at the time
	    the performance data is collected.	It includes
	    requests in service at the time of the
	    snapshot.  This is an instantaneous length, not
	    an average over the time interval. 
	    Multi-spindle disk devices can have multiple
	    requests active at one time, but other
	    concurrent requests are awaiting service.  This
	    counter might reflect a transitory high or low
	    queue length, but if there is a sustained load
	    on the disk drive, it is likely that this will
	    be consistently high.  Requests are
	    experiencing delays proportional to the length
	    of this queue minus the number of spindles on
	    the disks.	This difference should average less
	    than 2 for good performance."
    ::= { logicalDiskEntry 13 }

lDiskDiskBytesPerSec OBJECT-TYPE
    SYNTAX     Gauge32
    MAX-ACCESS read-only
    STATUS     current
    DESCRIPTION
	    "Disk Bytes/sec is the rate bytes are
	    transferred to or from the disk during write or
	    read operations."
    ::= { logicalDiskEntry 14 }

lDiskDiskReadBytesPerSec OBJECT-TYPE
    SYNTAX     Gauge32
    MAX-ACCESS read-only
    STATUS     current
    DESCRIPTION
	    "Disk Read Bytes/sec is the rate bytes are
	    transferred from the disk during read
	    operations."
    ::= { logicalDiskEntry 15 }

lDiskDiskReadsPerSec OBJECT-TYPE
    SYNTAX     Gauge32
    MAX-ACCESS read-only
    STATUS     current
    DESCRIPTION
	    "Disk Reads/sec is the rate of read operations
	    on the disk."
    ::= { logicalDiskEntry 16 }

lDiskDiskTransfersPerSec OBJECT-TYPE
    SYNTAX     Gauge32
    MAX-ACCESS read-only
    STATUS     current
    DESCRIPTION
	    "Disk Transfers/sec is the rate of read and
	    write operations on the disk."
    ::= { logicalDiskEntry 17 }

lDiskDiskWriteBytesPerSec OBJECT-TYPE
    SYNTAX     Gauge32
    MAX-ACCESS read-only
    STATUS     current
    DESCRIPTION
	    "Disk Write Bytes is rate bytes are transferred
	    to the disk during write operations."
    ::= { logicalDiskEntry 18 }

lDiskDiskWritesPerSec OBJECT-TYPE
    SYNTAX     Gauge32
    MAX-ACCESS read-only
    STATUS     current
    DESCRIPTION
	    "Disk Writes/sec is the rate of write
	    operations on the disk."
    ::= { logicalDiskEntry 19 }

lDiskFreeMegabytes OBJECT-TYPE
    SYNTAX     Gauge32
    MAX-ACCESS read-only
    STATUS     current
    DESCRIPTION
	    "Free Megabytes displays the unallocated space
	    on the disk drive in megabytes. One megabyte =
	    1,048,576 bytes."
    ::= { logicalDiskEntry 20 }

lDiskSplitIOPerSec OBJECT-TYPE
    SYNTAX     Gauge32
    MAX-ACCESS read-only
    STATUS     current
    DESCRIPTION
	    "Split IO/Sec reports the rate that I/Os to the
	    disk were split into multiple I/Os.  A split
	    I/O may result from requesting data in a size
	    that is too large to fit into a single I/O or
	    that the disk is fragmented."
    ::= { logicalDiskEntry 21 }

memory OBJECT-IDENTITY
    STATUS     current
    DESCRIPTION
	    "The Memory performance object consists of
	    counters that describe the behavior of physical
	    and virtual memory on the computer. Physical
	    memory is the amount of random-access memory
	    (RAM) on the computer. Virtual memory consists
	    of space in physical memory and on disk. Many
	    of the memory counters monitor paging, which is
	    the movement of pages of code and data between
	    disk and physical memory. Excessive paging, a
	    symptom of a memory shortage, can cause delays
	    which interfere with all system processes."
    ::= { standard 2 }

memoryAvailableBytes OBJECT-TYPE
    SYNTAX     Gauge32
    MAX-ACCESS read-only
    STATUS     current
    DESCRIPTION
	    "Available Bytes is the amount of physical
	    memory available to processes running on the
	    computer, in bytes.  It is calculated by
	    summing space on the Zeroed, Free, and Stand by
	    memory lists.  Free memory is ready for use;
	    Zeroed memory are pages of memory filled with
	    zeros to prevent later processes from seeing
	    data used by a previous process. Standby memory
	    is memory removed from a process' working set
	    (its physical memory) on route to disk, but is
	    still available to be recalled.  This counter
	    displays the last observed value only; it is
	    not an average. "
    ::= { memory 1 }

memoryAvailableKBytes OBJECT-TYPE
    SYNTAX     Gauge32
    MAX-ACCESS read-only
    STATUS     current
    DESCRIPTION
	    "Available KBytes is the amount of physical
	    memory available to processes running on the
	    computer, in Kilobytes (Bytes / 1,024).  It is
	    calculated by summing space on the Zeroed,
	    Free, and Stand by memory lists.  Free memory
	    is ready for use; Zeroed memory are pages of
	    memory filled with zeros to prevent later
	    processes from seeing data used by a previous
	    process. Standby memory is memory removed from
	    a process' working set (its physical memory) on
	    route to disk, but is still available to be
	    recalled.  This counter displays the last
	    observed value only; it is not an average. "
    ::= { memory 2 }

memoryAvailableMBytes OBJECT-TYPE
    SYNTAX     Gauge32
    MAX-ACCESS read-only
    STATUS     current
    DESCRIPTION
	    "Available MBytes is the amount of physical
	    memory available to processes running on the
	    computer, in Megabytes (Bytes / 1,048,576).  It
	    is calculated by summing space on the Zeroed,
	    Free, and Stand by memory lists.  Free memory
	    is ready for use; Zeroed memory are pages of
	    memory filled with zeros to prevent later
	    processes from seeing data used by a previous
	    process. Standby memory is memory removed from
	    a process' working set (its physical memory) on
	    route to disk, but is still available to be
	    recalled.  This counter displays the last
	    observed value only; it is not an average. "
    ::= { memory 3 }

memoryCommittedBytes OBJECT-TYPE
    SYNTAX     Gauge32
    MAX-ACCESS read-only
    STATUS     current
    DESCRIPTION
	    "Committed Bytes is the amount of committed
	    virtual memory, in bytes.  (Committed memory is
	    physical memory for which space has been
	    reserved on the disk paging file in case it
	    needs to be written back to disk). This counter
	    displays the last observed value only; it is
	    not an average. "
    ::= { memory 4 }

memoryCacheBytes OBJECT-TYPE
    SYNTAX     Gauge32
    MAX-ACCESS read-only
    STATUS     current
    DESCRIPTION
	    "Cache Bytes is the sum of the System Cache
	    Resident Bytes, System Driver Resident Bytes,
	    System Code Resident Bytes, and Pool Paged
	    Resident Bytes counters.  This counter displays
	    the last observed value only; it is not an
	    average. "
    ::= { memory 5 }

memoryCacheBytesPeak OBJECT-TYPE
    SYNTAX     Gauge32
    MAX-ACCESS read-only
    STATUS     current
    DESCRIPTION
	    "Cache Bytes Peak is the maximum value of Cache
	    Bytes since the system was last restarted. 
	    This value might be larger than the current
	    size of the cache.	Cache Bytes is the sum of
	    the System Cache Resident Bytes, System Driver
	    Resident Bytes, System Code Resident Bytes, and
	    Pool Paged Resident Bytes counters.  This
	    counter displays the last observed value only;
	    it is not an average. "
    ::= { memory 6 }

memoryPageFaultsPerSec OBJECT-TYPE
    SYNTAX     Gauge32
    MAX-ACCESS read-only
    STATUS     current
    DESCRIPTION
	    "Page Faults/sec is the overall rate faulted
	    pages are handled by the processor.  It is
	    measured in numbers of pages faulted per
	    second.  A page fault occurs when a process
	    requires code or data that is not in its
	    working set (its space in physical memory). 
	    This counter includes both hard faults (those
	    that require disk access) and soft faults
	    (where the faulted page is found elsewhere in
	    physical memory). Most processors can handle
	    large numbers of soft faults without
	    consequence.  However, hard faults can cause
	    significant delays. This counter displays the
	    difference between the values observed in the
	    last two samples, divided by the duration of
	    the sample interval. "
    ::= { memory 7 }

memoryPagesInputPerSec OBJECT-TYPE
    SYNTAX     Gauge32
    MAX-ACCESS read-only
    STATUS     current
    DESCRIPTION
	    "Pages Input/sec is the number of pages read
	    from disk to resolve hard page faults.  (Hard
	    page faults occur when a process requires code
	    or data that is not in its working set or
	    elsewhere in physical memory, and must be
	    retrieved from disk). This counter was designed
	    as a primary indicator of the kinds of faults
	    that cause system-wide delays.  It includes
	    pages retrieved to satisfy faults in the file
	    system cache (usually requested by
	    applications) and in non-cached mapped memory
	    files.  This counter counts numbers of pages,
	    and can be compared to other counts of pages,
	    such as Memory: Page Faults/sec, without
	    conversion.  This counter displays the
	    difference between the values observed in the
	    last two samples, divided by the duration of
	    the sample interval. "
    ::= { memory 8 }

memoryPagesOutputPerSec OBJECT-TYPE
    SYNTAX     Gauge32
    MAX-ACCESS read-only
    STATUS     current
    DESCRIPTION
	    "Pages Output/sec is the number of pages
	    written to disk to free up space in physical
	    memory.  Pages are written back to disk only if
	    they are changed in physical memory, so they
	    are likely to hold data, not code.	A high rate
	    of pages output might indicate a memory
	    shortage.  Windows NT writes more pages back to
	    disk to free up space when physical memory is
	    in short supply.  This counter counts numbers
	    of pages, and can be compared to other counts
	    of pages, without conversion.  This counter
	    displays the difference between the values
	    observed in the last two samples, divided by
	    the duration of the sample interval. "
    ::= { memory 9 }

memoryPagesPerSec OBJECT-TYPE
    SYNTAX     Gauge32
    MAX-ACCESS read-only
    STATUS     current
    DESCRIPTION
	    "Pages/sec is the number of pages read from or
	    written to disk to resolve hard page faults. 
	    (Hard page faults occur when a process requires
	    code or data that is not in its working set or
	    elsewhere in physical memory, and must be
	    retrieved from disk). This counter was designed
	    as a primary indicator of the kinds of faults
	    that cause system-wide delays.  It is the sum
	    of Memory: Pages Input/sec and Memory: Pages
	    Output/sec.  It is counted in numbers of pages,
	    so it can be compared to other counts of pages,
	    such as Memory: Page Faults/sec, without
	    conversion.  It includes pages retrieved to
	    satisfy faults in the file system cache
	    (usually requested by applications) non-cached
	    mapped memory files.  This counter displays the
	    difference between the values observed in the
	    last two samples, divided by the duration of
	    the sample interval. "
    ::= { memory 10 }

memoryPoolNonpagedBytes OBJECT-TYPE
    SYNTAX     Gauge32
    MAX-ACCESS read-only
    STATUS     current
    DESCRIPTION
	    "Pool Nonpaged Bytes is the number of bytes in
	    the nonpaged pool, an area of system memory
	    (physical memory used by the operating system)
	    for objects that cannot be written to disk, but
	    must remain in physical memory as long as they
	    are allocated.  Memory: Pool Nonpaged Bytes is
	    calculated differently than Process: Pool
	    Nonpaged Bytes, so it might not equal Process:
	    Pool Nonpaged Bytes: _Total.  This counter
	    displays the last observed value only; it is
	    not an average.  "
    ::= { memory 11 }

memoryPoolPagedBytes OBJECT-TYPE
    SYNTAX     Gauge32
    MAX-ACCESS read-only
    STATUS     current
    DESCRIPTION
	    "Pool Paged Bytes is the number of bytes in the
	    paged pool, an area of system memory (physical
	    memory used by the operating system) for
	    objects that can be written to disk when they
	    are not being used.  Memory: Pool Paged Bytes
	    is calculated differently than Process: Pool
	    Paged Bytes, so it might not equal Process:
	    Pool Paged Bytes: _Total.  This counter
	    displays the last observed value only; it is
	    not an average.  "
    ::= { memory 12 }

memoryPoolPagedResidentBytes OBJECT-TYPE
    SYNTAX     Gauge32
    MAX-ACCESS read-only
    STATUS     current
    DESCRIPTION
	    "Pool Paged Resident Bytes is the current size
	    of paged pool in bytes.  The paged pool is an
	    area of system memory (physical memory used by
	    the operating system) for objects that can be
	    written to disk when they are not being used. 
	    Space used by the paged and nonpaged pools are
	    taken from physical memory, so a pool that is
	    too large denies memory space to processes. 
	    This counter displays the last observed value
	    only; it is not an average. "
    ::= { memory 13 }

memorySystemCacheResidentBytes OBJECT-TYPE
    SYNTAX     Gauge32
    MAX-ACCESS read-only
    STATUS     current
    DESCRIPTION
	    "System Cache Resident Bytes is the number of
	    bytes from the file system cache that are
	    resident in physical memory.  This value
	    includes only current physical pages and does
	    not include any virtual memory pages not
	    currently resident.  As such this value may be
	    smaller than the actual amount of virtual
	    memory in use by the file system cache.  This
	    value is a component of Memory: System Code
	    Resident Bytes.  This counter displays the last
	    observed value only; it is not an average. "
    ::= { memory 14 }

memorySystemCodeResidentBytes OBJECT-TYPE
    SYNTAX     Gauge32
    MAX-ACCESS read-only
    STATUS     current
    DESCRIPTION
	    "System Code Resident Bytes is the number of
	    bytes of operating system code currently in
	    physical memory that can be written to disk
	    when not in use. This value is a component of
	    System Code Total Bytes, which also includes
	    operating system code on disk.  System Code
	    Resident Bytes (and System Code Total Bytes)
	    does not include code that must remain in
	    physical memory and cannot be written to disk. 
	    This counter displays the last observed value
	    only; it is not an average.  "
    ::= { memory 15 }

memorySystemCodeTotalBytes OBJECT-TYPE
    SYNTAX     Gauge32
    MAX-ACCESS read-only
    STATUS     current
    DESCRIPTION
	    "System Code Total Bytes is the number of bytes
	    of pageable operating system code currently in
	    virtual memory.  It is a measure of the amount
	    of physical memory being used by the operating
	    system that can be written to disk when not in
	    use.  This value is calculated by summing the
	    bytes in Ntoskrnl.exe, Hal.dll, the boot
	    drivers, and file systems loaded by
	    Ntldr/osloader.  This counter does not include
	    code that must remain in physical memory and
	    cannot be written to disk.	This counter
	    displays the last observed value only; it is
	    not an average. "
    ::= { memory 16 }

memorySystemDriverResidentBytes OBJECT-TYPE
    SYNTAX     Gauge32
    MAX-ACCESS read-only
    STATUS     current
    DESCRIPTION
	    "System Driver Resident Bytes is the number of
	    bytes of pageable physical memory being used by
	    device drivers.  It is the working set
	    (physical memory area) of the drivers.  This
	    value is a component of Memory: System Driver
	    Total Bytes, which also includes driver memory
	    that has been written to disk.  Neither System
	    Driver Resident Bytes nor System Driver Total
	    Bytes includes memory that cannot be written to
	    disk."
    ::= { memory 17 }

memorySystemDriverTotalBytes OBJECT-TYPE
    SYNTAX     Gauge32
    MAX-ACCESS read-only
    STATUS     current
    DESCRIPTION
	    "System Driver Total Bytes is the number of
	    bytes of pageable virtual memory currently
	    being used by device drivers.  (Pageable memory
	    can be written to disk when it is not being
	    used). It includes physical memory (Memory:
	    System Driver Resident Bytes) and code and data
	    paged to disk.  It is a component of Memory:
	    System Code Total Bytes.  This counter displays
	    the last observed value only; it is not an
	    average.  "
    ::= { memory 18 }

networkInterfaceTable OBJECT-TYPE
    SYNTAX     SEQUENCE OF NetworkInterfaceEntry
    MAX-ACCESS not-accessible
    STATUS     current
    DESCRIPTION
	    "The Network Interface performance object
	    consists of counters that measure the rates at
	    which bytes and packets are sent and received
	    over a TCP/IP connection. It includes counters
	    that monitor connection errors. The Network
	    Interface counters display data about the
	    network adapters on the server computer. The
	    first instance of the Network Interface object
	    (Instance 1) that you see in System Monitor
	    represents the loopback. The loopback is a
	    local path through the protocol driver and the
	    network adapter. All other instances represent
	    installed network adapters."
    ::= { standard 3 }

networkInterfaceEntry OBJECT-TYPE
    SYNTAX     NetworkInterfaceEntry
    MAX-ACCESS not-accessible
    STATUS     current
    DESCRIPTION
	    "Performance information for one particular
	    instance of 'Network Interface' object."
    INDEX      { netInstance }
    ::= { networkInterfaceTable 1 }

NetworkInterfaceEntry ::= SEQUENCE {
    netInstance InstanceName,
    netBytesReceivedPerSec Gauge32,
    netBytesSentPerSec Gauge32,
    netBytesTotalPerSec Gauge32,
    netCurrentBandwidth Gauge32,
    netOutputQueueLength Gauge32,
    netPacketsOutboundDiscarded Gauge32,
    netPacketsOutboundErrors Gauge32,
    netPacketsReceivedDiscarded Gauge32,
    netPacketsReceivedErrors Gauge32,
    netPacketsReceivedUnknown Gauge32,
    netPacketsReceivedPerSec Gauge32,
    netPacketsSentPerSec Gauge32,
    netPacketsPerSec Gauge32
}

netInstance OBJECT-TYPE
    SYNTAX     InstanceName
    MAX-ACCESS read-only
    STATUS     current
    DESCRIPTION
	    "Instance name."
    ::= { networkInterfaceEntry 1 }

netBytesReceivedPerSec OBJECT-TYPE
    SYNTAX     Gauge32
    MAX-ACCESS read-only
    STATUS     current
    DESCRIPTION
	    "Bytes Received/sec is the rate at which bytes
	    are received on the interface, including
	    framing characters."
    ::= { networkInterfaceEntry 2 }

netBytesSentPerSec OBJECT-TYPE
    SYNTAX     Gauge32
    MAX-ACCESS read-only
    STATUS     current
    DESCRIPTION
	    "Bytes Sent/sec is the rate at which bytes are
	    sent on the interface, including framing
	    characters."
    ::= { networkInterfaceEntry 3 }

netBytesTotalPerSec OBJECT-TYPE
    SYNTAX     Gauge32
    MAX-ACCESS read-only
    STATUS     current
    DESCRIPTION
	    "Bytes Total/sec is the rate at which bytes are
	    sent and received on the interface, including
	    framing characters."
    ::= { networkInterfaceEntry 4 }

netCurrentBandwidth OBJECT-TYPE
    SYNTAX     Gauge32
    MAX-ACCESS read-only
    STATUS     current
    DESCRIPTION
	    "Current Bandwidth is an estimate of the
	    interface's current bandwidth in bits per
	    second (BPS).  For interfaces that do not vary
	    in bandwidth or for those where no accurate
	    estimation can be made, this value is the
	    nominal bandwidth."
    ::= { networkInterfaceEntry 5 }

netOutputQueueLength OBJECT-TYPE
    SYNTAX     Gauge32
    MAX-ACCESS read-only
    STATUS     current
    DESCRIPTION
	    "Output Queue Length is the length of the
	    output packet queue (in packets).  If this is
	    longer than 2, delays are being experienced and
	    the bottleneck should be found and eliminated
	    if possible.  Since the requests are queued by
	    NDIS in this implementation, this will always
	    be 0."
    ::= { networkInterfaceEntry 6 }

netPacketsOutboundDiscarded OBJECT-TYPE
    SYNTAX     Gauge32
    MAX-ACCESS read-only
    STATUS     current
    DESCRIPTION
	    "Packets Outbound Discarded is the number of
	    outbound packets that were chosen to be
	    discarded even though no errors had been
	    detected to prevent their being transmitted. 
	    One possible reason for discarding such a
	    packet could be to free up buffer space."
    ::= { networkInterfaceEntry 7 }

netPacketsOutboundErrors OBJECT-TYPE
    SYNTAX     Gauge32
    MAX-ACCESS read-only
    STATUS     current
    DESCRIPTION
	    "Packets Outbound Errors is the number of
	    outbound packets that could not be transmitted
	    because of errors."
    ::= { networkInterfaceEntry 8 }

netPacketsReceivedDiscarded OBJECT-TYPE
    SYNTAX     Gauge32
    MAX-ACCESS read-only
    STATUS     current
    DESCRIPTION
	    "Packets Received Discarded is the number of
	    inbound packets that were chosen to be
	    discarded even though no errors had been
	    detected to prevent their being deliverable to
	    a higher-layer protocol.  One possible reason
	    for discarding such a packet could be to free
	    up buffer space."
    ::= { networkInterfaceEntry 9 }

netPacketsReceivedErrors OBJECT-TYPE
    SYNTAX     Gauge32
    MAX-ACCESS read-only
    STATUS     current
    DESCRIPTION
	    "Packets Received Errors is the number of
	    inbound packets that contained errors
	    preventing them from being deliverable to a
	    higher-layer protocol."
    ::= { networkInterfaceEntry 10 }

netPacketsReceivedUnknown OBJECT-TYPE
    SYNTAX     Gauge32
    MAX-ACCESS read-only
    STATUS     current
    DESCRIPTION
	    "Packets Received Unknown is the number of
	    packets received via the interface that were
	    discarded because of an unknown or unsupported
	    protocol."
    ::= { networkInterfaceEntry 11 }

netPacketsReceivedPerSec OBJECT-TYPE
    SYNTAX     Gauge32
    MAX-ACCESS read-only
    STATUS     current
    DESCRIPTION
	    "Packets Received/sec is the rate at which
	    packets are received on the network interface."
    ::= { networkInterfaceEntry 12 }

netPacketsSentPerSec OBJECT-TYPE
    SYNTAX     Gauge32
    MAX-ACCESS read-only
    STATUS     current
    DESCRIPTION
	    "Packets Sent/sec is the rate at which packets
	    are sent on the network interface."
    ::= { networkInterfaceEntry 13 }

netPacketsPerSec OBJECT-TYPE
    SYNTAX     Gauge32
    MAX-ACCESS read-only
    STATUS     current
    DESCRIPTION
	    "Packets/sec is the rate at which packets are
	    sent and received on the network interface."
    ::= { networkInterfaceEntry 14 }

objects OBJECT-IDENTITY
    STATUS     current
    DESCRIPTION
	    "The Objects performance object consists of
	    counters that monitor logical objects in the
	    system, such as processes, threads, mutexes,
	    and semaphores. This information can be used to
	    detect the unnecessary consumption of computer
	    resources. Each object requires memory to store
	    basic information about the object."
    ::= { standard 4 }

objectsProcesses OBJECT-TYPE
    SYNTAX     Gauge32
    MAX-ACCESS read-only
    STATUS     current
    DESCRIPTION
	    "Processes is the number of processes in the
	    computer at the time of data collection. 
	    Notice that this is an instantaneous count, not
	    an average over the time interval.	Each
	    process represents the running of a program."
    ::= { objects 1 }

objectsThreads OBJECT-TYPE
    SYNTAX     Gauge32
    MAX-ACCESS read-only
    STATUS     current
    DESCRIPTION
	    "Threads is the number of threads in the
	    computer at the time of data collection. 
	    Notice that this is an instantaneous count, not
	    an average over the time interval.	A thread is
	    the basic executable entity that can execute
	    instructions in a processor."
    ::= { objects 2 }

processorTable OBJECT-TYPE
    SYNTAX     SEQUENCE OF ProcessorEntry
    MAX-ACCESS not-accessible
    STATUS     current
    DESCRIPTION
	    "The Processor performance object consists of
	    counters that measure aspects of processor
	    activity. The processor is the part of the
	    computer that performs arithmetic and logical
	    computations, initiates operations on
	    peripherals, and runs the threads of processes.
	    A computer can have multiple processors. The
	    processor object represents each processor as
	    an instance of the object."
    ::= { standard 5 }

processorEntry OBJECT-TYPE
    SYNTAX     ProcessorEntry
    MAX-ACCESS not-accessible
    STATUS     current
    DESCRIPTION
	    "Performance information for one particular
	    instance of 'Processor' object."
    INDEX      { cpuInstance }
    ::= { processorTable 1 }

ProcessorEntry ::= SEQUENCE {
    cpuInstance InstanceName,
    cpuPercentDPCTime Gauge32,
    cpuPercentInterruptTime Gauge32,
    cpuPercentPrivilegedTime Gauge32,
    cpuPercentProcessorTime Gauge32,
    cpuPercentUserTime Gauge32,
    cpuAPCBypassesPerSec Gauge32,
    cpuDPCBypassesPerSec Gauge32,
    cpuDPCRate Gauge32,
    cpuDPCsQueuedPerSec Gauge32,
    cpuInterruptsPerSec Gauge32
}

cpuInstance OBJECT-TYPE
    SYNTAX     InstanceName
    MAX-ACCESS read-only
    STATUS     current
    DESCRIPTION
	    "Instance name."
    ::= { processorEntry 1 }

cpuPercentDPCTime OBJECT-TYPE
    SYNTAX     Gauge32
    MAX-ACCESS read-only
    STATUS     current
    DESCRIPTION
	    "% DPC Time is the percentage of time that the
	    processor spent receiving and servicing
	    deferred procedure calls (DPCs) during the
	    sample interval.  (DPCs are interrupts that run
	    at a lower priority than standard interrupts).
	    % DPC Time is a component of % Privileged Time
	    because DPCs are executed in privileged mode. 
	    They are counted separately and are not a
	    component of the interrupt counters.  This
	    counter displays the average busy time as a
	    percentage of the sample time. "
    ::= { processorEntry 2 }

cpuPercentInterruptTime OBJECT-TYPE
    SYNTAX     Gauge32
    MAX-ACCESS read-only
    STATUS     current
    DESCRIPTION
	    "% Interrupt Time is the percentage of time the
	    processor spent receiving and servicing
	    hardware interrupts during the sample interval.
	     This value is an indirect indicator of the
	    activity of devices that generate interrupts,
	    such as the system clock, the mouse, disk
	    drivers, data communication lines, network
	    interface cards and other peripheral devices.
	    These devices normally interrupt the processor
	    when they have completed a task or require
	    attention.	Normal thread execution is
	    suspended during interrupts.  Most system
	    clocks interrupt the processor every 10
	    milliseconds, creating a background of
	    interrupt activity.  This counter displays the
	    average busy time as a percentage of the sample
	    time. "
    ::= { processorEntry 3 }

cpuPercentPrivilegedTime OBJECT-TYPE
    SYNTAX     Gauge32
    MAX-ACCESS read-only
    STATUS     current
    DESCRIPTION
	    "% Privileged Time is the percentage of
	    non-idle processor time spent in privileged
	    mode.  (Privileged mode is a processing mode
	    designed for operating system components and
	    hardware-manipulating drivers.  It allows
	    direct access to hardware and all memory.  The
	    alternative, user mode, is a restricted
	    processing mode designed for applications,
	    environment subsystems, and integral
	    subsystems.  The operating system switches
	    application threads to privileged mode to
	    access operating system services). % Privileged
	    Time includes time servicing interrupts and
	    DPCs.  A high rate of privileged time might be
	    attributable to a large number of interrupts
	    generated by a failing device.  This counter
	    displays the average busy time as a percentage
	    of the sample time. "
    ::= { processorEntry 4 }

cpuPercentProcessorTime OBJECT-TYPE
    SYNTAX     Gauge32
    MAX-ACCESS read-only
    STATUS     current
    DESCRIPTION
	    "% Processor Time is the percentage of time
	    that the processor is executing a non-Idle
	    thread.  This counter was designed as a primary
	    indicator of processor activity.  It is
	    calculated by measuring the time that the
	    processor spends executing the thread of the
	    Idle process in each sample interval, and
	    subtracting that value from 100%.  (Each
	    processor has an Idle thread which consumes
	    cycles when no other threads are ready to run).
	    It can be viewed as the percentage of the
	    sample interval spent doing useful work.  This
	    counter displays the average percentage of busy
	    time observed during the sample interval.  It
	    is calculated by monitoring the time the
	    service was inactive, and then subtracting that
	    value from 100%."
    ::= { processorEntry 5 }

cpuPercentUserTime OBJECT-TYPE
    SYNTAX     Gauge32
    MAX-ACCESS read-only
    STATUS     current
    DESCRIPTION
	    "% User Time is the percentage of non-idle
	    processor time spent in user mode.	(User mode
	    is a restricted processing mode designed for
	    applications, environment subsystems, and
	    integral subsystems.  The alternative,
	    privileged mode, is designed for operating
	    system components and allows direct access to
	    hardware and all memory.  The operating system
	    switches application threads to privileged mode
	    to access operating system services). This
	    counter displays the average busy time as a
	    percentage of the sample time. "
    ::= { processorEntry 6 }

cpuAPCBypassesPerSec OBJECT-TYPE
    SYNTAX     Gauge32
    MAX-ACCESS read-only
    STATUS     current
    DESCRIPTION
	    "APC Bypasses/sec is the rate at which Kernel
	    APC interrupts were avoided.  APC Bypasses/sec
	    is the rate at which kernel APC interrupts were
	    short-circuited.  This counter displays the
	    difference between the values observed in the
	    last two samples, divided by the duration of
	    the sample interval."
    ::= { processorEntry 7 }

cpuDPCBypassesPerSec OBJECT-TYPE
    SYNTAX     Gauge32
    MAX-ACCESS read-only
    STATUS     current
    DESCRIPTION
	    "DPC Bypasses/sec is the rate at which deferred
	    procedure calls (DPCs) on all processors were
	    avoided.  (DPCs are interrupts that run at a
	    lower priority than standard interrupts). This
	    counter displays the difference between the
	    values observed in the last two samples,
	    divided by the duration of the sample
	    interval."
    ::= { processorEntry 8 }

cpuDPCRate OBJECT-TYPE
    SYNTAX     Gauge32
    MAX-ACCESS read-only
    STATUS     current
    DESCRIPTION
	    "DPC Rate is the rate at which deferred
	    procedure calls (DPCs) are added to the
	    processor's DPC queue between the timer ticks
	    of the processor clock.  (DPCs are interrupts
	    that run at a lower priority than standard
	    interrupts.  Each processor has its own DPC
	    queue). This counter measures the rate at which
	    DPCs are added to the queue, not the number of
	    DPCs in the queue.	This counter displays the
	    last observed value only; it is not an average.
	    "
    ::= { processorEntry 9 }

cpuDPCsQueuedPerSec OBJECT-TYPE
    SYNTAX     Gauge32
    MAX-ACCESS read-only
    STATUS     current
    DESCRIPTION
	    "DPCs Queued/sec is the overall rate at which
	    deferred procedure calls (DPCs) are added to
	    the processor's DPC queue.	(DPCs are
	    interrupts that run at a lower priority than
	    standard interrupts.  Each processor has its
	    own DPC queue). This counter measures the rate
	    at which DPCs are added to the queue, not the
	    number of DPCs in the queue.  This counter
	    displays the difference between the values
	    observed in the last two samples, divided by
	    the duration of the sample interval. "
    ::= { processorEntry 10 }

cpuInterruptsPerSec OBJECT-TYPE
    SYNTAX     Gauge32
    MAX-ACCESS read-only
    STATUS     current
    DESCRIPTION
	    "Interrupts/sec is the average number of
	    hardware interrupts the processor is receiving
	    and servicing in each second. It does not
	    include DPCs, which are counted separately.
	    This value is an indirect indicator of the
	    activity of devices that generate interrupts,
	    such as the system clock, the mouse, disk
	    drivers, data communication lines, network
	    interface cards and other peripheral devices.
	    These devices normally interrupt the processor
	    when they have completed a task or require
	    attention. Normal thread execution is suspended
	    during interrupts. Most system clocks interrupt
	    the processor every 10 milliseconds, creating a
	    background of interrupt activity. This counter
	    displays the difference between the values
	    observed in the last two samples, divided by
	    the duration of the sample interval. "
    ::= { processorEntry 11 }

system OBJECT-IDENTITY
    STATUS     current
    DESCRIPTION
	    "The System performance object consists of
	    counters that apply to more than one component
	    of the computer. Percentage counters by default
	    do not show values above 100 percent. See
	    'Overview of Performance Monitoring' in the
	    Windows 2000 Server Resource Kit Server
	    Operations Guide for instructions about
	    changing this default in the registry."
    ::= { standard 6 }

systemSystemUpTime OBJECT-TYPE
    SYNTAX     Gauge32
    MAX-ACCESS read-only
    STATUS     current
    DESCRIPTION
	    "System Up Time is the elapsed time (in
	    seconds) that the computer has been running
	    since it was last started.	This counter
	    displays the difference between the start time
	    and the current time. "
    ::= { system 1 }

END
