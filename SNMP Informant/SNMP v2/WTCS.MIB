WTCS DEFINITIONS ::= BEGIN

IMPORTS
    MODULE-IDENTITY, enterprises
        FROM SNMPv2-SMI
    TEXTUAL-CONVENTION
        FROM SNMPv2-TC;

wtcs MODULE-IDENTITY
    LAST-UPDATED "200402290616Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The Structure of Management Information for WTCS."
    REVISION      "200402290616Z"
    DESCRIPTION
            "Modified InstanceName to be UTF-8 format based."
    REVISION      "200311260000Z"
    DESCRIPTION
            "The initial revision of this MIB module."
    ::= { enterprises 9600 }

InstanceName ::= TEXTUAL-CONVENTION
    DISPLAY-HINT "64t"
    STATUS       current
    DESCRIPTION
            "The instance name for a specific performance counter
             in UTF-8 format."
    SYNTAX       OCTET STRING (SIZE (0..64))

informant OBJECT IDENTIFIER ::= { wtcs 1 }

END
