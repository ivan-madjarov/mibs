-- ***************************************************************
--  *************************************************************
--   *********************************************************** 
--                       NOC CUSTOM MIB
--
--              This mib is a custom mib defined  
--            under an experimental enterprises ID
--   *********************************************************** 
--  *************************************************************
-- ***************************************************************


    
             NOC-CUSTOM-MIB DEFINITIONS ::= BEGIN



-- **************************************************************
-- *                                                            *
-- *	ORGANIZATION:                                           *
-- *	   "Atos Information technology company"                *
-- *                                                            *
-- *	CONTACT-INFO:                                           *
-- *	   Unify Communications and Collaboration               *
-- *	   attn: David Duperre                                  *
-- *	   1630 Corporate Court                                 *
-- *	   Irving, TX, 75038                                    *
-- *        Tel.: +866 525 7544                                 *
-- *	   Email: ccs_m2m.zenoss_issues@atos.net                *
-- *                                                            *
-- **************************************************************
-- *                    Versions and Revisions                  *
-- *                                                            *
-- *       PLEASE CHANGE THE DATE OF LAST-UPDATE BELOW !!!      *
-- **************************************************************
-- Date      Description of modification           Version  Init
-- ---------|-------------------------------------|--------|-----
-- 08-12-10 |Initial Creation                     | V1.0   | RT
-- ---------|-------------------------------------|--------|-----
-- 09-12-10 |Convert: IANA PEN from Siemens to EXP| V2.0   | RT
-- ---------|-------------------------------------|--------|-----
-- 20-04-14 |Updated: Added PSAP trap config.     | V2.1   | DD
-- ---------|-------------------------------------|--------|-----
-- 21-09-02 |Updated: Added performace traps      | V2.2   | DD
-- ---------|-------------------------------------|--------|-----
-- 22-09-02 |Updated: Added link down traps       | V2.3   | DD
-- ---------|-------------------------------------|--------|-----
-- 22-09-12 |Updated: Added link status varbine   | V2.4   | DD
-- ---------|-------------------------------------|--------|-----
-- 22-12-05 |Updated: Added silent CI traps       | V2.5   | DD
-- ---------|-------------------------------------|--------|-----
-- 
-- Initials Declaration:
-- RT  = Riaan Timmerman
-- DD  = David Duperre
--
-- **************************************************************
-- **************************************************************

    
    IMPORTS
	enterprises
		FROM RFC1155-SMI 
	OBJECT-TYPE
		FROM RFC-1212
	TRAP-TYPE
		FROM RFC-1215
	DisplayString
		FROM RFC1213-MIB;


-- **************************************************************
--			tree structure
-- **************************************************************

	sennoc            OBJECT IDENTIFIER  ::= { enterprises 13203 }
	senNocCustomTrap  OBJECT IDENTIFIER  ::= { sennoc 99991 }


-- **************************************************************
--			Traps Definitions
-- **************************************************************

-- Trap type one: Alarms from aggregators. 
-- These traps are sent northbound when an aggregator detects an issue and notifies the NOC.
	
	zenossAlarm	TRAP-TYPE
    	ENTERPRISE	senNocCustomTrap
        VARIABLES   { nocHostName, nocSummary, nocSeverity, nocComponent }
    	DESCRIPTION	"This trap is used for interpreting events from Zenoss Aggregators"
    	::= 1

-- Trap type two: NOC Automation Alarms. 
-- These traps are sent northbound when an automation is run and an alarm is triggered by the automation.

	nocAutomation	TRAP-TYPE
    	ENTERPRISE	senNocCustomTrap
        VARIABLES   { nocHostName, nocSummary, nocSeverity, nocComponent }
    	DESCRIPTION	"This trap is used for interpreting events, generated via NOC automations or scripts"
    	::= 2

-- Trap type three: Call Behavior Notifications. 
-- These traps are sent northbound when a specific call-behavior condition is detected.
	    
	callBehavior	TRAP-TYPE
    	ENTERPRISE	senNocCustomTrap
        VARIABLES   { nocHostName, nocSummary, nocSeverity }
    	DESCRIPTION	"This trap is used for Call Behavior Monitoring"
    	::= 3

-- Trap type four: Aggregator Server Heartbeat. 
-- These traps are sent northbound from the aggregator at one minute intervals. Should the heartbeat
-- stop, a NOC automation will trigger a "NOC Automation Alarms" as indicated above.

	heartBeat	TRAP-TYPE
    	ENTERPRISE	senNocCustomTrap
        VARIABLES   { nocHostName, nocSummary, nocSeverity, nocEventSentTime }
    	DESCRIPTION	"This alarm is mainly aimed at looking for heartbeats from the aggregators"
    	::= 4

-- Trap type five: Traps forwarded from NG911 PSAP monitors
-- These traps are events sent from applications monitoring various other products which are
-- sourced from the configuration items monitored behind these applications.

	psapEvent	TRAP-TYPE
    	ENTERPRISE	senNocCustomTrap
        VARIABLES   { nocHostName, nocComponent, nocSummary, nocSeverity, nocEventSentTime, nocReferURL, nocEventId }
    	DESCRIPTION	"This trap is used for interpreting events forwarded from outside monitoring applications"
    	::= 5

-- Trap type six: Traps forwarded from NG911 SDWAN monitors
-- These traps are events sent from applications monitoring various other products which are
-- sourced from the configuration items monitored behind these applications.

	nocPerfEvent	TRAP-TYPE
    	ENTERPRISE	senNocCustomTrap
        VARIABLES   { nocHostName, nocComponent, nocSeverity, nocPerfType, nocPerfValue }
    	DESCRIPTION	"This trap is used for sending threshold breach events on various performance metrics"
    	::= 6

-- Trap type seven: Traps forwarded from NG911 SDWAN monitors
-- These traps are events sent from applications monitoring various other products which are
-- sourced from the configuration items monitored behind these applications.

	nocLinkEvent	TRAP-TYPE
    	ENTERPRISE	senNocCustomTrap
        VARIABLES   { nocHostName, nocComponent, nocSeverity, nocLinkSend, nocLinkRcvd, nocLinkStatus }
    	DESCRIPTION	"This trap is used for reporting when a link status has changed"
    	::= 7


-- **************************************************************
--			Varbind definitions
-- **************************************************************

-- first varbind	
	nocHostName	OBJECT-TYPE
      SYNTAX	DisplayString 
      ACCESS  read-only
      STATUS  mandatory
      DESCRIPTION
          "The host name of trap source"
     	::= { senNocCustomTrap 1 }

-- second varbind	
	nocSummary	OBJECT-TYPE
      SYNTAX	DisplayString 
      ACCESS  read-only
      STATUS  mandatory
      DESCRIPTION
          "The description of the event (i.e. a short summary of the alarm)"
     	::= { senNocCustomTrap 2 }
	
-- third varbind	
    nocSeverity	  OBJECT-TYPE
      SYNTAX  INTEGER
      ACCESS  read-only
      STATUS  mandatory
      DESCRIPTION
	       "The severity of the trap (5:crit, 4:error, 3:warn, 2:info, 1:debug, 0:clear)"
     	::= { senNocCustomTrap 3 }

-- fourth varbind	
	nocEventSentTime	  OBJECT-TYPE
      SYNTAX	DisplayString 
      ACCESS  read-only
      STATUS  mandatory
      DESCRIPTION
          "The epoch time of the system sending the trap (i.e. the moment the even occurred)"
     	::= { senNocCustomTrap 4 }

-- fifth varbind
	nocComponent	  OBJECT-TYPE
      SYNTAX	DisplayString
      ACCESS  read-only
      STATUS  mandatory
      DESCRIPTION
          "The subject of the alarm such as service or application"
     	::= { senNocCustomTrap 5 }

-- sixth varbind
	nocReferURL	  OBJECT-TYPE
      SYNTAX	DisplayString
      ACCESS  read-only
      STATUS  mandatory
      DESCRIPTION
          "The URL referencing the event source"
     	::= { senNocCustomTrap 6 }

-- seventh varbind
	nocEventId	  OBJECT-TYPE
      SYNTAX	DisplayString
      ACCESS  read-only
      STATUS  mandatory
      DESCRIPTION
          "The unique identifier of the event"
     	::= { senNocCustomTrap 7 }

-- eighth varbind
	nocPerfType	  OBJECT-TYPE
      SYNTAX	DisplayString
      ACCESS  read-only
      STATUS  mandatory
      DESCRIPTION
          "The type of performance metric (CPU, Memory, Network)"
     	::= { senNocCustomTrap 8 }

-- ninth varbind
	nocPerfValue	  OBJECT-TYPE
      SYNTAX	DisplayString
      ACCESS  read-only
      STATUS  mandatory
      DESCRIPTION
          "The current value of the performance metric"
     	::= { senNocCustomTrap 9 }

-- tenth varbind
	nocLinkSend	  OBJECT-TYPE
      SYNTAX	DisplayString
      ACCESS  read-only
      STATUS  mandatory
      DESCRIPTION
          "The host name of the sending link"
     	::= { senNocCustomTrap 10 }

-- eleventh varbind
	nocLinkRcvd	  OBJECT-TYPE
      SYNTAX	DisplayString
      ACCESS  read-only
      STATUS  mandatory
      DESCRIPTION
          "The host name of the receiving link"
     	::= { senNocCustomTrap 11 }

-- twelfth varbind
	nocLinkStatus	  OBJECT-TYPE
      SYNTAX	DisplayString
      ACCESS  read-only
      STATUS  mandatory
      DESCRIPTION
          "The status of the link (up or down)"
     	::= { senNocCustomTrap 12 }


-- **************************************************************
--		Additional Information about this mib
-- **************************************************************

-- This is the transform for Zenoss to handle the traps correctly:
-- evt.device = evt.nocHostName
-- evt.severity = evt.nocSeverity
-- evt.summary = evt.nocSummary
-- evt.dedupid = str(evt.nocHostName) +'|'+ str(evt.nocSummary)

-- Examples of test (alarm) traps from a Linux shell:
-- snmptrap -v 1 -c public 207.158.104.169 .1.3.6.1.4.1.13203.99991 '' 6 4 '' .1.3.6.1.4.1.13203.99991.1 s "siedem405" .1.3.6.1.4.1.13203.99991.2 s "Aggregator Heartbeat"    .1.3.6.1.4.1.13203.99991.3 i "5"
-- snmptrap -v 1 -c public 207.158.104.169 .1.3.6.1.4.1.13203.99991 '' 6 3 '' .1.3.6.1.4.1.13203.99991.1 s "siedem304" .1.3.6.1.4.1.13203.99991.2 s "Call Behavior Alarm"     .1.3.6.1.4.1.13203.99991.3 i "4"
-- snmptrap -v 1 -c public 207.158.104.169 .1.3.6.1.4.1.13203.99991 '' 6 2 '' .1.3.6.1.4.1.13203.99991.1 s "siedem303" .1.3.6.1.4.1.13203.99991.2 s "NOC Automation Alarm"    .1.3.6.1.4.1.13203.99991.3 i "3"
-- snmptrap -v 1 -c public 207.158.104.169 .1.3.6.1.4.1.13203.99991 '' 6 1 '' .1.3.6.1.4.1.13203.99991.1 s "siedem302" .1.3.6.1.4.1.13203.99991.2 s "Zenoss aggregator Alarm" .1.3.6.1.4.1.13203.99991.3 i "2"

-- Examples of test (clear) traps from a Linux shell:
-- snmptrap -v 1 -c public 207.158.104.169 .1.3.6.1.4.1.13203.99991 '' 6 4 '' .1.3.6.1.4.1.13203.99991.1 s "siedem405" .1.3.6.1.4.1.13203.99991.2 s "Aggregator Heartbeat"    .1.3.6.1.4.1.13203.99991.3 i "0"
-- snmptrap -v 1 -c public 207.158.104.169 .1.3.6.1.4.1.13203.99991 '' 6 3 '' .1.3.6.1.4.1.13203.99991.1 s "siedem304" .1.3.6.1.4.1.13203.99991.2 s "Call Behavior Alarm"     .1.3.6.1.4.1.13203.99991.3 i "0"
-- snmptrap -v 1 -c public 207.158.104.169 .1.3.6.1.4.1.13203.99991 '' 6 2 '' .1.3.6.1.4.1.13203.99991.1 s "siedem303" .1.3.6.1.4.1.13203.99991.2 s "NOC Automation Alarm"    .1.3.6.1.4.1.13203.99991.3 i "0"
-- snmptrap -v 1 -c public 207.158.104.169 .1.3.6.1.4.1.13203.99991 '' 6 1 '' .1.3.6.1.4.1.13203.99991.1 s "siedem302" .1.3.6.1.4.1.13203.99991.2 s "Zenoss aggregator Alarm" .1.3.6.1.4.1.13203.99991.3 i "0"

-- **************************************************************

END
