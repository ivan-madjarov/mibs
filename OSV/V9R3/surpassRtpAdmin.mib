SURPASS-RTP-ADMIN-MIB DEFINITIONS ::= BEGIN
-- ==================================================================
--  Copyright © Unify GmbH & Co. KG
--
--  All Rights Reserved.
--
--  Reproduction of this document is authorized on condition that
--  this copyright notice is included.
--
--  This MIB document embodies proprietary intellectual property. 
--  of Unify GmbH & Co. KG, which retains all title and
--  ownership in this MIB, including any revisions.
--
--  This module will be extended, as required.
--
--  Unify GmbH & Co. KG reserves the right to make 
--  changes in specification and other information contained in this 
--  document without prior notice. The reader should consult 
--  Unify GmbH & Co. KG to determine whether any such
--  changes have been made.
--
--  Copyright © Unify GmbH & Co. KG
-- ==================================================================

-- **************************************************************************
-- Revision History
-- 08/01/02     K. Teelucksingh      Initial code
-- 05/08/03     Polly Yu             Updated copyright text 
-- 06/12/08     C. Chatzidimitriou   Updated MIB to be fully compatible with SNMPv2
-- 10/22/2013   G.Kouris             Incorporate new Brand Name
--
-- **************************************************************************

IMPORTS
    surpassRtp                           
        FROM SURPASS-RTP-MIB
    MODULE-IDENTITY, OBJECT-IDENTITY                      
        FROM SNMPv2-SMI; 
	
-- **************************************************************************

    surpassRtpAdmin MODULE-IDENTITY
        LAST-UPDATED "201610251624Z"
        ORGANIZATION "Unify Software and Solutions GmbH & Co. KG"
        CONTACT-INFO "http://www.unify.com/us/Home/Internet/web/us/Home/contact-us.aspx"
        DESCRIPTION
                     "The MIB module describes the top level of the 
                     Surpass RTP Managed Objects."     
        REVISION     "201509141224Z"
        DESCRIPTION
                     "Updated the MIB with the new Brand Name"
        ::= { surpassRtp 2 }

    hiq8000Admin OBJECT-IDENTITY
        STATUS current
        DESCRIPTION
            "The hiQ 8000 Managed Object."
        ::= { surpassRtpAdmin 1 }

END
