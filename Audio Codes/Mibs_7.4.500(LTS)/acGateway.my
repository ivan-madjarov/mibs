AcGateway DEFINITIONS ::= BEGIN
	

   IMPORTS
       
	OBJECT-TYPE, 
	MODULE-IDENTITY                             FROM SNMPv2-SMI
	TAddress, 
	DisplayString, 
	DateAndTime, TEXTUAL-CONVENTION             FROM SNMPv2-TC
	RowPointer                                  FROM SNMPv2-TC
	IpAddress                                   FROM RFC1155-SMI
	Unsigned32,
	Integer32,
	Gauge32,			
	enterprises                                 FROM SNMPv2-SMI
	RowStatus                                   FROM SNMPv2-TC       

	SnmpAdminString                             FROM SNMP-FRAMEWORK-MIB
	audioCodes,
	acRegistrations,
	acGeneric,
	acProducts,acBoardMibs                      FROM AUDIOCODES-TYPES-MIB
	InetAddress, InetAddressType                FROM INET-ADDRESS-MIB;
       
	

acGateway MODULE-IDENTITY
	LAST-UPDATED "202202080929Z"          --Tuesday, February 8 2022
	ORGANIZATION "AudioCodes Ltd"
    	CONTACT-INFO
    	"Postal: Support
    	     AudioCodes LTD
             1 Hayarden Street
             Airport City
             Lod, ISRAEL 70151
	     ISRAEL
     Tel:    972-3-9764000
     Fax:    972-3-9764040
     Email:  support@audiocodes.com
     Web:    www.audiocodes.com"               
		
	DESCRIPTION 
		""

	::= {acBoardMibs 3}






     gwConfiguration OBJECT IDENTIFIER ::= {acGateway 1}


     common OBJECT IDENTIFIER ::= {gwConfiguration 1}


     channelsSetting OBJECT IDENTIFIER ::= {common 1}


     channelsSettingSelectMode OBJECT-TYPE
       SYNTAX INTEGER {
                  byDestPhoneNumber(0)
,
                  cyclicAscending(1)
,
                  ascendingAlways(2)
,
                  cyclicDescending(3)
,
                  descendingAlways(4)
,
                  byDestinationPhoneNumberCyclicAscending(5)
,
                  bySourcePhoneNumber(6)
,
                  trunkCyclicAscending(7)
,
                  trunkAndChannelCyclicAscending(8)
,
                  ringToHuntGroup(9)
,
                  selectTrunkBySuppelmentaryServicesTable(10)
,
                  destNumberAndAscending(11)

                  }
       MAX-ACCESS read-write
       STATUS current
       DESCRIPTION
           "Default method to use for trunk B-channel allocation (IP to
Tel calls).
Access: Instant.
AC INI-Param: CHANNELSELECTMODE"
       ::= {channelsSetting 1}



     -- ****************************************
     -- channels table declaration
     -- ****************************************
     channelsTable OBJECT-TYPE
       SYNTAX SEQUENCE OF ChannelsEntry
       MAX-ACCESS not-accessible
       STATUS current
       DESCRIPTION
           "The table defines trunk/hunt groups and phone numbers for gateway endpoints.
The endpoints that aren’t defined will be disabled."
       ::= {channelsSetting 21}



     -- ****************************************
     -- channels table entry
     -- ****************************************
     channelsEntry OBJECT-TYPE
       SYNTAX ChannelsEntry
       MAX-ACCESS not-accessible
       STATUS current
       DESCRIPTION
           ""
       INDEX {channelsIndex}
       ::= {channelsTable 1}



     -- ****************************************
     -- channels TABLE
     -- ****************************************
     ChannelsEntry ::= SEQUENCE {
       channelsIndex                                   Unsigned32,
       channelsRowStatus                               RowStatus,
       channelsAction                                  INTEGER,
       channelsActionResult                            INTEGER,
       channelsTrunkID                                 Unsigned32,
       channelsStartingCh                              Unsigned32,
       channelsLastCh                                  Unsigned32,
       channelsStartingPhoneNum                        SnmpAdminString,
       channelsTrunkGroupID                            Unsigned32,
       channelsProfileID                               Unsigned32,
       channelsLastTrunkID                             Unsigned32,
       channelsModule                                  Integer32
     }



     channelsIndex OBJECT-TYPE
       SYNTAX Unsigned32 (0..239)
       MAX-ACCESS not-accessible
       STATUS current
       DESCRIPTION
           "Channel numbers, starting at 0.
AC INI-Param: TrunkGroup_Index"
       ::= {channelsEntry 1}



     channelsRowStatus OBJECT-TYPE
       SYNTAX RowStatus
       MAX-ACCESS read-create
       STATUS current
       DESCRIPTION
           "Row-Status Textual Conventions as defined in RFC 2579: Textual
Conventions for SMIv2.
AC INI-Param: N/A"
       ::= {channelsEntry 2}



     channelsAction OBJECT-TYPE
       SYNTAX INTEGER {
                  developmentImpending(0)

                  }
       MAX-ACCESS read-only
       STATUS current
       DESCRIPTION
           "Development Impending.
AC INI-Param: N/A"
       ::= {channelsEntry 3}



     channelsActionResult OBJECT-TYPE
       SYNTAX INTEGER {
                  developmentImpending(0)

                  }
       MAX-ACCESS read-only
       STATUS current
       DESCRIPTION
           "Development Impending.
AC INI-Param: N/A"
       ::= {channelsEntry 4}



     channelsTrunkID OBJECT-TYPE
       SYNTAX Unsigned32 (0..255)
       MAX-ACCESS read-create
       STATUS current
       DESCRIPTION
           "Trunk/Hunt group ID.
Access: Instant.
AC INI-Param: TrunkGroup_FirstTrunkId"
       ::= {channelsEntry 5}



     channelsStartingCh OBJECT-TYPE
       SYNTAX Unsigned32 (1..2016)
       MAX-ACCESS read-create
       STATUS current
       DESCRIPTION
           "Starting Channel for this trunk/hunt group.
Access: Instant.
AC INI-Param: TrunkGroup_FirstBChannel"
       ::= {channelsEntry 6}



     channelsLastCh OBJECT-TYPE
       SYNTAX Unsigned32 (1..2016)
       MAX-ACCESS read-create
       STATUS current
       DESCRIPTION
           "Last Channel for the trunk/hunt group.
Access: Instant.
AC INI-Param: TrunkGroup_LastBChannel"
       ::= {channelsEntry 7}



     channelsStartingPhoneNum OBJECT-TYPE
       SYNTAX SnmpAdminString (SIZE (0..50))
       MAX-ACCESS read-create
       STATUS current
       DESCRIPTION
           "Starting Phone Number.
Access: Instant.
AC INI-Param: TrunkGroup_FirstPhoneNumber"
       ::= {channelsEntry 8}



     channelsTrunkGroupID OBJECT-TYPE
       SYNTAX Unsigned32 (0..255)
       MAX-ACCESS read-create
       STATUS current
       DESCRIPTION
           "Trunk/Hunt group ID.
Access: Instant.
AC INI-Param: TrunkGroup_TrunkGroupNum"
       ::= {channelsEntry 9}



     channelsProfileID OBJECT-TYPE
       SYNTAX Unsigned32 (0..9)
       MAX-ACCESS read-create
       STATUS current
       DESCRIPTION
           "Profile ID.
Access: Instant.
AC INI-Param: TrunkGroup_ProfileId"
       ::= {channelsEntry 10}



     channelsLastTrunkID OBJECT-TYPE
       SYNTAX Unsigned32 (0..255)
       MAX-ACCESS read-create
       STATUS current
       DESCRIPTION
           "Last Trunk/Hunt group ID.
Access: Instant.
AC INI-Param: TrunkGroup_LastTrunkId"
       ::= {channelsEntry 11}



     channelsModule OBJECT-TYPE
       SYNTAX Integer32 (-1..255)
       MAX-ACCESS read-create
       STATUS current
       DESCRIPTION
           "Channels Module.
Access: Instant.
AC INI-Param: TrunkGroup_Module"
       ::= {channelsEntry 12}



     -- ****************************************
     -- trunkGroupSettings table declaration
     -- ****************************************
     trunkGroupSettingsTable OBJECT-TYPE
       SYNTAX SEQUENCE OF TrunkGroupSettingsEntry
       MAX-ACCESS not-accessible
       STATUS current
       DESCRIPTION
           "The table defines trunk/hunt groups configuration"
       ::= {channelsSetting 22}



     -- ****************************************
     -- trunkGroupSettings table entry
     -- ****************************************
     trunkGroupSettingsEntry OBJECT-TYPE
       SYNTAX TrunkGroupSettingsEntry
       MAX-ACCESS not-accessible
       STATUS current
       DESCRIPTION
           ""
       INDEX {trunkGroupSettingsIndex}
       ::= {trunkGroupSettingsTable 1}



     -- ****************************************
     -- trunkGroupSettings TABLE
     -- ****************************************
     TrunkGroupSettingsEntry ::= SEQUENCE {
       trunkGroupSettingsIndex                         Unsigned32,
       trunkGroupSettingsRowStatus                     RowStatus,
       trunkGroupSettingsAction                        INTEGER,
       trunkGroupSettingsActionResult                  INTEGER,
       trunkGroupSettingsTrunkGroupID                  Unsigned32,
       trunkGroupSettingsChannelSelectMode             INTEGER,
       trunkGroupSettingsRegistrationMode              INTEGER,
       trunkGroupSettingsGatewayName                   SnmpAdminString,
       trunkGroupSettingsContactUser                   SnmpAdminString,
       trunkGroupSettingsServingIPGroup                Integer32,
       trunkGroupSettingsMwiInterrogationType          INTEGER,
       trunkGroupSettingsGrpName                       SnmpAdminString
     }



     trunkGroupSettingsIndex OBJECT-TYPE
       SYNTAX Unsigned32 (0..240)
       MAX-ACCESS not-accessible
       STATUS current
       DESCRIPTION
           "Trunk numbers, starting at 0. 
for M800/MP118/MP124 max value is 100.
AC INI-Param: TrunkGroupSettings_Index"
       ::= {trunkGroupSettingsEntry 1}



     trunkGroupSettingsRowStatus OBJECT-TYPE
       SYNTAX RowStatus
       MAX-ACCESS read-create
       STATUS current
       DESCRIPTION
           "Row-Status Textual Conventions as defined in RFC 2579: Textual
Conventions for SMIv2.
AC INI-Param: N/A"
       ::= {trunkGroupSettingsEntry 2}



     trunkGroupSettingsAction OBJECT-TYPE
       SYNTAX INTEGER {
                  developmentImpending(0)

                  }
       MAX-ACCESS read-only
       STATUS current
       DESCRIPTION
           "Development Impending.
AC INI-Param: N/A"
       ::= {trunkGroupSettingsEntry 3}



     trunkGroupSettingsActionResult OBJECT-TYPE
       SYNTAX INTEGER {
                  developmentImpending(0)

                  }
       MAX-ACCESS read-only
       STATUS current
       DESCRIPTION
           "Development Impending.
AC INI-Param: N/A"
       ::= {trunkGroupSettingsEntry 4}



     trunkGroupSettingsTrunkGroupID OBJECT-TYPE
       SYNTAX Unsigned32 (0..255)
       MAX-ACCESS read-create
       STATUS current
       DESCRIPTION
           "Trunk/Hunt group ID.
Access: Instant.
AC INI-Param: TrunkGroupSettings_TrunkGroupId"
       ::= {trunkGroupSettingsEntry 5}



     trunkGroupSettingsChannelSelectMode OBJECT-TYPE
       SYNTAX INTEGER {
                  byPhoneNumber(0)
,
                  cyclicAscending(1)
,
                  ascendingAlways(2)
,
                  cyclicDescending(3)
,
                  descendingAlways(4)
,
                  byPhoneNumberCyclicAscending(5)
,
                  bySourcePhoneNumber(6)
,
                  trunkCyclicAscending(7)
,
                  trunkAndChannelCyclicAscending(8)
,
                  ringToHuntGroup(9)
,
                  selectTrunkBySuppelmentaryServicesTable(10)
,
                  destNumberAndAscending(11)
,
                  valueNotSet(255)

                  }
       MAX-ACCESS read-create
       STATUS current
       DESCRIPTION
           "Selects the next available (free) Gateway port, FXO/PSTN: affects
outgoing calls chanel selection  FXS:affects incoming
call channel selection.
Access: Instant.
AC INI-Param: TrunkGroupSettings_ChannelSelectMode"
       ::= {trunkGroupSettingsEntry 6}



     trunkGroupSettingsRegistrationMode OBJECT-TYPE
       SYNTAX INTEGER {
                  perEndpoint(0)
,
                  perGateway(1)
,
                  notApplicable(2)
,
                  doNotRegister(4)
,
                  perAccount(5)
,
                  valueNotSet(255)

                  }
       MAX-ACCESS read-create
       STATUS current
       DESCRIPTION
           "
Access: Instant.
AC INI-Param: TrunkGroupSettings_RegistrationMode"
       ::= {trunkGroupSettingsEntry 7}



     trunkGroupSettingsGatewayName OBJECT-TYPE
       SYNTAX SnmpAdminString (SIZE (0..49))
       MAX-ACCESS read-create
       STATUS current
       DESCRIPTION
           "
Access: Instant.
AC INI-Param: TrunkGroupSettings_GatewayName"
       ::= {trunkGroupSettingsEntry 8}



     trunkGroupSettingsContactUser OBJECT-TYPE
       SYNTAX SnmpAdminString (SIZE (0..50))
       MAX-ACCESS read-create
       STATUS current
       DESCRIPTION
           "
Access: Instant.
AC INI-Param: TrunkGroupSettings_ContactUser"
       ::= {trunkGroupSettingsEntry 9}



     trunkGroupSettingsServingIPGroup OBJECT-TYPE
       SYNTAX Integer32 (-1..49)
       MAX-ACCESS read-create
       STATUS current
       DESCRIPTION
           "
Access: Instant.
AC INI-Param: TrunkGroupSettings_ServingIPGroup"
       ::= {trunkGroupSettingsEntry 10}



     trunkGroupSettingsMwiInterrogationType OBJECT-TYPE
       SYNTAX INTEGER {
                  none(0)
,
                  useActivateOnly(1)
,
                  resultNotUsed(2)
,
                  useResult(3)
,
                  notConfigured(255)

                  }
       MAX-ACCESS read-create
       STATUS current
       DESCRIPTION
           "
Access: Instant.
AC INI-Param: TrunkGroupSettings_MWIInterrogationType"
       ::= {trunkGroupSettingsEntry 11}



     trunkGroupSettingsGrpName OBJECT-TYPE
       SYNTAX SnmpAdminString (SIZE (0..240))
       MAX-ACCESS read-create
       STATUS current
       DESCRIPTION
           "
Access: Instant.
AC INI-Param: TrunkGroupSettings_TrunkGroupName"
       ::= {trunkGroupSettingsEntry 12}



     manipulationAndRouting OBJECT IDENTIFIER ::= {common 2}


     manipulationAndRoutingModeTel2Ip OBJECT-TYPE
       SYNTAX INTEGER {
                  routeBeforeMap(0)
,
                  routeAfterMap(1)

                  }
       MAX-ACCESS read-write
       STATUS current
       DESCRIPTION
           "Defines order between routing incoming calls from Tel side and
performing manipulations.
Access: Instant.
AC INI-Param: ROUTEMODETEL2IP"
       ::= {manipulationAndRouting 1}



     manipulationAndRoutingModeIp2Tel OBJECT-TYPE
       SYNTAX INTEGER {
                  routeBeforeMap(0)
,
                  routeAfterMap(1)

                  }
       MAX-ACCESS read-write
       STATUS current
       DESCRIPTION
           "Defines order between routing incoming calls from IP side and
performing manipulations.
Access: Instant.
AC INI-Param: ROUTEMODEIP2TEL"
       ::= {manipulationAndRouting 2}



     manipulationAndRoutingFilterCalls2Ip OBJECT-TYPE
       SYNTAX INTEGER {
                  no(0)
,
                  yes(1)

                  }
       MAX-ACCESS read-write
       STATUS current
       DESCRIPTION
           "When Gatekeeper/Proxy is enabled, do not start session if called
number is not listed or restricted in Tel to IP routing
table.
Access: Instant.
AC INI-Param: FILTERCALLS2IP"
       ::= {manipulationAndRouting 3}



     manipulationAndRoutingAltRoutingTel2IpEnable OBJECT-TYPE
       SYNTAX INTEGER {
                  disable(0)
,
                  enable(1)
,
                   statusOnly(2)

                  }
       MAX-ACCESS read-write
       STATUS current
       DESCRIPTION
           "Enable Tel to IP Alternative Routing. Can be enabled for status
only without affecting routing.
Access: Instant.
AC INI-Param: ALTROUTINGTEL2IPENABLE"
       ::= {manipulationAndRouting 4}



     manipulationAndRoutingAltRoutingTel2IpMode OBJECT-TYPE
       SYNTAX INTEGER {
                  none(0)
,
                  conn(1)
,
                  qos(2)
,
                  both(3)

                  }
       MAX-ACCESS read-write
       STATUS current
       DESCRIPTION
           "Methods used for Alternative Routing operation.
Access: Instant.
AC INI-Param: ALTROUTINGTEL2IPMODE"
       ::= {manipulationAndRouting 5}



     manipulationAndRoutingAltRoutingTel2IpQosAllowTheNCall OBJECT-TYPE
       SYNTAX Unsigned32 (0..100)
       MAX-ACCESS read-write
       STATUS current
       DESCRIPTION
           "in case of QOS problem, a call has this probability (in percents)
to continue, in order to reevaluate the QOS.
Access: Instant.
AC INI-Param: ALTROUTINGTEL2IPQOSALLOWPROB"
       ::= {manipulationAndRouting 6}



     manipulationAndRoutingPreferRouteTable OBJECT-TYPE
       SYNTAX INTEGER {
                  disable(0)
,
                  enable(1)

                  }
       MAX-ACCESS read-write
       STATUS current
       DESCRIPTION
           "Prefer Routing Table.
Access: Instant.
AC INI-Param: PREFERROUTETABLE"
       ::= {manipulationAndRouting 7}



     manipulationAndRoutingRedundantRoutingMode OBJECT-TYPE
       SYNTAX INTEGER {
                  disable(0)
,
                  routingTable(1)
,
                  proxy(2)

                  }
       MAX-ACCESS read-write
       STATUS current
       DESCRIPTION
           "Mode of redundant routing. 0 - Disabled, 1 - Use routing table,
2 - Use proxies list.
Access: Instant.
AC INI-Param: REDUNDANTROUTINGMODE"
       ::= {manipulationAndRouting 8}



     manipulationAndRoutingAltRoutingTel2IpConnMethod OBJECT-TYPE
       SYNTAX INTEGER {
                  ping(0)
,
                  options(1)

                  }
       MAX-ACCESS read-write
       STATUS current
       DESCRIPTION
           "Tel to IP Alternative Routing Connectivity Method.
Access: Instant.
AC INI-Param: ALTROUTINGTEL2IPCONNMETHOD"
       ::= {manipulationAndRouting 9}



     manipulationAndRoutingSIPReRoutingMode OBJECT-TYPE
       SYNTAX INTEGER {
                  standardMode(0)
,
                  sendInviteToProxy(1)
,
                  useRoutingTable(2)

                  }
       MAX-ACCESS read-write
       STATUS current
       DESCRIPTION
           "Defines the routing mode after receiving 3xx response or transfer
0 - standard mode
1 - send invite to proxy
2 - use routing table.
Access: Instant.
AC INI-Param: SIPREROUTINGMODE"
       ::= {manipulationAndRouting 10}



     manipulationAndRoutingAltRoutingToneDuration OBJECT-TYPE
       SYNTAX Unsigned32 (0..20000)
       MAX-ACCESS read-write
       STATUS current
       DESCRIPTION
           "Alternative Routing Tone Duration. 0 - disabled (milliseconds).
Access: Instant.
AC INI-Param: ALTROUTINGTONEDURATION"
       ::= {manipulationAndRouting 11}



     manipulationAndRoutingAltRoutingTel2IpKeepAliveTime OBJECT-TYPE
       SYNTAX Unsigned32 (5..2000000)
       MAX-ACCESS read-write
       STATUS current
       DESCRIPTION
           "Time interval between OPTIONS Keep-Alive messages for IP connectivity
(seconds).
Access: Instant.
AC INI-Param: ALTROUTINGTEL2IPKEEPALIVETIME"
       ::= {manipulationAndRouting 12}



     manipulationAndRoutingIP2TelTaggingDestDialPlanIndex OBJECT-TYPE
       SYNTAX Integer32 (-1..7)
       MAX-ACCESS read-write
       STATUS current
       DESCRIPTION
           "IP to Tel Tagging Destination Dial Plan Index.
Access: Instant.
AC INI-Param: IP2TELTAGGINGDESTDIALPLANINDEX"
       ::= {manipulationAndRouting 13}



     manipulationAndRoutingIP2TelTaggingSourceDialPlanIndex OBJECT-TYPE
       SYNTAX Integer32 (-1..7)
       MAX-ACCESS read-write
       STATUS current
       DESCRIPTION
           "IP to Tel Tagging Source Dial Plan Index.
Access: Instant.
AC INI-Param: IP2TELTAGGINGSOURCEDIALPLANINDEX"
       ::= {manipulationAndRouting 14}



     routing OBJECT IDENTIFIER ::= {manipulationAndRouting 20}


     -- ****************************************
     -- tel2IPRouting table declaration
     -- ****************************************
     tel2IPRoutingTable OBJECT-TYPE
       SYNTAX SEQUENCE OF Tel2IPRoutingEntry
       MAX-ACCESS not-accessible
       STATUS current
       DESCRIPTION
           "Phone prefix to IP address routing table.
The table is used for routing incoming PSTN to IP calls,
 if Gatekeeper is not used."
       ::= {routing 1}



     -- ****************************************
     -- tel2IPRouting table entry
     -- ****************************************
     tel2IPRoutingEntry OBJECT-TYPE
       SYNTAX Tel2IPRoutingEntry
       MAX-ACCESS not-accessible
       STATUS current
       DESCRIPTION
           ""
       INDEX {tel2IPRoutingIndex}
       ::= {tel2IPRoutingTable 1}



     -- ****************************************
     -- tel2IPRouting TABLE
     -- ****************************************
     Tel2IPRoutingEntry ::= SEQUENCE {
       tel2IPRoutingIndex                              Unsigned32,
       tel2IPRoutingRowStatus                          RowStatus,
       tel2IPRoutingAction                             INTEGER,
       tel2IPRoutingActionResult                       INTEGER,
       tel2IPRoutingPrefix                             SnmpAdminString,
       tel2IPRoutingAddress                            SnmpAdminString,
       tel2IPRoutingSrcPrefix                          SnmpAdminString,
       tel2IPRoutingProfileID                          Integer32,
       tel2IPRoutingChargeCode                         Unsigned32,
       tel2IPRoutingDestPort                           Unsigned32,
       tel2IPRoutingSourceIPGroupID                    Integer32,
       tel2IPRoutingDestHostPrefix                     SnmpAdminString,
       tel2IPRoutingDestIPGroupID                      Integer32,
       tel2IPRoutingSourceHostPrefix                   SnmpAdminString,
       tel2IPRoutingTransportType                      INTEGER,
       tel2IPRoutingSourceTrunkGroupID                 Integer32,
       tel2IPRoutingDestSRD                            Integer32,
       tel2IPRoutingCostGroupName                      RowPointer,
       tel2IPRoutingRouteName                          SnmpAdminString
     }



     tel2IPRoutingIndex OBJECT-TYPE
       SYNTAX Unsigned32 (0..179)
       MAX-ACCESS not-accessible
       STATUS current
       DESCRIPTION
           "Entry number, starting at 0.
AC INI-Param: PREFIX_Index"
       ::= {tel2IPRoutingEntry 1}



     tel2IPRoutingRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {tel2IPRoutingEntry 2}



     tel2IPRoutingAction OBJECT-TYPE
       SYNTAX INTEGER {
                  developmentImpending(0)

                  }
       MAX-ACCESS read-only
       STATUS current
       DESCRIPTION
           "Development Impending.
AC INI-Param: N/A"
       ::= {tel2IPRoutingEntry 3}



     tel2IPRoutingActionResult OBJECT-TYPE
       SYNTAX INTEGER {
                  developmentImpending(0)

                  }
       MAX-ACCESS read-only
       STATUS current
       DESCRIPTION
           "Development Impending.
AC INI-Param: N/A"
       ::= {tel2IPRoutingEntry 4}



     tel2IPRoutingPrefix OBJECT-TYPE
       SYNTAX SnmpAdminString (SIZE (0..50))
       MAX-ACCESS read-create
       STATUS current
       DESCRIPTION
           "Phone number prefix.
up to 50 digits.
can be used for defining range of phone numbers.
Access: Instant.
AC INI-Param: PREFIX_DestinationPrefix"
       ::= {tel2IPRoutingEntry 5}



     tel2IPRoutingAddress OBJECT-TYPE
       SYNTAX SnmpAdminString (SIZE (0..69))
       MAX-ACCESS read-create
       STATUS current
       DESCRIPTION
           "Address (IP or DNS name).
Access: Instant.
AC INI-Param: PREFIX_DestAddress"
       ::= {tel2IPRoutingEntry 6}



     tel2IPRoutingSrcPrefix OBJECT-TYPE
       SYNTAX SnmpAdminString (SIZE (0..50))
       MAX-ACCESS read-create
       STATUS current
       DESCRIPTION
           "Calling Phone number prefix.
up to 50 digits.
can be used for defining range of phone numbers.
Access: Instant.
AC INI-Param: PREFIX_SourcePrefix"
       ::= {tel2IPRoutingEntry 7}



     tel2IPRoutingProfileID OBJECT-TYPE
       SYNTAX Integer32 (-1..9)
       MAX-ACCESS read-create
       STATUS current
       DESCRIPTION
           "Profile ID.
Access: Instant.
AC INI-Param: PREFIX_ProfileId"
       ::= {tel2IPRoutingEntry 8}



     tel2IPRoutingChargeCode OBJECT-TYPE
       SYNTAX Unsigned32 (0..255)
       MAX-ACCESS read-create
       STATUS current
       DESCRIPTION
           "Charge code to use for generating metering tones.
Access: Instant.
AC INI-Param: PREFIX_MeteringCode"
       ::= {tel2IPRoutingEntry 9}



     tel2IPRoutingDestPort OBJECT-TYPE
       SYNTAX Unsigned32 (0..65534)
       MAX-ACCESS read-create
       STATUS current
       DESCRIPTION
           "Destination port.
Access: Instant.
AC INI-Param: PREFIX_DestPort"
       ::= {tel2IPRoutingEntry 10}



     tel2IPRoutingSourceIPGroupID OBJECT-TYPE
       SYNTAX Integer32 (-1..31)
       MAX-ACCESS read-create
       STATUS current
       DESCRIPTION
           "
Access: Instant.
AC INI-Param: PREFIX_SrcIPGroupID"
       ::= {tel2IPRoutingEntry 11}



     tel2IPRoutingDestHostPrefix OBJECT-TYPE
       SYNTAX SnmpAdminString (SIZE (0..49))
       MAX-ACCESS read-create
       STATUS current
       DESCRIPTION
           "
Access: Instant.
AC INI-Param: PREFIX_DestHostPrefix"
       ::= {tel2IPRoutingEntry 12}



     tel2IPRoutingDestIPGroupID OBJECT-TYPE
       SYNTAX Integer32 (-1..31)
       MAX-ACCESS read-create
       STATUS current
       DESCRIPTION
           "
Access: Instant.
AC INI-Param: PREFIX_DestIPGroupID"
       ::= {tel2IPRoutingEntry 13}



     tel2IPRoutingSourceHostPrefix OBJECT-TYPE
       SYNTAX SnmpAdminString (SIZE (0..49))
       MAX-ACCESS read-create
       STATUS current
       DESCRIPTION
           "
Access: Instant.
AC INI-Param: PREFIX_SrcHostPrefix"
       ::= {tel2IPRoutingEntry 14}



     tel2IPRoutingTransportType OBJECT-TYPE
       SYNTAX INTEGER {
                  notConfigured(-1)
,
                  udp(0)
,
                  tcp(1)
,
                  tls(2)

                  }
       MAX-ACCESS read-create
       STATUS current
       DESCRIPTION
           "
Access: Instant.
AC INI-Param: PREFIX_TransportType"
       ::= {tel2IPRoutingEntry 15}



     tel2IPRoutingSourceTrunkGroupID OBJECT-TYPE
       SYNTAX Integer32 (-1..99)
       MAX-ACCESS read-create
       STATUS current
       DESCRIPTION
           "
Access: Instant.
AC INI-Param: PREFIX_SrcTrunkGroupID"
       ::= {tel2IPRoutingEntry 16}



     tel2IPRoutingDestSRD OBJECT-TYPE
       SYNTAX Integer32 (-1..31)
       MAX-ACCESS read-create
       STATUS current
       DESCRIPTION
           "
Access: Instant.
AC INI-Param: PREFIX_DestSRD"
       ::= {tel2IPRoutingEntry 17}



     tel2IPRoutingCostGroupName OBJECT-TYPE
       SYNTAX RowPointer
       MAX-ACCESS read-create
       STATUS current
       DESCRIPTION
           "A row pointer to the costGroupName.
Access: Instant.
AC INI-Param: PREFIX_CostGroup"
       ::= {tel2IPRoutingEntry 18}



     tel2IPRoutingRouteName OBJECT-TYPE
       SYNTAX SnmpAdminString (SIZE (0..20))
       MAX-ACCESS read-create
       STATUS current
       DESCRIPTION
           "Route Name.
Access: Instant.
AC INI-Param: PREFIX_RouteName"
       ::= {tel2IPRoutingEntry 19}



     -- ****************************************
     -- iP2TelRouting table declaration
     -- ****************************************
     iP2TelRoutingTable OBJECT-TYPE
       SYNTAX SEQUENCE OF IP2TelRoutingEntry
       MAX-ACCESS not-accessible
       STATUS current
       DESCRIPTION
           "Phone prefix to Trunk group (or Hunt Group for MP-1xx)routing table. The table is used for routing outgoing IP Telco calls, according to received from IP destination phone number."
       ::= {routing 2}



     -- ****************************************
     -- iP2TelRouting table entry
     -- ****************************************
     iP2TelRoutingEntry OBJECT-TYPE
       SYNTAX IP2TelRoutingEntry
       MAX-ACCESS not-accessible
       STATUS current
       DESCRIPTION
           ""
       INDEX {iP2TelRoutingIndex}
       ::= {iP2TelRoutingTable 1}



     -- ****************************************
     -- iP2TelRouting TABLE
     -- ****************************************
     IP2TelRoutingEntry ::= SEQUENCE {
       iP2TelRoutingIndex                              Unsigned32,
       iP2TelRoutingRowStatus                          RowStatus,
       iP2TelRoutingAction                             INTEGER,
       iP2TelRoutingActionResult                       INTEGER,
       iP2TelRoutingPrefix                             SnmpAdminString,
       iP2TelRoutingTrunkGroupID                       Unsigned32,
       iP2TelRoutingSrcPrefix                          SnmpAdminString,
       iP2TelRoutingAddress                            SnmpAdminString,
       iP2TelRoutingProfileID                          Unsigned32,
       iP2TelRoutingSourceIPGroupID                    Integer32,
       iP2TelRoutingDestHostPrefix                     SnmpAdminString,
       iP2TelRoutingSourceHostPrefix                   SnmpAdminString,
       iP2TelRoutingTrunkId                            Integer32,
       iP2TelRoutingRouteName                          SnmpAdminString
     }



     iP2TelRoutingIndex OBJECT-TYPE
       SYNTAX Unsigned32 (0..119)
       MAX-ACCESS not-accessible
       STATUS current
       DESCRIPTION
           "Entry number, starting at 0.
AC INI-Param: PstnPrefix_Index"
       ::= {iP2TelRoutingEntry 1}



     iP2TelRoutingRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {iP2TelRoutingEntry 2}



     iP2TelRoutingAction OBJECT-TYPE
       SYNTAX INTEGER {
                  developmentImpending(0)

                  }
       MAX-ACCESS read-only
       STATUS current
       DESCRIPTION
           "Development Impending.
AC INI-Param: N/A"
       ::= {iP2TelRoutingEntry 3}



     iP2TelRoutingActionResult OBJECT-TYPE
       SYNTAX INTEGER {
                  developmentImpending(0)

                  }
       MAX-ACCESS read-only
       STATUS current
       DESCRIPTION
           "Development Impending.
AC INI-Param: N/A"
       ::= {iP2TelRoutingEntry 4}



     iP2TelRoutingPrefix OBJECT-TYPE
       SYNTAX SnmpAdminString (SIZE (0..80))
       MAX-ACCESS read-create
       STATUS current
       DESCRIPTION
           "Phone number prefix.
up to 80 digits.
can be used for defining range of phone numbers.
Access: Instant.
AC INI-Param: PstnPrefix_DestPrefix"
       ::= {iP2TelRoutingEntry 5}



     iP2TelRoutingTrunkGroupID OBJECT-TYPE
       SYNTAX Unsigned32 (0..99)
       MAX-ACCESS read-create
       STATUS current
       DESCRIPTION
           "Trunk/Hunt group ID.
Access: Instant.
AC INI-Param: PstnPrefix_TrunkGroupId"
       ::= {iP2TelRoutingEntry 6}



     iP2TelRoutingSrcPrefix OBJECT-TYPE
       SYNTAX SnmpAdminString (SIZE (0..49))
       MAX-ACCESS read-create
       STATUS current
       DESCRIPTION
           "Calling Phone number prefix.
up to 49 digits.
can be used for defining range of phone numbers.
Access: Instant.
AC INI-Param: PstnPrefix_SourcePrefix"
       ::= {iP2TelRoutingEntry 7}



     iP2TelRoutingAddress OBJECT-TYPE
       SYNTAX SnmpAdminString (SIZE (0..50))
       MAX-ACCESS read-create
       STATUS current
       DESCRIPTION
           "Address (IP or DNS name).
Access: Instant.
AC INI-Param: PstnPrefix_SourceAddress"
       ::= {iP2TelRoutingEntry 8}



     iP2TelRoutingProfileID OBJECT-TYPE
       SYNTAX Unsigned32 (0..9)
       MAX-ACCESS read-create
       STATUS current
       DESCRIPTION
           "Profile ID.
Access: Instant.
AC INI-Param: PstnPrefix_ProfileId"
       ::= {iP2TelRoutingEntry 9}



     iP2TelRoutingSourceIPGroupID OBJECT-TYPE
       SYNTAX Integer32 (-1..31)
       MAX-ACCESS read-create
       STATUS current
       DESCRIPTION
           "
Access: Instant.
AC INI-Param: PstnPrefix_SrcIPGroupID"
       ::= {iP2TelRoutingEntry 10}



     iP2TelRoutingDestHostPrefix OBJECT-TYPE
       SYNTAX SnmpAdminString (SIZE (0..49))
       MAX-ACCESS read-create
       STATUS current
       DESCRIPTION
           "
Access: Instant.
AC INI-Param: PstnPrefix_DestHostPrefix"
       ::= {iP2TelRoutingEntry 11}



     iP2TelRoutingSourceHostPrefix OBJECT-TYPE
       SYNTAX SnmpAdminString (SIZE (0..49))
       MAX-ACCESS read-create
       STATUS current
       DESCRIPTION
           "
Access: Instant.
AC INI-Param: PstnPrefix_SrcHostPrefix"
       ::= {iP2TelRoutingEntry 12}



     iP2TelRoutingTrunkId OBJECT-TYPE
       SYNTAX Integer32 (-1..83)
       MAX-ACCESS read-create
       STATUS current
       DESCRIPTION
           "TrunkId.
Access: Instant.
AC INI-Param: PstnPrefix_TrunkId"
       ::= {iP2TelRoutingEntry 13}



     iP2TelRoutingRouteName OBJECT-TYPE
       SYNTAX SnmpAdminString (SIZE (0..20))
       MAX-ACCESS read-create
       STATUS current
       DESCRIPTION
           "Route Name.
Access: Instant.
AC INI-Param: PstnPrefix_RouteName"
       ::= {iP2TelRoutingEntry 14}



     -- ****************************************
     -- dnsInfo table declaration
     -- ****************************************
     dnsInfoTable OBJECT-TYPE
       SYNTAX SEQUENCE OF DnsInfoEntry
       MAX-ACCESS not-accessible
       STATUS current
       DESCRIPTION
           ""
       ::= {routing 3}



     -- ****************************************
     -- dnsInfo table entry
     -- ****************************************
     dnsInfoEntry OBJECT-TYPE
       SYNTAX DnsInfoEntry
       MAX-ACCESS not-accessible
       STATUS current
       DESCRIPTION
           ""
       INDEX {dnsInfoIndex}
       ::= {dnsInfoTable 1}



     -- ****************************************
     -- dnsInfo TABLE
     -- ****************************************
     DnsInfoEntry ::= SEQUENCE {
       dnsInfoIndex                                    Unsigned32,
       dnsInfoRowStatus                                RowStatus,
       dnsInfoAction                                   INTEGER,
       dnsInfoActionResult                             INTEGER,
       dnsInfoDomainName                               SnmpAdminString,
       dnsInfoFirstIPAddress                           SnmpAdminString,
       dnsInfoSecondIPAddress                          SnmpAdminString,
       dnsInfoThirdIPAddress                           SnmpAdminString,
       dnsInfoFourthIPAddress                          SnmpAdminString
     }



     dnsInfoIndex OBJECT-TYPE
       SYNTAX Unsigned32 (0..19)
       MAX-ACCESS not-accessible
       STATUS current
       DESCRIPTION
           "Entry number, starting at 0.
AC INI-Param: Dns2Ip_Index"
       ::= {dnsInfoEntry 1}



     dnsInfoRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {dnsInfoEntry 2}



     dnsInfoAction OBJECT-TYPE
       SYNTAX INTEGER {
                  developmentImpending(0)

                  }
       MAX-ACCESS read-only
       STATUS current
       DESCRIPTION
           "Development Impending.
AC INI-Param: N/A"
       ::= {dnsInfoEntry 3}



     dnsInfoActionResult OBJECT-TYPE
       SYNTAX INTEGER {
                  developmentImpending(0)

                  }
       MAX-ACCESS read-only
       STATUS current
       DESCRIPTION
           "Development Impending.
AC INI-Param: N/A"
       ::= {dnsInfoEntry 4}



     dnsInfoDomainName OBJECT-TYPE
       SYNTAX SnmpAdminString (SIZE (0..69))
       MAX-ACCESS read-create
       STATUS current
       DESCRIPTION
           "Domain Name.
Access: Instant.
AC INI-Param: Dns2Ip_DomainName"
       ::= {dnsInfoEntry 5}



     dnsInfoFirstIPAddress OBJECT-TYPE
       SYNTAX SnmpAdminString (SIZE (0..15))
       MAX-ACCESS read-create
       STATUS deprecated
       DESCRIPTION
           "IP Address.
Access: Instant.
AC INI-Param: Dns2Ip_FirstIpAddress"
       ::= {dnsInfoEntry 6}



     dnsInfoSecondIPAddress OBJECT-TYPE
       SYNTAX SnmpAdminString (SIZE (0..15))
       MAX-ACCESS read-create
       STATUS deprecated
       DESCRIPTION
           "IP Address.
Access: Instant.
AC INI-Param: Dns2Ip_SecondIpAddress"
       ::= {dnsInfoEntry 7}



     dnsInfoThirdIPAddress OBJECT-TYPE
       SYNTAX SnmpAdminString (SIZE (0..15))
       MAX-ACCESS read-create
       STATUS deprecated
       DESCRIPTION
           "IP Address.
Access: Instant.
AC INI-Param: Dns2Ip_ThirdIpAddress"
       ::= {dnsInfoEntry 8}



     dnsInfoFourthIPAddress OBJECT-TYPE
       SYNTAX SnmpAdminString (SIZE (0..15))
       MAX-ACCESS read-create
       STATUS obsolete
       DESCRIPTION
           "IP Address.
Access: Instant.
AC INI-Param: Dns2Ip_FourthIpAddress"
       ::= {dnsInfoEntry 9}



     -- ****************************************
     -- srvInfo table declaration
     -- ****************************************
     srvInfoTable OBJECT-TYPE
       SYNTAX SEQUENCE OF SrvInfoEntry
       MAX-ACCESS not-accessible
       STATUS current
       DESCRIPTION
           ""
       ::= {routing 4}



     -- ****************************************
     -- srvInfo table entry
     -- ****************************************
     srvInfoEntry OBJECT-TYPE
       SYNTAX SrvInfoEntry
       MAX-ACCESS not-accessible
       STATUS current
       DESCRIPTION
           ""
       INDEX {srvInfoIndex}
       ::= {srvInfoTable 1}



     -- ****************************************
     -- srvInfo TABLE
     -- ****************************************
     SrvInfoEntry ::= SEQUENCE {
       srvInfoIndex                                    Unsigned32,
       srvInfoRecordNum                                Unsigned32,
       srvInfoRowStatus                                RowStatus,
       srvInfoAction                                   INTEGER,
       srvInfoActionResult                             INTEGER,
       srvInfoInternalDomainName                       SnmpAdminString,
       srvInfoTransportType                            INTEGER,
       srvInfoDNSName                                  SnmpAdminString,
       srvInfoPriority                                 Unsigned32,
       srvInfoWeight                                   Unsigned32,
       srvInfoPort                                     Unsigned32,
       srvInfoDNSName2                                 SnmpAdminString,
       srvInfoPriority2                                Unsigned32,
       srvInfoWeight2                                  Unsigned32,
       srvInfoPort2                                    Unsigned32,
       srvInfoDNSName3                                 SnmpAdminString,
       srvInfoPriority3                                Unsigned32,
       srvInfoWeight3                                  Unsigned32,
       srvInfoPort3                                    Unsigned32
     }



     srvInfoIndex OBJECT-TYPE
       SYNTAX Unsigned32 (0..9)
       MAX-ACCESS not-accessible
       STATUS current
       DESCRIPTION
           "Entry number, starting at 0.
AC INI-Param: Srv2Ip_Index"
       ::= {srvInfoEntry 1}



     srvInfoRecordNum OBJECT-TYPE
       SYNTAX Unsigned32 (0..9)
       MAX-ACCESS not-accessible
       STATUS current
       DESCRIPTION
           "Equals to the entry number.
AC INI-Param: Srv2Ip_Index"
       ::= {srvInfoEntry 2}



     srvInfoRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {srvInfoEntry 3}



     srvInfoAction OBJECT-TYPE
       SYNTAX INTEGER {
                  developmentImpending(0)

                  }
       MAX-ACCESS read-only
       STATUS current
       DESCRIPTION
           "Development Impending.
AC INI-Param: N/A"
       ::= {srvInfoEntry 4}



     srvInfoActionResult OBJECT-TYPE
       SYNTAX INTEGER {
                  developmentImpending(0)

                  }
       MAX-ACCESS read-only
       STATUS current
       DESCRIPTION
           "Development Impending.
AC INI-Param: N/A"
       ::= {srvInfoEntry 5}



     srvInfoInternalDomainName OBJECT-TYPE
       SYNTAX SnmpAdminString (SIZE (0..70))
       MAX-ACCESS read-create
       STATUS current
       DESCRIPTION
           "the Domain name for the SRV query.
Access: Instant.
AC INI-Param: Srv2Ip_InternalDomain"
       ::= {srvInfoEntry 6}



     srvInfoTransportType OBJECT-TYPE
       SYNTAX INTEGER {
                  uDP(0)
,
                  tCP(1)
,
                  tLS(2)

                  }
       MAX-ACCESS read-create
       STATUS current
       DESCRIPTION
           "the transport type.
Access: Instant.
AC INI-Param: Srv2Ip_TransportType"
       ::= {srvInfoEntry 7}



     srvInfoDNSName OBJECT-TYPE
       SYNTAX SnmpAdminString (SIZE (0..99))
       MAX-ACCESS read-create
       STATUS current
       DESCRIPTION
           "the DNS in the SRV Query Result.
Access: Instant.
AC INI-Param: Srv2Ip_Dns1"
       ::= {srvInfoEntry 8}



     srvInfoPriority OBJECT-TYPE
       SYNTAX Unsigned32 (0..65000)
       MAX-ACCESS read-create
       STATUS current
       DESCRIPTION
           "the Priority of this SRV Query.
Access: Instant.
AC INI-Param: Srv2Ip_Priority1"
       ::= {srvInfoEntry 9}



     srvInfoWeight OBJECT-TYPE
       SYNTAX Unsigned32 (0..65000)
       MAX-ACCESS read-create
       STATUS current
       DESCRIPTION
           "the Weight of this SRV Query.
Access: Instant.
AC INI-Param: Srv2Ip_Weight1"
       ::= {srvInfoEntry 10}



     srvInfoPort OBJECT-TYPE
       SYNTAX Unsigned32 (0..65534)
       MAX-ACCESS read-create
       STATUS current
       DESCRIPTION
           "the port of the DNS.
Access: Instant.
AC INI-Param: Srv2Ip_Port1"
       ::= {srvInfoEntry 11}



     srvInfoDNSName2 OBJECT-TYPE
       SYNTAX SnmpAdminString (SIZE (0..99))
       MAX-ACCESS read-create
       STATUS current
       DESCRIPTION
           "the DNS in the SRV Query Result.
Access: Instant.
AC INI-Param: Srv2Ip_Dns2"
       ::= {srvInfoEntry 12}



     srvInfoPriority2 OBJECT-TYPE
       SYNTAX Unsigned32 (0..65000)
       MAX-ACCESS read-create
       STATUS current
       DESCRIPTION
           "the Priority of this SRV Query.
Access: Instant.
AC INI-Param: Srv2Ip_Priority2"
       ::= {srvInfoEntry 13}



     srvInfoWeight2 OBJECT-TYPE
       SYNTAX Unsigned32 (0..65000)
       MAX-ACCESS read-create
       STATUS current
       DESCRIPTION
           "the Weight of this SRV Query.
Access: Instant.
AC INI-Param: Srv2Ip_Weight2"
       ::= {srvInfoEntry 14}



     srvInfoPort2 OBJECT-TYPE
       SYNTAX Unsigned32 (0..65534)
       MAX-ACCESS read-create
       STATUS current
       DESCRIPTION
           "the port of the DNS.
Access: Instant.
AC INI-Param: Srv2Ip_Port2"
       ::= {srvInfoEntry 15}



     srvInfoDNSName3 OBJECT-TYPE
       SYNTAX SnmpAdminString (SIZE (0..99))
       MAX-ACCESS read-create
       STATUS current
       DESCRIPTION
           "the DNS in the SRV Query Result.
Access: Instant.
AC INI-Param: Srv2Ip_Dns3"
       ::= {srvInfoEntry 16}



     srvInfoPriority3 OBJECT-TYPE
       SYNTAX Unsigned32 (0..65000)
       MAX-ACCESS read-create
       STATUS current
       DESCRIPTION
           "the Priority of this SRV Query.
Access: Instant.
AC INI-Param: Srv2Ip_Priority3"
       ::= {srvInfoEntry 17}



     srvInfoWeight3 OBJECT-TYPE
       SYNTAX Unsigned32 (0..65000)
       MAX-ACCESS read-create
       STATUS current
       DESCRIPTION
           "the Weight of this SRV Query.
Access: Instant.
AC INI-Param: Srv2Ip_Weight3"
       ::= {srvInfoEntry 18}



     srvInfoPort3 OBJECT-TYPE
       SYNTAX Unsigned32 (0..65534)
       MAX-ACCESS read-create
       STATUS current
       DESCRIPTION
           "the port of the DNS.
Access: Instant.
AC INI-Param: Srv2Ip_Port3"
       ::= {srvInfoEntry 19}



     -- ****************************************
     -- forwardOnBusyTrunkDest table declaration
     -- ****************************************
     forwardOnBusyTrunkDestTable OBJECT-TYPE
       SYNTAX SEQUENCE OF ForwardOnBusyTrunkDestEntry
       MAX-ACCESS not-accessible
       STATUS current
       DESCRIPTION
           "GwApp Forward On Busy Trunk Destination Table"
       ::= {routing 5}



     -- ****************************************
     -- forwardOnBusyTrunkDest table entry
     -- ****************************************
     forwardOnBusyTrunkDestEntry OBJECT-TYPE
       SYNTAX ForwardOnBusyTrunkDestEntry
       MAX-ACCESS not-accessible
       STATUS current
       DESCRIPTION
           ""
       INDEX {forwardOnBusyTrunkDestIndex}
       ::= {forwardOnBusyTrunkDestTable 1}



     -- ****************************************
     -- forwardOnBusyTrunkDest TABLE
     -- ****************************************
     ForwardOnBusyTrunkDestEntry ::= SEQUENCE {
       forwardOnBusyTrunkDestIndex                     Unsigned32,
       forwardOnBusyTrunkDestRowStatus                 RowStatus,
       forwardOnBusyTrunkDestAction                    INTEGER,
       forwardOnBusyTrunkDestActionResult              INTEGER,
       forwardOnBusyTrunkDestTrunkGroupId              Unsigned32,
       forwardOnBusyTrunkDestForwardDestination        SnmpAdminString
     }



     forwardOnBusyTrunkDestIndex OBJECT-TYPE
       SYNTAX Unsigned32 (0..99)
       MAX-ACCESS not-accessible
       STATUS current
       DESCRIPTION
           "Entry number, starting at 0.
AC INI-Param: ForwardOnBusyTrunkDest_Index"
       ::= {forwardOnBusyTrunkDestEntry 1}



     forwardOnBusyTrunkDestRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {forwardOnBusyTrunkDestEntry 2}



     forwardOnBusyTrunkDestAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {forwardOnBusyTrunkDestEntry 3}



     forwardOnBusyTrunkDestActionResult OBJECT-TYPE
       SYNTAX INTEGER {
                  developmentImpending(0)

                  }
       MAX-ACCESS read-only
       STATUS current
       DESCRIPTION
           "Development Impending.
AC INI-Param: N/A"
       ::= {forwardOnBusyTrunkDestEntry 4}



     forwardOnBusyTrunkDestTrunkGroupId OBJECT-TYPE
       SYNTAX Unsigned32 (0..99)
       MAX-ACCESS read-create
       STATUS current
       DESCRIPTION
           "GwApp Forward On Busy Trunk Destination Table.
Access: Instant.
AC INI-Param: ForwardOnBusyTrunkDest_TrunkGroupId"
       ::= {forwardOnBusyTrunkDestEntry 5}



     forwardOnBusyTrunkDestForwardDestination OBJECT-TYPE
       SYNTAX SnmpAdminString (SIZE (0..98))
       MAX-ACCESS read-create
       STATUS current
       DESCRIPTION
           "GwApp Forward On Busy Trunk Destination Table.
Access: Instant.
AC INI-Param: ForwardOnBusyTrunkDest_ForwardDestination"
       ::= {forwardOnBusyTrunkDestEntry 6}



     routingEnableDigitDelivery2IP OBJECT-TYPE
       SYNTAX INTEGER {
                  disable(0)
,
                  enable(1)

                  }
       MAX-ACCESS read-write
       STATUS current
       DESCRIPTION
           "Enable automatic digit delivery to IP side after call is connected.
Access: Offline.
AC INI-Param: ENABLEDIGITDELIVERY2IP"
       ::= {routing 21}



     routingSourceIPAddressInput OBJECT-TYPE
       SYNTAX INTEGER {
                  notConfigured(-1)
,
                  sIPContactHeader(0)
,
                  layer3SourceIP(1)

                  }
       MAX-ACCESS read-write
       STATUS current
       DESCRIPTION
           "Decides the origin of the source ip address looked at when routing
using the IP --> Tel table.
0 - Contact
1 - Recieved packet source IP address.
Access: Instant.
AC INI-Param: SOURCEIPADDRESSINPUT"
       ::= {routing 22}



     altRouteCause OBJECT IDENTIFIER ::= {routing 10}


     -- ****************************************
     -- altRouteCauseIP2TEL table declaration
     -- ****************************************
     altRouteCauseIP2TELTable OBJECT-TYPE
       SYNTAX SEQUENCE OF AltRouteCauseIP2TELEntry
       MAX-ACCESS not-accessible
       STATUS current
       DESCRIPTION
           ""
       ::= {altRouteCause 21}



     -- ****************************************
     -- altRouteCauseIP2TEL table entry
     -- ****************************************
     altRouteCauseIP2TELEntry OBJECT-TYPE
       SYNTAX AltRouteCauseIP2TELEntry
       MAX-ACCESS not-accessible
       STATUS current
       DESCRIPTION
           ""
       INDEX {altRouteCauseIP2TELIndex}
       ::= {altRouteCauseIP2TELTable 1}



     -- ****************************************
     -- altRouteCauseIP2TEL TABLE
     -- ****************************************
     AltRouteCauseIP2TELEntry ::= SEQUENCE {
       altRouteCauseIP2TELIndex                        Unsigned32,
       altRouteCauseIP2TELRowStatus                    RowStatus,
       altRouteCauseIP2TELAction                       INTEGER,
       altRouteCauseIP2TELActionResult                 INTEGER,
       altRouteCauseIP2TELReleaseCause                 INTEGER
     }



     altRouteCauseIP2TELIndex OBJECT-TYPE
       SYNTAX Unsigned32 (0..4)
       MAX-ACCESS not-accessible
       STATUS current
       DESCRIPTION
           "Entry number, starting at 0.
AC INI-Param: AltRouteCauseIp2Tel_Index"
       ::= {altRouteCauseIP2TELEntry 1}



     altRouteCauseIP2TELRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {altRouteCauseIP2TELEntry 2}



     altRouteCauseIP2TELAction OBJECT-TYPE
       SYNTAX INTEGER {
                  developmentImpending(0)

                  }
       MAX-ACCESS read-only
       STATUS current
       DESCRIPTION
           "Development Impending.
AC INI-Param: N/A"
       ::= {altRouteCauseIP2TELEntry 3}



     altRouteCauseIP2TELActionResult OBJECT-TYPE
       SYNTAX INTEGER {
                  developmentImpending(0)

                  }
       MAX-ACCESS read-only
       STATUS current
       DESCRIPTION
           "Development Impending.
AC INI-Param: N/A"
       ::= {altRouteCauseIP2TELEntry 4}



     altRouteCauseIP2TELReleaseCause OBJECT-TYPE
       SYNTAX INTEGER {
                  unassignedNumber(1)
,
                  noRouteToTransitNet(2)
,
                  noRouteToDestination(3)
,
                  channelUnacceptable(6)
,
                  callAwarded(7)
,
                  preemption(8)
,
                  normalClear(16)
,
                  userBusy(17)
,
                  noUserResponding(18)
,
                  noAnswer(19)
,
                  subscriberAbsent(20)
,
                  callRejected(21)
,
                  numberChanged(22)
,
                  nonselectedUserClearing(26)
,
                  destinationOutOfOrder(27)
,
                  invalidNumberFormat(28)
,
                  facilityRejected(29)
,
                  responseToStatusEnquiry(30)
,
                  normalUnspecified(31)
,
                  circuitCongestion(32)
,
                  userCongestion(33)
,
                  noCircuitAvailable(34)
,
                  networkOutOfOrder(38)
,
                  permanentFrameModeConnectionOoS(39)
,
                  permanentFrameModeConnectionOper(40)
,
                  temporaryFailure(41)
,
                  switchingEquipmentCongestion(42)
,
                  accessInformationDiscarded(43)
,
                  requestedCircuitNA(44)
,
                  precedenceCallBlocked(46)
,
                  resourceUnavailableUnspecified(47)
,
                  qoSNA(49)
,
                  requestedFacilityNotSubscribed(50)
,
                  outgoingCallsBarredWithinCUG(53)
,
                  incomingCallsBarredWithinCUG(55)
,
                  bCNotAuthorized(57)
,
                  bCNA(58)
,
                  inconsistencyInOutgoingIE(62)
,
                  serviceOrOptionNA(63)
,
                  bCNotImplemented(65)
,
                  channelTypeNotImplemented(66)
,
                  requestedFacilityNotImplemented(69)
,
                  onlyRestrictedInfoBC(70)
,
                  serviceNotImplementedUnspecified(79)
,
                  invalidCRValue(81)
,
                  identifiedChannelNotExist(82)
,
                  suspendedCallButCallIDNotExist(83)
,
                  callIdentityinUse(84)
,
                  noCallSuspended(85)
,
                  callHavingCallIDCleared(86)
,
                  userNotMemberofCUG(87)
,
                  incompatibleDestination(88)
,
                  nonExistentCUG(90)
,
                  invalidTransitNetworkSelection(91)
,
                  invalidMessageUnspecified(95)
,
                  mandatoryIEisMissing(96)
,
                  messageTypeNotImplemented(97)
,
                  messageStateInconsistency(98)
,
                  iENotImplemented(99)
,
                  invalidIEContents(100)
,
                  messageNotCompatible(101)
,
                  recoveryonTimerExpiry(102)
,
                  protocolErrorUnspecified(111)
,
                  unknownError(112)
,
                  interworkingUnspecified(127)

                  }
       MAX-ACCESS read-create
       STATUS current
       DESCRIPTION
           "Release Cause.
Access: Instant.
AC INI-Param: AltRouteCauseIp2Tel_ReleaseCause"
       ::= {altRouteCauseIP2TELEntry 5}



     -- ****************************************
     -- altRouteCauseTEL2IP table declaration
     -- ****************************************
     altRouteCauseTEL2IPTable OBJECT-TYPE
       SYNTAX SEQUENCE OF AltRouteCauseTEL2IPEntry
       MAX-ACCESS not-accessible
       STATUS current
       DESCRIPTION
           ""
       ::= {altRouteCause 22}



     -- ****************************************
     -- altRouteCauseTEL2IP table entry
     -- ****************************************
     altRouteCauseTEL2IPEntry OBJECT-TYPE
       SYNTAX AltRouteCauseTEL2IPEntry
       MAX-ACCESS not-accessible
       STATUS current
       DESCRIPTION
           ""
       INDEX {altRouteCauseTEL2IPIndex}
       ::= {altRouteCauseTEL2IPTable 1}



     -- ****************************************
     -- altRouteCauseTEL2IP TABLE
     -- ****************************************
     AltRouteCauseTEL2IPEntry ::= SEQUENCE {
       altRouteCauseTEL2IPIndex                        Unsigned32,
       altRouteCauseTEL2IPRowStatus                    RowStatus,
       altRouteCauseTEL2IPAction                       INTEGER,
       altRouteCauseTEL2IPActionResult                 INTEGER,
       altRouteCauseTEL2IPReleaseCause                 INTEGER
     }



     altRouteCauseTEL2IPIndex OBJECT-TYPE
       SYNTAX Unsigned32 (0..4)
       MAX-ACCESS not-accessible
       STATUS current
       DESCRIPTION
           "Entry number, starting at 0.
AC INI-Param: AltRouteCauseTel2Ip_Index"
       ::= {altRouteCauseTEL2IPEntry 1}



     altRouteCauseTEL2IPRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {altRouteCauseTEL2IPEntry 2}



     altRouteCauseTEL2IPAction OBJECT-TYPE
       SYNTAX INTEGER {
                  developmentImpending(0)

                  }
       MAX-ACCESS read-only
       STATUS current
       DESCRIPTION
           "Development Impending.
AC INI-Param: N/A"
       ::= {altRouteCauseTEL2IPEntry 3}



     altRouteCauseTEL2IPActionResult OBJECT-TYPE
       SYNTAX INTEGER {
                  developmentImpending(0)

                  }
       MAX-ACCESS read-only
       STATUS current
       DESCRIPTION
           "Development Impending.
AC INI-Param: N/A"
       ::= {altRouteCauseTEL2IPEntry 4}



     altRouteCauseTEL2IPReleaseCause OBJECT-TYPE
       SYNTAX INTEGER {
                  wildCard4xx(4)
,
                  wildCardFivexx(5)
,
                  wildCardSixxx(6)
,
                  badRequest(400)
,
                  unauthorized(401)
,
                  paymentRequired(402)
,
                  forbidden(403)
,
                  notFound(404)
,
                  methodNotAllowed(405)
,
                  requestNotAcceptable(406)
,
                  authenticationRequired(407)
,
                  requestTimeout(408)
,
                  conflict(409)
,
                  gone(410)
,
                  requestTooLarge(413)
,
                  requestURITooLong(414)
,
                  unsupportedMedia(415)
,
                  badExtension(420)
,
                  extensionRequired(421)
,
                  sessionIntervalTooSmall(423)
,
                  unavailable(480)
,
                  transactionDoesNotExist(481)
,
                  loopDetected(482)
,
                  tooManyHops(483)
,
                  addressIncomplete(484)
,
                  ambiguous(485)
,
                  busy(486)
,
                  requestTerminated(487)
,
                  notAcceptableHere(488)
,
                  requestPending(491)
,
                  undecipherable(493)
,
                  internalError(500)
,
                  notImplemented(501)
,
                  badGateway(502)
,
                  serviceUnavailable(503)
,
                  serverTimeout(504)
,
                  versionNotSupported(505)
,
                  messageTooLarge(513)
,
                  busyEverywhere(600)
,
                  decline(603)
,
                  doesNotExistAnywhere(604)
,
                  sDPNotAcceptable(606)
,
                  iPProfileCallLimit(805)
,
                  mediaLimitsExceeded(806)

                  }
       MAX-ACCESS read-create
       STATUS current
       DESCRIPTION
           "Release Cause.
Access: Instant.
AC INI-Param: AltRouteCauseTel2Ip_ReleaseCause"
       ::= {altRouteCauseTEL2IPEntry 5}



     manipulation OBJECT IDENTIFIER ::= {manipulationAndRouting 21}


     manipulationRemovePrefix OBJECT-TYPE
       SYNTAX INTEGER {
                  no(0)
,
                  yes(1)

                  }
       MAX-ACCESS read-write
       STATUS current
       DESCRIPTION
           "Remove prefix defined in IP to Trunk Group table (IP to Tel
calls).
Access: Instant.
AC INI-Param: REMOVEPREFIX"
       ::= {manipulation 1}



     manipulationAddTrunkGroupAsPrefix OBJECT-TYPE
       SYNTAX INTEGER {
                  no(0)
,
                  yes(1)

                  }
       MAX-ACCESS read-write
       STATUS current
       DESCRIPTION
           "Add Trunk Group ID on which the call was received as the called
number prefix.
Access: Instant.
AC INI-Param: ADDTRUNKGROUPASPREFIX"
       ::= {manipulation 2}



     manipulationAddPortAsPrefix OBJECT-TYPE
       SYNTAX INTEGER {
                  no(0)
,
                  yes(1)

                  }
       MAX-ACCESS read-write
       STATUS current
       DESCRIPTION
           "Add port number (Analog gateway) / Trunk ID (Digital gateway)
as called number prefix.
Access: Instant.
AC INI-Param: ADDPORTASPREFIX"
       ::= {manipulation 3}



     manipulationReplaceEmptyDstWithPortNumber OBJECT-TYPE
       SYNTAX INTEGER {
                  disable(0)
,
                  enable(1)

                  }
       MAX-ACCESS read-write
       STATUS current
       DESCRIPTION
           "Replace empty destination number (received from Tel side) with
port number.
Access: Instant.
AC INI-Param: REPLACEEMPTYDSTWITHPORTNUMBER"
       ::= {manipulation 4}



     manipulationCIDNotification OBJECT-TYPE
       SYNTAX INTEGER {
                  disable(0)
,
                  enable(1)

                  }
       MAX-ACCESS read-write
       STATUS current
       DESCRIPTION
           "If NO PRESENTATION arrived from PSTN and this parameter enabled,than
the presentation will be allowed. If this parameter
disabled, the, presentation will be restricted.
Access: Instant.
AC INI-Param: CIDNOTIFICATION"
       ::= {manipulation 5}



     manipulationUseSourceNumberAsDisplayName OBJECT-TYPE
       SYNTAX INTEGER {
                  disable (0)
,
                  enable (1)
,
                  overwrite(2)
,
                  original(3)

                  }
       MAX-ACCESS read-write
       STATUS current
       DESCRIPTION
           "if set to 1 Use source number as display name if empty.
if set to 2 always use source number as display name .
if set to 3 use the source number before manipulation, if empty.
Access: Instant.
AC INI-Param: USESOURCENUMBERASDISPLAYNAME"
       ::= {manipulation 6}



     manipulationAddNPIandTON2CalledNumber OBJECT-TYPE
       SYNTAX INTEGER {
                  disable(0)
,
                  enable(1)

                  }
       MAX-ACCESS read-write
       STATUS current
       DESCRIPTION
           "Add NPI and TON as prefix to called number.
Access: Instant.
AC INI-Param: ADDNPIANDTON2CALLEDNUMBER"
       ::= {manipulation 7}



     manipulationAddNPIandTON2CallingNumber OBJECT-TYPE
       SYNTAX INTEGER {
                  disable(0)
,
                  enable(1)

                  }
       MAX-ACCESS read-write
       STATUS current
       DESCRIPTION
           "Add NPI and TON as prefix to calling number.
Access: Instant.
AC INI-Param: ADDNPIANDTON2CALLINGNUMBER"
       ::= {manipulation 8}



     manipulationUseDisplayNameAsSourceNumber OBJECT-TYPE
       SYNTAX INTEGER {
                  disable(0)
,
                  enable(1)

                  }
       MAX-ACCESS read-write
       STATUS current
       DESCRIPTION
           "when set to 1 then If display name exists, use it as source
number. If not, set presentation as restricted.
Access: Instant.
AC INI-Param: USEDISPLAYNAMEASSOURCENUMBER"
       ::= {manipulation 9}



     manipulationAddPrefixToRedirectNumber OBJECT-TYPE
       SYNTAX SnmpAdminString (SIZE (0..7))
       MAX-ACCESS read-write
       STATUS current
       DESCRIPTION
           "Prefix which added to redirect phone number.
Access: Instant.
AC INI-Param: PREFIX2REDIRECTNUMBER"
       ::= {manipulation 10}



     manipulationAddPhoneContextAsPrefix OBJECT-TYPE
       SYNTAX INTEGER {
                  no(0)
,
                  yes(1)

                  }
       MAX-ACCESS read-write
       STATUS current
       DESCRIPTION
           "add the phone context to src/dest phone number as prefix.
Access: Instant.
AC INI-Param: ADDPHONECONTEXTASPREFIX"
       ::= {manipulation 11}



     manipulationBlindTransferAddPrefix OBJECT-TYPE
       SYNTAX INTEGER {
                  disable(0)
,
                  enable(1)

                  }
       MAX-ACCESS read-write
       STATUS current
       DESCRIPTION
           "Add keying sequence for performing blind transfer as transfer
number prefix.
Access: Instant.
AC INI-Param: KEYBLINDTRANSFERADDPREFIX"
       ::= {manipulation 12}



     manipulationSourceMode OBJECT-TYPE
       SYNTAX INTEGER {
                  fromAndPai(0)
,
                  fromOnly(1)

                  }
       MAX-ACCESS read-write
       STATUS current
       DESCRIPTION
           "Describes the headers containing source number after manipulation:
(0) both FROM and P-Asserted contain src number after manipulations
(1) only FROM contains src number after manipulation.
Access: Instant.
AC INI-Param: SOURCEMANIPULATIONMODE"
       ::= {manipulation 13}



     manipulationAddTrunkGroupAsPrefixToSource OBJECT-TYPE
       SYNTAX INTEGER {
                  no(0)
,
                  yes(1)

                  }
       MAX-ACCESS read-write
       STATUS current
       DESCRIPTION
           "Add Trunk Group ID on which the call was received as the calling
number prefix.
Access: Instant.
AC INI-Param: ADDTRUNKGROUPASPREFIXTOSOURCE"
       ::= {manipulation 14}



     manipulationSetTel2IpRedirectReason OBJECT-TYPE
       SYNTAX INTEGER {
                  notConfigured(-1)
,
                  unknown(0)
,
                  busy(1)
,
                  noReply(2)
,
                  networkBusy(3)
,
                  deflection(4)
,
                  dTEOutOfOrder(9)
,
                  forwardingDTE(10)
,
                  transfer(13)
,
                  pickUp(14)
,
                  systematicOrUnconditional(15)

                  }
       MAX-ACCESS read-write
       STATUS current
       DESCRIPTION
           "If redirect (diversion) data is received from the PSTN interface,
the redirect reason is set to the value of this parameter,
before transferring it to the IP. 
default value is -1 --> not change the received value.
.
Access: Instant.
AC INI-Param: SetTel2IpRedirectReason"
       ::= {manipulation 15}



     manipulationSetIp2TelRedirectReason OBJECT-TYPE
       SYNTAX INTEGER {
                  notConfigured(-1)
,
                  unknown(0)
,
                  busy(1)
,
                  noReply(2)
,
                  networkBusy(3)
,
                  deflection(4)
,
                  dTEOutOfOrder(9)
,
                  forwardingDTE(10)
,
                  transfer(13)
,
                  pickUp(14)
,
                  systematicOrUnconditional(15)

                  }
       MAX-ACCESS read-write
       STATUS current
       DESCRIPTION
           "If redirect (diversion) data is received from the IP side, the
redirect reason is set to the value of this parameter, before
transferring it to the PSTN interface. 
default value is -1 --> not change the received value.
.
Access: Instant.
AC INI-Param: SetIp2TelRedirectReason"
       ::= {manipulation 16}



     manipulationSetIp2TelRedirectScreeningIndicator OBJECT-TYPE
       SYNTAX INTEGER {
                  notConfigured(-1)
,
                  userProvided(0)
,
                  userPassed(1)
,
                  userFailed(2)
,
                  networkProvided(3)

                  }
       MAX-ACCESS read-write
       STATUS current
       DESCRIPTION
           "Override screening indicator value of the redirect number in
Setup messages to PSTN interface.
Access: Instant.
AC INI-Param: SetIp2TelRedirectScreeningInd"
       ::= {manipulation 17}



     manipulationTel2IPDefaultRedirectReason OBJECT-TYPE
       SYNTAX INTEGER {
                  notConfigured(-1)
,
                  busy(1)
,
                  noReply(2)
,
                  deflection(4)
,
                  dteOutOfOrder(9)
,
                  systematicUnconditional(15)

                  }
       MAX-ACCESS read-write
       STATUS current
       DESCRIPTION
           "Tel2IP Default Redirect Reason when PSTN Redirect Reason is
missing or unknown. 
default value is -1 - no change in the received value.
.
Access: Instant.
AC INI-Param: TEL2IPDEFAULTREDIRECTREASON"
       ::= {manipulation 18}



     manipulationAddNPIandTON2RedirectNumber OBJECT-TYPE
       SYNTAX INTEGER {
                  no(0)
,
                  yes(1)

                  }
       MAX-ACCESS read-write
       STATUS current
       DESCRIPTION
           "Add NPI and TON as prefix to redirect number.
Access: Instant.
AC INI-Param: ADDNPIANDTON2REDIRECTNUMBER"
       ::= {manipulation 19}



     -- ****************************************
     -- dstIP2TEL table declaration
     -- ****************************************
     dstIP2TELTable OBJECT-TYPE
       SYNTAX SEQUENCE OF DstIP2TELEntry
       MAX-ACCESS not-accessible
       STATUS current
       DESCRIPTION
           ""
       ::= {manipulation 21}



     -- ****************************************
     -- dstIP2TEL table entry
     -- ****************************************
     dstIP2TELEntry OBJECT-TYPE
       SYNTAX DstIP2TELEntry
       MAX-ACCESS not-accessible
       STATUS current
       DESCRIPTION
           ""
       INDEX {dstIP2TELIndex}
       ::= {dstIP2TELTable 1}



     -- ****************************************
     -- dstIP2TEL TABLE
     -- ****************************************
     DstIP2TELEntry ::= SEQUENCE {
       dstIP2TELIndex                                  Unsigned32,
       dstIP2TELRowStatus                              RowStatus,
       dstIP2TELAction                                 INTEGER,
       dstIP2TELActionResult                           INTEGER,
       dstIP2TELPrefix                                 SnmpAdminString,
       dstIP2TELNumOfStrippedDigits                    Unsigned32,
       dstIP2TELPrefixToAdd                            SnmpAdminString,
       dstIP2TELNumOfDigitsToLeave                     Unsigned32,
       dstIP2TELNumberPlan                             INTEGER,
       dstIP2TELNumberType                             INTEGER,
       dstIP2TELSourcePrefix                           SnmpAdminString,
       dstIP2TELSourceIP                               SnmpAdminString,
       dstIP2TELNumOfDigitsToRemFromRight              Unsigned32,
       dstIP2TELSuffix2Add                             SnmpAdminString,
       dstIP2TELIsPresentationRestricted               Unsigned32,
       dstIP2TELSrcHost                                SnmpAdminString,
       dstIP2TELDstHost                                SnmpAdminString,
       dstIP2TELManipulationName                       SnmpAdminString
     }



     dstIP2TELIndex OBJECT-TYPE
       SYNTAX Unsigned32 (0..99)
       MAX-ACCESS not-accessible
       STATUS current
       DESCRIPTION
           "Destination number, starting at 0.
AC INI-Param: NumberMapIp2Tel_Index"
       ::= {dstIP2TELEntry 1}



     dstIP2TELRowStatus OBJECT-TYPE
       SYNTAX RowStatus
       MAX-ACCESS read-create
       STATUS current
       DESCRIPTION
           "Row-Status Textual Conventions as defined in RFC 2579: Textual
Conventions for SMIv2.
AC INI-Param: N/A"
       ::= {dstIP2TELEntry 2}



     dstIP2TELAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {dstIP2TELEntry 3}



     dstIP2TELActionResult OBJECT-TYPE
       SYNTAX INTEGER {
                  developmentImpending(0)

                  }
       MAX-ACCESS read-only
       STATUS current
       DESCRIPTION
           "Development Impending.
AC INI-Param: N/A"
       ::= {dstIP2TELEntry 4}



     dstIP2TELPrefix OBJECT-TYPE
       SYNTAX SnmpAdminString (SIZE (0..100))
       MAX-ACCESS read-create
       STATUS current
       DESCRIPTION
           "
Access: Instant.
AC INI-Param: NumberMapIp2Tel_DestinationPrefix"
       ::= {dstIP2TELEntry 5}



     dstIP2TELNumOfStrippedDigits OBJECT-TYPE
       SYNTAX Unsigned32 (0..211)
       MAX-ACCESS read-create
       STATUS current
       DESCRIPTION
           "Num of stripped digits, Remove from left.
Access: Instant.
AC INI-Param: NumberMapIp2Tel_RemoveFromLeft"
       ::= {dstIP2TELEntry 6}



     dstIP2TELPrefixToAdd OBJECT-TYPE
       SYNTAX SnmpAdminString (SIZE (0..49))
       MAX-ACCESS read-create
       STATUS current
       DESCRIPTION
           "Prefix to Add.
Access: Instant.
AC INI-Param: NumberMapIp2Tel_Prefix2Add"
       ::= {dstIP2TELEntry 7}



     dstIP2TELNumOfDigitsToLeave OBJECT-TYPE
       SYNTAX Unsigned32 (0..255)
       MAX-ACCESS read-create
       STATUS current
       DESCRIPTION
           "Number of digits to leave.
Access: Instant.
AC INI-Param: NumberMapIp2Tel_LeaveFromRight"
       ::= {dstIP2TELEntry 8}



     dstIP2TELNumberPlan OBJECT-TYPE
       SYNTAX INTEGER {
                  unknown(0)
,
                  e164Public(1)
,
                  private(9)
,
                  notConfigured(255)

                  }
       MAX-ACCESS read-create
       STATUS current
       DESCRIPTION
           "Number Plan.
Access: Instant.
AC INI-Param: NumberMapIp2Tel_NumberPlan"
       ::= {dstIP2TELEntry 9}



     dstIP2TELNumberType OBJECT-TYPE
       SYNTAX INTEGER {
                  unknown(0)
,
                  international-Level2Regional(1)
,
                  national-Level1Regional(2)
,
                  networkSpecific-NetworkPISN(3)
,
                  subscriber-Level0Regional(4)
,
                  abbreviated(6)
,
                  notConfigured(255)

                  }
       MAX-ACCESS read-create
       STATUS current
       DESCRIPTION
           "Number Type.
Access: Instant.
AC INI-Param: NumberMapIp2Tel_NumberType"
       ::= {dstIP2TELEntry 10}



     dstIP2TELSourcePrefix OBJECT-TYPE
       SYNTAX SnmpAdminString (SIZE (0..100))
       MAX-ACCESS read-create
       STATUS current
       DESCRIPTION
           "Source Prefix.
Access: Instant.
AC INI-Param: NumberMapIp2Tel_SourcePrefix"
       ::= {dstIP2TELEntry 11}



     dstIP2TELSourceIP OBJECT-TYPE
       SYNTAX SnmpAdminString (SIZE (0..16))
       MAX-ACCESS read-create
       STATUS current
       DESCRIPTION
           "Source IP.
Access: Instant.
AC INI-Param: NumberMapIp2Tel_SourceAddress"
       ::= {dstIP2TELEntry 12}



     dstIP2TELNumOfDigitsToRemFromRight OBJECT-TYPE
       SYNTAX Unsigned32 (0..211)
       MAX-ACCESS read-create
       STATUS current
       DESCRIPTION
           "Num Of digits To Remove from Right.
Access: Instant.
AC INI-Param: NumberMapIp2Tel_RemoveFromRight"
       ::= {dstIP2TELEntry 13}



     dstIP2TELSuffix2Add OBJECT-TYPE
       SYNTAX SnmpAdminString (SIZE (0..49))
       MAX-ACCESS read-create
       STATUS current
       DESCRIPTION
           "Suffix To Add.
Access: Instant.
AC INI-Param: NumberMapIp2Tel_Suffix2Add"
       ::= {dstIP2TELEntry 14}



     dstIP2TELIsPresentationRestricted OBJECT-TYPE
       SYNTAX Unsigned32 (0..255)
       MAX-ACCESS read-create
       STATUS current
       DESCRIPTION
           "Is Presentation Restricted.
Access: Instant.
AC INI-Param: NumberMapIp2Tel_IsPresentationRestricted"
       ::= {dstIP2TELEntry 15}



     dstIP2TELSrcHost OBJECT-TYPE
       SYNTAX SnmpAdminString (SIZE (0..50))
       MAX-ACCESS read-create
       STATUS current
       DESCRIPTION
           "Source Host Prefix.
Access: Instant.
AC INI-Param: NumberMapIp2Tel_SrcHost"
       ::= {dstIP2TELEntry 16}



     dstIP2TELDstHost OBJECT-TYPE
       SYNTAX SnmpAdminString (SIZE (0..50))
       MAX-ACCESS read-create
       STATUS current
       DESCRIPTION
           "Destination Host Prefix.
Access: Instant.
AC INI-Param: NumberMapIp2Tel_DestHost"
       ::= {dstIP2TELEntry 17}



     dstIP2TELManipulationName OBJECT-TYPE
       SYNTAX SnmpAdminString (SIZE (0..20))
       MAX-ACCESS read-create
       STATUS current
       DESCRIPTION
           "Manipulation Name.
Access: Instant.
AC INI-Param: NumberMapIp2Tel_ManipulationName"
       ::= {dstIP2TELEntry 18}



     -- ****************************************
     -- dstTEL2IP table declaration
     -- ****************************************
     dstTEL2IPTable OBJECT-TYPE
       SYNTAX SEQUENCE OF DstTEL2IPEntry
       MAX-ACCESS not-accessible
       STATUS current
       DESCRIPTION
           ""
       ::= {manipulation 22}



     -- ****************************************
     -- dstTEL2IP table entry
     -- ****************************************
     dstTEL2IPEntry OBJECT-TYPE
       SYNTAX DstTEL2IPEntry
       MAX-ACCESS not-accessible
       STATUS current
       DESCRIPTION
           ""
       INDEX {dstTEL2IPIndex}
       ::= {dstTEL2IPTable 1}



     -- ****************************************
     -- dstTEL2IP TABLE
     -- ****************************************
     DstTEL2IPEntry ::= SEQUENCE {
       dstTEL2IPIndex                                  Unsigned32,
       dstTEL2IPRowStatus                              RowStatus,
       dstTEL2IPAction                                 INTEGER,
       dstTEL2IPActionResult                           INTEGER,
       dstTEL2IPPrefix                                 SnmpAdminString,
       dstTEL2IPNumOfStrippedDigits                    Unsigned32,
       dstTEL2IPPrefixToAdd                            SnmpAdminString,
       dstTEL2IPNumOfDigitsToLeave                     Unsigned32,
       dstTEL2IPNumberPlan                             INTEGER,
       dstTEL2IPNumberType                             INTEGER,
       dstTEL2IPSourcePrefix                           SnmpAdminString,
       dstTEL2IPNumOfDigitsToRemFromRight              Unsigned32,
       dstTEL2IPSuffix2Add                             SnmpAdminString,
       dstTEL2IPIsPresentationRestricted               Unsigned32,
       dstTEL2IPSourceIPAddress                        SnmpAdminString,
       dstTEL2IPSourceTrunkGroupID                     Integer32,
       dstTEL2IPSourceIPGroupID                        Integer32,
       dstTEL2IPDstIpGrpId                             Integer32,
       dstTEL2IPManipulationName                       SnmpAdminString
     }



     dstTEL2IPIndex OBJECT-TYPE
       SYNTAX Unsigned32 (0..119)
       MAX-ACCESS not-accessible
       STATUS current
       DESCRIPTION
           "Destination number, starting at 0.
AC INI-Param: NumberMapTel2Ip_Index"
       ::= {dstTEL2IPEntry 1}



     dstTEL2IPRowStatus OBJECT-TYPE
       SYNTAX RowStatus
       MAX-ACCESS read-create
       STATUS current
       DESCRIPTION
           "Row-Status Textual Conventions as defined in RFC 2579: Textual
Conventions for SMIv2.
AC INI-Param: N/A"
       ::= {dstTEL2IPEntry 2}



     dstTEL2IPAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {dstTEL2IPEntry 3}



     dstTEL2IPActionResult OBJECT-TYPE
       SYNTAX INTEGER {
                  developmentImpending(0)

                  }
       MAX-ACCESS read-only
       STATUS current
       DESCRIPTION
           "Development Impending.
AC INI-Param: N/A"
       ::= {dstTEL2IPEntry 4}



     dstTEL2IPPrefix OBJECT-TYPE
       SYNTAX SnmpAdminString (SIZE (0..100))
       MAX-ACCESS read-create
       STATUS current
       DESCRIPTION
           "
Access: Instant.
AC INI-Param: NumberMapTel2Ip_DestinationPrefix"
       ::= {dstTEL2IPEntry 5}



     dstTEL2IPNumOfStrippedDigits OBJECT-TYPE
       SYNTAX Unsigned32 (0..211)
       MAX-ACCESS read-create
       STATUS current
       DESCRIPTION
           "Num of stripped digits.
Access: Instant.
AC INI-Param: NumberMapTel2Ip_RemoveFromLeft"
       ::= {dstTEL2IPEntry 6}



     dstTEL2IPPrefixToAdd OBJECT-TYPE
       SYNTAX SnmpAdminString (SIZE (0..49))
       MAX-ACCESS read-create
       STATUS current
       DESCRIPTION
           "Prefix to Add.
Access: Instant.
AC INI-Param: NumberMapTel2Ip_Prefix2Add"
       ::= {dstTEL2IPEntry 7}



     dstTEL2IPNumOfDigitsToLeave OBJECT-TYPE
       SYNTAX Unsigned32 (0..255)
       MAX-ACCESS read-create
       STATUS current
       DESCRIPTION
           "Number of digits to leave.
Access: Instant.
AC INI-Param: NumberMapTel2Ip_LeaveFromRight"
       ::= {dstTEL2IPEntry 8}



     dstTEL2IPNumberPlan OBJECT-TYPE
       SYNTAX INTEGER {
                  unknown(0)
,
                  e164Public(1)
,
                  private(9)
,
                  notConfigured(255)

                  }
       MAX-ACCESS read-create
       STATUS current
       DESCRIPTION
           "Number Plan.
Access: Instant.
AC INI-Param: NumberMapTel2Ip_NumberPlan"
       ::= {dstTEL2IPEntry 9}



     dstTEL2IPNumberType OBJECT-TYPE
       SYNTAX INTEGER {
                  unknown(0)
,
                  international-Level2Regional(1)
,
                  national-Level1Regional(2)
,
                  networkSpecific-NetworkPISN(3)
,
                  subscriber-Level0Regional(4)
,
                  abbreviated(6)
,
                  notConfigured(255)

                  }
       MAX-ACCESS read-create
       STATUS current
       DESCRIPTION
           "Number Type.
Access: Instant.
AC INI-Param: NumberMapTel2Ip_NumberType"
       ::= {dstTEL2IPEntry 10}



     dstTEL2IPSourcePrefix OBJECT-TYPE
       SYNTAX SnmpAdminString (SIZE (0..100))
       MAX-ACCESS read-create
       STATUS current
       DESCRIPTION
           "
Access: Instant.
AC INI-Param: NumberMapTel2Ip_SourcePrefix"
       ::= {dstTEL2IPEntry 11}



     dstTEL2IPNumOfDigitsToRemFromRight OBJECT-TYPE
       SYNTAX Unsigned32 (0..211)
       MAX-ACCESS read-create
       STATUS current
       DESCRIPTION
           "Num Of digits To Remove from Right.
Access: Instant.
AC INI-Param: NumberMapTel2Ip_RemoveFromRight"
       ::= {dstTEL2IPEntry 12}



     dstTEL2IPSuffix2Add OBJECT-TYPE
       SYNTAX SnmpAdminString (SIZE (0..49))
       MAX-ACCESS read-create
       STATUS current
       DESCRIPTION
           "Suffix To Add.
Access: Instant.
AC INI-Param: NumberMapTel2Ip_Suffix2Add"
       ::= {dstTEL2IPEntry 13}



     dstTEL2IPIsPresentationRestricted OBJECT-TYPE
       SYNTAX Unsigned32 (0..255)
       MAX-ACCESS read-create
       STATUS current
       DESCRIPTION
           "Is Presentation Restricted.
Access: Instant.
AC INI-Param: NumberMapTel2Ip_IsPresentationRestricted"
       ::= {dstTEL2IPEntry 14}



     dstTEL2IPSourceIPAddress OBJECT-TYPE
       SYNTAX SnmpAdminString (SIZE (0..15))
       MAX-ACCESS read-create
       STATUS current
       DESCRIPTION
           "Source Address.
Access: Instant.
AC INI-Param: NumberMapTel2Ip_SourceAddress"
       ::= {dstTEL2IPEntry 15}



     dstTEL2IPSourceTrunkGroupID OBJECT-TYPE
       SYNTAX Integer32 (-1..99)
       MAX-ACCESS read-create
       STATUS current
       DESCRIPTION
           "GwApp Tel-to-IP Destination Phone Number Manipulation Rules
Table.
Access: Instant.
AC INI-Param: NumberMapTel2Ip_SrcTrunkGroupID"
       ::= {dstTEL2IPEntry 16}



     dstTEL2IPSourceIPGroupID OBJECT-TYPE
       SYNTAX Integer32 (-1..31)
       MAX-ACCESS read-create
       STATUS current
       DESCRIPTION
           "GwApp Tel-to-IP Destination Phone Number Manipulation Rules
Table.
Access: Instant.
AC INI-Param: NumberMapTel2Ip_SrcIPGroupID"
       ::= {dstTEL2IPEntry 17}



     dstTEL2IPDstIpGrpId OBJECT-TYPE
       SYNTAX Integer32 (-1..31)
       MAX-ACCESS read-create
       STATUS current
       DESCRIPTION
           "Dst Ip Group Id.
Access: Instant.
AC INI-Param: NumberMapTel2Ip_DestIPGroupID"
       ::= {dstTEL2IPEntry 18}



     dstTEL2IPManipulationName OBJECT-TYPE
       SYNTAX SnmpAdminString (SIZE (0..20))
       MAX-ACCESS read-create
       STATUS current
       DESCRIPTION
           "Manipulation Name.
Access: Instant.
AC INI-Param: NumberMapTel2Ip_ManipulationName"
       ::= {dstTEL2IPEntry 19}



     -- ****************************************
     -- srcIP2TEL table declaration
     -- ****************************************
     srcIP2TELTable OBJECT-TYPE
       SYNTAX SEQUENCE OF SrcIP2TELEntry
       MAX-ACCESS not-accessible
       STATUS current
       DESCRIPTION
           ""
       ::= {manipulation 23}



     -- ****************************************
     -- srcIP2TEL table entry
     -- ****************************************
     srcIP2TELEntry OBJECT-TYPE
       SYNTAX SrcIP2TELEntry
       MAX-ACCESS not-accessible
       STATUS current
       DESCRIPTION
           ""
       INDEX {srcIP2TELIndex}
       ::= {srcIP2TELTable 1}



     -- ****************************************
     -- srcIP2TEL TABLE
     -- ****************************************
     SrcIP2TELEntry ::= SEQUENCE {
       srcIP2TELIndex                                  Unsigned32,
       srcIP2TELRowStatus                              RowStatus,
       srcIP2TELAction                                 INTEGER,
       srcIP2TELActionResult                           INTEGER,
       srcIP2TELPrefix                                 SnmpAdminString,
       srcIP2TELNumOfStrippedDigits                    Unsigned32,
       srcIP2TELPrefixToAdd                            SnmpAdminString,
       srcIP2TELNumOfDigitsToLeave                     Unsigned32,
       srcIP2TELNumberPlan                             INTEGER,
       srcIP2TELNumberType                             INTEGER,
       srcIP2TELDestPrefix                             SnmpAdminString,
       srcIP2TELPresentation                           INTEGER,
       srcIP2TELNumOfDigitsToRemFromRight              Unsigned32,
       srcIP2TELSuffix2Add                             SnmpAdminString,
       srcIP2TELSourceIPAddress                        SnmpAdminString,
       srcIP2TELSrcHost                                SnmpAdminString,
       srcIP2TELDstHost                                SnmpAdminString,
       srcIP2TELManipulationName                       SnmpAdminString
     }



     srcIP2TELIndex OBJECT-TYPE
       SYNTAX Unsigned32 (0..19)
       MAX-ACCESS not-accessible
       STATUS current
       DESCRIPTION
           "Source number, starting at 0.
AC INI-Param: SourceNumberMapIp2Tel_Index"
       ::= {srcIP2TELEntry 1}



     srcIP2TELRowStatus OBJECT-TYPE
       SYNTAX RowStatus
       MAX-ACCESS read-create
       STATUS current
       DESCRIPTION
           "Row-Status Textual Conventions as defined in RFC 2579: Textual
Conventions for SMIv2.
AC INI-Param: N/A"
       ::= {srcIP2TELEntry 2}



     srcIP2TELAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {srcIP2TELEntry 3}



     srcIP2TELActionResult OBJECT-TYPE
       SYNTAX INTEGER {
                  developmentImpending(0)

                  }
       MAX-ACCESS read-only
       STATUS current
       DESCRIPTION
           "Development Impending.
AC INI-Param: N/A"
       ::= {srcIP2TELEntry 4}



     srcIP2TELPrefix OBJECT-TYPE
       SYNTAX SnmpAdminString (SIZE (0..100))
       MAX-ACCESS read-create
       STATUS current
       DESCRIPTION
           "
Access: Instant.
AC INI-Param: SourceNumberMapIp2Tel_SourcePrefix"
       ::= {srcIP2TELEntry 5}



     srcIP2TELNumOfStrippedDigits OBJECT-TYPE
       SYNTAX Unsigned32 (0..211)
       MAX-ACCESS read-create
       STATUS current
       DESCRIPTION
           "Num of stripped digits.
Access: Instant.
AC INI-Param: SourceNumberMapIp2Tel_RemoveFromLeft"
       ::= {srcIP2TELEntry 6}



     srcIP2TELPrefixToAdd OBJECT-TYPE
       SYNTAX SnmpAdminString (SIZE (0..49))
       MAX-ACCESS read-create
       STATUS current
       DESCRIPTION
           "Prefix to Add.
Access: Instant.
AC INI-Param: SourceNumberMapIp2Tel_Prefix2Add"
       ::= {srcIP2TELEntry 7}



     srcIP2TELNumOfDigitsToLeave OBJECT-TYPE
       SYNTAX Unsigned32 (0..255)
       MAX-ACCESS read-create
       STATUS current
       DESCRIPTION
           "Number of digits to leave.
Access: Instant.
AC INI-Param: SourceNumberMapIp2Tel_LeaveFromRight"
       ::= {srcIP2TELEntry 8}



     srcIP2TELNumberPlan OBJECT-TYPE
       SYNTAX INTEGER {
                  unknown(0)
,
                  e164Public(1)
,
                  private(9)
,
                  notConfigured(255)

                  }
       MAX-ACCESS read-create
       STATUS current
       DESCRIPTION
           "Number Plan.
Access: Instant.
AC INI-Param: SourceNumberMapIp2Tel_NumberPlan"
       ::= {srcIP2TELEntry 9}



     srcIP2TELNumberType OBJECT-TYPE
       SYNTAX INTEGER {
                  unknown(0)
,
                  international-Level2Regional(1)
,
                  national-Level1Regional(2)
,
                  networkSpecific-NetworkPISN(3)
,
                  subscriber-Level0Regional(4)
,
                  abbreviated(6)
,
                  notConfigured(255)

                  }
       MAX-ACCESS read-create
       STATUS current
       DESCRIPTION
           "Number Type.
Access: Instant.
AC INI-Param: SourceNumberMapIp2Tel_NumberType"
       ::= {srcIP2TELEntry 10}



     srcIP2TELDestPrefix OBJECT-TYPE
       SYNTAX SnmpAdminString (SIZE (0..100))
       MAX-ACCESS read-create
       STATUS current
       DESCRIPTION
           "
Access: Instant.
AC INI-Param: SourceNumberMapIp2Tel_DestinationPrefix"
       ::= {srcIP2TELEntry 11}



     srcIP2TELPresentation OBJECT-TYPE
       SYNTAX INTEGER {
                  notBlocked(0)
,
                  blocked(1)
,
                  notConfigured(255)

                  }
       MAX-ACCESS read-create
       STATUS current
       DESCRIPTION
           "Presentation.
Access: Instant.
AC INI-Param: SourceNumberMapIp2Tel_IsPresentationRestricted"
       ::= {srcIP2TELEntry 12}



     srcIP2TELNumOfDigitsToRemFromRight OBJECT-TYPE
       SYNTAX Unsigned32 (0..211)
       MAX-ACCESS read-create
       STATUS current
       DESCRIPTION
           "Num Of digits To Remove from Right.
Access: Instant.
AC INI-Param: SourceNumberMapIp2Tel_RemoveFromRight"
       ::= {srcIP2TELEntry 13}



     srcIP2TELSuffix2Add OBJECT-TYPE
       SYNTAX SnmpAdminString (SIZE (0..49))
       MAX-ACCESS read-create
       STATUS current
       DESCRIPTION
           "Suffix To Add.
Access: Instant.
AC INI-Param: SourceNumberMapIp2Tel_Suffix2Add"
       ::= {srcIP2TELEntry 14}



     srcIP2TELSourceIPAddress OBJECT-TYPE
       SYNTAX SnmpAdminString (SIZE (0..15))
       MAX-ACCESS read-create
       STATUS current
       DESCRIPTION
           "Source Address.
Access: Instant.
AC INI-Param: SourceNumberMapIp2Tel_SourceAddress"
       ::= {srcIP2TELEntry 15}



     srcIP2TELSrcHost OBJECT-TYPE
       SYNTAX SnmpAdminString (SIZE (0..50))
       MAX-ACCESS read-create
       STATUS current
       DESCRIPTION
           "Source Host Prefix.
Access: Instant.
AC INI-Param: SourceNumberMapIp2Tel_SrcHost"
       ::= {srcIP2TELEntry 16}



     srcIP2TELDstHost OBJECT-TYPE
       SYNTAX SnmpAdminString (SIZE (0..50))
       MAX-ACCESS read-create
       STATUS current
       DESCRIPTION
           "Destination Host Prefix.
Access: Instant.
AC INI-Param: SourceNumberMapIp2Tel_DestHost"
       ::= {srcIP2TELEntry 17}



     srcIP2TELManipulationName OBJECT-TYPE
       SYNTAX SnmpAdminString (SIZE (0..20))
       MAX-ACCESS read-create
       STATUS current
       DESCRIPTION
           "Manipulation Name.
Access: Instant.
AC INI-Param: SourceNumberMapIp2Tel_ManipulationName"
       ::= {srcIP2TELEntry 18}



     -- ****************************************
     -- srcTEL2IP table declaration
     -- ****************************************
     srcTEL2IPTable OBJECT-TYPE
       SYNTAX SEQUENCE OF SrcTEL2IPEntry
       MAX-ACCESS not-accessible
       STATUS current
       DESCRIPTION
           ""
       ::= {manipulation 24}



     -- ****************************************
     -- srcTEL2IP table entry
     -- ****************************************
     srcTEL2IPEntry OBJECT-TYPE
       SYNTAX SrcTEL2IPEntry
       MAX-ACCESS not-accessible
       STATUS current
       DESCRIPTION
           ""
       INDEX {srcTEL2IPIndex}
       ::= {srcTEL2IPTable 1}



     -- ****************************************
     -- srcTEL2IP TABLE
     -- ****************************************
     SrcTEL2IPEntry ::= SEQUENCE {
       srcTEL2IPIndex                                  Unsigned32,
       srcTEL2IPRowStatus                              RowStatus,
       srcTEL2IPAction                                 INTEGER,
       srcTEL2IPActionResult                           INTEGER,
       srcTEL2IPPrefix                                 SnmpAdminString,
       srcTEL2IPNumOfStrippedDigits                    Unsigned32,
       srcTEL2IPPrefixToAdd                            SnmpAdminString,
       srcTEL2IPNumOfDigitsToLeave                     Unsigned32,
       srcTEL2IPNumberPlan                             INTEGER,
       srcTEL2IPNumberType                             INTEGER,
       srcTEL2IPDestPrefix                             SnmpAdminString,
       srcTEL2IPPresentation                           INTEGER,
       srcTEL2IPNumOfDigitsToRemFromRight              Unsigned32,
       srcTEL2IPSuffix2Add                             SnmpAdminString,
       srcTEL2IPSourceIPAddress                        SnmpAdminString,
       srcTEL2IPSourceTrunkGroupID                     Integer32,
       srcTEL2IPSourceIPGroupID                        Integer32,
       srcTEL2IPSrcHost                                SnmpAdminString,
       srcTEL2IPDstHost                                SnmpAdminString,
       srcTEL2IPManipulationName                       SnmpAdminString
     }



     srcTEL2IPIndex OBJECT-TYPE
       SYNTAX Unsigned32 (0..119)
       MAX-ACCESS not-accessible
       STATUS current
       DESCRIPTION
           "Source number, starting at 0.
AC INI-Param: SourceNumberMapTel2Ip_Index"
       ::= {srcTEL2IPEntry 1}



     srcTEL2IPRowStatus OBJECT-TYPE
       SYNTAX RowStatus
       MAX-ACCESS read-create
       STATUS current
       DESCRIPTION
           "Row-Status Textual Conventions as defined in RFC 2579: Textual
Conventions for SMIv2.
AC INI-Param: N/A"
       ::= {srcTEL2IPEntry 2}



     srcTEL2IPAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {srcTEL2IPEntry 3}



     srcTEL2IPActionResult OBJECT-TYPE
       SYNTAX INTEGER {
                  developmentImpending(0)

                  }
       MAX-ACCESS read-only
       STATUS current
       DESCRIPTION
           "Development Impending.
AC INI-Param: N/A"
       ::= {srcTEL2IPEntry 4}



     srcTEL2IPPrefix OBJECT-TYPE
       SYNTAX SnmpAdminString (SIZE (0..100))
       MAX-ACCESS read-create
       STATUS current
       DESCRIPTION
           "
Access: Instant.
AC INI-Param: SourceNumberMapTel2Ip_SourcePrefix"
       ::= {srcTEL2IPEntry 5}



     srcTEL2IPNumOfStrippedDigits OBJECT-TYPE
       SYNTAX Unsigned32 (0..211)
       MAX-ACCESS read-create
       STATUS current
       DESCRIPTION
           "Num of stripped digits, Remove from left.
Access: Instant.
AC INI-Param: SourceNumberMapTel2Ip_RemoveFromLeft"
       ::= {srcTEL2IPEntry 6}



     srcTEL2IPPrefixToAdd OBJECT-TYPE
       SYNTAX SnmpAdminString (SIZE (0..49))
       MAX-ACCESS read-create
       STATUS current
       DESCRIPTION
           "Prefix to Add.
Access: Instant.
AC INI-Param: SourceNumberMapTel2Ip_Prefix2Add"
       ::= {srcTEL2IPEntry 7}



     srcTEL2IPNumOfDigitsToLeave OBJECT-TYPE
       SYNTAX Unsigned32 (0..255)
       MAX-ACCESS read-create
       STATUS current
       DESCRIPTION
           "Number of digits to leave.
Access: Instant.
AC INI-Param: SourceNumberMapTel2Ip_LeaveFromRight"
       ::= {srcTEL2IPEntry 8}



     srcTEL2IPNumberPlan OBJECT-TYPE
       SYNTAX INTEGER {
                  unknown(0)
,
                  e164Public(1)
,
                  private(9)
,
                  notConfigured(255)

                  }
       MAX-ACCESS read-create
       STATUS current
       DESCRIPTION
           "Number Plan.
Access: Instant.
AC INI-Param: SourceNumberMapTel2Ip_NumberPlan"
       ::= {srcTEL2IPEntry 9}



     srcTEL2IPNumberType OBJECT-TYPE
       SYNTAX INTEGER {
                  unknown(0)
,
                  international-Level2Regional(1)
,
                  national-Level1Regional(2)
,
                  networkSpecific-NetworkPISN(3)
,
                  subscriber-Level0Regional(4)
,
                  abbreviated(6)
,
                  notConfigured(255)

                  }
       MAX-ACCESS read-create
       STATUS current
       DESCRIPTION
           "Number Type.
Access: Instant.
AC INI-Param: SourceNumberMapTel2Ip_NumberType"
       ::= {srcTEL2IPEntry 10}



     srcTEL2IPDestPrefix OBJECT-TYPE
       SYNTAX SnmpAdminString (SIZE (0..100))
       MAX-ACCESS read-create
       STATUS current
       DESCRIPTION
           "
Access: Instant.
AC INI-Param: SourceNumberMapTel2Ip_DestinationPrefix"
       ::= {srcTEL2IPEntry 11}



     srcTEL2IPPresentation OBJECT-TYPE
       SYNTAX INTEGER {
                  notBlocked(0)
,
                  blocked(1)
,
                  notConfigured(255)

                  }
       MAX-ACCESS read-create
       STATUS current
       DESCRIPTION
           "Presentation.
Access: Instant.
AC INI-Param: SourceNumberMapTel2Ip_IsPresentationRestricted"
       ::= {srcTEL2IPEntry 12}



     srcTEL2IPNumOfDigitsToRemFromRight OBJECT-TYPE
       SYNTAX Unsigned32 (0..211)
       MAX-ACCESS read-create
       STATUS current
       DESCRIPTION
           "Num Of digits To Remove from Right.
Access: Instant.
AC INI-Param: SourceNumberMapTel2Ip_RemoveFromRight"
       ::= {srcTEL2IPEntry 13}



     srcTEL2IPSuffix2Add OBJECT-TYPE
       SYNTAX SnmpAdminString (SIZE (0..49))
       MAX-ACCESS read-create
       STATUS current
       DESCRIPTION
           "Suffix To Add.
Access: Instant.
AC INI-Param: SourceNumberMapTel2Ip_Suffix2Add"
       ::= {srcTEL2IPEntry 14}



     srcTEL2IPSourceIPAddress OBJECT-TYPE
       SYNTAX SnmpAdminString (SIZE (0..15))
       MAX-ACCESS read-create
       STATUS current
       DESCRIPTION
           "Source Address.
Access: Instant.
AC INI-Param: SourceNumberMapTel2Ip_SourceAddress"
       ::= {srcTEL2IPEntry 15}



     srcTEL2IPSourceTrunkGroupID OBJECT-TYPE
       SYNTAX Integer32 (-1..99)
       MAX-ACCESS read-create
       STATUS current
       DESCRIPTION
           "GwApp IP-toTel Destination Phone Number Manipulation Rules Table.
Access: Instant.
AC INI-Param: NumberMapIp2Tel_SrcTrunkGroupID"
       ::= {srcTEL2IPEntry 16}



     srcTEL2IPSourceIPGroupID OBJECT-TYPE
       SYNTAX Integer32 (-1..31)
       MAX-ACCESS read-create
       STATUS current
       DESCRIPTION
           "GwApp IP-toTel Destination Phone Number Manipulation Rules Table.
Access: Instant.
AC INI-Param: NumberMapIp2Tel_SrcIPGroupID"
       ::= {srcTEL2IPEntry 17}



     srcTEL2IPSrcHost OBJECT-TYPE
       SYNTAX SnmpAdminString (SIZE (0..50))
       MAX-ACCESS read-create
       STATUS current
       DESCRIPTION
           "Source Host Prefix.
Access: Instant.
AC INI-Param: SourceNumberMapTel2Ip_SrcHost"
       ::= {srcTEL2IPEntry 18}



     srcTEL2IPDstHost OBJECT-TYPE
       SYNTAX SnmpAdminString (SIZE (0..50))
       MAX-ACCESS read-create
       STATUS current
       DESCRIPTION
           "Destination Host Prefix.
Access: Instant.
AC INI-Param: SourceNumberMapIp2Tel_DestHost"
       ::= {srcTEL2IPEntry 19}



     srcTEL2IPManipulationName OBJECT-TYPE
       SYNTAX SnmpAdminString (SIZE (0..20))
       MAX-ACCESS read-create
       STATUS current
       DESCRIPTION
           "Manipulation Name.
Access: Instant.
AC INI-Param: SourceNumberMapTel2Ip_ManipulationName"
       ::= {srcTEL2IPEntry 20}



     -- ****************************************
     -- phoneContext table declaration
     -- ****************************************
     phoneContextTable OBJECT-TYPE
       SYNTAX SEQUENCE OF PhoneContextEntry
       MAX-ACCESS not-accessible
       STATUS current
       DESCRIPTION
           ""
       ::= {manipulation 25}



     -- ****************************************
     -- phoneContext table entry
     -- ****************************************
     phoneContextEntry OBJECT-TYPE
       SYNTAX PhoneContextEntry
       MAX-ACCESS not-accessible
       STATUS current
       DESCRIPTION
           ""
       INDEX {phoneContextIndex}
       ::= {phoneContextTable 1}



     -- ****************************************
     -- phoneContext TABLE
     -- ****************************************
     PhoneContextEntry ::= SEQUENCE {
       phoneContextIndex                               Unsigned32,
       phoneContextRowStatus                           RowStatus,
       phoneContextAction                              INTEGER,
       phoneContextActionResult                        INTEGER,
       phoneContextNPI                                 INTEGER,
       phoneContextTON                                 INTEGER,
       phoneContextPhoneContext                        SnmpAdminString
     }



     phoneContextIndex OBJECT-TYPE
       SYNTAX Unsigned32 (0..19)
       MAX-ACCESS not-accessible
       STATUS current
       DESCRIPTION
           "Entry number, starting at 0.
AC INI-Param: PhoneContext_Index"
       ::= {phoneContextEntry 1}



     phoneContextRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {phoneContextEntry 2}



     phoneContextAction OBJECT-TYPE
       SYNTAX INTEGER {
                  developmentImpending(0)

                  }
       MAX-ACCESS read-only
       STATUS current
       DESCRIPTION
           "Development Impending.
AC INI-Param: N/A"
       ::= {phoneContextEntry 3}



     phoneContextActionResult OBJECT-TYPE
       SYNTAX INTEGER {
                  developmentImpending(0)

                  }
       MAX-ACCESS read-only
       STATUS current
       DESCRIPTION
           "Development Impending.
AC INI-Param: N/A"
       ::= {phoneContextEntry 4}



     phoneContextNPI OBJECT-TYPE
       SYNTAX INTEGER {
                  notConfigured(255)
,
                  unknown(0)
,
                  e164Public(1)
,
                  data(3)
,
                  telex(4)
,
                  national(8)
,
                  private(9)
,
                  reservedExtension(15)

                  }
       MAX-ACCESS read-create
       STATUS current
       DESCRIPTION
           "Number Plan.
Access: Instant.
AC INI-Param: PhoneContext_Npi"
       ::= {phoneContextEntry 5}



     phoneContextTON OBJECT-TYPE
       SYNTAX INTEGER {
                  notConfigured(255)
,
                  unknown(0)
,
                  international-Level2Regional(1)
,
                  national-Level1Regional(2)
,
                  networkSpecific-NetworkPISN(3)
,
                  subscriber-Level0Regional(4)
,
                  abbreviated(6)
,
                  reservedExtension(7)

                  }
       MAX-ACCESS read-create
       STATUS current
       DESCRIPTION
           "Number Type.
Access: Instant.
AC INI-Param: PhoneContext_Ton"
       ::= {phoneContextEntry 6}



     phoneContextPhoneContext OBJECT-TYPE
       SYNTAX SnmpAdminString (SIZE (0..99))
       MAX-ACCESS read-create
       STATUS current
       DESCRIPTION
           "Phone-Context.
Access: Instant.
AC INI-Param: PhoneContext_Context"
       ::= {phoneContextEntry 7}



     -- ****************************************
     -- redirectNumberMapIp2Tel table declaration
     -- ****************************************
     redirectNumberMapIp2TelTable OBJECT-TYPE
       SYNTAX SEQUENCE OF RedirectNumberMapIp2TelEntry
       MAX-ACCESS not-accessible
       STATUS current
       DESCRIPTION
           "GwApp IP-to-Tel Redirect Phone Number Manipulation Rules Table"
       ::= {manipulation 26}



     -- ****************************************
     -- redirectNumberMapIp2Tel table entry
     -- ****************************************
     redirectNumberMapIp2TelEntry OBJECT-TYPE
       SYNTAX RedirectNumberMapIp2TelEntry
       MAX-ACCESS not-accessible
       STATUS current
       DESCRIPTION
           ""
       INDEX {redirectNumberMapIp2TelIndex}
       ::= {redirectNumberMapIp2TelTable 1}



     -- ****************************************
     -- redirectNumberMapIp2Tel TABLE
     -- ****************************************
     RedirectNumberMapIp2TelEntry ::= SEQUENCE {
       redirectNumberMapIp2TelIndex                    Unsigned32,
       redirectNumberMapIp2TelRowStatus                RowStatus,
       redirectNumberMapIp2TelAction                   INTEGER,
       redirectNumberMapIp2TelActionResult             INTEGER,
       redirectNumberMapIp2TelDestinationPrefix        SnmpAdminString,
       redirectNumberMapIp2TelRedirectPrefix           SnmpAdminString,
       redirectNumberMapIp2TelSourceAddress            SnmpAdminString,
       redirectNumberMapIp2TelNumberType               INTEGER,
       redirectNumberMapIp2TelNumberPlan               INTEGER,
       redirectNumberMapIp2TelRemoveFromLeft           Unsigned32,
       redirectNumberMapIp2TelRemoveFromRight          Unsigned32,
       redirectNumberMapIp2TelLeaveFromRight           Unsigned32,
       redirectNumberMapIp2TelPrefixToAdd              SnmpAdminString,
       redirectNumberMapIp2TelSuffixToAdd              SnmpAdminString,
       redirectNumberMapIp2TelIsPresentationRestricted INTEGER,
       redirectNumberMapIp2TelSrcTrunkGroupID          Integer32,
       redirectNumberMapIp2TelSrcIPGroupID             Integer32,
       redirectNumberMapIp2TelSrcHost                  SnmpAdminString,
       redirectNumberMapIp2TelDstHost                  SnmpAdminString,
       redirectNumberMapIp2TelManipulationName         SnmpAdminString
     }



     redirectNumberMapIp2TelIndex OBJECT-TYPE
       SYNTAX Unsigned32 (0..19)
       MAX-ACCESS not-accessible
       STATUS current
       DESCRIPTION
           "Entry number, starting at 0.
AC INI-Param: RedirectNumberMapIp2Tel_Index"
       ::= {redirectNumberMapIp2TelEntry 1}



     redirectNumberMapIp2TelRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {redirectNumberMapIp2TelEntry 2}



     redirectNumberMapIp2TelAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {redirectNumberMapIp2TelEntry 3}



     redirectNumberMapIp2TelActionResult OBJECT-TYPE
       SYNTAX INTEGER {
                  developmentImpending(0)

                  }
       MAX-ACCESS read-only
       STATUS current
       DESCRIPTION
           "Development Impending.
AC INI-Param: N/A"
       ::= {redirectNumberMapIp2TelEntry 4}



     redirectNumberMapIp2TelDestinationPrefix OBJECT-TYPE
       SYNTAX SnmpAdminString (SIZE (0..100))
       MAX-ACCESS read-create
       STATUS current
       DESCRIPTION
           "
Access: Instant.
AC INI-Param: RedirectNumberMapIp2Tel_DestinationPrefix"
       ::= {redirectNumberMapIp2TelEntry 5}



     redirectNumberMapIp2TelRedirectPrefix OBJECT-TYPE
       SYNTAX SnmpAdminString (SIZE (0..100))
       MAX-ACCESS read-create
       STATUS current
       DESCRIPTION
           "
Access: Instant.
AC INI-Param: RedirectNumberMapIp2Tel_RedirectPrefix"
       ::= {redirectNumberMapIp2TelEntry 6}



     redirectNumberMapIp2TelSourceAddress OBJECT-TYPE
       SYNTAX SnmpAdminString (SIZE (0..70))
       MAX-ACCESS read-create
       STATUS current
       DESCRIPTION
           "
Access: Instant.
AC INI-Param: RedirectNumberMapIp2Tel_SourceAddress"
       ::= {redirectNumberMapIp2TelEntry 7}



     redirectNumberMapIp2TelNumberType OBJECT-TYPE
       SYNTAX INTEGER {
                  notConfigured(255)
,
                  unknown(0)
,
                  international(1)
,
                  national(2)
,
                  networkSpecific(3)
,
                  subscriber(4)
,
                  abbreviated(6)

                  }
       MAX-ACCESS read-create
       STATUS current
       DESCRIPTION
           "
Access: Instant.
AC INI-Param: RedirectNumberMapIp2Tel_NumberType"
       ::= {redirectNumberMapIp2TelEntry 8}



     redirectNumberMapIp2TelNumberPlan OBJECT-TYPE
       SYNTAX INTEGER {
                  notConfigured(255)
,
                  unknown(0)
,
                  e164Public(1)
,
                  private(9)

                  }
       MAX-ACCESS read-create
       STATUS current
       DESCRIPTION
           "
Access: Instant.
AC INI-Param: RedirectNumberMapIp2Tel_NumberPlan"
       ::= {redirectNumberMapIp2TelEntry 9}



     redirectNumberMapIp2TelRemoveFromLeft OBJECT-TYPE
       SYNTAX Unsigned32 (0..211)
       MAX-ACCESS read-create
       STATUS current
       DESCRIPTION
           "
Access: Instant.
AC INI-Param: RedirectNumberMapIp2Tel_RemoveFromLeft"
       ::= {redirectNumberMapIp2TelEntry 10}



     redirectNumberMapIp2TelRemoveFromRight OBJECT-TYPE
       SYNTAX Unsigned32 (0..211)
       MAX-ACCESS read-create
       STATUS current
       DESCRIPTION
           "
Access: Instant.
AC INI-Param: RedirectNumberMapIp2Tel_RemoveFromRight"
       ::= {redirectNumberMapIp2TelEntry 11}



     redirectNumberMapIp2TelLeaveFromRight OBJECT-TYPE
       SYNTAX Unsigned32 (0..2147483647)
       MAX-ACCESS read-create
       STATUS current
       DESCRIPTION
           "
Access: Instant.
AC INI-Param: RedirectNumberMapIp2Tel_LeaveFromRight"
       ::= {redirectNumberMapIp2TelEntry 12}



     redirectNumberMapIp2TelPrefixToAdd OBJECT-TYPE
       SYNTAX SnmpAdminString (SIZE (0..49))
       MAX-ACCESS read-create
       STATUS current
       DESCRIPTION
           "
Access: Instant.
AC INI-Param: RedirectNumberMapIp2Tel_Prefix2Add"
       ::= {redirectNumberMapIp2TelEntry 13}



     redirectNumberMapIp2TelSuffixToAdd OBJECT-TYPE
       SYNTAX SnmpAdminString (SIZE (0..49))
       MAX-ACCESS read-create
       STATUS current
       DESCRIPTION
           "
Access: Instant.
AC INI-Param: RedirectNumberMapIp2Tel_Suffix2Add"
       ::= {redirectNumberMapIp2TelEntry 14}



     redirectNumberMapIp2TelIsPresentationRestricted OBJECT-TYPE
       SYNTAX INTEGER {
                  notConfigured(255)
,
                  allowed(0)
,
                  restricted(1)

                  }
       MAX-ACCESS read-create
       STATUS current
       DESCRIPTION
           "
Access: Instant.
AC INI-Param: RedirectNumberMapIp2Tel_IsPresentationRestricted"
       ::= {redirectNumberMapIp2TelEntry 15}



     redirectNumberMapIp2TelSrcTrunkGroupID OBJECT-TYPE
       SYNTAX Integer32 (-1..99)
       MAX-ACCESS read-create
       STATUS current
       DESCRIPTION
           "
Access: Instant.
AC INI-Param: RedirectNumberMapIp2Tel_SrcTrunkGroupID"
       ::= {redirectNumberMapIp2TelEntry 16}



     redirectNumberMapIp2TelSrcIPGroupID OBJECT-TYPE
       SYNTAX Integer32 (-1..31)
       MAX-ACCESS read-create
       STATUS current
       DESCRIPTION
           "
Access: Instant.
AC INI-Param: RedirectNumberMapIp2Tel_SrcIPGroupID"
       ::= {redirectNumberMapIp2TelEntry 17}



     redirectNumberMapIp2TelSrcHost OBJECT-TYPE
       SYNTAX SnmpAdminString (SIZE (0..50))
       MAX-ACCESS read-create
       STATUS current
       DESCRIPTION
           "Source Host Prefix.
Access: Instant.
AC INI-Param: RedirectNumberMapIp2Tel_SrcHost"
       ::= {redirectNumberMapIp2TelEntry 18}



     redirectNumberMapIp2TelDstHost OBJECT-TYPE
       SYNTAX SnmpAdminString (SIZE (0..50))
       MAX-ACCESS read-create
       STATUS current
       DESCRIPTION
           "Destination Host Prefix.
Access: Instant.
AC INI-Param: RedirectNumberMapIp2Tel_DestHost"
       ::= {redirectNumberMapIp2TelEntry 19}



     redirectNumberMapIp2TelManipulationName OBJECT-TYPE
       SYNTAX SnmpAdminString (SIZE (0..20))
       MAX-ACCESS read-create
       STATUS current
       DESCRIPTION
           "Manipulation Name.
Access: Instant.
AC INI-Param: RedirectNumberMapIp2Tel_ManipulationName"
       ::= {redirectNumberMapIp2TelEntry 20}



     -- ****************************************
     -- redirectNumberMapTel2Ip table declaration
     -- ****************************************
     redirectNumberMapTel2IpTable OBJECT-TYPE
       SYNTAX SEQUENCE OF RedirectNumberMapTel2IpEntry
       MAX-ACCESS not-accessible
       STATUS current
       DESCRIPTION
           "GwApp Tel-to-IP Redirect Phone Number Manipulation Rules Table"
       ::= {manipulation 27}



     -- ****************************************
     -- redirectNumberMapTel2Ip table entry
     -- ****************************************
     redirectNumberMapTel2IpEntry OBJECT-TYPE
       SYNTAX RedirectNumberMapTel2IpEntry
       MAX-ACCESS not-accessible
       STATUS current
       DESCRIPTION
           ""
       INDEX {redirectNumberMapTel2IpIndex}
       ::= {redirectNumberMapTel2IpTable 1}



     -- ****************************************
     -- redirectNumberMapTel2Ip TABLE
     -- ****************************************
     RedirectNumberMapTel2IpEntry ::= SEQUENCE {
       redirectNumberMapTel2IpIndex                    Unsigned32,
       redirectNumberMapTel2IpRowStatus                RowStatus,
       redirectNumberMapTel2IpAction                   INTEGER,
       redirectNumberMapTel2IpActionResult             INTEGER,
       redirectNumberMapTel2IpDestinationPrefix        SnmpAdminString,
       redirectNumberMapTel2IpRedirectPrefix           SnmpAdminString,
       redirectNumberMapTel2IpSourceAddress            SnmpAdminString,
       redirectNumberMapTel2IpNumberType               Unsigned32,
       redirectNumberMapTel2IpNumberPlan               Unsigned32,
       redirectNumberMapTel2IpRemoveFromLeft           Unsigned32,
       redirectNumberMapTel2IpRemoveFromRight          Unsigned32,
       redirectNumberMapTel2IpLeaveFromRight           Unsigned32,
       redirectNumberMapTel2IpPrefixToAdd              SnmpAdminString,
       redirectNumberMapTel2IpSuffixToAdd              SnmpAdminString,
       redirectNumberMapTel2IpIsPresentationRestricted INTEGER,
       redirectNumberMapTel2IpSrcTrunkGroupID          Integer32,
       redirectNumberMapTel2IpSrcIPGroupID             Integer32,
       redirectNumberMapTel2IpSrcHost                  SnmpAdminString,
       redirectNumberMapTel2IpDstHost                  SnmpAdminString,
       redirectNumberMapTel2IpManipulationName         SnmpAdminString
     }



     redirectNumberMapTel2IpIndex OBJECT-TYPE
       SYNTAX Unsigned32 (0..19)
       MAX-ACCESS not-accessible
       STATUS current
       DESCRIPTION
           "Entry number, starting at 0.
AC INI-Param: RedirectNumberMapTel2Ip_Index"
       ::= {redirectNumberMapTel2IpEntry 1}



     redirectNumberMapTel2IpRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {redirectNumberMapTel2IpEntry 2}



     redirectNumberMapTel2IpAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {redirectNumberMapTel2IpEntry 3}



     redirectNumberMapTel2IpActionResult OBJECT-TYPE
       SYNTAX INTEGER {
                  developmentImpending(0)

                  }
       MAX-ACCESS read-only
       STATUS current
       DESCRIPTION
           "Development Impending.
AC INI-Param: N/A"
       ::= {redirectNumberMapTel2IpEntry 4}



     redirectNumberMapTel2IpDestinationPrefix OBJECT-TYPE
       SYNTAX SnmpAdminString (SIZE (0..100))
       MAX-ACCESS read-create
       STATUS current
       DESCRIPTION
           "
Access: Instant.
AC INI-Param: RedirectNumberMapTel2Ip_DestinationPrefix"
       ::= {redirectNumberMapTel2IpEntry 5}



     redirectNumberMapTel2IpRedirectPrefix OBJECT-TYPE
       SYNTAX SnmpAdminString (SIZE (0..100))
       MAX-ACCESS read-create
       STATUS current
       DESCRIPTION
           "
Access: Instant.
AC INI-Param: RedirectNumberMapTel2Ip_RedirectPrefix"
       ::= {redirectNumberMapTel2IpEntry 6}



     redirectNumberMapTel2IpSourceAddress OBJECT-TYPE
       SYNTAX SnmpAdminString (SIZE (0..70))
       MAX-ACCESS read-create
       STATUS current
       DESCRIPTION
           "
Access: Instant.
AC INI-Param: RedirectNumberMapTel2Ip_SourceAddress"
       ::= {redirectNumberMapTel2IpEntry 7}



     redirectNumberMapTel2IpNumberType OBJECT-TYPE
       SYNTAX Unsigned32 (0..2147483647)
       MAX-ACCESS read-create
       STATUS current
       DESCRIPTION
           "
Access: Instant.
AC INI-Param: RedirectNumberMapTel2Ip_NumberType"
       ::= {redirectNumberMapTel2IpEntry 8}



     redirectNumberMapTel2IpNumberPlan OBJECT-TYPE
       SYNTAX Unsigned32 (0..2147483647)
       MAX-ACCESS read-create
       STATUS current
       DESCRIPTION
           "
Access: Instant.
AC INI-Param: RedirectNumberMapTel2Ip_NumberPlan"
       ::= {redirectNumberMapTel2IpEntry 9}



     redirectNumberMapTel2IpRemoveFromLeft OBJECT-TYPE
       SYNTAX Unsigned32 (0..211)
       MAX-ACCESS read-create
       STATUS current
       DESCRIPTION
           "
Access: Instant.
AC INI-Param: RedirectNumberMapTel2Ip_RemoveFromLeft"
       ::= {redirectNumberMapTel2IpEntry 10}



     redirectNumberMapTel2IpRemoveFromRight OBJECT-TYPE
       SYNTAX Unsigned32 (0..211)
       MAX-ACCESS read-create
       STATUS current
       DESCRIPTION
           "
Access: Instant.
AC INI-Param: RedirectNumberMapTel2Ip_RemoveFromRight"
       ::= {redirectNumberMapTel2IpEntry 11}



     redirectNumberMapTel2IpLeaveFromRight OBJECT-TYPE
       SYNTAX Unsigned32 (0..2147483647)
       MAX-ACCESS read-create
       STATUS current
       DESCRIPTION
           "
Access: Instant.
AC INI-Param: RedirectNumberMapTel2Ip_LeaveFromRight"
       ::= {redirectNumberMapTel2IpEntry 12}



     redirectNumberMapTel2IpPrefixToAdd OBJECT-TYPE
       SYNTAX SnmpAdminString (SIZE (0..49))
       MAX-ACCESS read-create
       STATUS current
       DESCRIPTION
           "
Access: Instant.
AC INI-Param: RedirectNumberMapTel2Ip_Prefix2Add"
       ::= {redirectNumberMapTel2IpEntry 13}



     redirectNumberMapTel2IpSuffixToAdd OBJECT-TYPE
       SYNTAX SnmpAdminString (SIZE (0..49))
       MAX-ACCESS read-create
       STATUS current
       DESCRIPTION
           "
Access: Instant.
AC INI-Param: RedirectNumberMapTel2Ip_Suffix2Add"
       ::= {redirectNumberMapTel2IpEntry 14}



     redirectNumberMapTel2IpIsPresentationRestricted OBJECT-TYPE
       SYNTAX INTEGER {
                  notConfigured(255)
,
                  allowed(0)
,
                  restricted(1)

                  }
       MAX-ACCESS read-create
       STATUS current
       DESCRIPTION
           "
Access: Instant.
AC INI-Param: RedirectNumberMapTel2Ip_IsPresentationRestricted"
       ::= {redirectNumberMapTel2IpEntry 15}



     redirectNumberMapTel2IpSrcTrunkGroupID OBJECT-TYPE
       SYNTAX Integer32 (-1..99)
       MAX-ACCESS read-create
       STATUS current
       DESCRIPTION
           "
Access: Instant.
AC INI-Param: RedirectNumberMapTel2Ip_SrcTrunkGroupID"
       ::= {redirectNumberMapTel2IpEntry 16}



     redirectNumberMapTel2IpSrcIPGroupID OBJECT-TYPE
       SYNTAX Integer32 (-1..31)
       MAX-ACCESS read-create
       STATUS current
       DESCRIPTION
           "
Access: Instant.
AC INI-Param: RedirectNumberMapTel2Ip_SrcIPGroupID"
       ::= {redirectNumberMapTel2IpEntry 17}



     redirectNumberMapTel2IpSrcHost OBJECT-TYPE
       SYNTAX SnmpAdminString (SIZE (0..50))
       MAX-ACCESS read-create
       STATUS current
       DESCRIPTION
           "Source Host Prefix.
Access: Instant.
AC INI-Param: RedirectNumberMapTel2Ip_SrcHost"
       ::= {redirectNumberMapTel2IpEntry 18}



     redirectNumberMapTel2IpDstHost OBJECT-TYPE
       SYNTAX SnmpAdminString (SIZE (0..50))
       MAX-ACCESS read-create
       STATUS current
       DESCRIPTION
           "Destination Host Prefix.
Access: Instant.
AC INI-Param: RedirectNumberMapTel2Ip_DestHost"
       ::= {redirectNumberMapTel2IpEntry 19}



     redirectNumberMapTel2IpManipulationName OBJECT-TYPE
       SYNTAX SnmpAdminString (SIZE (0..20))
       MAX-ACCESS read-create
       STATUS current
       DESCRIPTION
           "Manipulation Name.
Access: Instant.
AC INI-Param: RedirectNumberMapTel2Ip_ManipulationName"
       ::= {redirectNumberMapTel2IpEntry 20}



     connectivityQos OBJECT IDENTIFIER ::= {manipulationAndRouting 22}


     connectivityQosMaxAllowedPL OBJECT-TYPE
       SYNTAX Unsigned32 (0..100)
       MAX-ACCESS read-write
       STATUS current
       DESCRIPTION
           "The maximum percentage of packet loss that will not prevent
normal routing.
Access: Instant.
AC INI-Param: IPCONNQOSMAXALLOWEDPL"
       ::= {connectivityQos 1}



     connectivityQosMaxAllowedDelay OBJECT-TYPE
       SYNTAX Unsigned32 (0..10000)
       MAX-ACCESS read-write
       STATUS current
       DESCRIPTION
           "The maximum delay that will not prevent normal routing (msec).
Access: Instant.
AC INI-Param: IPCONNQOSMAXALLOWEDDELAY"
       ::= {connectivityQos 2}



     connectivityQosEffectivePeriod OBJECT-TYPE
       SYNTAX Unsigned32 (0..10000)
       MAX-ACCESS read-write
       STATUS current
       DESCRIPTION
           "if during this period [in seconds], no updated qos info received,
theold qos info is discarded. if qos poor, and no calls
alowed, after this period, calls will be allowed again.
Access: Instant.
AC INI-Param: IPCONNQOSEFFECTIVEPERIOD"
       ::= {connectivityQos 3}



     connectivityQosSamplesToAvarage OBJECT-TYPE
       SYNTAX Unsigned32 (1..255)
       MAX-ACCESS read-write
       STATUS current
       DESCRIPTION
           "number of samples to avarage. in other words define the weiught
of the new sample.
Access: Instant.
AC INI-Param: IPCONNQOSSAMPLESTOAVARAGE"
       ::= {connectivityQos 4}



     digitalGW OBJECT IDENTIFIER ::= {common 3}


     digitalGWBChannelNegotiation OBJECT-TYPE
       SYNTAX INTEGER {
                  no(0)
,
                  yes(1)
,
                  any(2)

                  }
       MAX-ACCESS read-write
       STATUS current
       DESCRIPTION
           "ISDN B-Channel negotiation mode.
Access: Instant.
AC INI-Param: BCHANNELNEGOTIATION"
       ::= {digitalGW 1}



     digitalGWSwapRedirectNumber OBJECT-TYPE
       SYNTAX INTEGER {
                  no(0)
,
                  yes(1)

                  }
       MAX-ACCESS read-write
       STATUS current
       DESCRIPTION
           "Swap Redirect and Called numbers.
Access: Instant.
AC INI-Param: SWAPREDIRECTNUMBER"
       ::= {digitalGW 2}



     digitalGWEnableTransferCap OBJECT-TYPE
       SYNTAX INTEGER {
                  no(0)
,
                  yes(1)

                  }
       MAX-ACCESS read-write
       STATUS obsolete
       DESCRIPTION
           "Select Transfer Capabilities method between H.323/Q.931 and
ISDN/Q.931.
Access: Instant.
AC INI-Param: ENABLETRANSFERCAP"
       ::= {digitalGW 3}



     digitalGWR2Category OBJECT-TYPE
       SYNTAX Unsigned32 (1..15)
       MAX-ACCESS read-write
       STATUS current
       DESCRIPTION
           "MFC\R2 Calling Party's category.
Access: Instant.
AC INI-Param: R2CATEGORY"
       ::= {digitalGW 4}



     digitalGWISDNRxOverlap OBJECT-TYPE
       SYNTAX INTEGER {
                  no(0)
,
                  yes(1)

                  }
       MAX-ACCESS read-write
       STATUS obsolete
       DESCRIPTION
           "Enable reception of overlap dialing from ISDN side.
Access: Instant.
AC INI-Param: ISDNRXOVERLAP"
       ::= {digitalGW 5}



     digitalGWCASSendHookFlash OBJECT-TYPE
       SYNTAX INTEGER {
                  disable(0)
,
                  enable(1)

                  }
       MAX-ACCESS read-write
       STATUS current
       DESCRIPTION
           "0 (default): Hookflash not forwarded 1:HookFlash forwarded -
Testing.
Access: Instant.
AC INI-Param: CASSENDHOOKFLASH"
       ::= {digitalGW 6}



     digitalGWISDNTransferCapability OBJECT-TYPE
       SYNTAX INTEGER {
                  doNotOverwrite(-1)
,
                  modem(0)
,
                  voice(1)
,
                  data(2)
,
                  audio(3)

                  }
       MAX-ACCESS read-write
       STATUS obsolete
       DESCRIPTION
           "Send transfer capability to ISDN side on setup message  -1:Do
not Overwrite 0:Audio 3.1 1:Speech 2:Data 3:Audio.
Access: Instant.
AC INI-Param: ISDNTRANSFERCAPABILITY"
       ::= {digitalGW 7}



     digitalGWEnableTDMOverIp OBJECT-TYPE
       SYNTAX INTEGER {
                  disable(0)
,
                  enable(1)

                  }
       MAX-ACCESS read-write
       STATUS current
       DESCRIPTION
           "Enable gateway to maintain a permanent RTP connection.
Access: Offline.
AC INI-Param: ENABLETDMOVERIP"
       ::= {digitalGW 8}



     digitalGWTransparentCoderOnDataCall OBJECT-TYPE
       SYNTAX INTEGER {
                  disable(0)
,
                  enable(1)

                  }
       MAX-ACCESS read-write
       STATUS current
       DESCRIPTION
           "In case the transfer capability of a call from ISDN is data
open with transparent coder.
Access: Instant.
AC INI-Param: TRANSPARENTCODERONDATACALL"
       ::= {digitalGW 9}



     digitalGWSupportRedirectInFacility OBJECT-TYPE
       SYNTAX INTEGER {
                  disable(0)
,
                  enable(1)

                  }
       MAX-ACCESS read-write
       STATUS current
       DESCRIPTION
           "Search for redirect number in facility IE.
Access: Instant.
AC INI-Param: SUPPORTREDIRECTINFACILITY"
       ::= {digitalGW 10}



     digitalGWPIForDisconnectMsg OBJECT-TYPE
       SYNTAX Integer32 (-1..8)
       MAX-ACCESS read-write
       STATUS obsolete
       DESCRIPTION
           "Configure PIForDisconnectMsg in order to overwrite PI value
received in ISDN Disconnect message.
Access: Instant.
AC INI-Param: PIFORDISCONNECTMSG"
       ::= {digitalGW 11}



     digitalGWConnectOnProgressInd OBJECT-TYPE
       SYNTAX INTEGER {
                  disable(0)
,
                  enable(1)

                  }
       MAX-ACCESS read-write
       STATUS current
       DESCRIPTION
           "FXS:generate CallerId siganls during ringing FXO:collect CallerId
and use it in Setup message.
Access: Instant.
AC INI-Param: CONNECTONPROGRESSIND"
       ::= {digitalGW 12}



     digitalGWLocalISDNRBSource OBJECT-TYPE
       SYNTAX INTEGER {
                  pbx(0)
,
                  gateway(1)

                  }
       MAX-ACCESS read-write
       STATUS obsolete
       DESCRIPTION
           "If the ringback tone source is not IP, who should supply the
Ringback tone. 0 - PBX/PSTN (default) ; 1- GW.
Access: Instant.
AC INI-Param: LOCALISDNRBSOURCE"
       ::= {digitalGW 13}



     digitalGWEnableUuiTel2Ip OBJECT-TYPE
       SYNTAX INTEGER {
                  disable(0)
,
                  enable(1)

                  }
       MAX-ACCESS read-write
       STATUS current
       DESCRIPTION
           "Enable User-User IE to pass in Setup from ISDN to IP.
Access: Instant.
AC INI-Param: ENABLEUUITEL2IP"
       ::= {digitalGW 14}



     digitalGWEnableUuiIp2Tel OBJECT-TYPE
       SYNTAX INTEGER {
                  disable(0)
,
                  enable(1)

                  }
       MAX-ACCESS read-write
       STATUS current
       DESCRIPTION
           "Enable User-User IE to pass in Setup from IP to ISDN.
Access: Instant.
AC INI-Param: ENABLEUUIIP2TEL"
       ::= {digitalGW 15}



     digitalGWSendISDNTransferOnConnect OBJECT-TYPE
       SYNTAX INTEGER {
                  disable(0)
,
                  enable(1)

                  }
       MAX-ACCESS read-write
       STATUS current
       DESCRIPTION
           "Send TBCT/ECT/RLT request only when second leg call is connected.
Access: Instant.
AC INI-Param: SENDISDNTRANSFERONCONNECT"
       ::= {digitalGW 16}



     digitalGWEnableISDNTunnelingTel2Ip OBJECT-TYPE
       SYNTAX INTEGER {
                  disable(0)
,
                  usingHeader(1)
,
                  usingBody(2)

                  }
       MAX-ACCESS read-write
       STATUS current
       DESCRIPTION
           "Enable ISDN tunneling to pass Setup and Facility messages from
ISDN to IP.
Access: Instant.
AC INI-Param: ENABLEISDNTUNNELINGTEL2IP"
       ::= {digitalGW 17}



     digitalGWEnableISDNTunnelingIp2Tel OBJECT-TYPE
       SYNTAX INTEGER {
                  disable(0)
,
                  usingHeader(1)
,
                  usingBody(2)

                  }
       MAX-ACCESS read-write
       STATUS current
       DESCRIPTION
           "Enable ISDN tunneling to pass Setup and Facility messages from
IP to ISDN.
Access: Instant.
AC INI-Param: ENABLEISDNTUNNELINGIP2TEL"
       ::= {digitalGW 18}



     digitalGWEnableCallingPartyCategory OBJECT-TYPE
       SYNTAX INTEGER {
                  disable(0)
,
                  enable(1)

                  }
       MAX-ACCESS read-write
       STATUS current
       DESCRIPTION
           "Enables NI2 calling party category translation to SIP.
Access: Instant.
AC INI-Param: ENABLECALLINGPARTYCATEGORY"
       ::= {digitalGW 19}



     digitalGWPlayRBTOnISDNTransfer OBJECT-TYPE
       SYNTAX INTEGER {
                  disable(0)
,
                  enable(1)

                  }
       MAX-ACCESS read-write
       STATUS current
       DESCRIPTION
           "Play local RBT on TBCT/ECT/RLT transfer.
Access: Instant.
AC INI-Param: PLAYRBTONISDNTRANSFER"
       ::= {digitalGW 40}



     digitalGWSendLocalTimeToISDNConnect OBJECT-TYPE
       SYNTAX INTEGER {
                  disable(0)
,
                  enable(1)

                  }
       MAX-ACCESS read-write
       STATUS current
       DESCRIPTION
           "Send Local Date and Time To ISDN Connect if SIP 200OK does not
contain Date header.
Access: Instant.
AC INI-Param: SendLocalTimeToISDNConnect"
       ::= {digitalGW 41}



     digitalGWUuiHeaderFormat OBJECT-TYPE
       SYNTAX Unsigned32 (0..3)
       MAX-ACCESS read-write
       STATUS current
       DESCRIPTION
           "(0): X-UserToUser, (1): format: User-to-User with protocol discriminator,
(2): format: User-to-User with 'encoding=hex'
at the end, (3): format: User-to-User with text presentation.
Access: Instant.
AC INI-Param: USERTOUSERHEADERFORMAT"
       ::= {digitalGW 42}



     digitalGWTransferCapabilityForDataCalls OBJECT-TYPE
       SYNTAX INTEGER {
                  sixtyFourKUnrestricted(0)
,
                  accordingToISDNTransferCapability(1)

                  }
       MAX-ACCESS read-write
       STATUS current
       DESCRIPTION
           "0: ISDN Transfer Capability for data calls will be 64k unrestricted
(data), 1:ISDN Transfer Capability  for Data calls will
be set according to ISDNTransferCapability parameter.
Access: Instant.
AC INI-Param: TRANSFERCAPABILITYFORDATACALLS"
       ::= {digitalGW 43}



     digitalGWDisconnectCallWithPIIfAlt OBJECT-TYPE
       SYNTAX INTEGER {
                  disable(0)
,
                  enable(1)

                  }
       MAX-ACCESS read-write
       STATUS current
       DESCRIPTION
           "If set to 1 and ISDN DISCONNECT with PI is received, 183 with
SDP will be sent toward IP only in case no PSTN Alternative
call is possible.
Access: Instant.
AC INI-Param: DISCONNECTCALLWITHPIIFALT"
       ::= {digitalGW 44}



     -- ****************************************
     -- iSDNRxOverlap table declaration
     -- ****************************************
     iSDNRxOverlapTable OBJECT-TYPE
       SYNTAX SEQUENCE OF ISDNRxOverlapEntry
       MAX-ACCESS not-accessible
       STATUS current
       DESCRIPTION
           "Choose either: Disabled or Enabled (default).
Any number bigger than one = Number of digits to receive.
Note 1: If enabled, the Mediant 2000 receives ISDN called number that is sent in the 'Overlap' mode.
Note 2: The SETUP to IP is sent only after the number (including 'Sending Complete' Info Element) was
fully received (via SETUP and/or subsequent INFO Q.931 messages)."
       ::= {digitalGW 21}



     -- ****************************************
     -- iSDNRxOverlap table entry
     -- ****************************************
     iSDNRxOverlapEntry OBJECT-TYPE
       SYNTAX ISDNRxOverlapEntry
       MAX-ACCESS not-accessible
       STATUS current
       DESCRIPTION
           ""
       INDEX {iSDNRxOverlapIndex}
       ::= {iSDNRxOverlapTable 1}



     -- ****************************************
     -- iSDNRxOverlap TABLE
     -- ****************************************
     ISDNRxOverlapEntry ::= SEQUENCE {
       iSDNRxOverlapIndex                              Unsigned32,
       iSDNRxOverlapEnable                             INTEGER
     }



     iSDNRxOverlapIndex OBJECT-TYPE
       SYNTAX Unsigned32 (0..84)
       MAX-ACCESS not-accessible
       STATUS current
       DESCRIPTION
           "Trunk number.
AC INI-Param: N/A"
       ::= {iSDNRxOverlapEntry 1}



     iSDNRxOverlapEnable OBJECT-TYPE
       SYNTAX INTEGER {
                  none(0)
,
                  localReceiving(1)
,
                  throughSIP(2)

                  }
       MAX-ACCESS read-write
       STATUS current
       DESCRIPTION
           "Receive overlap from ISDN side.
Access: Instant.
AC INI-Param: ISDNRXOVERLAP"
       ::= {iSDNRxOverlapEntry 2}



     -- ****************************************
     -- trunkTransfer table declaration
     -- ****************************************
     trunkTransferTable OBJECT-TYPE
       SYNTAX SEQUENCE OF TrunkTransferEntry
       MAX-ACCESS not-accessible
       STATUS current
       DESCRIPTION
           "Trunk Transfer Mode table."
       ::= {digitalGW 22}



     -- ****************************************
     -- trunkTransfer table entry
     -- ****************************************
     trunkTransferEntry OBJECT-TYPE
       SYNTAX TrunkTransferEntry
       MAX-ACCESS not-accessible
       STATUS current
       DESCRIPTION
           ""
       INDEX {trunkTransferIndex}
       ::= {trunkTransferTable 1}



     -- ****************************************
     -- trunkTransfer TABLE
     -- ****************************************
     TrunkTransferEntry ::= SEQUENCE {
       trunkTransferIndex                              Unsigned32,
       trunkTransferMode                               INTEGER
     }



     trunkTransferIndex OBJECT-TYPE
       SYNTAX Unsigned32 (0..84)
       MAX-ACCESS not-accessible
       STATUS current
       DESCRIPTION
           "Trunk number.
AC INI-Param: N/A"
       ::= {trunkTransferEntry 1}



     trunkTransferMode OBJECT-TYPE
       SYNTAX INTEGER {
                  none(0)
,
                  casNFA(1)
,
                  iSDN(2)
,
                  casNormal(3)
,
                  qSIGSingleStep(4)
,
                  qSIGPathReplacement(5)

                  }
       MAX-ACCESS read-write
       STATUS current
       DESCRIPTION
           "The type of transfer the PSTN/PBX supports.
Access: Instant.
AC INI-Param: TRUNKTRANSFERMODE"
       ::= {trunkTransferEntry 2}



     -- ****************************************
     -- progressIndicatorToISDN table declaration
     -- ****************************************
     progressIndicatorToISDNTable OBJECT-TYPE
       SYNTAX SEQUENCE OF ProgressIndicatorToISDNEntry
       MAX-ACCESS not-accessible
       STATUS current
       DESCRIPTION
           "Progress Indicator To ISDN table."
       ::= {digitalGW 23}



     -- ****************************************
     -- progressIndicatorToISDN table entry
     -- ****************************************
     progressIndicatorToISDNEntry OBJECT-TYPE
       SYNTAX ProgressIndicatorToISDNEntry
       MAX-ACCESS not-accessible
       STATUS current
       DESCRIPTION
           ""
       INDEX {progressIndicatorToISDNIndex}
       ::= {progressIndicatorToISDNTable 1}



     -- ****************************************
     -- progressIndicatorToISDN TABLE
     -- ****************************************
     ProgressIndicatorToISDNEntry ::= SEQUENCE {
       progressIndicatorToISDNIndex                    Unsigned32,
       progressIndicatorToISDNValue                    INTEGER
     }



     progressIndicatorToISDNIndex OBJECT-TYPE
       SYNTAX Unsigned32 (0..84)
       MAX-ACCESS not-accessible
       STATUS current
       DESCRIPTION
           "Trunk number.
AC INI-Param: N/A"
       ::= {progressIndicatorToISDNEntry 1}



     progressIndicatorToISDNValue OBJECT-TYPE
       SYNTAX INTEGER {
                  notSet(-1)
,
                  localRB(0)
,
                  remoteRB1(1)
,
                  remoteRB8(8)

                  }
       MAX-ACCESS read-write
       STATUS current
       DESCRIPTION
           "Override the value of progress indicator to ISDN side in ALERT
PROGRESS and PROCEEDING messages.
Access: Instant.
AC INI-Param: PROGRESSINDICATOR2ISDN"
       ::= {progressIndicatorToISDNEntry 2}



     -- ****************************************
     -- playRBToneToTrunk table declaration
     -- ****************************************
     playRBToneToTrunkTable OBJECT-TYPE
       SYNTAX SEQUENCE OF PlayRBToneToTrunkEntry
       MAX-ACCESS not-accessible
       STATUS current
       DESCRIPTION
           "Play RB Tone To Trunk table."
       ::= {digitalGW 24}



     -- ****************************************
     -- playRBToneToTrunk table entry
     -- ****************************************
     playRBToneToTrunkEntry OBJECT-TYPE
       SYNTAX PlayRBToneToTrunkEntry
       MAX-ACCESS not-accessible
       STATUS current
       DESCRIPTION
           ""
       INDEX {playRBToneToTrunkIndex}
       ::= {playRBToneToTrunkTable 1}



     -- ****************************************
     -- playRBToneToTrunk TABLE
     -- ****************************************
     PlayRBToneToTrunkEntry ::= SEQUENCE {
       playRBToneToTrunkIndex                          Unsigned32,
       playRBToneToTrunkValue                          INTEGER
     }



     playRBToneToTrunkIndex OBJECT-TYPE
       SYNTAX Unsigned32 (0..84)
       MAX-ACCESS not-accessible
       STATUS current
       DESCRIPTION
           "Trunk number.
AC INI-Param: N/A"
       ::= {playRBToneToTrunkEntry 1}



     playRBToneToTrunkValue OBJECT-TYPE
       SYNTAX INTEGER {
                  notConfigured(-1)
,
                  doNotPlay(0)
,
                  playOnLocal(1)
,
                  preferIp(2)
,
                  playLocalUntilRemoteMediaArrives(3)

                  }
       MAX-ACCESS read-write
       STATUS current
       DESCRIPTION
           "Enable ringback tone playing towards trunk side. Refer to User's
Manual for details.
Access: Instant.
AC INI-Param: PLAYRBTONE2TRUNK"
       ::= {playRBToneToTrunkEntry 2}



     -- ****************************************
     -- iSDNTransferCapability table declaration
     -- ****************************************
     iSDNTransferCapabilityTable OBJECT-TYPE
       SYNTAX SEQUENCE OF ISDNTransferCapabilityEntry
       MAX-ACCESS not-accessible
       STATUS current
       DESCRIPTION
           "ISDN Transfer Capability Trunk table."
       ::= {digitalGW 25}



     -- ****************************************
     -- iSDNTransferCapability table entry
     -- ****************************************
     iSDNTransferCapabilityEntry OBJECT-TYPE
       SYNTAX ISDNTransferCapabilityEntry
       MAX-ACCESS not-accessible
       STATUS current
       DESCRIPTION
           ""
       INDEX {iSDNTransferCapabilityIndex}
       ::= {iSDNTransferCapabilityTable 1}



     -- ****************************************
     -- iSDNTransferCapability TABLE
     -- ****************************************
     ISDNTransferCapabilityEntry ::= SEQUENCE {
       iSDNTransferCapabilityIndex                     Unsigned32,
       iSDNTransferCapabilityValue                     INTEGER
     }



     iSDNTransferCapabilityIndex OBJECT-TYPE
       SYNTAX Unsigned32 (0..84)
       MAX-ACCESS not-accessible
       STATUS current
       DESCRIPTION
           "Trunk number.
AC INI-Param: N/A"
       ::= {iSDNTransferCapabilityEntry 1}



     iSDNTransferCapabilityValue OBJECT-TYPE
       SYNTAX INTEGER {
                  doNotOverwrite(-1)
,
                  modem(0)
,
                  voice(1)
,
                  data(2)
,
                  audio(3)

                  }
       MAX-ACCESS read-write
       STATUS current
       DESCRIPTION
           "Send transfer capability to ISDN side on setup message  -1:Do
not Overwrite 0:Audio 3.1 1:Speech 2:Data 3:Audio.
Access: Instant.
AC INI-Param: ISDNTRANSFERCAPABILITY"
       ::= {iSDNTransferCapabilityEntry 2}



     -- ****************************************
     -- localISDNRBSource table declaration
     -- ****************************************
     localISDNRBSourceTable OBJECT-TYPE
       SYNTAX SEQUENCE OF LocalISDNRBSourceEntry
       MAX-ACCESS not-accessible
       STATUS current
       DESCRIPTION
           "Play RB Tone To Trunk table."
       ::= {digitalGW 26}



     -- ****************************************
     -- localISDNRBSource table entry
     -- ****************************************
     localISDNRBSourceEntry OBJECT-TYPE
       SYNTAX LocalISDNRBSourceEntry
       MAX-ACCESS not-accessible
       STATUS current
       DESCRIPTION
           ""
       INDEX {localISDNRBSourceIndex}
       ::= {localISDNRBSourceTable 1}



     -- ****************************************
     -- localISDNRBSource TABLE
     -- ****************************************
     LocalISDNRBSourceEntry ::= SEQUENCE {
       localISDNRBSourceIndex                          Unsigned32,
       localISDNRBSourceValue                          INTEGER
     }



     localISDNRBSourceIndex OBJECT-TYPE
       SYNTAX Unsigned32 (0..84)
       MAX-ACCESS not-accessible
       STATUS current
       DESCRIPTION
           "Trunk number.
AC INI-Param: N/A"
       ::= {localISDNRBSourceEntry 1}



     localISDNRBSourceValue OBJECT-TYPE
       SYNTAX INTEGER {
                  pbx(0)
,
                  gateway(1)

                  }
       MAX-ACCESS read-write
       STATUS current
       DESCRIPTION
           "If the ringback tone source is not IP, who should supply the
Ringback tone. 0 - PBX/PSTN (default) ; 1- GW.
Access: Instant.
AC INI-Param: LOCALISDNRBSOURCE"
       ::= {localISDNRBSourceEntry 2}



     -- ****************************************
     -- pIForDisconnectMsg table declaration
     -- ****************************************
     pIForDisconnectMsgTable OBJECT-TYPE
       SYNTAX SEQUENCE OF PIForDisconnectMsgEntry
       MAX-ACCESS not-accessible
       STATUS current
       DESCRIPTION
           "PI For Disconnect Message Trunk table."
       ::= {digitalGW 27}



     -- ****************************************
     -- pIForDisconnectMsg table entry
     -- ****************************************
     pIForDisconnectMsgEntry OBJECT-TYPE
       SYNTAX PIForDisconnectMsgEntry
       MAX-ACCESS not-accessible
       STATUS current
       DESCRIPTION
           ""
       INDEX {pIForDisconnectMsgIndex}
       ::= {pIForDisconnectMsgTable 1}



     -- ****************************************
     -- pIForDisconnectMsg TABLE
     -- ****************************************
     PIForDisconnectMsgEntry ::= SEQUENCE {
       pIForDisconnectMsgIndex                         Unsigned32,
       pIForDisconnectMsgValue                         Integer32
     }



     pIForDisconnectMsgIndex OBJECT-TYPE
       SYNTAX Unsigned32 (0..84)
       MAX-ACCESS not-accessible
       STATUS current
       DESCRIPTION
           "Trunk number.
AC INI-Param: N/A"
       ::= {pIForDisconnectMsgEntry 1}



     pIForDisconnectMsgValue OBJECT-TYPE
       SYNTAX Integer32 (-1..8)
       MAX-ACCESS read-write
       STATUS current
       DESCRIPTION
           "Configure PIForDisconnectMsg in order to overwrite PI value
received in ISDN Disconnect message.
Access: Instant.
AC INI-Param: PIFORDISCONNECTMSG"
       ::= {pIForDisconnectMsgEntry 2}



     -- ****************************************
     -- pSTNAlertTimeout table declaration
     -- ****************************************
     pSTNAlertTimeoutTable OBJECT-TYPE
       SYNTAX SEQUENCE OF PSTNAlertTimeoutEntry
       MAX-ACCESS not-accessible
       STATUS current
       DESCRIPTION
           "PSTN Alert Timeout"
       ::= {digitalGW 28}



     -- ****************************************
     -- pSTNAlertTimeout table entry
     -- ****************************************
     pSTNAlertTimeoutEntry OBJECT-TYPE
       SYNTAX PSTNAlertTimeoutEntry
       MAX-ACCESS not-accessible
       STATUS current
       DESCRIPTION
           ""
       INDEX {pSTNAlertTimeoutIndex}
       ::= {pSTNAlertTimeoutTable 1}



     -- ****************************************
     -- pSTNAlertTimeout TABLE
     -- ****************************************
     PSTNAlertTimeoutEntry ::= SEQUENCE {
       pSTNAlertTimeoutIndex                           Unsigned32,
       pSTNAlertTimeoutValue                           Integer32
     }



     pSTNAlertTimeoutIndex OBJECT-TYPE
       SYNTAX Unsigned32 (0..84)
       MAX-ACCESS not-accessible
       STATUS current
       DESCRIPTION
           "Trunk number.
AC INI-Param: N/A"
       ::= {pSTNAlertTimeoutEntry 1}



     pSTNAlertTimeoutValue OBJECT-TYPE
       SYNTAX Integer32 (-1..600)
       MAX-ACCESS read-write
       STATUS current
       DESCRIPTION
           "Max time (in seconds) to wait for connect from PSTN.
Access: Instant.
AC INI-Param: TRUNKPSTNALERTTIMEOUT"
       ::= {pSTNAlertTimeoutEntry 2}



     iE OBJECT IDENTIFIER ::= {digitalGW 20}


     iEAddIEInSetup OBJECT-TYPE
       SYNTAX SnmpAdminString (SIZE (0..49))
       MAX-ACCESS read-write
       STATUS current
       DESCRIPTION
           "Additional information element to send in ISDN Setup message.
Access: Instant.
AC INI-Param: ADDIEINSETUP"
       ::= {iE 1}



     iESendIEOnTG OBJECT-TYPE
       SYNTAX SnmpAdminString (SIZE (0..49))
       MAX-ACCESS read-write
       STATUS current
       DESCRIPTION
           "Configure trunk groups on which to send additional IE.
Access: Instant.
AC INI-Param: SENDIEONTG"
       ::= {iE 2}



     mlpp OBJECT IDENTIFIER ::= {digitalGW 29}


     mlppCallPriorityMode OBJECT-TYPE
       SYNTAX INTEGER {
                  disable(0)
,
                  mLPP(1)
,
                  emergency(2)

                  }
       MAX-ACCESS read-write
       STATUS current
       DESCRIPTION
           "Priority mode:
0-disable
1-MLPP
2-emergency.
Access: Instant.
AC INI-Param: CALLPRIORITYMODE"
       ::= {mlpp 1}



     mlppDefaultNamespace OBJECT-TYPE
       SYNTAX INTEGER {
                  dSN(1)
,
                  dOD(2)
,
                  dRSN(3)
,
                  uC(5)

                  }
       MAX-ACCESS read-write
       STATUS current
       DESCRIPTION
           "MLPP Default Namespace.
Access: Instant.
AC INI-Param: MLPPDEFAULTNAMESPACE"
       ::= {mlpp 2}



     mlppDefaultCallPriority OBJECT-TYPE
       SYNTAX SnmpAdminString (SIZE (0..29))
       MAX-ACCESS read-write
       STATUS current
       DESCRIPTION
           "SIP Default Call Priority.
Access: Instant.
AC INI-Param: SIPDEFAULTCALLPRIORITY"
       ::= {mlpp 3}



     mlppDiffServ OBJECT-TYPE
       SYNTAX Unsigned32 (0..63)
       MAX-ACCESS read-write
       STATUS current
       DESCRIPTION
           "DiffServ value for MLPP calls.
Access: Instant.
AC INI-Param: MLPPDIFFSERV"
       ::= {mlpp 4}



     mlppPreemptionToneDuration OBJECT-TYPE
       SYNTAX Unsigned32 (0..60)
       MAX-ACCESS read-write
       STATUS current
       DESCRIPTION
           "Preemption Tone Duration, 0-60 seconds.
Access: Instant.
AC INI-Param: PreemptionToneDuration"
       ::= {mlpp 5}



     mlppDefaultServiceDomain OBJECT-TYPE
       SYNTAX SnmpAdminString (SIZE (0..6))
       MAX-ACCESS read-write
       STATUS current
       DESCRIPTION
           "MLPP Default Service Domain String  (6 Hex Digits).
Access: Instant.
AC INI-Param: MLPPDefaultServiceDomain"
       ::= {mlpp 6}



     mlppNormalizedServiceDomain OBJECT-TYPE
       SYNTAX SnmpAdminString (SIZE (0..6))
       MAX-ACCESS read-write
       STATUS current
       DESCRIPTION
           "MLPP Normalized Service Domain String  (6 Hex Digits).
Access: Instant.
AC INI-Param: MLPPNormalizedServiceDomain"
       ::= {mlpp 7}



     mlppRoutineRTPDSCP OBJECT-TYPE
       SYNTAX Integer32 (-1..63)
       MAX-ACCESS read-write
       STATUS current
       DESCRIPTION
           "Defines the RTP DSCP for MLPP Routine call.
Access: Instant.
AC INI-Param: MLPPROUTINERTPDSCP"
       ::= {mlpp 8}



     mlppPriorityRTPDSCP OBJECT-TYPE
       SYNTAX Integer32 (-1..63)
       MAX-ACCESS read-write
       STATUS current
       DESCRIPTION
           "Defines the RTP DSCP for MLPP Priority call.
Access: Instant.
AC INI-Param: MLPPPRIORITYRTPDSCP"
       ::= {mlpp 9}



     mlppImmediateRTPDSCP OBJECT-TYPE
       SYNTAX Integer32 (-1..63)
       MAX-ACCESS read-write
       STATUS current
       DESCRIPTION
           "Defines the RTP DSCP for MLPP Immediate call.
Access: Instant.
AC INI-Param: MLPPIMMEDIATERTPDSCP"
       ::= {mlpp 10}



     mlppFlashRTPDSCP OBJECT-TYPE
       SYNTAX Integer32 (-1..63)
       MAX-ACCESS read-write
       STATUS current
       DESCRIPTION
           "Defines the RTP DSCP for MLPP Flash call.
Access: Instant.
AC INI-Param: MLPPFLASHRTPDSCP"
       ::= {mlpp 11}



     mlppFlashOverRTPDSCP OBJECT-TYPE
       SYNTAX Integer32 (-1..63)
       MAX-ACCESS read-write
       STATUS current
       DESCRIPTION
           "Defines the RTP DSCP for MLPP Flash-Override call.
Access: Instant.
AC INI-Param: MLPPFLASHOVERRTPDSCP"
       ::= {mlpp 12}



     mlppFlashOverOverRTPDSCP OBJECT-TYPE
       SYNTAX Integer32 (-1..63)
       MAX-ACCESS read-write
       STATUS current
       DESCRIPTION
           "Defines the RTP DSCP for MLPP Flash-Override-Override call.
Access: Instant.
AC INI-Param: MLPPFLASHOVEROVERRTPDSCP"
       ::= {mlpp 13}



     mlppE911Behavior OBJECT-TYPE
       SYNTAX INTEGER {
                  standardMode(0)
,
                  routineMode(1)

                  }
       MAX-ACCESS read-write
       STATUS current
       DESCRIPTION
           "Defines the MLPP E911 Preemption mode:
(0)-Standard Mode (ets calls will have the highest priority
and can preemt any mlpp call),
(1)-Treat as routine mode (ets calls are treated as routine
calls).
Access: Instant.
AC INI-Param: E911MLPPBEHAVIOR"
       ::= {mlpp 14}



     analogGW OBJECT IDENTIFIER ::= {common 4}


     analogGWEnableReversalPolarity OBJECT-TYPE
       SYNTAX INTEGER {
                  no(0)
,
                  yes(1)

                  }
       MAX-ACCESS read-write
       STATUS current
       DESCRIPTION
           "FXO: CONNECT/DISCONNECT calls upon detection of polarity signal.
FXS: generate the signal.
Access: Instant.
AC INI-Param: ENABLEREVERSALPOLARITY"
       ::= {analogGW 1}



     analogGWEnableCurrentDisconnect OBJECT-TYPE
       SYNTAX INTEGER {
                  no(0)
,
                  yes(1)

                  }
       MAX-ACCESS read-write
       STATUS current
       DESCRIPTION
           "Disconnect call upon detection of current disconnect signal.
Access: Instant.
AC INI-Param: ENABLECURRENTDISCONNECT"
       ::= {analogGW 2}



     analogGWRegretTime OBJECT-TYPE
       SYNTAX Unsigned32 (0..255)
       MAX-ACCESS read-write
       STATUS current
       DESCRIPTION
           "Time to wait between phone hang up and call termination.
Access: Instant.
AC INI-Param: REGRETTIME"
       ::= {analogGW 3}



     analogGWHotLineToneDuration OBJECT-TYPE
       SYNTAX Unsigned32 (0..60)
       MAX-ACCESS read-write
       STATUS current
       DESCRIPTION
           "Duration of played hotline tone, after the gateway seizes the
line in response to ringing.
Access: Instant.
AC INI-Param: HOTLINETONEDURATION"
       ::= {analogGW 4}



     -- ****************************************
     -- enableCallWaitingPerPort table declaration
     -- ****************************************
     enableCallWaitingPerPortTable OBJECT-TYPE
       SYNTAX SEQUENCE OF EnableCallWaitingPerPortEntry
       MAX-ACCESS not-accessible
       STATUS current
       DESCRIPTION
           ""
       ::= {analogGW 21}



     -- ****************************************
     -- enableCallWaitingPerPort table entry
     -- ****************************************
     enableCallWaitingPerPortEntry OBJECT-TYPE
       SYNTAX EnableCallWaitingPerPortEntry
       MAX-ACCESS not-accessible
       STATUS current
       DESCRIPTION
           "table"
       INDEX {enableCallWaitingPerPortIndex}
       ::= {enableCallWaitingPerPortTable 1}



     -- ****************************************
     -- enableCallWaitingPerPort TABLE
     -- ****************************************
     EnableCallWaitingPerPortEntry ::= SEQUENCE {
       enableCallWaitingPerPortIndex                   Unsigned32,
       enableCallWaitingPerPortIsUsed                  INTEGER,
       enableCallWaitingPerPortModule                  Unsigned32,
       enableCallWaitingPerPortPort                    Unsigned32,
       enableCallWaitingPerPortAction                  INTEGER,
       enableCallWaitingPerPortActionResult            INTEGER,
       enableCallWaitingPerPortEnable                  INTEGER
     }



     enableCallWaitingPerPortIndex OBJECT-TYPE
       SYNTAX Unsigned32 (0..23)
       MAX-ACCESS read-only
       STATUS current
       DESCRIPTION
           ".
AC INI-Param: CallWaitingPerPort_Index"
       ::= {enableCallWaitingPerPortEntry 1}



     enableCallWaitingPerPortIsUsed OBJECT-TYPE
       SYNTAX INTEGER {
                  no(0)
,
                  yes(1)

                  }
       MAX-ACCESS read-write
       STATUS current
       DESCRIPTION
           "Is this index used.
Access: Instant.
AC INI-Param: CallWaitingPerPort_IsUsed"
       ::= {enableCallWaitingPerPortEntry 2}



     enableCallWaitingPerPortModule OBJECT-TYPE
       SYNTAX Unsigned32 (0..255)
       MAX-ACCESS read-only
       STATUS current
       DESCRIPTION
           "module.
AC INI-Param: CallWaitingPerPort_Module"
       ::= {enableCallWaitingPerPortEntry 3}



     enableCallWaitingPerPortPort OBJECT-TYPE
       SYNTAX Unsigned32 (0..65535)
       MAX-ACCESS read-only
       STATUS current
       DESCRIPTION
           "port.
AC INI-Param: CallWaitingPerPort_Port"
       ::= {enableCallWaitingPerPortEntry 4}



     enableCallWaitingPerPortAction OBJECT-TYPE
       SYNTAX INTEGER {
                  developmentImpending(0)

                  }
       MAX-ACCESS read-only
       STATUS current
       DESCRIPTION
           "Development Impending.
AC INI-Param: N/A"
       ::= {enableCallWaitingPerPortEntry 5}



     enableCallWaitingPerPortActionResult OBJECT-TYPE
       SYNTAX INTEGER {
                  developmentImpending(0)

                  }
       MAX-ACCESS read-only
       STATUS current
       DESCRIPTION
           "Development Impending.
AC INI-Param: N/A"
       ::= {enableCallWaitingPerPortEntry 6}



     enableCallWaitingPerPortEnable OBJECT-TYPE
       SYNTAX INTEGER {
                  no(0)
,
                  yes(1)
,
                  valueNotSet(255)

                  }
       MAX-ACCESS read-write
       STATUS current
       DESCRIPTION
           "Enable.
Access: Instant.
AC INI-Param: CallWaitingPerPort_IsEnabled"
       ::= {enableCallWaitingPerPortEntry 7}



     fxs OBJECT IDENTIFIER ::= {analogGW 10}


     fxsCutThrough OBJECT-TYPE
       SYNTAX INTEGER {
                  disable(0)
,
                  enable(1)

                  }
       MAX-ACCESS read-write
       STATUS current
       DESCRIPTION
           "Enable call connection without On-Hook/Off-Hook process 'Cut-Through'.
Access: Instant.
AC INI-Param: CUTTHROUGH"
       ::= {fxs 1}



     fxsMeteringMode OBJECT-TYPE
       SYNTAX INTEGER {
                  disable(0)
,
                  routingTable(1)

                  }
       MAX-ACCESS read-write
       STATUS current
       DESCRIPTION
           "Method of automatic generation of payphone metering pulses.
Access: Instant.
AC INI-Param: PAYPHONEMETERINGMODE"
       ::= {fxs 2}



     fxsFXSOOSBehavior OBJECT-TYPE
       SYNTAX INTEGER {
                  none(0)
,
                  reorderTone(1)
,
                  polarityReversal(2)
,
                  currentDisconnect(4)

                  }
       MAX-ACCESS read-write
       STATUS current
       DESCRIPTION
           "FxsOosBehavior control how the fxs endpoints of a gateway,
will behave in case of Out of Service. 
OutofService state may be result of two scenarios:
a. EndPoint not configured in trunkgroup (Disabled)
b. runtime busy out situation

0: NONE - no special activity. Disabled endpoint not responses,
      bsyout endpoint responses as usual
1: Play ReOrder tone
2: Reverse Polarity
3: Play ReOrder tone and Reverse Polarity.
Access: Instant.
AC INI-Param: FXSOOSBEHAVIOR"
       ::= {fxs 3}



     fxsSetOOSOnRegistrationFail OBJECT-TYPE
       SYNTAX INTEGER {
                  disable(0)
,
                  enable(1)

                  }
       MAX-ACCESS read-write
       STATUS current
       DESCRIPTION
           "Should deactivate endpoint service on registration failure.
Access: Instant.
AC INI-Param: OOSONREGISTRATIONFAIL"
       ::= {fxs 4}



     -- ****************************************
     -- chargeCodes table declaration
     -- ****************************************
     chargeCodesTable OBJECT-TYPE
       SYNTAX SEQUENCE OF ChargeCodesEntry
       MAX-ACCESS not-accessible
       STATUS obsolete
       DESCRIPTION
           ""
       ::= {fxs 21}



     -- ****************************************
     -- chargeCodes table entry
     -- ****************************************
     chargeCodesEntry OBJECT-TYPE
       SYNTAX ChargeCodesEntry
       MAX-ACCESS not-accessible
       STATUS obsolete
       DESCRIPTION
           ""
       INDEX {chargeCodesIndex}
       ::= {chargeCodesTable 1}



     -- ****************************************
     -- chargeCodes TABLE
     -- ****************************************
     ChargeCodesEntry ::= SEQUENCE {
       chargeCodesIndex                                Unsigned32,
       chargeCodesRowStatus                            RowStatus,
       chargeCodesAction                               INTEGER,
       chargeCodesActionResult                         INTEGER,
       chargeCodesPeriod1EndTime                       Unsigned32,
       chargeCodesPeriod1PulseInterval                 Unsigned32,
       chargeCodesPeriod1PulsesOnAnswer                Unsigned32,
       chargeCodesPeriod2EndTime                       Unsigned32,
       chargeCodesPeriod2PulseInterval                 Unsigned32,
       chargeCodesPeriod2PulsesOnAnswer                Unsigned32,
       chargeCodesPeriod3EndTime                       Unsigned32,
       chargeCodesPeriod3PulseInterval                 Unsigned32,
       chargeCodesPeriod3PulsesOnAnswer                Unsigned32,
       chargeCodesPeriod4EndTime                       Unsigned32,
       chargeCodesPeriod4PulseInterval                 Unsigned32,
       chargeCodesPeriod4PulsesOnAnswer                Unsigned32
     }



     chargeCodesIndex OBJECT-TYPE
       SYNTAX Unsigned32 (0..24)
       MAX-ACCESS not-accessible
       STATUS obsolete
       DESCRIPTION
           "Charge code index.
AC INI-Param: ChargeCode_Index"
       ::= {chargeCodesEntry 1}



     chargeCodesRowStatus OBJECT-TYPE
       SYNTAX RowStatus
       MAX-ACCESS read-create
       STATUS obsolete
       DESCRIPTION
           "Row-Status Textual Conventions as defined in RFC 2579: Textual
Conventions for SMIv2.
AC INI-Param: N/A"
       ::= {chargeCodesEntry 2}



     chargeCodesAction OBJECT-TYPE
       SYNTAX INTEGER {
                  developmentImpending(0)

                  }
       MAX-ACCESS read-only
       STATUS obsolete
       DESCRIPTION
           "Development Impending.
AC INI-Param: N/A"
       ::= {chargeCodesEntry 3}



     chargeCodesActionResult OBJECT-TYPE
       SYNTAX INTEGER {
                  developmentImpending(0)

                  }
       MAX-ACCESS read-only
       STATUS obsolete
       DESCRIPTION
           "Development Impending.
AC INI-Param: N/A"
       ::= {chargeCodesEntry 4}



     chargeCodesPeriod1EndTime OBJECT-TYPE
       SYNTAX Unsigned32 (0..255)
       MAX-ACCESS read-create
       STATUS obsolete
       DESCRIPTION
           "
Access: Instant.
AC INI-Param: ChargeCode_EndTime1"
       ::= {chargeCodesEntry 5}



     chargeCodesPeriod1PulseInterval OBJECT-TYPE
       SYNTAX Unsigned32 (0..5000)
       MAX-ACCESS read-create
       STATUS obsolete
       DESCRIPTION
           "
Access: Instant.
AC INI-Param: ChargeCode_PulseInterval1"
       ::= {chargeCodesEntry 6}



     chargeCodesPeriod1PulsesOnAnswer OBJECT-TYPE
       SYNTAX Unsigned32 (0..255)
       MAX-ACCESS read-create
       STATUS obsolete
       DESCRIPTION
           "
Access: Instant.
AC INI-Param: ChargeCode_PulsesOnAnswer1"
       ::= {chargeCodesEntry 7}



     chargeCodesPeriod2EndTime OBJECT-TYPE
       SYNTAX Unsigned32 (0..255)
       MAX-ACCESS read-create
       STATUS obsolete
       DESCRIPTION
           "
Access: Instant.
AC INI-Param: ChargeCode_EndTime2"
       ::= {chargeCodesEntry 8}



     chargeCodesPeriod2PulseInterval OBJECT-TYPE
       SYNTAX Unsigned32 (0..5000)
       MAX-ACCESS read-create
       STATUS obsolete
       DESCRIPTION
           "
Access: Instant.
AC INI-Param: ChargeCode_PulseInterval2"
       ::= {chargeCodesEntry 9}



     chargeCodesPeriod2PulsesOnAnswer OBJECT-TYPE
       SYNTAX Unsigned32 (0..255)
       MAX-ACCESS read-create
       STATUS obsolete
       DESCRIPTION
           "
Access: Instant.
AC INI-Param: ChargeCode_PulsesOnAnswer2"
       ::= {chargeCodesEntry 10}



     chargeCodesPeriod3EndTime OBJECT-TYPE
       SYNTAX Unsigned32 (0..255)
       MAX-ACCESS read-create
       STATUS obsolete
       DESCRIPTION
           "
Access: Instant.
AC INI-Param: ChargeCode_EndTime3"
       ::= {chargeCodesEntry 11}



     chargeCodesPeriod3PulseInterval OBJECT-TYPE
       SYNTAX Unsigned32 (0..5000)
       MAX-ACCESS read-create
       STATUS obsolete
       DESCRIPTION
           "
Access: Instant.
AC INI-Param: ChargeCode_PulseInterval3"
       ::= {chargeCodesEntry 12}



     chargeCodesPeriod3PulsesOnAnswer OBJECT-TYPE
       SYNTAX Unsigned32 (0..255)
       MAX-ACCESS read-create
       STATUS obsolete
       DESCRIPTION
           "
Access: Instant.
AC INI-Param: ChargeCode_PulsesOnAnswer3"
       ::= {chargeCodesEntry 13}



     chargeCodesPeriod4EndTime OBJECT-TYPE
       SYNTAX Unsigned32 (0..255)
       MAX-ACCESS read-create
       STATUS obsolete
       DESCRIPTION
           "
Access: Instant.
AC INI-Param: ChargeCode_EndTime4"
       ::= {chargeCodesEntry 14}



     chargeCodesPeriod4PulseInterval OBJECT-TYPE
       SYNTAX Unsigned32 (0..5000)
       MAX-ACCESS read-create
       STATUS obsolete
       DESCRIPTION
           "
Access: Instant.
AC INI-Param: ChargeCode_PulseInterval4"
       ::= {chargeCodesEntry 15}



     chargeCodesPeriod4PulsesOnAnswer OBJECT-TYPE
       SYNTAX Unsigned32 (0..255)
       MAX-ACCESS read-create
       STATUS obsolete
       DESCRIPTION
           "
Access: Instant.
AC INI-Param: ChargeCode_PulsesOnAnswer4"
       ::= {chargeCodesEntry 16}



     -- ****************************************
     -- toneIndex table declaration
     -- ****************************************
     toneIndexTable OBJECT-TYPE
       SYNTAX SEQUENCE OF ToneIndexEntry
       MAX-ACCESS not-accessible
       STATUS current
       DESCRIPTION
           ""
       ::= {fxs 22}



     -- ****************************************
     -- toneIndex table entry
     -- ****************************************
     toneIndexEntry OBJECT-TYPE
       SYNTAX ToneIndexEntry
       MAX-ACCESS not-accessible
       STATUS current
       DESCRIPTION
           ""
       INDEX {toneIndexIndex}
       ::= {toneIndexTable 1}



     -- ****************************************
     -- toneIndex TABLE
     -- ****************************************
     ToneIndexEntry ::= SEQUENCE {
       toneIndexIndex                                  Unsigned32,
       toneIndexRowStatus                              RowStatus,
       toneIndexAction                                 INTEGER,
       toneIndexActionResult                           INTEGER,
       toneIndexFXSPortFirst                           Unsigned32,
       toneIndexFXSPortLast                            Unsigned32,
       toneIndexSourcePrefix                           SnmpAdminString,
       toneIndexPriorityIndex                          Unsigned32
     }



     toneIndexIndex OBJECT-TYPE
       SYNTAX Unsigned32 (0..23)
       MAX-ACCESS not-accessible
       STATUS current
       DESCRIPTION
           "Charge code index.
AC INI-Param: ToneIndex_Index"
       ::= {toneIndexEntry 1}



     toneIndexRowStatus OBJECT-TYPE
       SYNTAX RowStatus
       MAX-ACCESS read-create
       STATUS current
       DESCRIPTION
           "Row-Status Textual Conventions as defined in RFC 2579: Textual
Conventions for SMIv2.
AC INI-Param: N/A"
       ::= {toneIndexEntry 2}



     toneIndexAction OBJECT-TYPE
       SYNTAX INTEGER {
                  developmentImpending(0)

                  }
       MAX-ACCESS read-only
       STATUS current
       DESCRIPTION
           "Development Impending.
AC INI-Param: N/A"
       ::= {toneIndexEntry 3}



     toneIndexActionResult OBJECT-TYPE
       SYNTAX INTEGER {
                  developmentImpending(0)

                  }
       MAX-ACCESS read-only
       STATUS current
       DESCRIPTION
           "Development Impending.
AC INI-Param: N/A"
       ::= {toneIndexEntry 4}



     toneIndexFXSPortFirst OBJECT-TYPE
       SYNTAX Unsigned32 (1..24)
       MAX-ACCESS read-create
       STATUS current
       DESCRIPTION
           "Staring Range of FXS Port.
Access: Instant.
AC INI-Param: ToneIndex_FXSPort_First"
       ::= {toneIndexEntry 5}



     toneIndexFXSPortLast OBJECT-TYPE
       SYNTAX Unsigned32 (1..24)
       MAX-ACCESS read-create
       STATUS current
       DESCRIPTION
           "End Range of FXS Port.
Access: Instant.
AC INI-Param: ToneIndex_FXSPort_Last"
       ::= {toneIndexEntry 6}



     toneIndexSourcePrefix OBJECT-TYPE
       SYNTAX SnmpAdminString (SIZE (0..23))
       MAX-ACCESS read-create
       STATUS current
       DESCRIPTION
           "Source Prefix.
Access: Instant.
AC INI-Param: ToneIndex_SourcePrefix"
       ::= {toneIndexEntry 7}



     toneIndexPriorityIndex OBJECT-TYPE
       SYNTAX Unsigned32 (0..16)
       MAX-ACCESS read-create
       STATUS current
       DESCRIPTION
           "Index used for distinctive ringing and call waiting tones.
Access: Instant.
AC INI-Param: ToneIndex_PriorityIndex"
       ::= {toneIndexEntry 8}



     -- ****************************************
     -- rejectAnonymousCallPerPort table declaration
     -- ****************************************
     rejectAnonymousCallPerPortTable OBJECT-TYPE
       SYNTAX SEQUENCE OF RejectAnonymousCallPerPortEntry
       MAX-ACCESS not-accessible
       STATUS current
       DESCRIPTION
           ""
       ::= {fxs 23}



     -- ****************************************
     -- rejectAnonymousCallPerPort table entry
     -- ****************************************
     rejectAnonymousCallPerPortEntry OBJECT-TYPE
       SYNTAX RejectAnonymousCallPerPortEntry
       MAX-ACCESS not-accessible
       STATUS current
       DESCRIPTION
           ""
       INDEX {rejectAnonymousCallPerPortIndex}
       ::= {rejectAnonymousCallPerPortTable 1}



     -- ****************************************
     -- rejectAnonymousCallPerPort TABLE
     -- ****************************************
     RejectAnonymousCallPerPortEntry ::= SEQUENCE {
       rejectAnonymousCallPerPortIndex                 Unsigned32,
       rejectAnonymousCallPerPortIsUsed                INTEGER,
       rejectAnonymousCallPerPortAction                INTEGER,
       rejectAnonymousCallPerPortActionResult          INTEGER,
       rejectAnonymousCallPerPortEnable                INTEGER,
       rejectAnonymousCallPerPortModule                Unsigned32,
       rejectAnonymousCallPerPortPort                  Unsigned32,
       rejectAnonymousCallPerPortPortType              SnmpAdminString
     }



     rejectAnonymousCallPerPortIndex OBJECT-TYPE
       SYNTAX Unsigned32 (0..23)
       MAX-ACCESS not-accessible
       STATUS current
       DESCRIPTION
           "Reject anonymous call per port index.
AC INI-Param: RejectAnonymousCallPerPort_Index"
       ::= {rejectAnonymousCallPerPortEntry 1}



     rejectAnonymousCallPerPortIsUsed OBJECT-TYPE
       SYNTAX INTEGER {
                  no(0)
,
                  yes(1)

                  }
       MAX-ACCESS read-write
       STATUS current
       DESCRIPTION
           "Is Used.
Access: Instant.
AC INI-Param: RejectAnonymousCallPerPort_IsUsed"
       ::= {rejectAnonymousCallPerPortEntry 2}



     rejectAnonymousCallPerPortAction OBJECT-TYPE
       SYNTAX INTEGER {
                  developmentImpending(0)

                  }
       MAX-ACCESS read-only
       STATUS current
       DESCRIPTION
           "Development Impending.
AC INI-Param: RejectAnonymousCallPerPort_Action"
       ::= {rejectAnonymousCallPerPortEntry 3}



     rejectAnonymousCallPerPortActionResult OBJECT-TYPE
       SYNTAX INTEGER {
                  developmentImpending(0)

                  }
       MAX-ACCESS read-only
       STATUS current
       DESCRIPTION
           "Development Impending.
AC INI-Param: RejectAnonymousCallPerPort_ActionRes"
       ::= {rejectAnonymousCallPerPortEntry 4}



     rejectAnonymousCallPerPortEnable OBJECT-TYPE
       SYNTAX INTEGER {
                  disable(0)
,
                  enable(1)

                  }
       MAX-ACCESS read-write
       STATUS current
       DESCRIPTION
           "Reject Calls Enable.
Access: Instant.
AC INI-Param: RejectAnonymousCallPerPort_Enable"
       ::= {rejectAnonymousCallPerPortEntry 5}



     rejectAnonymousCallPerPortModule OBJECT-TYPE
       SYNTAX Unsigned32 (0..255)
       MAX-ACCESS read-only
       STATUS current
       DESCRIPTION
           "Module.
AC INI-Param: RejectAnonymousCallPerPort_Module"
       ::= {rejectAnonymousCallPerPortEntry 6}



     rejectAnonymousCallPerPortPort OBJECT-TYPE
       SYNTAX Unsigned32 (0..65535)
       MAX-ACCESS read-only
       STATUS current
       DESCRIPTION
           "Port.
AC INI-Param: RejectAnonymousCallPerPort_Port"
       ::= {rejectAnonymousCallPerPortEntry 7}



     rejectAnonymousCallPerPortPortType OBJECT-TYPE
       SYNTAX SnmpAdminString (SIZE (0..10))
       MAX-ACCESS read-only
       STATUS current
       DESCRIPTION
           "PortType.
AC INI-Param: RejectAnonymousCallPerPort_PortType"
       ::= {rejectAnonymousCallPerPortEntry 8}



     fxo OBJECT IDENTIFIER ::= {analogGW 11}


     fxoIsTwoStageDial OBJECT-TYPE
       SYNTAX INTEGER {
                  oneStage(0)
,
                  twoStages(1)

                  }
       MAX-ACCESS read-write
       STATUS current
       DESCRIPTION
           "Dialing Mode - One-Stage (PBX Pass-thru) or Two-Stage.
Access: Instant.
AC INI-Param: ISTWOSTAGEDIAL"
       ::= {fxo 1}



     fxoWaitForDialTone OBJECT-TYPE
       SYNTAX INTEGER {
                  no(0)
,
                  yes(1)

                  }
       MAX-ACCESS read-write
       STATUS current
       DESCRIPTION
           "Wait for dial tone before initiating an outgoing call to PBX/PSTN
(FXO one-stage dialing mode).
Access: Instant.
AC INI-Param: ISWAITFORDIALTONE"
       ::= {fxo 2}



     fxoWaitForDialTime OBJECT-TYPE
       SYNTAX Unsigned32 (0..20000000)
       MAX-ACCESS read-write
       STATUS current
       DESCRIPTION
           "Time delay between seizing the line and start dialing (if ISWAITFORDIALTONE
disabled) or after hookflash before dialing.
Access: Instant.
AC INI-Param: WAITFORDIALTIME"
       ::= {fxo 3}



     fxoBetweenRingTime OBJECT-TYPE
       SYNTAX Unsigned32 (0..20000000)
       MAX-ACCESS read-write
       STATUS current
       DESCRIPTION
           "Timeout for releasing FXO to IP call, if FXO port doesn't detect
ringing signal for this timeout.
Access: Instant.
AC INI-Param: FXOBETWEENRINGTIME"
       ::= {fxo 4}



     fxoEnableVoiceDetection OBJECT-TYPE
       SYNTAX INTEGER {
                  no(0)
,
                  yes(1)

                  }
       MAX-ACCESS read-write
       STATUS current
       DESCRIPTION
           "On FXO GWs enables sending of connect/200 OK message on speech/fax/modem
detection [default 0]. In order to activate feature
DSPVersionTemplateNumber should be 2 or 3.
Access: Instant.
AC INI-Param: ENABLEVOICEDETECTION"
       ::= {fxo 5}



     fxoRingsBeforeCallerID OBJECT-TYPE
       SYNTAX Unsigned32 (0..2)
       MAX-ACCESS read-write
       STATUS current
       DESCRIPTION
           "Number of rings after which the Caller ID is detected.
Access: Instant.
AC INI-Param: RINGSBEFORECALLERID"
       ::= {fxo 6}



     fxoGuardTimeBetweenCalls OBJECT-TYPE
       SYNTAX Unsigned32 (0..10)
       MAX-ACCESS read-write
       STATUS current
       DESCRIPTION
           "Only for FXO: the time between the time that the EP execute
OnHook, to the time that this EP is capable to except new IP2TEL
call 
(and execute OfHook).
Access: Instant.
AC INI-Param: GUARDTIMEBETWEENCALLS"
       ::= {fxo 7}



     fxoAutoDialPlayBusyTone OBJECT-TYPE
       SYNTAX INTEGER {
                  disable(0)
,
                  enable(1)

                  }
       MAX-ACCESS read-write
       STATUS current
       DESCRIPTION
           "Only for FXO, Tel2IP calls: If enable (1) - On receiving release,
if autodial is used, the FXO seize the line and play Busy/Reorder
tone toward the PSTN for Reorder-time duration.
.
Access: Instant.
AC INI-Param: FXOAutoDialPlayBusyTone"
       ::= {fxo 8}



     fxoRingTimeout OBJECT-TYPE
       SYNTAX Unsigned32 (0..50)
       MAX-ACCESS read-write
       STATUS current
       DESCRIPTION
           "Defines the delay (in 100 msec) for generating INVITE after
RING_START detection. The valid range is 0 to 50.
Access: Instant.
AC INI-Param: FXORINGTIMEOUT"
       ::= {fxo 9}



     dialing OBJECT IDENTIFIER ::= {analogGW 12}


     dialingMaxDigits OBJECT-TYPE
       SYNTAX Unsigned32 (1..49)
       MAX-ACCESS read-write
       STATUS current
       DESCRIPTION
           "Maximum number of digits before dialing starts.
Access: Instant.
AC INI-Param: MAXDIGITS"
       ::= {dialing 1}



     dialingTimeBetweenDigits OBJECT-TYPE
       SYNTAX Unsigned32 (1..10)
       MAX-ACCESS read-write
       STATUS current
       DESCRIPTION
           "Timeout in seconds between dialed digits.
Access: Instant.
AC INI-Param: TIMEBETWEENDIGITS"
       ::= {dialing 2}



     dialingIsSpecialDigits OBJECT-TYPE
       SYNTAX INTEGER {
                  no(0)
,
                  yes(1)

                  }
       MAX-ACCESS read-write
       STATUS current
       DESCRIPTION
           "When disabled, pressing special digits (* or #) will terminate
digit collection. When enabled, special digits can be received
as part of the dialed number or Endpoint phone number.
Access: Instant.
AC INI-Param: ISSPECIALDIGITS"
       ::= {dialing 3}



     dialingDigitMapping OBJECT-TYPE
       SYNTAX SnmpAdminString (SIZE (0..152))
       MAX-ACCESS read-write
       STATUS current
       DESCRIPTION
           "The digit map patterns separated by a vertical bar (|), as defined
in the MEGACO RFC.
Access: Instant.
AC INI-Param: DIGITMAPPING"
       ::= {dialing 4}



     dialingEnableDigitDelivery OBJECT-TYPE
       SYNTAX INTEGER {
                  disable(0)
,
                  enable(1)

                  }
       MAX-ACCESS read-write
       STATUS current
       DESCRIPTION
           "Enable automatic digit delivery to Tel side after line is off-hooked
or seized.
Access: Instant.
AC INI-Param: ENABLEDIGITDELIVERY"
       ::= {dialing 5}



     dialingDialPlanIndex OBJECT-TYPE
       SYNTAX Integer32 (-1..7)
       MAX-ACCESS read-write
       STATUS current
       DESCRIPTION
           "Defines the plan index to be used from the external Dial Plan
file.
Access: Instant.
AC INI-Param: DIALPLANINDEX"
       ::= {dialing 6}



     -- ****************************************
     -- autoDial table declaration
     -- ****************************************
     autoDialTable OBJECT-TYPE
       SYNTAX SEQUENCE OF AutoDialEntry
       MAX-ACCESS not-accessible
       STATUS current
       DESCRIPTION
           ""
       ::= {dialing 21}



     -- ****************************************
     -- autoDial table entry
     -- ****************************************
     autoDialEntry OBJECT-TYPE
       SYNTAX AutoDialEntry
       MAX-ACCESS not-accessible
       STATUS current
       DESCRIPTION
           ""
       INDEX {autoDialIndex}
       ::= {autoDialTable 1}



     -- ****************************************
     -- autoDial TABLE
     -- ****************************************
     AutoDialEntry ::= SEQUENCE {
       autoDialIndex                                   Unsigned32,
       autoDialIsUsed                                  INTEGER,
       autoDialAction                                  INTEGER,
       autoDialActionResult                            INTEGER,
       autoDialDestPhoneNumber                         SnmpAdminString,
       autoDialType                                    INTEGER,
       autoDialModule                                  Unsigned32,
       autoDialPort                                    Unsigned32
     }



     autoDialIndex OBJECT-TYPE
       SYNTAX Unsigned32 (0..23)
       MAX-ACCESS read-only
       STATUS current
       DESCRIPTION
           "Entry number, starting at 0.
AC INI-Param: TargetOfChannel_Index"
       ::= {autoDialEntry 1}



     autoDialIsUsed OBJECT-TYPE
       SYNTAX INTEGER {
                  no(0)
,
                  yes(1)

                  }
       MAX-ACCESS read-write
       STATUS current
       DESCRIPTION
           "Is this index used.
AC INI-Param: TargetOfChannel_IsUsed "
       ::= {autoDialEntry 2}



     autoDialAction OBJECT-TYPE
       SYNTAX INTEGER {
                  developmentImpending(0)

                  }
       MAX-ACCESS read-only
       STATUS current
       DESCRIPTION
           "Development Impending.
AC INI-Param: N/A"
       ::= {autoDialEntry 3}



     autoDialActionResult OBJECT-TYPE
       SYNTAX INTEGER {
                  developmentImpending(0)

                  }
       MAX-ACCESS read-only
       STATUS current
       DESCRIPTION
           "Development Impending.
AC INI-Param: N/A"
       ::= {autoDialEntry 4}



     autoDialDestPhoneNumber OBJECT-TYPE
       SYNTAX SnmpAdminString (SIZE (0..15))
       MAX-ACCESS read-write
       STATUS current
       DESCRIPTION
           "
Access: Instant.
AC INI-Param: TargetOfChannel_Destination"
       ::= {autoDialEntry 5}



     autoDialType OBJECT-TYPE
       SYNTAX INTEGER {
                  none(0)
,
                  autoDial(1)
,
                  delayHotLine(2)

                  }
       MAX-ACCESS read-write
       STATUS current
       DESCRIPTION
           "Choose auto dial type.
Access: Instant.
AC INI-Param: TargetOfChannel_Type"
       ::= {autoDialEntry 6}



     autoDialModule OBJECT-TYPE
       SYNTAX Unsigned32 (0..255)
       MAX-ACCESS read-only
       STATUS current
       DESCRIPTION
           "Channels Module.
AC INI-Param: TargetOfChannel_Module"
       ::= {autoDialEntry 7}



     autoDialPort OBJECT-TYPE
       SYNTAX Unsigned32 (0..65535)
       MAX-ACCESS read-only
       STATUS current
       DESCRIPTION
           "Channels Port.
AC INI-Param: TargetOfChannel_Port"
       ::= {autoDialEntry 8}



     callerID OBJECT IDENTIFIER ::= {analogGW 13}


     callerIDEnable OBJECT-TYPE
       SYNTAX INTEGER {
                  no(0)
,
                  yes(1)

                  }
       MAX-ACCESS read-write
       STATUS current
       DESCRIPTION
           "FXS:generate CallerId siganls during ringing FXO:collect CallerId
and use it in Setup message.
Access: Instant.
AC INI-Param: ENABLECALLERID"
       ::= {callerID 1}



     -- ****************************************
     -- callerDisplay table declaration
     -- ****************************************
     callerDisplayTable OBJECT-TYPE
       SYNTAX SEQUENCE OF CallerDisplayEntry
       MAX-ACCESS not-accessible
       STATUS current
       DESCRIPTION
           ""
       ::= {callerID 21}



     -- ****************************************
     -- callerDisplay table entry
     -- ****************************************
     callerDisplayEntry OBJECT-TYPE
       SYNTAX CallerDisplayEntry
       MAX-ACCESS not-accessible
       STATUS current
       DESCRIPTION
           ""
       INDEX {callerDisplayIndex}
       ::= {callerDisplayTable 1}



     -- ****************************************
     -- callerDisplay TABLE
     -- ****************************************
     CallerDisplayEntry ::= SEQUENCE {
       callerDisplayIndex                              Unsigned32,
       callerDisplayIsUsed                             INTEGER,
       callerDisplayAction                             INTEGER,
       callerDisplayActionResult                       INTEGER,
       callerDisplayCallerDisplay                      SnmpAdminString,
       callerDisplayRestriction                        INTEGER,
       callerDisplayModule                             Unsigned32,
       callerDisplayPort                               Unsigned32
     }



     callerDisplayIndex OBJECT-TYPE
       SYNTAX Unsigned32 (0..23)
       MAX-ACCESS read-only
       STATUS current
       DESCRIPTION
           "Entry number, starting at 0.
AC INI-Param: CallerDisplayInfo_Index"
       ::= {callerDisplayEntry 1}



     callerDisplayIsUsed OBJECT-TYPE
       SYNTAX INTEGER {
                  no(0)
,
                  yes(1)

                  }
       MAX-ACCESS read-write
       STATUS current
       DESCRIPTION
           "Is this index used.
AC INI-Param: CallerDisplayInfo_IsUsed"
       ::= {callerDisplayEntry 2}



     callerDisplayAction OBJECT-TYPE
       SYNTAX INTEGER {
                  developmentImpending(0)

                  }
       MAX-ACCESS read-only
       STATUS current
       DESCRIPTION
           "Development Impending.
AC INI-Param: N/A"
       ::= {callerDisplayEntry 3}



     callerDisplayActionResult OBJECT-TYPE
       SYNTAX INTEGER {
                  developmentImpending(0)

                  }
       MAX-ACCESS read-only
       STATUS current
       DESCRIPTION
           "Development Impending.
AC INI-Param: N/A"
       ::= {callerDisplayEntry 4}



     callerDisplayCallerDisplay OBJECT-TYPE
       SYNTAX SnmpAdminString (SIZE (0..20))
       MAX-ACCESS read-write
       STATUS current
       DESCRIPTION
           "Caller Name.
Access: Instant.
AC INI-Param: CallerDisplayInfo_DisplayString"
       ::= {callerDisplayEntry 5}



     callerDisplayRestriction OBJECT-TYPE
       SYNTAX INTEGER {
                  notBlocked(0)
,
                  blocked(1)

                  }
       MAX-ACCESS read-write
       STATUS current
       DESCRIPTION
           "Restriction.
Access: Instant.
AC INI-Param: CallerDisplayInfo_IsCidRestricted"
       ::= {callerDisplayEntry 6}



     callerDisplayModule OBJECT-TYPE
       SYNTAX Unsigned32 (0..255)
       MAX-ACCESS read-only
       STATUS current
       DESCRIPTION
           "Channels Module.
AC INI-Param: CallerDisplayInfo_Module"
       ::= {callerDisplayEntry 7}



     callerDisplayPort OBJECT-TYPE
       SYNTAX Unsigned32 (0..65535)
       MAX-ACCESS read-only
       STATUS current
       DESCRIPTION
           "Channels Port.
AC INI-Param: CallerDisplayInfo_Port"
       ::= {callerDisplayEntry 8}



     -- ****************************************
     -- callerIDperPort table declaration
     -- ****************************************
     callerIDperPortTable OBJECT-TYPE
       SYNTAX SEQUENCE OF CallerIDperPortEntry
       MAX-ACCESS not-accessible
       STATUS current
       DESCRIPTION
           ""
       ::= {callerID 22}



     -- ****************************************
     -- callerIDperPort table entry
     -- ****************************************
     callerIDperPortEntry OBJECT-TYPE
       SYNTAX CallerIDperPortEntry
       MAX-ACCESS not-accessible
       STATUS current
       DESCRIPTION
           ""
       INDEX {callerIDperPortIndex}
       ::= {callerIDperPortTable 1}



     -- ****************************************
     -- callerIDperPort TABLE
     -- ****************************************
     CallerIDperPortEntry ::= SEQUENCE {
       callerIDperPortIndex                            Unsigned32,
       callerIDperPortIsUsed                           INTEGER,
       callerIDperPortAction                           INTEGER,
       callerIDperPortActionResult                     INTEGER,
       callerIDperPortEnable                           INTEGER,
       callerIDperPortModule                           Unsigned32,
       callerIDperPortPort                             Unsigned32
     }



     callerIDperPortIndex OBJECT-TYPE
       SYNTAX Unsigned32 (0..23)
       MAX-ACCESS read-only
       STATUS current
       DESCRIPTION
           ".
AC INI-Param: EnableCallerId_Index"
       ::= {callerIDperPortEntry 1}



     callerIDperPortIsUsed OBJECT-TYPE
       SYNTAX INTEGER {
                  no(0)
,
                  yes(1)

                  }
       MAX-ACCESS read-write
       STATUS current
       DESCRIPTION
           "Is this index used.
Access: Offline.
AC INI-Param: EnableCallerId_IsUsed"
       ::= {callerIDperPortEntry 2}



     callerIDperPortAction OBJECT-TYPE
       SYNTAX INTEGER {
                  developmentImpending(0)

                  }
       MAX-ACCESS read-only
       STATUS current
       DESCRIPTION
           "Development Impending.
AC INI-Param: N/A"
       ::= {callerIDperPortEntry 3}



     callerIDperPortActionResult OBJECT-TYPE
       SYNTAX INTEGER {
                  developmentImpending(0)

                  }
       MAX-ACCESS read-only
       STATUS current
       DESCRIPTION
           "Development Impending.
AC INI-Param: N/A"
       ::= {callerIDperPortEntry 4}



     callerIDperPortEnable OBJECT-TYPE
       SYNTAX INTEGER {
                  disable(0)
,
                  enable(1)
,
                  valueNotSet(255)

                  }
       MAX-ACCESS read-write
       STATUS current
       DESCRIPTION
           "Enable.
Access: Instant.
AC INI-Param: EnableCallerId_IsEnabled"
       ::= {callerIDperPortEntry 5}



     callerIDperPortModule OBJECT-TYPE
       SYNTAX Unsigned32 (0..255)
       MAX-ACCESS read-only
       STATUS current
       DESCRIPTION
           "Channels Module.
AC INI-Param: EnableCallerId_Module"
       ::= {callerIDperPortEntry 6}



     callerIDperPortPort OBJECT-TYPE
       SYNTAX Unsigned32 (0..65535)
       MAX-ACCESS read-only
       STATUS current
       DESCRIPTION
           "Channels Port.
AC INI-Param: EnableCallerId_Port"
       ::= {callerIDperPortEntry 7}



     keypadFeatures OBJECT IDENTIFIER ::= {analogGW 14}


     keypadFeaturesCFUncond OBJECT-TYPE
       SYNTAX SnmpAdminString (SIZE (0..15))
       MAX-ACCESS read-write
       STATUS current
       DESCRIPTION
           "Keying sequence for activating immediate Call Forward.
Access: Instant.
AC INI-Param: KEYCFUNCOND"
       ::= {keypadFeatures 1}



     keypadFeaturesCFDeact OBJECT-TYPE
       SYNTAX SnmpAdminString (SIZE (0..15))
       MAX-ACCESS read-write
       STATUS current
       DESCRIPTION
           "Keying sequence for deactivating Call Forward.
Access: Instant.
AC INI-Param: KEYCFDEACT"
       ::= {keypadFeatures 2}



     keypadFeaturesCFNoAnswer OBJECT-TYPE
       SYNTAX SnmpAdminString (SIZE (0..15))
       MAX-ACCESS read-write
       STATUS current
       DESCRIPTION
           "Keying sequence for activating Call Forward on no answer.
Access: Instant.
AC INI-Param: KEYCFNOANSWER"
       ::= {keypadFeatures 3}



     keypadFeaturesCFBusy OBJECT-TYPE
       SYNTAX SnmpAdminString (SIZE (0..15))
       MAX-ACCESS read-write
       STATUS current
       DESCRIPTION
           "Keying sequence for activating Call Forward on busy.
Access: Instant.
AC INI-Param: KEYCFBUSY"
       ::= {keypadFeatures 4}



     keypadFeaturesCLIR OBJECT-TYPE
       SYNTAX SnmpAdminString (SIZE (0..15))
       MAX-ACCESS read-write
       STATUS current
       DESCRIPTION
           "Keying sequence for activating restricted Caller ID.
Access: Instant.
AC INI-Param: KEYCLIR"
       ::= {keypadFeatures 5}



     keypadFeaturesCLIRDeact OBJECT-TYPE
       SYNTAX SnmpAdminString (SIZE (0..15))
       MAX-ACCESS read-write
       STATUS current
       DESCRIPTION
           "Keying sequence for deactivating restricted Caller ID.
Access: Instant.
AC INI-Param: KEYCLIRDEACT"
       ::= {keypadFeatures 6}



     keypadFeaturesHotLine OBJECT-TYPE
       SYNTAX SnmpAdminString (SIZE (0..15))
       MAX-ACCESS read-write
       STATUS current
       DESCRIPTION
           "Keying sequence for activating delayed Hot-line.
Access: Instant.
AC INI-Param: KEYHOTLINE"
       ::= {keypadFeatures 7}



     keypadFeaturesHotLineDeact OBJECT-TYPE
       SYNTAX SnmpAdminString (SIZE (0..15))
       MAX-ACCESS read-write
       STATUS current
       DESCRIPTION
           "Keying sequence for deactivating delayed Hot-line.
Access: Instant.
AC INI-Param: KEYHOTLINEDEACT"
       ::= {keypadFeatures 8}



     keypadFeaturesCFBusyOrNoAnswer OBJECT-TYPE
       SYNTAX SnmpAdminString (SIZE (0..15))
       MAX-ACCESS read-write
       STATUS current
       DESCRIPTION
           "Keying sequence for activating Call Forward on busy or no answer.
Access: Instant.
AC INI-Param: KEYCFBUSYORNOANSWER"
       ::= {keypadFeatures 9}



     keypadFeaturesCFDoNotDisturb OBJECT-TYPE
       SYNTAX SnmpAdminString (SIZE (0..15))
       MAX-ACCESS read-write
       STATUS current
       DESCRIPTION
           "Keying sequence for activating Do Not Disturb.
Access: Instant.
AC INI-Param: KEYCFDONOTDISTURB"
       ::= {keypadFeatures 10}



     keypadFeaturesBlindTransfer OBJECT-TYPE
       SYNTAX SnmpAdminString (SIZE (0..15))
       MAX-ACCESS read-write
       STATUS current
       DESCRIPTION
           "Keying sequence for performing blind transfer.
Access: Instant.
AC INI-Param: KEYBLINDTRANSFER"
       ::= {keypadFeatures 11}



     keypadFeaturesKeypadFeaturesCW OBJECT-TYPE
       SYNTAX SnmpAdminString (SIZE (0..15))
       MAX-ACCESS read-write
       STATUS current
       DESCRIPTION
           "Keying sequence for activating call waiting.
Access: Instant.
AC INI-Param: KEYCALLWAITINGDEACT"
       ::= {keypadFeatures 12}



     keypadFeaturesKeypadFeaturesCWDeact OBJECT-TYPE
       SYNTAX SnmpAdminString (SIZE (0..15))
       MAX-ACCESS read-write
       STATUS current
       DESCRIPTION
           "Keying sequence for deactivating call waiting.
Access: Instant.
AC INI-Param: KEYCALLWAITINGDEACT"
       ::= {keypadFeatures 13}



     keypadFeaturesRejectAnonymousCall OBJECT-TYPE
       SYNTAX SnmpAdminString (SIZE (0..15))
       MAX-ACCESS read-write
       STATUS current
       DESCRIPTION
           "Key pad pattern for rejecting anonymous call.
Access: Instant.
AC INI-Param: KeyRejectAnonymousCall"
       ::= {keypadFeatures 14}



     keypadFeaturesRejectAnonymousCallDeact OBJECT-TYPE
       SYNTAX SnmpAdminString (SIZE (0..15))
       MAX-ACCESS read-write
       STATUS current
       DESCRIPTION
           "Key pad pattern for accepting anonymous call.
Access: Instant.
AC INI-Param: KeyRejectAnonymousCallDeact"
       ::= {keypadFeatures 15}



     portName OBJECT IDENTIFIER ::= {analogGW 15}


     -- ****************************************
     -- names table declaration
     -- ****************************************
     namesTable OBJECT-TYPE
       SYNTAX SEQUENCE OF NamesEntry
       MAX-ACCESS not-accessible
       STATUS current
       DESCRIPTION
           ""
       ::= {portName 21}



     -- ****************************************
     -- names table entry
     -- ****************************************
     namesEntry OBJECT-TYPE
       SYNTAX NamesEntry
       MAX-ACCESS not-accessible
       STATUS current
       DESCRIPTION
           ""
       INDEX {namesIndex}
       ::= {namesTable 1}



     -- ****************************************
     -- names TABLE
     -- ****************************************
     NamesEntry ::= SEQUENCE {
       namesIndex                                      Unsigned32,
       namesIsUsed                                     INTEGER,
       namesAction                                     INTEGER,
       namesActionResult                               INTEGER,
       namesPortName                                   SnmpAdminString,
       namesModule                                     Unsigned32,
       namesPort                                       Unsigned32
     }



     namesIndex OBJECT-TYPE
       SYNTAX Unsigned32 (0..23)
       MAX-ACCESS read-only
       STATUS current
       DESCRIPTION
           "Entry number, starting at 0.
AC INI-Param: PortName_Index"
       ::= {namesEntry 1}



     namesIsUsed OBJECT-TYPE
       SYNTAX INTEGER {
                  no(0)
,
                  yes(1)

                  }
       MAX-ACCESS read-write
       STATUS current
       DESCRIPTION
           "Is this index used.
AC INI-Param: PortName_IsUsed"
       ::= {namesEntry 2}



     namesAction OBJECT-TYPE
       SYNTAX INTEGER {
                  developmentImpending(0)

                  }
       MAX-ACCESS read-only
       STATUS current
       DESCRIPTION
           "Development Impending.
AC INI-Param: N/A"
       ::= {namesEntry 3}



     namesActionResult OBJECT-TYPE
       SYNTAX INTEGER {
                  developmentImpending(0)

                  }
       MAX-ACCESS read-only
       STATUS current
       DESCRIPTION
           "Development Impending.
AC INI-Param: N/A"
       ::= {namesEntry 4}



     namesPortName OBJECT-TYPE
       SYNTAX SnmpAdminString (SIZE (0..20))
       MAX-ACCESS read-write
       STATUS current
       DESCRIPTION
           "
Access: Instant.
AC INI-Param: PortName_Name"
       ::= {namesEntry 5}



     namesModule OBJECT-TYPE
       SYNTAX Unsigned32 (0..255)
       MAX-ACCESS read-only
       STATUS current
       DESCRIPTION
           "Module.
AC INI-Param: PortName_Module"
       ::= {namesEntry 6}



     namesPort OBJECT-TYPE
       SYNTAX Unsigned32 (0..65535)
       MAX-ACCESS read-only
       STATUS current
       DESCRIPTION
           "Port.
AC INI-Param: PortName_Port"
       ::= {namesEntry 7}



     dID OBJECT IDENTIFIER ::= {analogGW 16}


     dIDEnable OBJECT-TYPE
       SYNTAX INTEGER {
                  disable(0)
,
                  enable(1)

                  }
       MAX-ACCESS read-write
       STATUS current
       DESCRIPTION
           "Enable DID support.
Access: Instant.
AC INI-Param: ENABLEDID"
       ::= {dID 1}



     dIDEnableWink OBJECT-TYPE
       SYNTAX INTEGER {
                  disable(0)
,
                  single(1)
,
                  doubleWink(2)
,
                  winkAndPolarity(3)

                  }
       MAX-ACCESS read-write
       STATUS current
       DESCRIPTION
           "Enable support for DID lines using Wink.
Access: Instant.
AC INI-Param: ENABLEDIDWINK"
       ::= {dID 2}



     dIDDelayBeforeDidWink OBJECT-TYPE
       SYNTAX Unsigned32 (0..1000)
       MAX-ACCESS read-write
       STATUS current
       DESCRIPTION
           "delay between Off-Hook detection and Wink generation (relevant
only for FXS).
unit - ms.
Access: Instant.
AC INI-Param: DELAYBEFOREDIDWINK"
       ::= {dID 3}



     -- ****************************************
     -- enableDidPort table declaration
     -- ****************************************
     enableDidPortTable OBJECT-TYPE
       SYNTAX SEQUENCE OF EnableDidPortEntry
       MAX-ACCESS not-accessible
       STATUS current
       DESCRIPTION
           ""
       ::= {dID 21}



     -- ****************************************
     -- enableDidPort table entry
     -- ****************************************
     enableDidPortEntry OBJECT-TYPE
       SYNTAX EnableDidPortEntry
       MAX-ACCESS not-accessible
       STATUS current
       DESCRIPTION
           ""
       INDEX {enableDidPortIndex}
       ::= {enableDidPortTable 1}



     -- ****************************************
     -- enableDidPort TABLE
     -- ****************************************
     EnableDidPortEntry ::= SEQUENCE {
       enableDidPortIndex                              Unsigned32,
       enableDidPortIsUsed                             INTEGER,
       enableDidPortAction                             INTEGER,
       enableDidPortActionResult                       INTEGER,
       enableDidPortEnable                             INTEGER,
       enableDidPortModule                             Unsigned32,
       enableDidPortPort                               Unsigned32
     }



     enableDidPortIndex OBJECT-TYPE
       SYNTAX Unsigned32 (0..23)
       MAX-ACCESS read-only
       STATUS current
       DESCRIPTION
           ".
AC INI-Param: EnableDid_Index"
       ::= {enableDidPortEntry 1}



     enableDidPortIsUsed OBJECT-TYPE
       SYNTAX INTEGER {
                  no(0)
,
                  yes(1)

                  }
       MAX-ACCESS read-write
       STATUS current
       DESCRIPTION
           "Is this index used.
Access: Offline.
AC INI-Param: EnableDid_IsUsed"
       ::= {enableDidPortEntry 2}



     enableDidPortAction OBJECT-TYPE
       SYNTAX INTEGER {
                  developmentImpending(0)

                  }
       MAX-ACCESS read-only
       STATUS current
       DESCRIPTION
           "Development Impending.
AC INI-Param: N/A"
       ::= {enableDidPortEntry 3}



     enableDidPortActionResult OBJECT-TYPE
       SYNTAX INTEGER {
                  developmentImpending(0)

                  }
       MAX-ACCESS read-only
       STATUS current
       DESCRIPTION
           "Development Impending.
AC INI-Param: N/A"
       ::= {enableDidPortEntry 4}



     enableDidPortEnable OBJECT-TYPE
       SYNTAX INTEGER {
                  no(0)
,
                  yes(1)

                  }
       MAX-ACCESS read-write
       STATUS current
       DESCRIPTION
           "Enable.
Access: Instant.
AC INI-Param: EnableDid_IsEnable"
       ::= {enableDidPortEntry 5}



     enableDidPortModule OBJECT-TYPE
       SYNTAX Unsigned32 (0..255)
       MAX-ACCESS read-only
       STATUS current
       DESCRIPTION
           "Channels Module.
AC INI-Param: EnableDid_Module"
       ::= {enableDidPortEntry 6}



     enableDidPortPort OBJECT-TYPE
       SYNTAX Unsigned32 (0..65535)
       MAX-ACCESS read-only
       STATUS current
       DESCRIPTION
           "Channels Port.
AC INI-Param: EnableDid_Port"
       ::= {enableDidPortEntry 7}



     mediaGW OBJECT IDENTIFIER ::= {common 5}


     mediaGWMediaChannels OBJECT-TYPE
       SYNTAX Unsigned32 (0..2016)
       MAX-ACCESS read-write
       STATUS current
       DESCRIPTION
           "Number of channels associated with media services (announcements,
conferencing).
Access: Offline.
AC INI-Param: MEDIACHANNELS"
       ::= {mediaGW 1}



     conference OBJECT IDENTIFIER ::= {mediaGW 10}


     conferenceID OBJECT-TYPE
       SYNTAX SnmpAdminString (SIZE (0..20))
       MAX-ACCESS read-write
       STATUS current
       DESCRIPTION
           "Identification of conference call (To be used by SIP INVITE).
Access: Instant.
AC INI-Param: CONFERENCEID"
       ::= {conference 1}



     conferenceBipOnConference OBJECT-TYPE
       SYNTAX INTEGER {
                  no(0)
,
                  yes(1)

                  }
       MAX-ACCESS read-write
       STATUS obsolete
       DESCRIPTION
           "Beep when a new participant joins a conference.
Access: Instant.
AC INI-Param: BIPONCONFERENCE"
       ::= {conference 2}



     conferenceEnableDTMFReporting OBJECT-TYPE
       SYNTAX INTEGER {
                  disable(0)
,
                  enable(1)

                  }
       MAX-ACCESS read-write
       STATUS current
       DESCRIPTION
           "EnableConferenceDTMFReporting- if enable report in out of band
 format about  detected DTMF digits (values 1-Report,0 -
Not Report).
Access: Instant.
AC INI-Param: EnableConferenceDTMFReporting"
       ::= {conference 3}



     conferenceEnableDTMFClamping OBJECT-TYPE
       SYNTAX INTEGER {
                  disable(0)
,
                  enable(1)

                  }
       MAX-ACCESS read-write
       STATUS obsolete
       DESCRIPTION
           "EnableConferenceDTMFClamp - if enable remove detected DTMF digits
from the audio stream on simple conference participant.
Access: Instant.
AC INI-Param: EnableConferenceDTMFClamp"
       ::= {conference 4}



     conference3WayMode OBJECT-TYPE
       SYNTAX INTEGER {
                  audioCodesMediaServer(0)
,
                  noneAudioCodesMediaServer(1)
,
                  onBoard(2)

                  }
       MAX-ACCESS read-write
       STATUS current
       DESCRIPTION
           "If 3wayConferenceMode=0, the usual conference mode will be used,
this mode wil be compatible with our IPmedia server. The
INVITE messages that are used to form a conference call, all
will contain the same conIfD in sip INVITE requests.

If 3wayConferenceMode=1,  only the first INVITE send to conference
server will use the confID. In  contact header of 200OK
response, the conference server returns a conference URI.
This conference URI will be included (by our MP gateway) in
REFER-TO header in the REFER messages, send by the MP GW to
other sip clients. The sip client will  join to conference
by  sending INVITEs to the conference server using this conference
URI .

3wayConferenceMode = 2: InBoard 3w Conference.
Access: Instant.
AC INI-Param: 3WAYCONFERENCEMODE"
       ::= {conference 5}



     conferenceMaxInBoardCalls OBJECT-TYPE
       SYNTAX Unsigned32 (0..2)
       MAX-ACCESS read-write
       STATUS current
       DESCRIPTION
           "Max InBoard Conference Calls.
Access: Offline.
AC INI-Param: MaxInBoardConferenceCalls"
       ::= {conference 6}



     -- ****************************************
     -- acTWCnonAllocateablePorts table declaration
     -- ****************************************
     acTWCnonAllocateablePortsTable OBJECT-TYPE
       SYNTAX SEQUENCE OF AcTWCnonAllocateablePortsEntry
       MAX-ACCESS not-accessible
       STATUS current
       DESCRIPTION
           ""
       ::= {conference 21}



     -- ****************************************
     -- acTWCnonAllocateablePorts table entry
     -- ****************************************
     acTWCnonAllocateablePortsEntry OBJECT-TYPE
       SYNTAX AcTWCnonAllocateablePortsEntry
       MAX-ACCESS not-accessible
       STATUS current
       DESCRIPTION
           ""
       INDEX {acTWCnonAllocateablePortsIndex}
       ::= {acTWCnonAllocateablePortsTable 1}



     -- ****************************************
     -- acTWCnonAllocateablePorts TABLE
     -- ****************************************
     AcTWCnonAllocateablePortsEntry ::= SEQUENCE {
       acTWCnonAllocateablePortsIndex                  Unsigned32,
       acTWCnonAllocateablePortsNumber                 Unsigned32
     }



     acTWCnonAllocateablePortsIndex OBJECT-TYPE
       SYNTAX Unsigned32 (0..7)
       MAX-ACCESS not-accessible
       STATUS current
       DESCRIPTION
           "Line index.
AC INI-Param: N/A"
       ::= {acTWCnonAllocateablePortsEntry 1}



     acTWCnonAllocateablePortsNumber OBJECT-TYPE
       SYNTAX Unsigned32 (0..24)
       MAX-ACCESS read-write
       STATUS current
       DESCRIPTION
           "Define the Ports that are not hit by 3w conference feature.
Access: Instant.
AC INI-Param: 3WayConfNoneAllocateablePorts"
       ::= {acTWCnonAllocateablePortsEntry 2}



     announcement OBJECT IDENTIFIER ::= {mediaGW 11}


     announcementID OBJECT-TYPE
       SYNTAX SnmpAdminString (SIZE (0..15))
       MAX-ACCESS read-write
       STATUS obsolete
       DESCRIPTION
           "Identification of a play voice prompt call (To be used by SIP
INVITE).
Access: Instant.
AC INI-Param: ANNOUNCEMENTID"
       ::= {announcement 1}



     announcementNumOfEndPoints OBJECT-TYPE
       SYNTAX Unsigned32 (0..240)
       MAX-ACCESS read-write
       STATUS obsolete
       DESCRIPTION
           "Number of Annuncment endpoints.
Access: Offline.
AC INI-Param: NUMOFANNOUNCENDPOINTS"
       ::= {announcement 2}



     announcementToneID OBJECT-TYPE
       SYNTAX SnmpAdminString (SIZE (0..15))
       MAX-ACCESS read-write
       STATUS obsolete
       DESCRIPTION
           "Identification of a play call progress tone call (To be used
by SIP INVITE).
Access: Instant.
AC INI-Param: TONEID"
       ::= {announcement 3}



     streaming OBJECT IDENTIFIER ::= {announcement 10}


     streamingID OBJECT-TYPE
       SYNTAX SnmpAdminString (SIZE (0..15))
       MAX-ACCESS read-write
       STATUS obsolete
       DESCRIPTION
           "Identification of HTTP played voice prompt (To be used by SIP
INVITE).
Access: Instant.
AC INI-Param: STREAMINGID"
       ::= {streaming 1}



     streamingNumOfEndPoints OBJECT-TYPE
       SYNTAX Unsigned32 (0..240)
       MAX-ACCESS read-write
       STATUS obsolete
       DESCRIPTION
           "Number of Streaming  endpoints.
Access: Offline.
AC INI-Param: NUMOFSTREAMINGENDPOINTS"
       ::= {streaming 2}



     streamingRecordScriptPath OBJECT-TYPE
       SYNTAX SnmpAdminString (SIZE (0..128))
       MAX-ACCESS read-write
       STATUS obsolete
       DESCRIPTION
           "Identification of HTTP Record Script (To be used by FOR RECORD).
Access: Offline.
AC INI-Param: RecordScriptPath"
       ::= {streaming 3}



     streamingMediaID OBJECT-TYPE
       SYNTAX SnmpAdminString (SIZE (0..16))
       MAX-ACCESS read-write
       STATUS obsolete
       DESCRIPTION
           "Identification of HTTP played voice prompt (To be used by SIP
INVITE).
Access: Instant.
AC INI-Param: MediaStreamingID"
       ::= {streaming 4}



     streamingStopRecordingOnNoSpeachTimeout OBJECT-TYPE
       SYNTAX Integer32 (-1..10000000)
       MAX-ACCESS read-write
       STATUS obsolete
       DESCRIPTION
           "Timeout for no speech detection used to stop recording.
Access: Instant.
AC INI-Param: STOPRECORDINGONNOSPEACHTIMEOUT"
       ::= {streaming 5}



     streamingPlayFromID OBJECT-TYPE
       SYNTAX SnmpAdminString (SIZE (0..15))
       MAX-ACCESS read-write
       STATUS obsolete
       DESCRIPTION
           "Identification of voice stream play location (To be used by
SIP INVITE).
Access: Instant.
AC INI-Param: PLAYFROMID"
       ::= {streaming 6}



     streamingRecordToID OBJECT-TYPE
       SYNTAX SnmpAdminString (SIZE (0..15))
       MAX-ACCESS read-write
       STATUS obsolete
       DESCRIPTION
           "Identification of voice stream recording location (To be used
by SIP INVITE).
Access: Instant.
AC INI-Param: RECORDTOID"
       ::= {streaming 7}



     streamingNetAnnAnncID OBJECT-TYPE
       SYNTAX SnmpAdminString (SIZE (0..15))
       MAX-ACCESS read-write
       STATUS obsolete
       DESCRIPTION
           "NetAnn Announcement ID.
Access: Instant.
AC INI-Param: NETANNANNCID"
       ::= {streaming 8}



     streamingMscmlID OBJECT-TYPE
       SYNTAX SnmpAdminString (SIZE (0..15))
       MAX-ACCESS read-write
       STATUS obsolete
       DESCRIPTION
           "Identification of HTTP played voice prompt using mscml(To be
used by SIP INVITE).
Access: Instant.
AC INI-Param: MSCMLID"
       ::= {streaming 9}



     streamingMonitorID OBJECT-TYPE
       SYNTAX SnmpAdminString (SIZE (0..15))
       MAX-ACCESS read-write
       STATUS obsolete
       DESCRIPTION
           "Identification of Calea call (To be used by SIP INVITE).
Access: Instant.
AC INI-Param: MONITORID"
       ::= {streaming 10}



     vxml OBJECT IDENTIFIER ::= {mediaGW 12}


     vxmlID OBJECT-TYPE
       SYNTAX SnmpAdminString (SIZE (0..15))
       MAX-ACCESS read-write
       STATUS obsolete
       DESCRIPTION
           "Identification of VoiceXML call (To be used by SIP INVITE).
Access: Instant.
AC INI-Param: VXMLID"
       ::= {vxml 1}



     vxmlNumOfEndPoints OBJECT-TYPE
       SYNTAX Unsigned32 (0..240)
       MAX-ACCESS read-write
       STATUS obsolete
       DESCRIPTION
           "Number of VXML endpoints.
Access: Offline.
AC INI-Param: NUMOFVXMLENDPOINTS"
       ::= {vxml 2}



     calea  OBJECT IDENTIFIER ::= {mediaGW 13}


     caleaInterceptionDirection OBJECT-TYPE
       SYNTAX INTEGER {
                  outgoing(0)
,
                  incoming(1)

                  }
       MAX-ACCESS read-write
       STATUS current
       DESCRIPTION
           "Defines the direction of interception of a BCT listener.
Access: Offline.
AC INI-Param: INTERCEPTIONDIRECTION"
       ::= {calea 1}



     transcoding OBJECT IDENTIFIER ::= {mediaGW 14}


     transcodingID OBJECT-TYPE
       SYNTAX SnmpAdminString (SIZE (0..15))
       MAX-ACCESS read-write
       STATUS current
       DESCRIPTION
           "SIP Transcoding ID.
Access: Instant.
AC INI-Param: TRANSCODINGID"
       ::= {transcoding 1}



     coders OBJECT IDENTIFIER ::= {common 6}


     -- ****************************************
     -- coders table declaration
     -- ****************************************
     codersTable OBJECT-TYPE
       SYNTAX SEQUENCE OF CodersEntry
       MAX-ACCESS not-accessible
       STATUS current
       DESCRIPTION
           "The names of the five possible coders."
       ::= {coders 1}



     -- ****************************************
     -- coders table entry
     -- ****************************************
     codersEntry OBJECT-TYPE
       SYNTAX CodersEntry
       MAX-ACCESS not-accessible
       STATUS current
       DESCRIPTION
           ""
       INDEX {codersIndex}
       ::= {codersTable 1}



     -- ****************************************
     -- coders TABLE
     -- ****************************************
     CodersEntry ::= SEQUENCE {
       codersIndex                                     Unsigned32,
       codersRowStatus                                 RowStatus,
       codersAction                                    INTEGER,
       codersActionResult                              INTEGER,
       codersName                                      INTEGER,
       codersInterval                                  Unsigned32,
       codersRate                                      Unsigned32,
       codersPayloadType                               Unsigned32,
       codersSilenceSuppression                        INTEGER
     }



     codersIndex OBJECT-TYPE
       SYNTAX Unsigned32 (0..24)
       MAX-ACCESS not-accessible
       STATUS obsolete
       DESCRIPTION
           "Entry number, starting at 0.
AC INI-Param: CoderName_Index"
       ::= {codersEntry 1}



     codersRowStatus OBJECT-TYPE
       SYNTAX RowStatus
       MAX-ACCESS read-create
       STATUS obsolete
       DESCRIPTION
           "Row-Status Textual Conventions as defined in RFC 2579: Textual
Conventions for SMIv2.
AC INI-Param: N/A"
       ::= {codersEntry 2}



     codersAction OBJECT-TYPE
       SYNTAX INTEGER {
                  developmentImpending(0)

                  }
       MAX-ACCESS read-only
       STATUS obsolete
       DESCRIPTION
           "Development Impending.
AC INI-Param: N/A"
       ::= {codersEntry 3}



     codersActionResult OBJECT-TYPE
       SYNTAX INTEGER {
                  developmentImpending(0)

                  }
       MAX-ACCESS read-only
       STATUS obsolete
       DESCRIPTION
           "Development Impending.
AC INI-Param: N/A"
       ::= {codersEntry 4}



     codersName OBJECT-TYPE
       SYNTAX INTEGER {
                  g7231(0)
,
                  g711Alaw64k(1)
,
                  g711Ulaw64k(2)
,
                  g729(3)
,
                  g726(5)
,
                  g726r16(6)
,
                  g726r24(7)
,
                  g726r32(8)
,
                  g726r40(9)
,
                  netCoder8(10)
,
                  netCoder6-4(11)
,
                  netCoder7-2(12)
,
                  netCoder8-8(13)
,
                  gWTransparent(14)
,
                  g729AnnexB(17)
,
                  eVRC(22)
,
                  amr(23)
,
                  gsm-fr(24)
,
                  gsm-ms(25)
,
                  gsmEfr(26)
,
                  iLBC(27)
,
                  qCELP(28)
,
                  t38(29)
,
                  g711Alaw64k-VBD (30)
,
                  g711Ulaw64k-VBD (31)
,
                  eVRC-B(32)
,
                  g722(33)
,
                  aMR-WB(34)
,
                  eg711Alaw(35)
,
                  eg711Ulaw(36)
,
                   g7291(37)
,
                  v1501mr(38)
,
                  ms-rta-nb(39)
,
                  wb-rta(40)
,
                  speex-NB(41)
,
                  speex-WB(42)
,
                  silk-nb(43)
,
                  silk-wb(44)
,
                  invalideCoder(99)

                  }
       MAX-ACCESS read-create
       STATUS obsolete
       DESCRIPTION
           "Coder Name.
Access: Offline.
AC INI-Param: N/A"
       ::= {codersEntry 5}



     codersInterval OBJECT-TYPE
       SYNTAX Unsigned32 (10..255)
       MAX-ACCESS read-create
       STATUS obsolete
       DESCRIPTION
           "Coder Interval.
Access: Offline.
AC INI-Param: CoderName_PacketInterval"
       ::= {codersEntry 6}



     codersRate OBJECT-TYPE
       SYNTAX Unsigned32 (0..64000)
       MAX-ACCESS read-create
       STATUS obsolete
       DESCRIPTION
           "Rate in bit per second.
Access: Offline.
AC INI-Param: CoderName_rate"
       ::= {codersEntry 7}



     codersPayloadType OBJECT-TYPE
       SYNTAX Unsigned32 (0..255)
       MAX-ACCESS read-create
       STATUS obsolete
       DESCRIPTION
           "Payload type.
Access: Offline.
AC INI-Param: CoderName_PayloadType"
       ::= {codersEntry 8}



     codersSilenceSuppression OBJECT-TYPE
       SYNTAX INTEGER {
                  disable(0)
,
                  enable(1)
,
                  enableAdaptations(2)
,
                  notConfigured(255)

                  }
       MAX-ACCESS read-create
       STATUS obsolete
       DESCRIPTION
           "Silence Suppression.
Access: Offline.
AC INI-Param: CoderName_Sce"
       ::= {codersEntry 9}



     -- ****************************************
     -- codersGroup0 table declaration
     -- ****************************************
     codersGroup0Table OBJECT-TYPE
       SYNTAX SEQUENCE OF CodersGroup0Entry
       MAX-ACCESS not-accessible
       STATUS current
       DESCRIPTION
           ""
       ::= {coders 2}



     -- ****************************************
     -- codersGroup0 table entry
     -- ****************************************
     codersGroup0Entry OBJECT-TYPE
       SYNTAX CodersGroup0Entry
       MAX-ACCESS not-accessible
       STATUS current
       DESCRIPTION
           ""
       INDEX {codersGroup0Index}
       ::= {codersGroup0Table 1}



     -- ****************************************
     -- codersGroup0 TABLE
     -- ****************************************
     CodersGroup0Entry ::= SEQUENCE {
       codersGroup0Index                               Unsigned32,
       codersGroup0RowStatus                           RowStatus,
       codersGroup0Action                              INTEGER,
       codersGroup0ActionRes                           INTEGER,
       codersGroup0Name                                INTEGER,
       codersGroup0PacketizationTime                   Unsigned32,
       codersGroup0Rate                                Unsigned32,
       codersGroup0PayloadType                         Integer32,
       codersGroup0SilenceSuppression                  INTEGER
     }



     codersGroup0Index OBJECT-TYPE
       SYNTAX Unsigned32 (0..9)
       MAX-ACCESS not-accessible
       STATUS obsolete
       DESCRIPTION
           "Index Field for line.
AC INI-Param: CodersGroup0_Index"
       ::= {codersGroup0Entry 1}



     codersGroup0RowStatus OBJECT-TYPE
       SYNTAX RowStatus
       MAX-ACCESS read-create
       STATUS obsolete
       DESCRIPTION
           "ROWSTATUS field for line.
AC INI-Param: N/A"
       ::= {codersGroup0Entry 2}



     codersGroup0Action OBJECT-TYPE
       SYNTAX INTEGER {
                  none(0)

                  }
       MAX-ACCESS read-create
       STATUS obsolete
       DESCRIPTION
           "Mangement Field for ACTIONS.
AC INI-Param: N/A"
       ::= {codersGroup0Entry 3}



     codersGroup0ActionRes OBJECT-TYPE
       SYNTAX INTEGER {
                  succeeded(0)

                  }
       MAX-ACCESS read-only
       STATUS obsolete
       DESCRIPTION
           "Mangement Field for ACTIONS RESULT.
AC INI-Param: N/A"
       ::= {codersGroup0Entry 4}



     codersGroup0Name OBJECT-TYPE
       SYNTAX INTEGER {
                  g7231(0)
,
                  g711Alaw64k(1)
,
                  g711Ulaw64k(2)
,
                  g729(3)
,
                  g726(5)
,
                  g726r16(6)
,
                  g726r24(7)
,
                  g726r32(8)
,
                  g726r40(9)
,
                  netCoder8(10)
,
                  netCoder6-4(11)
,
                  netCoder7-2(12)
,
                  netCoder8-8(13)
,
                  gWTransparent(14)
,
                  g729AnnexB(17)
,
                  eVRC(22)
,
                  amr(23)
,
                  gsm-fr(24)
,
                  gsm-ms(25)
,
                  gsmEfr(26)
,
                  iLBC(27)
,
                  qCELP(28)
,
                  t38(29)
,
                  g711Alaw64k-VBD (30)
,
                  g711Ulaw64k-VBD (31)
,
                  eVRC-B(32)
,
                  g722(33)
,
                  aMR-WB(34)
,
                  eg711Alaw(35)
,
                  eg711Ulaw(36)
,
                   g7291(37)
,
                  v1501mr(38)
,
                  ms-rta-nb(39)
,
                  wb-rta(40)
,
                  speex-NB(41)
,
                  speex-WB(42)
,
                  silk-nb(43)
,
                  silk-wb(44)
,
                  invalideCoder(99)

                  }
       MAX-ACCESS read-create
       STATUS obsolete
       DESCRIPTION
           "Coders Group name.
Access: Instant.
AC INI-Param: CodersGroup0_Name"
       ::= {codersGroup0Entry 5}



     codersGroup0PacketizationTime OBJECT-TYPE
       SYNTAX Unsigned32 (0..4294967295)
       MAX-ACCESS read-create
       STATUS obsolete
       DESCRIPTION
           "Coders Group packetization time.
Access: Instant.
AC INI-Param: CodersGroup0_pTime"
       ::= {codersGroup0Entry 6}



     codersGroup0Rate OBJECT-TYPE
       SYNTAX Unsigned32 (0..64000)
       MAX-ACCESS read-create
       STATUS obsolete
       DESCRIPTION
           "Coders Group rate.
Access: Instant.
AC INI-Param: CodersGroup0_rate"
       ::= {codersGroup0Entry 7}



     codersGroup0PayloadType OBJECT-TYPE
       SYNTAX Integer32 (-1..127)
       MAX-ACCESS read-create
       STATUS obsolete
       DESCRIPTION
           "Coders Group payload type.
Access: Instant.
AC INI-Param: CodersGroup0_PayloadType"
       ::= {codersGroup0Entry 8}



     codersGroup0SilenceSuppression OBJECT-TYPE
       SYNTAX INTEGER {
                  disable(0)
,
                  enable(1)
,
                  enableAdaptations(2)

                  }
       MAX-ACCESS read-create
       STATUS obsolete
       DESCRIPTION
           "Coders Group silence suppression.
Access: Instant.
AC INI-Param: CodersGroup0_Sce"
       ::= {codersGroup0Entry 9}



     -- ****************************************
     -- codersGroup1 table declaration
     -- ****************************************
     codersGroup1Table OBJECT-TYPE
       SYNTAX SEQUENCE OF CodersGroup1Entry
       MAX-ACCESS not-accessible
       STATUS current
       DESCRIPTION
           ""
       ::= {coders 3}



     -- ****************************************
     -- codersGroup1 table entry
     -- ****************************************
     codersGroup1Entry OBJECT-TYPE
       SYNTAX CodersGroup1Entry
       MAX-ACCESS not-accessible
       STATUS current
       DESCRIPTION
           ""
       INDEX {codersGroup1Index}
       ::= {codersGroup1Table 1}



     -- ****************************************
     -- codersGroup1 TABLE
     -- ****************************************
     CodersGroup1Entry ::= SEQUENCE {
       codersGroup1Index                               Unsigned32,
       codersGroup1RowStatus                           RowStatus,
       codersGroup1Action                              INTEGER,
       codersGroup1ActionRes                           INTEGER,
       codersGroup1Name                                INTEGER,
       codersGroup1PacketizationTime                   Unsigned32,
       codersGroup1Rate                                Unsigned32,
       codersGroup1PayloadType                         Integer32,
       codersGroup1SilenceSuppression                  INTEGER
     }



     codersGroup1Index OBJECT-TYPE
       SYNTAX Unsigned32 (0..9)
       MAX-ACCESS not-accessible
       STATUS obsolete
       DESCRIPTION
           "Index Field for line.
AC INI-Param: CodersGroup1_Index"
       ::= {codersGroup1Entry 1}



     codersGroup1RowStatus OBJECT-TYPE
       SYNTAX RowStatus
       MAX-ACCESS read-create
       STATUS obsolete
       DESCRIPTION
           "ROWSTATUS field for line.
AC INI-Param: N/A"
       ::= {codersGroup1Entry 2}



     codersGroup1Action OBJECT-TYPE
       SYNTAX INTEGER {
                  none(0)

                  }
       MAX-ACCESS read-create
       STATUS obsolete
       DESCRIPTION
           "Mangement Field for ACTIONS.
AC INI-Param: N/A"
       ::= {codersGroup1Entry 3}



     codersGroup1ActionRes OBJECT-TYPE
       SYNTAX INTEGER {
                  succeeded(0)

                  }
       MAX-ACCESS read-only
       STATUS obsolete
       DESCRIPTION
           "Mangement Field for ACTIONS RESULT.
AC INI-Param: N/A"
       ::= {codersGroup1Entry 4}



     codersGroup1Name OBJECT-TYPE
       SYNTAX INTEGER {
                  g7231(0)
,
                  g711Alaw64k(1)
,
                  g711Ulaw64k(2)
,
                  g729(3)
,
                  g726(5)
,
                  g726r16(6)
,
                  g726r24(7)
,
                  g726r32(8)
,
                  g726r40(9)
,
                  netCoder8(10)
,
                  netCoder6-4(11)
,
                  netCoder7-2(12)
,
                  netCoder8-8(13)
,
                  gWTransparent(14)
,
                  g729AnnexB(17)
,
                  eVRC(22)
,
                  amr(23)
,
                  gsm-fr(24)
,
                  gsm-ms(25)
,
                  gsmEfr(26)
,
                  iLBC(27)
,
                  qCELP(28)
,
                  t38(29)
,
                  g711Alaw64k-VBD (30)
,
                  g711Ulaw64k-VBD (31)
,
                  eVRC-B(32)
,
                  g722(33)
,
                  aMR-WB(34)
,
                  eg711Alaw(35)
,
                  eg711Ulaw(36)
,
                   g7291(37)
,
                  v1501mr(38)
,
                  ms-rta-nb(39)
,
                  wb-rta(40)
,
                  speex-NB(41)
,
                  speex-WB(42)
,
                  silk-nb(43)
,
                  silk-wb(44)
,
                  invalideCoder(99)

                  }
       MAX-ACCESS read-create
       STATUS obsolete
       DESCRIPTION
           "Coders Group name.
Access: Instant.
AC INI-Param: CodersGroup1_Name"
       ::= {codersGroup1Entry 5}



     codersGroup1PacketizationTime OBJECT-TYPE
       SYNTAX Unsigned32 (0..4294967295)
       MAX-ACCESS read-create
       STATUS obsolete
       DESCRIPTION
           "Coders Group packetization time.
Access: Instant.
AC INI-Param: CodersGroup1_pTime"
       ::= {codersGroup1Entry 6}



     codersGroup1Rate OBJECT-TYPE
       SYNTAX Unsigned32 (0..64000)
       MAX-ACCESS read-create
       STATUS obsolete
       DESCRIPTION
           "Coders Group rate.
Access: Instant.
AC INI-Param: CodersGroup1_rate"
       ::= {codersGroup1Entry 7}



     codersGroup1PayloadType OBJECT-TYPE
       SYNTAX Integer32 (-1..127)
       MAX-ACCESS read-create
       STATUS obsolete
       DESCRIPTION
           "Coders Group payload type.
Access: Instant.
AC INI-Param: CodersGroup1_PayloadType"
       ::= {codersGroup1Entry 8}



     codersGroup1SilenceSuppression OBJECT-TYPE
       SYNTAX INTEGER {
                  disable(0)
,
                  enable(1)
,
                  enableAdaptations(2)

                  }
       MAX-ACCESS read-create
       STATUS obsolete
       DESCRIPTION
           "Coders Group silence suppression.
Access: Instant.
AC INI-Param: CodersGroup1_Sce"
       ::= {codersGroup1Entry 9}



     -- ****************************************
     -- codersGroup2 table declaration
     -- ****************************************
     codersGroup2Table OBJECT-TYPE
       SYNTAX SEQUENCE OF CodersGroup2Entry
       MAX-ACCESS not-accessible
       STATUS current
       DESCRIPTION
           ""
       ::= {coders 4}



     -- ****************************************
     -- codersGroup2 table entry
     -- ****************************************
     codersGroup2Entry OBJECT-TYPE
       SYNTAX CodersGroup2Entry
       MAX-ACCESS not-accessible
       STATUS current
       DESCRIPTION
           ""
       INDEX {codersGroup2Index}
       ::= {codersGroup2Table 1}



     -- ****************************************
     -- codersGroup2 TABLE
     -- ****************************************
     CodersGroup2Entry ::= SEQUENCE {
       codersGroup2Index                               Unsigned32,
       codersGroup2RowStatus                           RowStatus,
       codersGroup2Action                              INTEGER,
       codersGroup2ActionRes                           INTEGER,
       codersGroup2Name                                INTEGER,
       codersGroup2PacketizationTime                   Unsigned32,
       codersGroup2Rate                                Unsigned32,
       codersGroup2PayloadType                         Integer32,
       codersGroup2SilenceSuppression                  INTEGER
     }



     codersGroup2Index OBJECT-TYPE
       SYNTAX Unsigned32 (0..9)
       MAX-ACCESS not-accessible
       STATUS obsolete
       DESCRIPTION
           "Index Field for line.
AC INI-Param: CodersGroup2_Index"
       ::= {codersGroup2Entry 1}



     codersGroup2RowStatus OBJECT-TYPE
       SYNTAX RowStatus
       MAX-ACCESS read-create
       STATUS obsolete
       DESCRIPTION
           "ROWSTATUS field for line.
AC INI-Param: N/A"
       ::= {codersGroup2Entry 2}



     codersGroup2Action OBJECT-TYPE
       SYNTAX INTEGER {
                  none(0)

                  }
       MAX-ACCESS read-create
       STATUS obsolete
       DESCRIPTION
           "Mangement Field for ACTIONS.
AC INI-Param: N/A"
       ::= {codersGroup2Entry 3}



     codersGroup2ActionRes OBJECT-TYPE
       SYNTAX INTEGER {
                  succeeded(0)

                  }
       MAX-ACCESS read-only
       STATUS obsolete
       DESCRIPTION
           "Mangement Field for ACTIONS RESULT.
AC INI-Param: N/A"
       ::= {codersGroup2Entry 4}



     codersGroup2Name OBJECT-TYPE
       SYNTAX INTEGER {
                  g7231(0)
,
                  g711Alaw64k(1)
,
                  g711Ulaw64k(2)
,
                  g729(3)
,
                  g726(5)
,
                  g726r16(6)
,
                  g726r24(7)
,
                  g726r32(8)
,
                  g726r40(9)
,
                  netCoder8(10)
,
                  netCoder6-4(11)
,
                  netCoder7-2(12)
,
                  netCoder8-8(13)
,
                  gWTransparent(14)
,
                  g729AnnexB(17)
,
                  eVRC(22)
,
                  amr(23)
,
                  gsm-fr(24)
,
                  gsm-ms(25)
,
                  gsmEfr(26)
,
                  iLBC(27)
,
                  qCELP(28)
,
                  t38(29)
,
                  g711Alaw64k-VBD (30)
,
                  g711Ulaw64k-VBD (31)
,
                  eVRC-B(32)
,
                  g722(33)
,
                  aMR-WB(34)
,
                  eg711Alaw(35)
,
                  eg711Ulaw(36)
,
                   g7291(37)
,
                  v1501mr(38)
,
                  ms-rta-nb(39)
,
                  wb-rta(40)
,
                  speex-NB(41)
,
                  speex-WB(42)
,
                  silk-nb(43)
,
                  silk-wb(44)
,
                  invalideCoder(99)

                  }
       MAX-ACCESS read-create
       STATUS obsolete
       DESCRIPTION
           "Coders Group name.
Access: Instant.
AC INI-Param: CodersGroup2_Name"
       ::= {codersGroup2Entry 5}



     codersGroup2PacketizationTime OBJECT-TYPE
       SYNTAX Unsigned32 (0..4294967295)
       MAX-ACCESS read-create
       STATUS obsolete
       DESCRIPTION
           "Coders Group packetization time.
Access: Instant.
AC INI-Param: CodersGroup2_pTime"
       ::= {codersGroup2Entry 6}



     codersGroup2Rate OBJECT-TYPE
       SYNTAX Unsigned32 (0..64000)
       MAX-ACCESS read-create
       STATUS obsolete
       DESCRIPTION
           "Coders Group rate.
Access: Instant.
AC INI-Param: CodersGroup2_rate"
       ::= {codersGroup2Entry 7}



     codersGroup2PayloadType OBJECT-TYPE
       SYNTAX Integer32 (-1..127)
       MAX-ACCESS read-create
       STATUS obsolete
       DESCRIPTION
           "Coders Group payload type.
Access: Instant.
AC INI-Param: CodersGroup2_PayloadType"
       ::= {codersGroup2Entry 8}



     codersGroup2SilenceSuppression OBJECT-TYPE
       SYNTAX INTEGER {
                  disable(0)
,
                  enable(1)
,
                  enableAdaptations(2)

                  }
       MAX-ACCESS read-create
       STATUS obsolete
       DESCRIPTION
           "Coders Group silence suppression.
Access: Instant.
AC INI-Param: CodersGroup2_Sce"
       ::= {codersGroup2Entry 9}



     -- ****************************************
     -- codersGroup3 table declaration
     -- ****************************************
     codersGroup3Table OBJECT-TYPE
       SYNTAX SEQUENCE OF CodersGroup3Entry
       MAX-ACCESS not-accessible
       STATUS current
       DESCRIPTION
           ""
       ::= {coders 5}



     -- ****************************************
     -- codersGroup3 table entry
     -- ****************************************
     codersGroup3Entry OBJECT-TYPE
       SYNTAX CodersGroup3Entry
       MAX-ACCESS not-accessible
       STATUS current
       DESCRIPTION
           ""
       INDEX {codersGroup3Index}
       ::= {codersGroup3Table 1}



     -- ****************************************
     -- codersGroup3 TABLE
     -- ****************************************
     CodersGroup3Entry ::= SEQUENCE {
       codersGroup3Index                               Unsigned32,
       codersGroup3RowStatus                           RowStatus,
       codersGroup3Action                              INTEGER,
       codersGroup3ActionRes                           INTEGER,
       codersGroup3Name                                INTEGER,
       codersGroup3PacketizationTime                   Unsigned32,
       codersGroup3Rate                                Unsigned32,
       codersGroup3PayloadType                         Integer32,
       codersGroup3SilenceSuppression                  INTEGER
     }



     codersGroup3Index OBJECT-TYPE
       SYNTAX Unsigned32 (0..9)
       MAX-ACCESS not-accessible
       STATUS obsolete
       DESCRIPTION
           "Index Field for line.
AC INI-Param: CodersGroup3_Index"
       ::= {codersGroup3Entry 1}



     codersGroup3RowStatus OBJECT-TYPE
       SYNTAX RowStatus
       MAX-ACCESS read-create
       STATUS obsolete
       DESCRIPTION
           "ROWSTATUS field for line.
AC INI-Param: N/A"
       ::= {codersGroup3Entry 2}



     codersGroup3Action OBJECT-TYPE
       SYNTAX INTEGER {
                  none(0)

                  }
       MAX-ACCESS read-create
       STATUS obsolete
       DESCRIPTION
           "Mangement Field for ACTIONS.
AC INI-Param: N/A"
       ::= {codersGroup3Entry 3}



     codersGroup3ActionRes OBJECT-TYPE
       SYNTAX INTEGER {
                  succeeded(0)

                  }
       MAX-ACCESS read-only
       STATUS obsolete
       DESCRIPTION
           "Mangement Field for ACTIONS RESULT.
AC INI-Param: N/A"
       ::= {codersGroup3Entry 4}



     codersGroup3Name OBJECT-TYPE
       SYNTAX INTEGER {
                  g7231(0)
,
                  g711Alaw64k(1)
,
                  g711Ulaw64k(2)
,
                  g729(3)
,
                  g726(5)
,
                  g726r16(6)
,
                  g726r24(7)
,
                  g726r32(8)
,
                  g726r40(9)
,
                  netCoder8(10)
,
                  netCoder6-4(11)
,
                  netCoder7-2(12)
,
                  netCoder8-8(13)
,
                  gWTransparent(14)
,
                  g729AnnexB(17)
,
                  eVRC(22)
,
                  amr(23)
,
                  gsm-fr(24)
,
                  gsm-ms(25)
,
                  gsmEfr(26)
,
                  iLBC(27)
,
                  qCELP(28)
,
                  t38(29)
,
                  g711Alaw64k-VBD (30)
,
                  g711Ulaw64k-VBD (31)
,
                  eVRC-B(32)
,
                  g722(33)
,
                  aMR-WB(34)
,
                  eg711Alaw(35)
,
                  eg711Ulaw(36)
,
                   g7291(37)
,
                  v1501mr(38)
,
                  ms-rta-nb(39)
,
                  wb-rta(40)
,
                  speex-NB(41)
,
                  speex-WB(42)
,
                  silk-nb(43)
,
                  silk-wb(44)
,
                  invalideCoder(99)

                  }
       MAX-ACCESS read-create
       STATUS obsolete
       DESCRIPTION
           "Coders Group name.
Access: Instant.
AC INI-Param: CodersGroup3_Name"
       ::= {codersGroup3Entry 5}



     codersGroup3PacketizationTime OBJECT-TYPE
       SYNTAX Unsigned32 (0..4294967295)
       MAX-ACCESS read-create
       STATUS obsolete
       DESCRIPTION
           "Coders Group packetization time.
Access: Instant.
AC INI-Param: CodersGroup3_pTime"
       ::= {codersGroup3Entry 6}



     codersGroup3Rate OBJECT-TYPE
       SYNTAX Unsigned32 (0..64000)
       MAX-ACCESS read-create
       STATUS obsolete
       DESCRIPTION
           "Coders Group rate.
Access: Instant.
AC INI-Param: CodersGroup3_rate"
       ::= {codersGroup3Entry 7}



     codersGroup3PayloadType OBJECT-TYPE
       SYNTAX Integer32 (-1..127)
       MAX-ACCESS read-create
       STATUS obsolete
       DESCRIPTION
           "Coders Group payload type.
Access: Instant.
AC INI-Param: CodersGroup3_PayloadType"
       ::= {codersGroup3Entry 8}



     codersGroup3SilenceSuppression OBJECT-TYPE
       SYNTAX INTEGER {
                  disable(0)
,
                  enable(1)
,
                  enableAdaptations(2)

                  }
       MAX-ACCESS read-create
       STATUS obsolete
       DESCRIPTION
           "Coders Group silence suppression.
Access: Instant.
AC INI-Param: CodersGroup3_Sce"
       ::= {codersGroup3Entry 9}



     -- ****************************************
     -- codersGroup4 table declaration
     -- ****************************************
     codersGroup4Table OBJECT-TYPE
       SYNTAX SEQUENCE OF CodersGroup4Entry
       MAX-ACCESS not-accessible
       STATUS current
       DESCRIPTION
           ""
       ::= {coders 6}



     -- ****************************************
     -- codersGroup4 table entry
     -- ****************************************
     codersGroup4Entry OBJECT-TYPE
       SYNTAX CodersGroup4Entry
       MAX-ACCESS not-accessible
       STATUS current
       DESCRIPTION
           ""
       INDEX {codersGroup4Index}
       ::= {codersGroup4Table 1}



     -- ****************************************
     -- codersGroup4 TABLE
     -- ****************************************
     CodersGroup4Entry ::= SEQUENCE {
       codersGroup4Index                               Unsigned32,
       codersGroup4RowStatus                           RowStatus,
       codersGroup4Action                              INTEGER,
       codersGroup4ActionRes                           INTEGER,
       codersGroup4Name                                INTEGER,
       codersGroup4PacketizationTime                   Unsigned32,
       codersGroup4Rate                                Unsigned32,
       codersGroup4PayloadType                         Integer32,
       codersGroup4SilenceSuppression                  INTEGER
     }



     codersGroup4Index OBJECT-TYPE
       SYNTAX Unsigned32 (0..9)
       MAX-ACCESS not-accessible
       STATUS obsolete
       DESCRIPTION
           "Index Field for line.
AC INI-Param: CodersGroup4_Index"
       ::= {codersGroup4Entry 1}



     codersGroup4RowStatus OBJECT-TYPE
       SYNTAX RowStatus
       MAX-ACCESS read-create
       STATUS obsolete
       DESCRIPTION
           "ROWSTATUS field for line.
AC INI-Param: N/A"
       ::= {codersGroup4Entry 2}



     codersGroup4Action OBJECT-TYPE
       SYNTAX INTEGER {
                  none(0)

                  }
       MAX-ACCESS read-create
       STATUS obsolete
       DESCRIPTION
           "Mangement Field for ACTIONS.
AC INI-Param: N/A"
       ::= {codersGroup4Entry 3}



     codersGroup4ActionRes OBJECT-TYPE
       SYNTAX INTEGER {
                  succeeded(0)

                  }
       MAX-ACCESS read-only
       STATUS obsolete
       DESCRIPTION
           "Mangement Field for ACTIONS RESULT.
AC INI-Param: N/A"
       ::= {codersGroup4Entry 4}



     codersGroup4Name OBJECT-TYPE
       SYNTAX INTEGER {
                  g7231(0)
,
                  g711Alaw64k(1)
,
                  g711Ulaw64k(2)
,
                  g729(3)
,
                  g726(5)
,
                  g726r16(6)
,
                  g726r24(7)
,
                  g726r32(8)
,
                  g726r40(9)
,
                  netCoder8(10)
,
                  netCoder6-4(11)
,
                  netCoder7-2(12)
,
                  netCoder8-8(13)
,
                  gWTransparent(14)
,
                  g729AnnexB(17)
,
                  eVRC(22)
,
                  amr(23)
,
                  gsm-fr(24)
,
                  gsm-ms(25)
,
                  gsmEfr(26)
,
                  iLBC(27)
,
                  qCELP(28)
,
                  t38(29)
,
                  g711Alaw64k-VBD (30)
,
                  g711Ulaw64k-VBD (31)
,
                  eVRC-B(32)
,
                  g722(33)
,
                  aMR-WB(34)
,
                  eg711Alaw(35)
,
                  eg711Ulaw(36)
,
                   g7291(37)
,
                  v1501mr(38)
,
                  ms-rta-nb(39)
,
                  wb-rta(40)
,
                  speex-NB(41)
,
                  speex-WB(42)
,
                  silk-nb(43)
,
                  silk-wb(44)
,
                  invalideCoder(99)

                  }
       MAX-ACCESS read-create
       STATUS obsolete
       DESCRIPTION
           "Coders Group name.
Access: Instant.
AC INI-Param: CodersGroup4_Name"
       ::= {codersGroup4Entry 5}



     codersGroup4PacketizationTime OBJECT-TYPE
       SYNTAX Unsigned32 (0..4294967295)
       MAX-ACCESS read-create
       STATUS obsolete
       DESCRIPTION
           "Coders Group packetization time.
Access: Instant.
AC INI-Param: CodersGroup4_pTime"
       ::= {codersGroup4Entry 6}



     codersGroup4Rate OBJECT-TYPE
       SYNTAX Unsigned32 (0..64000)
       MAX-ACCESS read-create
       STATUS obsolete
       DESCRIPTION
           "Coders Group rate.
Access: Instant.
AC INI-Param: CodersGroup4_rate"
       ::= {codersGroup4Entry 7}



     codersGroup4PayloadType OBJECT-TYPE
       SYNTAX Integer32 (-1..127)
       MAX-ACCESS read-create
       STATUS obsolete
       DESCRIPTION
           "Coders Group payload type.
Access: Instant.
AC INI-Param: CodersGroup4_PayloadType"
       ::= {codersGroup4Entry 8}



     codersGroup4SilenceSuppression OBJECT-TYPE
       SYNTAX INTEGER {
                  disable(0)
,
                  enable(1)
,
                  enableAdaptations(2)

                  }
       MAX-ACCESS read-create
       STATUS obsolete
       DESCRIPTION
           "Coders Group silence suppression.
Access: Instant.
AC INI-Param: CodersGroup4_Sce"
       ::= {codersGroup4Entry 9}



     -- ****************************************
     -- codersGroup table declaration
     -- ****************************************
     codersGroupTable OBJECT-TYPE
       SYNTAX SEQUENCE OF CodersGroupEntry
       MAX-ACCESS not-accessible
       STATUS current
       DESCRIPTION
           ""
       ::= {coders 7}



     -- ****************************************
     -- codersGroup table entry
     -- ****************************************
     codersGroupEntry OBJECT-TYPE
       SYNTAX CodersGroupEntry
       MAX-ACCESS not-accessible
       STATUS current
       DESCRIPTION
           ""
       INDEX {codersGroupTableIdx,codersGroupIndex}
       ::= {codersGroupTable 1}



     -- ****************************************
     -- codersGroup TABLE
     -- ****************************************
     CodersGroupEntry ::= SEQUENCE {
       codersGroupTableIdx                             Unsigned32,
       codersGroupIndex                                Unsigned32,
       codersGroupRowStatus                            RowStatus,
       codersGroupAction                               INTEGER,
       codersGroupActionRes                            INTEGER,
       codersGroupName                                 INTEGER,
       codersGroupPacketizationTime                    Unsigned32,
       codersGroupRate                                 Unsigned32,
       codersGroupPayloadType                          Integer32,
       codersGroupSilenceSuppression                   INTEGER,
       codersGroupCoderSpecific                        SnmpAdminString
     }



     codersGroupTableIdx OBJECT-TYPE
       SYNTAX Unsigned32 (0..10)
       MAX-ACCESS not-accessible
       STATUS current
       DESCRIPTION
           "Index field for table.
AC INI-Param: N/A"
       ::= {codersGroupEntry 1}



     codersGroupIndex OBJECT-TYPE
       SYNTAX Unsigned32 (0..9)
       MAX-ACCESS not-accessible
       STATUS current
       DESCRIPTION
           "Index Field for line.
AC INI-Param: CodersGroup_Index"
       ::= {codersGroupEntry 2}



     codersGroupRowStatus OBJECT-TYPE
       SYNTAX RowStatus
       MAX-ACCESS read-create
       STATUS current
       DESCRIPTION
           "ROWSTATUS field for line.
AC INI-Param: N/A"
       ::= {codersGroupEntry 3}



     codersGroupAction OBJECT-TYPE
       SYNTAX INTEGER {
                  none(0)

                  }
       MAX-ACCESS read-create
       STATUS current
       DESCRIPTION
           "Mangement Field for ACTIONS.
AC INI-Param: N/A"
       ::= {codersGroupEntry 4}



     codersGroupActionRes OBJECT-TYPE
       SYNTAX INTEGER {
                  succeeded(0)

                  }
       MAX-ACCESS read-only
       STATUS current
       DESCRIPTION
           "Mangement Field for ACTIONS RESULT.
AC INI-Param: N/A"
       ::= {codersGroupEntry 5}



     codersGroupName OBJECT-TYPE
       SYNTAX INTEGER {
                  g7231(0)
,
                  g711Alaw64k(1)
,
                  g711Ulaw64k(2)
,
                  g729(3)
,
                  g726(5)
,
                  g726r16(6)
,
                  g726r24(7)
,
                  g726r32(8)
,
                  g726r40(9)
,
                  netCoder8(10)
,
                  netCoder6-4(11)
,
                  netCoder7-2(12)
,
                  netCoder8-8(13)
,
                  gWTransparent(14)
,
                  g729AnnexB(17)
,
                  eVRC(22)
,
                  amr(23)
,
                  gsm-fr(24)
,
                  gsm-ms(25)
,
                  gsmEfr(26)
,
                  iLBC(27)
,
                  qCELP(28)
,
                  t38(29)
,
                  g711Alaw64k-VBD (30)
,
                  g711Ulaw64k-VBD (31)
,
                  eVRC-B(32)
,
                  g722(33)
,
                  aMR-WB(34)
,
                  eg711Alaw(35)
,
                  eg711Ulaw(36)
,
                   g7291(37)
,
                  v1501mr(38)
,
                  ms-rta-nb(39)
,
                  wb-rta(40)
,
                  speex-NB(41)
,
                  speex-WB(42)
,
                  silk-nb(43)
,
                  silk-wb(44)
,
                  invalideCoder(99)

                  }
       MAX-ACCESS read-create
       STATUS current
       DESCRIPTION
           "Coders Group name.
Access: Instant.
AC INI-Param: CodersGroup_Name"
       ::= {codersGroupEntry 6}



     codersGroupPacketizationTime OBJECT-TYPE
       SYNTAX Unsigned32 (0..4294967295)
       MAX-ACCESS read-create
       STATUS current
       DESCRIPTION
           "Coders Group packetization time.
Access: Instant.
AC INI-Param: CodersGroup_pTime"
       ::= {codersGroupEntry 7}



     codersGroupRate OBJECT-TYPE
       SYNTAX Unsigned32 (0..64000)
       MAX-ACCESS read-create
       STATUS current
       DESCRIPTION
           "Coders Group rate.
Access: Instant.
AC INI-Param: CodersGroup_rate"
       ::= {codersGroupEntry 8}



     codersGroupPayloadType OBJECT-TYPE
       SYNTAX Integer32 (-1..127)
       MAX-ACCESS read-create
       STATUS current
       DESCRIPTION
           "Coders Group payload type.
Access: Instant.
AC INI-Param: CodersGroup_PayloadType"
       ::= {codersGroupEntry 9}



     codersGroupSilenceSuppression OBJECT-TYPE
       SYNTAX INTEGER {
                  disable(0)
,
                  enable(1)
,
                  enableAdaptations(2)

                  }
       MAX-ACCESS read-create
       STATUS current
       DESCRIPTION
           "Coders Group silence suppression.
Access: Instant.
AC INI-Param: CodersGroup_Sce"
       ::= {codersGroupEntry 10}



     codersGroupCoderSpecific OBJECT-TYPE
       SYNTAX SnmpAdminString (SIZE (0..30))
       MAX-ACCESS read-create
       STATUS current
       DESCRIPTION
           "Coders Specific.
Access: Instant.
AC INI-Param: CodersGroup_CoderSpecific"
       ::= {codersGroupEntry 11}



     -- ****************************************
     -- codersGroupFather table declaration
     -- ****************************************
     codersGroupFatherTable OBJECT-TYPE
       SYNTAX SEQUENCE OF CodersGroupFatherEntry
       MAX-ACCESS not-accessible
       STATUS current
       DESCRIPTION
           ""
       ::= {coders 8}



     -- ****************************************
     -- codersGroupFather table entry
     -- ****************************************
     codersGroupFatherEntry OBJECT-TYPE
       SYNTAX CodersGroupFatherEntry
       MAX-ACCESS not-accessible
       STATUS current
       DESCRIPTION
           ""
       INDEX {codersGroupFatherIndex}
       ::= {codersGroupFatherTable 1}



     -- ****************************************
     -- codersGroupFather TABLE
     -- ****************************************
     CodersGroupFatherEntry ::= SEQUENCE {
       codersGroupFatherIndex                          Unsigned32,
       codersGroupFatherName                           SnmpAdminString,
       codersGroupFatherNumOfEntries                   Unsigned32
     }



     codersGroupFatherIndex OBJECT-TYPE
       SYNTAX Unsigned32 (0..10)
       MAX-ACCESS not-accessible
       STATUS current
       DESCRIPTION
           "Index Field for line. Internal parameter.
AC INI-Param: CodersGroupFather_Index"
       ::= {codersGroupFatherEntry 1}



     codersGroupFatherName OBJECT-TYPE
       SYNTAX SnmpAdminString (SIZE (0..0))
       MAX-ACCESS read-only
       STATUS current
       DESCRIPTION
           "Indicates the TableIdx Of CodersGroup.
AC INI-Param: codersGroupFather_Name"
       ::= {codersGroupFatherEntry 2}



     codersGroupFatherNumOfEntries OBJECT-TYPE
       SYNTAX Unsigned32 (0..9)
       MAX-ACCESS read-only
       STATUS current
       DESCRIPTION
           "Indicates the Index Of CodersGroup.
AC INI-Param: codersGroupFather_NumOfEntries"
       ::= {codersGroupFatherEntry 3}



     -- ****************************************
     -- allowedCodersGroupFather table declaration
     -- ****************************************
     allowedCodersGroupFatherTable OBJECT-TYPE
       SYNTAX SEQUENCE OF AllowedCodersGroupFatherEntry
       MAX-ACCESS not-accessible
       STATUS current
       DESCRIPTION
           ""
       ::= {coders 9}



     -- ****************************************
     -- allowedCodersGroupFather table entry
     -- ****************************************
     allowedCodersGroupFatherEntry OBJECT-TYPE
       SYNTAX AllowedCodersGroupFatherEntry
       MAX-ACCESS not-accessible
       STATUS current
       DESCRIPTION
           ""
       INDEX {allowedCodersGroupFatherIndex}
       ::= {allowedCodersGroupFatherTable 1}



     -- ****************************************
     -- allowedCodersGroupFather TABLE
     -- ****************************************
     AllowedCodersGroupFatherEntry ::= SEQUENCE {
       allowedCodersGroupFatherIndex                   Unsigned32,
       allowedCodersGroupFatherName                    SnmpAdminString,
       allowedCodersGroupFatherNumOfEntries            Unsigned32
     }



     allowedCodersGroupFatherIndex OBJECT-TYPE
       SYNTAX Unsigned32 (0..4)
       MAX-ACCESS not-accessible
       STATUS current
       DESCRIPTION
           "Index Field for line. Internal parameter.
AC INI-Param: AllowedCodersGroupFather_Index"
       ::= {allowedCodersGroupFatherEntry 1}



     allowedCodersGroupFatherName OBJECT-TYPE
       SYNTAX SnmpAdminString (SIZE (0..0))
       MAX-ACCESS read-only
       STATUS current
       DESCRIPTION
           "Indicates the TableIdx Of AllowedCodersGroup.
AC INI-Param: AllowedCodersGroupFather_Name"
       ::= {allowedCodersGroupFatherEntry 2}



     allowedCodersGroupFatherNumOfEntries OBJECT-TYPE
       SYNTAX Unsigned32 (0..9)
       MAX-ACCESS read-only
       STATUS current
       DESCRIPTION
           "Indicates the Index Of AllowedCodersGroup.
AC INI-Param: AllowedCodersGroupFather_NumOfEntries"
       ::= {allowedCodersGroupFatherEntry 3}



     -- ****************************************
     -- allowedCodersGroup table declaration
     -- ****************************************
     allowedCodersGroupTable OBJECT-TYPE
       SYNTAX SEQUENCE OF AllowedCodersGroupEntry
       MAX-ACCESS not-accessible
       STATUS current
       DESCRIPTION
           ""
       ::= {coders 10}



     -- ****************************************
     -- allowedCodersGroup table entry
     -- ****************************************
     allowedCodersGroupEntry OBJECT-TYPE
       SYNTAX AllowedCodersGroupEntry
       MAX-ACCESS not-accessible
       STATUS current
       DESCRIPTION
           ""
       INDEX {allowedCodersGroupTableIdx,allowedCodersGroupIndex}
       ::= {allowedCodersGroupTable 1}



     -- ****************************************
     -- allowedCodersGroup TABLE
     -- ****************************************
     AllowedCodersGroupEntry ::= SEQUENCE {
       allowedCodersGroupTableIdx                      Unsigned32,
       allowedCodersGroupIndex                         Unsigned32,
       allowedCodersGroupRowStatus                     RowStatus,
       allowedCodersGroupAction                        INTEGER,
       allowedCodersGroupActionRes                     INTEGER,
       allowedCodersGroupName                          INTEGER
     }



     allowedCodersGroupTableIdx OBJECT-TYPE
       SYNTAX Unsigned32 (0..4)
       MAX-ACCESS not-accessible
       STATUS current
       DESCRIPTION
           "Index field for table.
AC INI-Param: N/A"
       ::= {allowedCodersGroupEntry 1}



     allowedCodersGroupIndex OBJECT-TYPE
       SYNTAX Unsigned32 (0..9)
       MAX-ACCESS not-accessible
       STATUS current
       DESCRIPTION
           "Index Field for line.
AC INI-Param: AllowedCodersGroup_Index"
       ::= {allowedCodersGroupEntry 2}



     allowedCodersGroupRowStatus OBJECT-TYPE
       SYNTAX RowStatus
       MAX-ACCESS read-create
       STATUS current
       DESCRIPTION
           "ROWSTATUS field for line.
Access: Offline.
AC INI-Param: N/A"
       ::= {allowedCodersGroupEntry 3}



     allowedCodersGroupAction OBJECT-TYPE
       SYNTAX INTEGER {
                  none(0)

                  }
       MAX-ACCESS read-create
       STATUS current
       DESCRIPTION
           "Mangement Field for ACTIONS.
Access: Offline.
AC INI-Param: N/A"
       ::= {allowedCodersGroupEntry 4}



     allowedCodersGroupActionRes OBJECT-TYPE
       SYNTAX INTEGER {
                  succeeded(0)

                  }
       MAX-ACCESS read-only
       STATUS current
       DESCRIPTION
           "Mangement Field for ACTIONS RESULT.
AC INI-Param: N/A"
       ::= {allowedCodersGroupEntry 5}



     allowedCodersGroupName OBJECT-TYPE
       SYNTAX INTEGER {
                  g7231(0)
,
                  g711Alaw64k(1)
,
                  g711Ulaw64k(2)
,
                  g729(3)
,
                  g726(5)
,
                  g726r16(6)
,
                  g726r24(7)
,
                  g726r32(8)
,
                  g726r40(9)
,
                  netCoder8(10)
,
                  netCoder6-4(11)
,
                  netCoder7-2(12)
,
                  netCoder8-8(13)
,
                  gWTransparent(14)
,
                  g729AnnexB(17)
,
                  eVRC(22)
,
                  amr(23)
,
                  gsm-fr(24)
,
                  gsm-ms(25)
,
                  gsmEfr(26)
,
                  iLBC(27)
,
                  qCELP(28)
,
                  t38(29)
,
                  g711Alaw64k-VBD (30)
,
                  g711Ulaw64k-VBD (31)
,
                  eVRC-B(32)
,
                  g722(33)
,
                  aMR-WB(34)
,
                  eg711Alaw(35)
,
                  eg711Ulaw(36)
,
                   g7291(37)
,
                  v1501mr(38)
,
                  ms-rta-nb(39)
,
                  wb-rta(40)
,
                  speex-NB(41)
,
                  speex-WB(42)
,
                  silk-nb(43)
,
                  silk-wb(44)
,
                  invalideCoder(99)

                  }
       MAX-ACCESS read-create
       STATUS current
       DESCRIPTION
           "allowed Coders Group name.
Access: Offline.
AC INI-Param: AllowedCodersGroup_Name"
       ::= {allowedCodersGroupEntry 6}



     -- ****************************************
     -- allowedVideoCodersGroupFather table declaration
     -- ****************************************
     allowedVideoCodersGroupFatherTable OBJECT-TYPE
       SYNTAX SEQUENCE OF AllowedVideoCodersGroupFatherEntry
       MAX-ACCESS not-accessible
       STATUS current
       DESCRIPTION
           ""
       ::= {coders 11}



     -- ****************************************
     -- allowedVideoCodersGroupFather table entry
     -- ****************************************
     allowedVideoCodersGroupFatherEntry OBJECT-TYPE
       SYNTAX AllowedVideoCodersGroupFatherEntry
       MAX-ACCESS not-accessible
       STATUS current
       DESCRIPTION
           ""
       INDEX {allowedVideoCodersGroupFatherIndex}
       ::= {allowedVideoCodersGroupFatherTable 1}



     -- ****************************************
     -- allowedVideoCodersGroupFather TABLE
     -- ****************************************
     AllowedVideoCodersGroupFatherEntry ::= SEQUENCE {
       allowedVideoCodersGroupFatherIndex              Unsigned32,
       allowedVideoCodersGroupFatherName               SnmpAdminString,
       allowedVideoCodersGroupFatherNumOfEntries       Unsigned32
     }



     allowedVideoCodersGroupFatherIndex OBJECT-TYPE
       SYNTAX Unsigned32 (0..4)
       MAX-ACCESS not-accessible
       STATUS current
       DESCRIPTION
           "Index Field for line. Internal parameter.
AC INI-Param: AllowedVideoCodersGroupFather_Index"
       ::= {allowedVideoCodersGroupFatherEntry 1}



     allowedVideoCodersGroupFatherName OBJECT-TYPE
       SYNTAX SnmpAdminString (SIZE (0..0))
       MAX-ACCESS read-only
       STATUS current
       DESCRIPTION
           "Indicates the TableIdx Of AllowedVideoCodersGroup.
AC INI-Param: AllowedVideoCodersGroupFather_Name"
       ::= {allowedVideoCodersGroupFatherEntry 2}



     allowedVideoCodersGroupFatherNumOfEntries OBJECT-TYPE
       SYNTAX Unsigned32 (0..9)
       MAX-ACCESS read-only
       STATUS current
       DESCRIPTION
           "Indicates the Index Of AllowedVideoCodersGroup.
AC INI-Param: AllowedVideoCodersGroupFather_NumOfEntries"
       ::= {allowedVideoCodersGroupFatherEntry 3}



     -- ****************************************
     -- allowedVideoCodersGroup table declaration
     -- ****************************************
     allowedVideoCodersGroupTable OBJECT-TYPE
       SYNTAX SEQUENCE OF AllowedVideoCodersGroupEntry
       MAX-ACCESS not-accessible
       STATUS current
       DESCRIPTION
           ""
       ::= {coders 12}



     -- ****************************************
     -- allowedVideoCodersGroup table entry
     -- ****************************************
     allowedVideoCodersGroupEntry OBJECT-TYPE
       SYNTAX AllowedVideoCodersGroupEntry
       MAX-ACCESS not-accessible
       STATUS current
       DESCRIPTION
           ""
       INDEX {allowedVideoCodersGroupTableIdx,allowedVideoCodersGroupIndex}
       ::= {allowedVideoCodersGroupTable 1}



     -- ****************************************
     -- allowedVideoCodersGroup TABLE
     -- ****************************************
     AllowedVideoCodersGroupEntry ::= SEQUENCE {
       allowedVideoCodersGroupTableIdx                 Unsigned32,
       allowedVideoCodersGroupIndex                    Unsigned32,
       allowedVideoCodersGroupRowStatus                RowStatus,
       allowedVideoCodersGroupAction                   INTEGER,
       allowedVideoCodersGroupActionRes                INTEGER,
       allowedVideoCodersGroupName                     SnmpAdminString
     }



     allowedVideoCodersGroupTableIdx OBJECT-TYPE
       SYNTAX Unsigned32 (0..4)
       MAX-ACCESS not-accessible
       STATUS current
       DESCRIPTION
           "Index field for table.
AC INI-Param: N/A"
       ::= {allowedVideoCodersGroupEntry 1}



     allowedVideoCodersGroupIndex OBJECT-TYPE
       SYNTAX Unsigned32 (0..9)
       MAX-ACCESS not-accessible
       STATUS current
       DESCRIPTION
           "Index Field for line.
AC INI-Param: AllowedVideoCodersGroup_Index"
       ::= {allowedVideoCodersGroupEntry 2}



     allowedVideoCodersGroupRowStatus OBJECT-TYPE
       SYNTAX RowStatus
       MAX-ACCESS read-create
       STATUS current
       DESCRIPTION
           "ROWSTATUS field for line.
Access: Offline.
AC INI-Param: N/A"
       ::= {allowedVideoCodersGroupEntry 3}



     allowedVideoCodersGroupAction OBJECT-TYPE
       SYNTAX INTEGER {
                  none(0)

                  }
       MAX-ACCESS read-create
       STATUS current
       DESCRIPTION
           "Mangement Field for ACTIONS.
Access: Offline.
AC INI-Param: N/A"
       ::= {allowedVideoCodersGroupEntry 4}



     allowedVideoCodersGroupActionRes OBJECT-TYPE
       SYNTAX INTEGER {
                  succeeded(0)

                  }
       MAX-ACCESS read-only
       STATUS current
       DESCRIPTION
           "Mangement Field for ACTIONS RESULT.
AC INI-Param: N/A"
       ::= {allowedVideoCodersGroupEntry 5}



     allowedVideoCodersGroupName OBJECT-TYPE
       SYNTAX SnmpAdminString (SIZE (0..24))
       MAX-ACCESS read-create
       STATUS current
       DESCRIPTION
           "allowed Video Coders Group name.
Access: Offline.
AC INI-Param: AllowedVideoCodersGroup_Name"
       ::= {allowedVideoCodersGroupEntry 6}



     supServices OBJECT IDENTIFIER ::= {common 7}


     supServicesEnableHold OBJECT-TYPE
       SYNTAX INTEGER {
                  no(0)
,
                  yes(1)

                  }
       MAX-ACCESS read-write
       STATUS current
       DESCRIPTION
           "Enable Call Hold service.
Access: Instant.
AC INI-Param: ENABLEHOLD"
       ::= {supServices 1}



     supServicesNameID OBJECT-TYPE
       SYNTAX INTEGER {
                  disable(0)
,
                  enable(1)

                  }
       MAX-ACCESS read-write
       STATUS obsolete
       DESCRIPTION
           "Enable Name Identification service.
Access: Instant.
AC INI-Param: ENABLENAMEIDENTIFICATION"
       ::= {supServices 2}



     supServicesHoldFormat OBJECT-TYPE
       SYNTAX INTEGER {
                  zeroIP(0)
,
                  sendOnly(1)
,
                  inactive(2)

                  }
       MAX-ACCESS read-write
       STATUS current
       DESCRIPTION
           "Call Hold format - Zero IP, 'sendonly' SDP attribute or Original
IP and 'inactive' attribute.
Access: Instant.
AC INI-Param: HOLDFORMAT"
       ::= {supServices 3}



     supServicesSendMeteringMessageToIP OBJECT-TYPE
       SYNTAX INTEGER {
                  disable(0)
,
                  enable(1)

                  }
       MAX-ACCESS read-write
       STATUS current
       DESCRIPTION
           "Send metering messages to IP on detection of analog metering
pulses.
Access: Instant.
AC INI-Param: SENDMETERING2IP"
       ::= {supServices 4}



     supServicesHeldTimeout OBJECT-TYPE
       SYNTAX Integer32 (-1..2400)
       MAX-ACCESS read-write
       STATUS current
       DESCRIPTION
           "Maximum time allowed for call to be retreived from IP (seconds).
Access: Instant.
AC INI-Param: HELDTIMEOUT"
       ::= {supServices 5}



     supServicesHookFlashCode OBJECT-TYPE
       SYNTAX SnmpAdminString (SIZE (0..25))
       MAX-ACCESS read-write
       STATUS current
       DESCRIPTION
           "If this code received during session, act as if hook flash received
from the TEL side.
This parameter can use DIGIT MAP syntax.
Access: Instant.
AC INI-Param: HookFlashCode"
       ::= {supServices 6}



     supServicesCHRRTimeout OBJECT-TYPE
       SYNTAX Unsigned32
       MAX-ACCESS read-write
       STATUS current
       DESCRIPTION
           "Call hold reminder ring maximum ringing time (in seconds).
Access: Instant.
AC INI-Param: CHRRTIMEOUT"
       ::= {supServices 7}



     supServicesEnableHold2ISDN OBJECT-TYPE
       SYNTAX INTEGER {
                  disable(0)
,
                  enable(1)

                  }
       MAX-ACCESS read-write
       STATUS current
       DESCRIPTION
           "Enable Hold/retrieve from and to ISDN.
Access: Instant.
AC INI-Param: ENABLEHOLD2ISDN"
       ::= {supServices 8}



     supServicesEnableMOH OBJECT-TYPE
       SYNTAX INTEGER {
                  disable(0)
,
                  enable(1)

                  }
       MAX-ACCESS read-write
       STATUS current
       DESCRIPTION
           "FXS: enable playing Music On Hold (instead of Held tone to the
PSTN side).
Access: Instant.
AC INI-Param: EnableMOH"
       ::= {supServices 9}



     supServicesBlindTransferDisconnectTimeout OBJECT-TYPE
       SYNTAX Unsigned32 (0..1000000)
       MAX-ACCESS read-write
       STATUS current
       DESCRIPTION
           "Maximum time (milliseconds) to wait for disconnect from tel
before performing blind transfer.
Access: Instant.
AC INI-Param: BLINDTRANSFERDISCONNECTTIMEOUT"
       ::= {supServices 30}



     supServicesCodeCFU OBJECT-TYPE
       SYNTAX SnmpAdminString (SIZE (0..15))
       MAX-ACCESS read-write
       STATUS current
       DESCRIPTION
           "Supp Serv code for activating Call Forward Unconditional.
Access: Instant.
AC INI-Param: SUPPSERVCODECFU"
       ::= {supServices 31}



     supServicesCodeCFUDeact OBJECT-TYPE
       SYNTAX SnmpAdminString (SIZE (0..15))
       MAX-ACCESS read-write
       STATUS current
       DESCRIPTION
           "Supp Serv code for deactivating Call Forward Unconditional.
Access: Instant.
AC INI-Param: SUPPSERVCODECFUDEACT"
       ::= {supServices 32}



     supServicesCodeCFB OBJECT-TYPE
       SYNTAX SnmpAdminString (SIZE (0..15))
       MAX-ACCESS read-write
       STATUS current
       DESCRIPTION
           "Supp Serv code for activating Call Forward Busy.
Access: Instant.
AC INI-Param: SUPPSERVCODECFB"
       ::= {supServices 33}



     supServicesCodeCFBDeact OBJECT-TYPE
       SYNTAX SnmpAdminString (SIZE (0..15))
       MAX-ACCESS read-write
       STATUS current
       DESCRIPTION
           "Supp Serv code for deactivating Call Forward Busy.
Access: Instant.
AC INI-Param: SUPPSERVCODECFBDEACT"
       ::= {supServices 34}



     supServicesCodeCFNR OBJECT-TYPE
       SYNTAX SnmpAdminString (SIZE (0..15))
       MAX-ACCESS read-write
       STATUS current
       DESCRIPTION
           "Supp Serv code for activating Call Forward No Reply.
Access: Instant.
AC INI-Param: SUPPSERVCODECFNR"
       ::= {supServices 35}



     supServicesCodeCFNRDeact OBJECT-TYPE
       SYNTAX SnmpAdminString (SIZE (0..15))
       MAX-ACCESS read-write
       STATUS current
       DESCRIPTION
           "Supp Serv code for deactivating Call Forward No Reply.
Access: Instant.
AC INI-Param: SUPPSERVCODECFNRDEACT"
       ::= {supServices 36}



     transfer OBJECT IDENTIFIER ::= {supServices 10}


     transferEnable OBJECT-TYPE
       SYNTAX INTEGER {
                  no(0)
,
                  yes(1)

                  }
       MAX-ACCESS read-write
       STATUS current
       DESCRIPTION
           "Enable Call Transfer service.
Access: Instant.
AC INI-Param: ENABLETRANSFER"
       ::= {transfer 1}



     transferXferPrefix OBJECT-TYPE
       SYNTAX SnmpAdminString (SIZE (0..9))
       MAX-ACCESS read-write
       STATUS current
       DESCRIPTION
           "Prefix added to the called number of a transferred call.
Access: Instant.
AC INI-Param: XFERPREFIX"
       ::= {transfer 2}



     callWaiting OBJECT IDENTIFIER ::= {supServices 11}


     callWaitingEnable OBJECT-TYPE
       SYNTAX INTEGER {
                  no(0)
,
                  yes(1)

                  }
       MAX-ACCESS read-write
       STATUS current
       DESCRIPTION
           "Enable Call Waiting service.
Access: Instant.
AC INI-Param: ENABLECALLWAITING"
       ::= {callWaiting 1}



     callWaitingNumberOfIndications OBJECT-TYPE
       SYNTAX Unsigned32 (1..100)
       MAX-ACCESS read-write
       STATUS current
       DESCRIPTION
           "Number of Call Waiting indications to be played to the user.
Access: Instant.
AC INI-Param: NUMBEROFWAITINGINDICATIONS"
       ::= {callWaiting 2}



     callWaitingTimeBetweenIndications OBJECT-TYPE
       SYNTAX Unsigned32 (1..100)
       MAX-ACCESS read-write
       STATUS current
       DESCRIPTION
           "Time between one call waiting indication to the next (seconds).
Access: Instant.
AC INI-Param: TIMEBETWEENWAITINGINDICATIONS"
       ::= {callWaiting 3}



     callWaitingWaitingBeepDuration OBJECT-TYPE
       SYNTAX Unsigned32 (100..65535)
       MAX-ACCESS read-write
       STATUS current
       DESCRIPTION
           "Call Waiting tone beep length (msec).
Access: Instant.
AC INI-Param: WAITINGBEEPDURATION"
       ::= {callWaiting 4}



     callWaitingTimeBeforeWaitingIndications OBJECT-TYPE
       SYNTAX Unsigned32 (0..100)
       MAX-ACCESS read-write
       STATUS current
       DESCRIPTION
           "Time before call waiting indication is sent to a busy line (seconds).
Access: Instant.
AC INI-Param: TIMEBEFOREWAITINGINDICATIONS"
       ::= {callWaiting 5}



     forwardSettings OBJECT IDENTIFIER ::= {supServices 12}


     forwardSettingsEnable OBJECT-TYPE
       SYNTAX INTEGER {
                  no(0)
,
                  yes(1)

                  }
       MAX-ACCESS read-write
       STATUS current
       DESCRIPTION
           "Enable Call Forward service.
Access: Instant.
AC INI-Param: ENABLEFORWARD"
       ::= {forwardSettings 1}



     -- ****************************************
     -- forward table declaration
     -- ****************************************
     forwardTable OBJECT-TYPE
       SYNTAX SEQUENCE OF ForwardEntry
       MAX-ACCESS not-accessible
       STATUS current
       DESCRIPTION
           ""
       ::= {forwardSettings 21}



     -- ****************************************
     -- forward table entry
     -- ****************************************
     forwardEntry OBJECT-TYPE
       SYNTAX ForwardEntry
       MAX-ACCESS not-accessible
       STATUS current
       DESCRIPTION
           ""
       INDEX {forwardIndex}
       ::= {forwardTable 1}



     -- ****************************************
     -- forward TABLE
     -- ****************************************
     ForwardEntry ::= SEQUENCE {
       forwardIndex                                    Unsigned32,
       forwardIsUsed                                   INTEGER,
       forwardAction                                   INTEGER,
       forwardActionResult                             INTEGER,
       forwardForwardType                              INTEGER,
       forwardForwardedToNumber                        SnmpAdminString,
       forwardTimeForNoReply                           Unsigned32,
       forwardModule                                   Unsigned32,
       forwardPort                                     Unsigned32
     }



     forwardIndex OBJECT-TYPE
       SYNTAX Unsigned32 (0..23)
       MAX-ACCESS read-only
       STATUS current
       DESCRIPTION
           "Entry number, starting at 0.
AC INI-Param: FwdInfo_Index"
       ::= {forwardEntry 1}



     forwardIsUsed OBJECT-TYPE
       SYNTAX INTEGER {
                  no(0)
,
                  yes(1)

                  }
       MAX-ACCESS read-write
       STATUS current
       DESCRIPTION
           "Is this index used.
AC INI-Param: FwdInfo_IsUsed"
       ::= {forwardEntry 2}



     forwardAction OBJECT-TYPE
       SYNTAX INTEGER {
                  developmentImpending(0)

                  }
       MAX-ACCESS read-only
       STATUS current
       DESCRIPTION
           "Development Impending.
AC INI-Param: N/A"
       ::= {forwardEntry 3}



     forwardActionResult OBJECT-TYPE
       SYNTAX INTEGER {
                  developmentImpending(0)

                  }
       MAX-ACCESS read-only
       STATUS current
       DESCRIPTION
           "Development Impending.
AC INI-Param: N/A"
       ::= {forwardEntry 4}



     forwardForwardType OBJECT-TYPE
       SYNTAX INTEGER {
                  unknown(0)
,
                  busy(1)
,
                  immediate(2)
,
                  noAnswer(3)
,
                  busyOrNoAnswer(4)
,
                  dontDisturb(5)

                  }
       MAX-ACCESS read-write
       STATUS current
       DESCRIPTION
           "
Access: Instant.
AC INI-Param: FwdInfo_Type"
       ::= {forwardEntry 5}



     forwardForwardedToNumber OBJECT-TYPE
       SYNTAX SnmpAdminString (SIZE (0..50))
       MAX-ACCESS read-write
       STATUS current
       DESCRIPTION
           "
Access: Instant.
AC INI-Param: FwdInfo_Destination"
       ::= {forwardEntry 6}



     forwardTimeForNoReply OBJECT-TYPE
       SYNTAX Unsigned32 (0..180)
       MAX-ACCESS read-write
       STATUS current
       DESCRIPTION
           "
Access: Instant.
AC INI-Param: FwdInfo_NoReplyTime"
       ::= {forwardEntry 7}



     forwardModule OBJECT-TYPE
       SYNTAX Unsigned32 (0..255)
       MAX-ACCESS read-only
       STATUS current
       DESCRIPTION
           "Module.
AC INI-Param: FwdInfo_Module"
       ::= {forwardEntry 8}



     forwardPort OBJECT-TYPE
       SYNTAX Unsigned32 (0..65535)
       MAX-ACCESS read-only
       STATUS current
       DESCRIPTION
           "Port.
AC INI-Param: FwdInfo_Port"
       ::= {forwardEntry 9}



     mWI OBJECT IDENTIFIER ::= {supServices 13}


     mWIEnable OBJECT-TYPE
       SYNTAX INTEGER {
                  disable(0)
,
                  enable(1)

                  }
       MAX-ACCESS read-write
       STATUS current
       DESCRIPTION
           "Enable MWI support (Message Waiting Indicator).
Access: Instant.
AC INI-Param: ENABLEMWI"
       ::= {mWI 1}



     mWIAnalogLamp OBJECT-TYPE
       SYNTAX INTEGER {
                  disable(0)
,
                  enable(1)

                  }
       MAX-ACCESS read-write
       STATUS current
       DESCRIPTION
           "Enable MWI support using an analog lamp (110 Volt).
Access: Instant.
AC INI-Param: MWIANALOGLAMP"
       ::= {mWI 2}



     mWIDisplay OBJECT-TYPE
       SYNTAX INTEGER {
                  disable(0)
,
                  enable(1)

                  }
       MAX-ACCESS read-write
       STATUS current
       DESCRIPTION
           "Enable MWI support using Caller ID interface.
Access: Instant.
AC INI-Param: MWIDISPLAY"
       ::= {mWI 3}



     mWIServerIP OBJECT-TYPE
       SYNTAX SnmpAdminString (SIZE (0..49))
       MAX-ACCESS read-write
       STATUS current
       DESCRIPTION
           "MWI server IP address.
Access: Instant.
AC INI-Param: MWISERVERIP"
       ::= {mWI 4}



     mWIExpirationTime OBJECT-TYPE
       SYNTAX Unsigned32 (10..2000000)
       MAX-ACCESS read-write
       STATUS current
       DESCRIPTION
           "MWI service subscription expiration time (seconds).
Access: Instant.
AC INI-Param: MWIEXPIRATIONTIME"
       ::= {mWI 5}



     mWIServerTransportType OBJECT-TYPE
       SYNTAX INTEGER {
                  notConfigured(-1)
,
                  uDP(0)
,
                  tCP(1)
,
                  tLS(2)

                  }
       MAX-ACCESS read-write
       STATUS current
       DESCRIPTION
           "MWI server transport type.
Access: Instant.
AC INI-Param: MWISERVERTRANSPORTTYPE"
       ::= {mWI 6}



     supServicesConference OBJECT IDENTIFIER ::= {supServices 14}


     supServicesConferenceEnable3Way OBJECT-TYPE
       SYNTAX INTEGER {
                  disable(0)
,
                  enable(1)

                  }
       MAX-ACCESS read-write
       STATUS current
       DESCRIPTION
           "Enable 3 way conference feature.
Access: Offline.
AC INI-Param: ENABLE3WAYCONFERENCE"
       ::= {supServicesConference 1}



     supServicesConferenceEstablishCode OBJECT-TYPE
       SYNTAX SnmpAdminString (SIZE (0..25))
       MAX-ACCESS read-write
       STATUS current
       DESCRIPTION
           "Control Key activation of the 3 way conference.
Access: Instant.
AC INI-Param: CONFERENCECODE"
       ::= {supServicesConference 2}



     tones OBJECT IDENTIFIER ::= {common 8}


     tonesTimeForReorderTone OBJECT-TYPE
       SYNTAX Unsigned32 (0..255)
       MAX-ACCESS read-write
       STATUS current
       DESCRIPTION
           "Duration of reorder tone playing before FXO releases line.
Access: Instant.
AC INI-Param: TIMEFORREORDERTONE"
       ::= {tones 1}



     tonesTimeForDialTone OBJECT-TYPE
       SYNTAX Unsigned32 (0..60)
       MAX-ACCESS read-write
       STATUS current
       DESCRIPTION
           "Duration of played dial tone after the gateway seizes the line
in response to ringing.
Access: Instant.
AC INI-Param: TIMEFORDIALTONE"
       ::= {tones 2}



     tonesPlayRBTone2Ip OBJECT-TYPE
       SYNTAX INTEGER {
                  no(0)
,
                  yes(1)

                  }
       MAX-ACCESS read-write
       STATUS current
       DESCRIPTION
           "Enable ringback tone playing towards IP. Refer to User's Manual
for details.
Access: Instant.
AC INI-Param: PLAYRBTONE2IP"
       ::= {tones 3}



     tonesPlayRBTone2Tel OBJECT-TYPE
       SYNTAX INTEGER {
                  doNotPlay(0)
,
                  playOnLocal(1)
,
                  preferIp(2)
,
                  playLocalUntilRemoteMediaArrives(3)

                  }
       MAX-ACCESS read-write
       STATUS current
       DESCRIPTION
           "Enable ringback tone playing towards Tel side. Refer to User's
Manual for details.
Access: Instant.
AC INI-Param: PLAYRBTONE2TEL"
       ::= {tones 4}



     tonesStutterToneDuration OBJECT-TYPE
       SYNTAX Unsigned32 (0..60000)
       MAX-ACCESS read-write
       STATUS current
       DESCRIPTION
           "Time for playing confirmation tone before normal dial tone is
played (msec).
Access: Instant.
AC INI-Param: STUTTERTONEDURATION"
       ::= {tones 5}



     tonesPlayRBToneXferSuccess OBJECT-TYPE
       SYNTAX INTEGER {
                  disable(0)
,
                  enable(1)

                  }
       MAX-ACCESS read-write
       STATUS current
       DESCRIPTION
           "Play RB tone on transfer success.
Access: Instant.
AC INI-Param: PLAYRBTONEONXFER"
       ::= {tones 6}



     tonesFirstCallRBTId OBJECT-TYPE
       SYNTAX Integer32 (-1..1000)
       MAX-ACCESS read-write
       STATUS current
       DESCRIPTION
           "The index of the first Call RB tone in the call-progress tones
 file.
Access: Instant.
AC INI-Param: FIRSTCALLRBTID"
       ::= {tones 7}



     tonesPrecedenceRingingType OBJECT-TYPE
       SYNTAX Integer32 (-1..16)
       MAX-ACCESS read-write
       STATUS current
       DESCRIPTION
           "The index of the first Call RB tone in the call-progress tones
 file.
Access: Instant.
AC INI-Param: PRECEDENCERINGINGTYPE"
       ::= {tones 8}



     tonesFirstCallWaitingToneID OBJECT-TYPE
       SYNTAX Integer32 (-1..1000)
       MAX-ACCESS read-write
       STATUS current
       DESCRIPTION
           "The index of the first Call Waiting tone in the call-progress
tones  file.
Access: Instant.
AC INI-Param: FIRSTCALLWAITINGTONEID"
       ::= {tones 9}



     tonesEnableComfortTone OBJECT-TYPE
       SYNTAX INTEGER {
                  disable(0)
,
                  enable(1)

                  }
       MAX-ACCESS read-write
       STATUS current
       DESCRIPTION
           "Enable Comfort Tone for playing a patience comfort tone between
Invite and 18x response.
[0] - Disabled
[1] - Enabled. Comfort Tone will be played.
Access: Instant.
AC INI-Param: ENABLECOMFORTTONE"
       ::= {tones 10}



     tonesCutThroughTimeForReorderTone OBJECT-TYPE
       SYNTAX Unsigned32 (0..30)
       MAX-ACCESS read-write
       STATUS current
       DESCRIPTION
           "Duration of reorder tone played after release from IP side for
CutThrogh application.
Access: Instant.
AC INI-Param: CUTTHROUGHTIMEFORREORDERTONE"
       ::= {tones 11}



     logger OBJECT IDENTIFIER ::= {common 9}


     loggerGwAppCdrReportLevel OBJECT-TYPE
       SYNTAX INTEGER {
                  no(0)
,
                  endCall(1)
,
                  startAndEndCall(2)
,
                  connectAndEndCall(3)
,
                  startConnectAndEndCall(4)

                  }
       MAX-ACCESS read-write
       STATUS current
       DESCRIPTION
           "CDR reports timing.
Access: Instant.
AC INI-Param: N/A"
       ::= {logger 1}



     loggerGwDebugLevel OBJECT-TYPE
       SYNTAX INTEGER {
                  logLevel0(0)
,
                  logLevel1(1)
,
                  logLevel2(2)
,
                  logLevel3(3)
,
                  logLevel4(4)
,
                  logLevel5(5)
,
                  logLevel6(6)
,
                  logLevel7(7)
,
                  logLevel100(100)
,
                  logLevel200(200) 

                  }
       MAX-ACCESS read-write
       STATUS current
       DESCRIPTION
           "Configure different debug level.
Access: Instant.
AC INI-Param: N/A"
       ::= {logger 2}



     loggerCDRSyslogServerIP OBJECT-TYPE
       SYNTAX IpAddress
       MAX-ACCESS read-write
       STATUS deprecated
       DESCRIPTION
           "Syslog server IP address for sending CDRs.
Access: Instant.
AC INI-Param: CDRSYSLOGSERVERIP"
       ::= {logger 3}



     loggerGwAppMediaCdrReportLevel OBJECT-TYPE
       SYNTAX INTEGER {
                  none(0)
,
                  endMedia(1)
,
                  startAndEndMedia(2)
,
                  updateAndEndMedia(3)
,
                  startAndEndAndUpdateMedia(4)

                  }
       MAX-ACCESS read-write
       STATUS current
       DESCRIPTION
           "Media CDR Report Level.
Access: Instant.
AC INI-Param: MEDIACDRREPORTLEVEL"
       ::= {logger 4}



     loggerDebugRecordingDestIP OBJECT-TYPE
       SYNTAX IpAddress
       MAX-ACCESS read-write
       STATUS deprecated
       DESCRIPTION
           "Defines the destination IP address for Debug Recording default
target.
Access: Instant.
AC INI-Param: DebugRecordingDestIP"
       ::= {logger 5}



     loggerDebugRecordingDestPort OBJECT-TYPE
       SYNTAX Unsigned32 (1..65535)
       MAX-ACCESS read-write
       STATUS current
       DESCRIPTION
           "Defines the destination UDP Port for Debug Recording default
target.
Access: Instant.
AC INI-Param: DebugRecordingDestPort"
       ::= {logger 6}



     loggerDebugRecordingStatus OBJECT-TYPE
       SYNTAX INTEGER {
                  stop(0)
,
                  start(1)

                  }
       MAX-ACCESS read-write
       STATUS current
       DESCRIPTION
           "Determines if Debug Recording should be Stopped (0) or Started
(1).
Access: Instant.
AC INI-Param: DebugRecordingStatus"
       ::= {logger 7}



     -- ****************************************
     -- loggingFilters table declaration
     -- ****************************************
     loggingFiltersTable OBJECT-TYPE
       SYNTAX SEQUENCE OF LoggingFiltersEntry
       MAX-ACCESS not-accessible
       STATUS current
       DESCRIPTION
           "Logging Filters Table"
       ::= {logger 21}



     -- ****************************************
     -- loggingFilters table entry
     -- ****************************************
     loggingFiltersEntry OBJECT-TYPE
       SYNTAX LoggingFiltersEntry
       MAX-ACCESS not-accessible
       STATUS current
       DESCRIPTION
           ""
       INDEX {loggingFiltersIndex}
       ::= {loggingFiltersTable 1}



     -- ****************************************
     -- loggingFilters TABLE
     -- ****************************************
     LoggingFiltersEntry ::= SEQUENCE {
       loggingFiltersIndex                             Unsigned32,
       loggingFiltersRowStatus                         RowStatus,
       loggingFiltersAction                            INTEGER,
       loggingFiltersActionResult                      INTEGER,
       loggingFiltersType                              INTEGER,
       loggingFiltersValue                             SnmpAdminString,
       loggingFiltersSyslog                            INTEGER,
       loggingFiltersCaptureType                       INTEGER
     }



     loggingFiltersIndex OBJECT-TYPE
       SYNTAX Unsigned32 (0..29)
       MAX-ACCESS read-only
       STATUS current
       DESCRIPTION
           "The index of the cost group.
AC INI-Param: LoggingFilters_Index"
       ::= {loggingFiltersEntry 1}



     loggingFiltersRowStatus OBJECT-TYPE
       SYNTAX RowStatus
       MAX-ACCESS read-create
       STATUS current
       DESCRIPTION
           "Row-Status Textual Conventions as defined in RFC 2579: Textual
Conventions for SMIv2.
AC INI-Param: LoggingFilters_RowStatus"
       ::= {loggingFiltersEntry 2}



     loggingFiltersAction OBJECT-TYPE
       SYNTAX INTEGER {
                  developmentImpending(0)

                  }
       MAX-ACCESS read-only
       STATUS current
       DESCRIPTION
           "Development Impending.
AC INI-Param: LoggingFilters_Action"
       ::= {loggingFiltersEntry 3}



     loggingFiltersActionResult OBJECT-TYPE
       SYNTAX INTEGER {
                  developmentImpending(0)

                  }
       MAX-ACCESS read-only
       STATUS current
       DESCRIPTION
           "Development Impending.
AC INI-Param: LoggingFilters_ActionRes"
       ::= {loggingFiltersEntry 4}



     loggingFiltersType OBJECT-TYPE
       SYNTAX INTEGER {
                  unknownFilter(0)
,
                  anyFilter(1)
,
                  trunkIdFilter(2)
,
                  trunkGroupIdFilter(3)
,
                  bChannelFilter(4)
,
                  fxsFxoFilter(5)
,
                  telToIpFilter(6)
,
                  ipToTelFilter(7)
,
                  ipGroupdFilter(8)
,
                  srdFilter(9)
,
                  classificationFilter(10)
,
                  ipToIpRoutingFilter(11)
,
                  userFilter(12)

                  }
       MAX-ACCESS read-create
       STATUS current
       DESCRIPTION
           "Type of logging filter.
Access: Online.
AC INI-Param: LoggingFilters_FilterType"
       ::= {loggingFiltersEntry 5}



     loggingFiltersValue OBJECT-TYPE
       SYNTAX SnmpAdminString (SIZE (0..19))
       MAX-ACCESS read-create
       STATUS current
       DESCRIPTION
           "Value of log filter.
Access: Online.
AC INI-Param: LoggingFilters_Value"
       ::= {loggingFiltersEntry 6}



     loggingFiltersSyslog OBJECT-TYPE
       SYNTAX INTEGER {
                  disable(0)
,
                  enable(1)

                  }
       MAX-ACCESS read-create
       STATUS current
       DESCRIPTION
           "Print Syslog false(0) true(1).
Access: Online.
AC INI-Param: LoggingFilters_Syslog"
       ::= {loggingFiltersEntry 7}



     loggingFiltersCaptureType OBJECT-TYPE
       SYNTAX INTEGER {
                  captureNone(0)
,
                  captureSig(1)
,
                  captureSigMedia(2)
,
                   captureSigMediaPCM(3)
,
                  capturePSTN(4)

                  }
       MAX-ACCESS read-create
       STATUS current
       DESCRIPTION
           "Capture Type.
Access: Online.
AC INI-Param: LoggingFilters_CaptureType"
       ::= {loggingFiltersEntry 8}



     progressIndicators OBJECT IDENTIFIER ::= {common 10}


     progressIndicators2ISDN OBJECT-TYPE
       SYNTAX INTEGER {
                  notSet(-1)
,
                  localRB(0)
,
                  remoteRB1(1)
,
                  remoteRB8(8)

                  }
       MAX-ACCESS read-write
       STATUS obsolete
       DESCRIPTION
           "Override the value of progress indicator to ISDN side in ALERT
PROGRESS and PROCEEDING messages.
Access: Instant.
AC INI-Param: PROGRESSINDICATOR2ISDN"
       ::= {progressIndicators 1}



     progressIndicators2IP OBJECT-TYPE
       SYNTAX INTEGER {
                  notSet(-1)
,
                  localRB(0)
,
                  remoteRB1(1)
,
                  remoteRB8(8)

                  }
       MAX-ACCESS read-write
       STATUS current
       DESCRIPTION
           "Determine whether to send the Progress Indicator to IP.
Access: Instant.
AC INI-Param: PROGRESSINDICATOR2IP"
       ::= {progressIndicators 2}



     screeningIndicators OBJECT IDENTIFIER ::= {progressIndicators 20}


     screeningIndicators2Ip OBJECT-TYPE
       SYNTAX INTEGER {
                  notOverwrited(-1)
,
                  userProvided(0)
,
                  userPassed(1)
,
                  userFailed(2)
,
                  networkProvided(3)

                  }
       MAX-ACCESS read-write
       STATUS current
       DESCRIPTION
           "Override screening indicator value in Setup messages to IP.
Access: Instant.
AC INI-Param: SCREENINGIND2IP"
       ::= {screeningIndicators 1}



     screeningIndicators2ISDN OBJECT-TYPE
       SYNTAX INTEGER {
                  notOverwrited(-1)
,
                  userProvided(0)
,
                  userPassed(1)
,
                  userFailed(2)
,
                  networkProvided(3)

                  }
       MAX-ACCESS read-write
       STATUS current
       DESCRIPTION
           "Override screening indicator value in Setup messages to ISDN.
Access: Instant.
AC INI-Param: SCREENINGIND2ISDN"
       ::= {screeningIndicators 2}



     misc OBJECT IDENTIFIER ::= {common 11}


     miscDisconnectOnBusyTone OBJECT-TYPE
       SYNTAX INTEGER {
                  no(0)
,
                  yes(1)

                  }
       MAX-ACCESS read-write
       STATUS current
       DESCRIPTION
           "Release call if gateway receives busy or fast busy tone before
the call is answered.
Access: Instant.
AC INI-Param: DISCONNECTONBUSYTONE"
       ::= {misc 1}



     miscDisconnectOnSilence OBJECT-TYPE
       SYNTAX INTEGER {
                  no(0)
,
                  yes(1)

                  }
       MAX-ACCESS read-write
       STATUS current
       DESCRIPTION
           "Disconnect calls on a configured silence timeout.
Access: Offline.
AC INI-Param: ENABLESILENCEDISCONNECT"
       ::= {misc 2}



     miscEnableBusyOut OBJECT-TYPE
       SYNTAX INTEGER {
                  no(0)
,
                  yes(1)

                  }
       MAX-ACCESS read-write
       STATUS current
       DESCRIPTION
           "Take trunks out of service in case of LAN down.
Access: Instant.
AC INI-Param: ENABLEBUSYOUT"
       ::= {misc 3}



     miscSecureCallsFromIp OBJECT-TYPE
       SYNTAX INTEGER {
                  disable(0)
,
                  secureIncomingCalls(1)
,
                  secureAllCalls(2)

                  }
       MAX-ACCESS read-write
       STATUS current
       DESCRIPTION
           "Gateway will either only accept calls from IP addresses that
are defined in the Tel to IP Routing table (1) or handle all
calls from/to IP addresses that are defined in the Tel to
IP Routing table (2).
Access: Instant.
AC INI-Param: SECURECALLSFROMIP"
       ::= {misc 4}



     miscStaticNATIP OBJECT-TYPE
       SYNTAX SnmpAdminString (SIZE (0..15))
       MAX-ACCESS read-write
       STATUS current
       DESCRIPTION
           "static NAT IP, to be supported by the gateway.
Access: Offline.
AC INI-Param: STATICNATIP"
       ::= {misc 5}



     miscSilenceDisconnectTimeout OBJECT-TYPE
       SYNTAX Unsigned32 (10..28800)
       MAX-ACCESS read-write
       STATUS current
       DESCRIPTION
           "Defines the Silence period to be detected.
Access: Offline.
AC INI-Param: FarEndDisconnectSilencePeriod"
       ::= {misc 6}



     miscIsFaxUsed OBJECT-TYPE
       SYNTAX INTEGER {
                  noFax(0)
,
                  t38(1)
,
                  g711(2)
,
                  fallBack(3)

                  }
       MAX-ACCESS read-write
       STATUS current
       DESCRIPTION
           "Enable T.38 Fax signaling.
Access: Instant.
AC INI-Param: IsFaxUsed"
       ::= {misc 7}



     miscDelayTime OBJECT-TYPE
       SYNTAX Unsigned32 (0..45)
       MAX-ACCESS read-write
       STATUS current
       DESCRIPTION
           "Gateway delay time after reset (seconds).
Access: Instant.
AC INI-Param: GWAPPDelayTime"
       ::= {misc 8}



     miscDetFaxOnAnswerTone OBJECT-TYPE
       SYNTAX INTEGER {
                  disable(0)
,
                  enable(1)

                  }
       MAX-ACCESS read-write
       STATUS current
       DESCRIPTION
           "Start T.38 fax procedure after fax answer tone detection or
after HDLC preamble signal detection.
Access: Instant.
AC INI-Param: DETFAXONANSWERTONE"
       ::= {misc 9}



     miscDefaultReleaseCause OBJECT-TYPE
       SYNTAX Unsigned32 (1..128)
       MAX-ACCESS read-write
       STATUS current
       DESCRIPTION
           "The release cause that will be sent to IP or to Tel when gateway
initiates release by itself.
Access: Instant.
AC INI-Param: DEFAULTRELEASECAUSE"
       ::= {misc 10}



     miscT38UseRTPPort OBJECT-TYPE
       SYNTAX INTEGER {
                  disable(0)
,
                  enable(1)

                  }
       MAX-ACCESS read-write
       STATUS current
       DESCRIPTION
           "T.38 packets will be received on RTP port.
Access: Instant.
AC INI-Param: T38USERTPPORT"
       ::= {misc 11}



     miscRFC2833PayloadType OBJECT-TYPE
       SYNTAX Unsigned32 (96..127)
       MAX-ACCESS read-write
       STATUS current
       DESCRIPTION
           "control the RFC 2833 Relay RTP Payload type.
Access: Online.
AC INI-Param: RFC2833TxPayloadType"
       ::= {misc 12}



     miscIsCiscoSceMode OBJECT-TYPE
       SYNTAX INTEGER {
                  disable(0)
,
                  enable(1)

                  }
       MAX-ACCESS read-write
       STATUS current
       DESCRIPTION
           "In use with G.729 - if enabled and SCE=2 then AnnexB=no.
Access: Instant.
AC INI-Param: ISCISCOSCEMODE"
       ::= {misc 13}



     miscDisconnectOnDialTone OBJECT-TYPE
       SYNTAX INTEGER {
                  disable(0)
,
                  enable(1)

                  }
       MAX-ACCESS read-write
       STATUS current
       DESCRIPTION
           "Release call if gateway receives dial tone before the call is
answered or during voice session.
Access: Instant.
AC INI-Param: DISCONNECTONDIALTONE"
       ::= {misc 14}



     miscEnableSemiAttendedTransfer OBJECT-TYPE
       SYNTAX INTEGER {
                  disable(0)
,
                  enable(1)

                  }
       MAX-ACCESS read-write
       STATUS obsolete
       DESCRIPTION
           "
Access: Instant.
AC INI-Param: ENABLESEMIATTENDEDTRANSFER"
       ::= {misc 15}



     miscHookFlashCodeIP OBJECT-TYPE
       SYNTAX SnmpAdminString (SIZE (0..25))
       MAX-ACCESS read-write
       STATUS current
       DESCRIPTION
           "The string represent HookFlash, when reported to or from IP.
Currently used in H.323 only (H245UserOutput, H245Signal or
Q931UserInfo).
Access: Instant.
AC INI-Param: HookFlashCodeIP"
       ::= {misc 16}



     miscEnableFaxRerouting OBJECT-TYPE
       SYNTAX INTEGER {
                  disable(0)
,
                  enable(1)

                  }
       MAX-ACCESS read-write
       STATUS current
       DESCRIPTION
           "Enable rerouting of FAX calls to FAX destination.
Access: Instant.
AC INI-Param: ENABLEFAXREROUTING"
       ::= {misc 17}



     miscT38MaxDatagramSize OBJECT-TYPE
       SYNTAX Unsigned32 (122..1024)
       MAX-ACCESS read-write
       STATUS current
       DESCRIPTION
           "T.38 coder - Max Datagram Size.
Access: Instant.
AC INI-Param: T38MAXDATAGRAMSIZE"
       ::= {misc 18}



     miscIsdnDisconnectOnBusyTone OBJECT-TYPE
       SYNTAX INTEGER {
                  disable(0)
,
                  enable(1)

                  }
       MAX-ACCESS read-write
       STATUS current
       DESCRIPTION
           "1 - Release call if gateway receives busy or fast busy tone.
0 - don't release.
Access: Instant.
AC INI-Param: ISDNDISCONNECTONBUSYTONE"
       ::= {misc 19}



     miscFaxCNGMode OBJECT-TYPE
       SYNTAX INTEGER {
                  disable(0)
,
                  enable(1)

                  }
       MAX-ACCESS read-write
       STATUS current
       DESCRIPTION
           "Enables sending of ReInvite on detection of FAX CNG tone when
CNGDetectorMode=1.
Access: Instant.
AC INI-Param: FAXCNGMODE"
       ::= {misc 20}



     miscGracefulBusyOutTimeout OBJECT-TYPE
       SYNTAX Unsigned32 (0..3600)
       MAX-ACCESS read-write
       STATUS current
       DESCRIPTION
           "Graceful Busy Out Timeout in seconds. Sets the time before a
busy out signal will be sent to a trunk even if there are still
active calls on the trunk.
Access: Instant.
AC INI-Param: GRACEFULBUSYOUTTIMEOUT"
       ::= {misc 21}



     miscT38FaxMaxBufferSize OBJECT-TYPE
       SYNTAX Unsigned32 (500..3000)
       MAX-ACCESS read-write
       STATUS current
       DESCRIPTION
           "Defines the fax max buffer size in T38 SDP negotiation.
Access: Instant.
AC INI-Param: T38FAXMAXBUFFERSIZE"
       ::= {misc 22}



     miscReliableConnectionPersistentMode OBJECT-TYPE
       SYNTAX INTEGER {
                  disable(0)
,
                  enable(1)

                  }
       MAX-ACCESS read-write
       STATUS current
       DESCRIPTION
           "if set to 1 - All  TCP/TLS connections will be set as persistent
and will  not be released.
Access: Instant.
AC INI-Param: RELIABLECONNECTIONPERSISTENTMODE"
       ::= {misc 23}



     miscWANIPAddress OBJECT-TYPE
       SYNTAX IpAddress
       MAX-ACCESS read-write
       STATUS deprecated
       DESCRIPTION
           "Sets the WAN address to be used by VOIP signalling applications.
Range =  IPv4 address in dotted decimal notation
xxx.xxx.xxx.xxx
Default = 0.0.0.0.
Access: Instant.
AC INI-Param: WANIPAddress"
       ::= {misc 24}



     miscEnableDelayedOffer OBJECT-TYPE
       SYNTAX INTEGER {
                  disable(0)
,
                  enable(1)

                  }
       MAX-ACCESS read-write
       STATUS current
       DESCRIPTION
           "Send INVITE message with/without sdp offer.
[0] - (default) means SDP will be offered in the INVITE message.
[1] - means SDP will be offered by the other side in the first
reliable response(1xx or 200 OK INVITE).
Access: Instant.
AC INI-Param: ENABLEDELAYEDOFFER"
       ::= {misc 25}



     miscEnableNRTSubscription OBJECT-TYPE
       SYNTAX INTEGER {
                  disable(0)
,
                  enable(1)

                  }
       MAX-ACCESS read-write
       STATUS current
       DESCRIPTION
           "Enable subscription for Call forward ringtone Indicator service.
Access: Instant.
AC INI-Param: ENABLENRTSUBSCRIPTION"
       ::= {misc 26}



     miscASSubscribeIPGroupID OBJECT-TYPE
       SYNTAX Integer32 (-1..65525)
       MAX-ACCESS read-write
       STATUS current
       DESCRIPTION
           "IPGroup ID for AS server subscribe purposes.
Access: Instant.
AC INI-Param: ASSUBSCRIBEIPGROUPID"
       ::= {misc 27}



     miscNRTSubscriptionRetryTime OBJECT-TYPE
       SYNTAX Unsigned32 (0..2000000)
       MAX-ACCESS read-write
       STATUS current
       DESCRIPTION
           "NRT service subscription retry time after last subscription
failure (in seconds).
Access: Instant.
AC INI-Param: NRTSUBSCRIBERETRYTIME"
       ::= {misc 28}



     miscCallForwardRingToneID OBJECT-TYPE
       SYNTAX Unsigned32 (1..65525)
       MAX-ACCESS read-write
       STATUS current
       DESCRIPTION
           "Ringtone type for Call forward notification.
Access: Instant.
AC INI-Param: CALLFORWARDRINGTONEID"
       ::= {misc 29}



     miscKeyCallPickup OBJECT-TYPE
       SYNTAX SnmpAdminString (SIZE (0..15))
       MAX-ACCESS read-write
       STATUS current
       DESCRIPTION
           "Keying sequence for performing call pickup.
Access: Instant.
AC INI-Param: KEYCALLPICKUP"
       ::= {misc 30}



     miscEnableRFC4117Transcoding OBJECT-TYPE
       SYNTAX INTEGER {
                  disable(0)
,
                  enable(1)

                  }
       MAX-ACCESS read-write
       STATUS current
       DESCRIPTION
           "Enable transcoding call  RFC4117.
Access: Offline.
AC INI-Param: ENABLERFC4117TRANSCODING"
       ::= {misc 31}



     miscEnableSingleDSPTranscoding OBJECT-TYPE
       SYNTAX INTEGER {
                  disable(0)
,
                  enable(1)

                  }
       MAX-ACCESS read-write
       STATUS obsolete
       DESCRIPTION
           "Enable/Disable using single DSP for g711 <--> LBR coder.
Access: Offline.
AC INI-Param: ENABLESINGLEDSPTRANSCODING"
       ::= {misc 32}



     miscEnableNetworkISDNTransfer OBJECT-TYPE
       SYNTAX INTEGER {
                  disable(0)
,
                  enable(1)

                  }
       MAX-ACCESS read-write
       STATUS current
       DESCRIPTION
           "if set to 0 reject ISDN transfer request.
Access: Instant.
AC INI-Param: ENABLENETWORKISDNTRANSFER"
       ::= {misc 33}



     miscLDAPocsNumberAttributeName OBJECT-TYPE
       SYNTAX SnmpAdminString (SIZE (0..48))
       MAX-ACCESS read-write
       STATUS current
       DESCRIPTION
           "The name of the attribute which represents the user OCS  number
in the Microsoft AD data base.
Access: Instant.
AC INI-Param: MSLDAPOCSNUMATTRIBUTENAME"
       ::= {misc 34}



     miscLDAPpbxNumberAttributeName OBJECT-TYPE
       SYNTAX SnmpAdminString (SIZE (0..48))
       MAX-ACCESS read-write
       STATUS current
       DESCRIPTION
           "The name of the attribute which represents the user PBX number
in the Microsoft AD data base.
Access: Instant.
AC INI-Param: MSLDAPPBXNUMATTRIBUTENAME"
       ::= {misc 35}



     miscLDAPMobileNumberAttributeName OBJECT-TYPE
       SYNTAX SnmpAdminString (SIZE (0..48))
       MAX-ACCESS read-write
       STATUS current
       DESCRIPTION
           "The name of the attribute which represents the user Mobile number
in the Microsoft AD data base.
Access: Instant.
AC INI-Param: MSLDAPMOBILENUMATTRIBUTENAME"
       ::= {misc 36}



     miscAmdBeepDetectionMode OBJECT-TYPE
       SYNTAX INTEGER {
                  disabled(0)
,
                  startAfterAmdDetection(1)
,
                  startImmediately(2)

                  }
       MAX-ACCESS read-write
       STATUS current
       DESCRIPTION
           "Set the AMD beep detection mode:
 0 - disabled
1- start after AMD detection
2 - start immediately.
Access: Instant.
AC INI-Param: AmdBeepDetectionMode"
       ::= {misc 37}



     miscFakeRetryAfter OBJECT-TYPE
       SYNTAX Unsigned32 (0..3600)
       MAX-ACCESS read-write
       STATUS current
       DESCRIPTION
           "0 - disabled. 
Any positive value - when the GW receives 503 without Retry-After
response-header, it will behave as the 503 response includes
a Retry-After response-header with the period specified
by this parameter.
Access: Instant.
AC INI-Param: FAKERETRYAFTER"
       ::= {misc 38}



     miscEnableEarly183 OBJECT-TYPE
       SYNTAX INTEGER {
                  disable(0)
,
                  enable(1)

                  }
       MAX-ACCESS read-write
       STATUS current
       DESCRIPTION
           "Enable Early 183.
Access: Instant.
AC INI-Param: ENABLEEARLY183"
       ::= {misc 39}



     miscSelectSourceHeaderForCalledNumber OBJECT-TYPE
       SYNTAX INTEGER {
                  useRequestURIHeader(0)
,
                  useToHeader(1)
,
                  usePCalledPartyIDHeader(2)

                  }
       MAX-ACCESS read-write
       STATUS current
       DESCRIPTION
           "Select source header for called number (IP->TEL), either from
the user part of To header or the P-Called-Party-ID header.
0- use RequestURI header
1- use To header
2- use P-Called-Party-ID header.
Access: Instant.
AC INI-Param: SELECTSOURCEHEADERFORCALLEDNUMBER"
       ::= {misc 40}



     miscH323GKRegister OBJECT-TYPE
       SYNTAX INTEGER {
                  disable(0)
,
                  enable(1)

                  }
       MAX-ACCESS read-write
       STATUS current
       DESCRIPTION
           "This parameter related to Register/UnRegister buttons.
Access: Instant.
AC INI-Param: SHOULDREGISTER"
       ::= {misc 41}



     miscTel2IPSourceNumberMappingDialPlanMode OBJECT-TYPE
       SYNTAX INTEGER {
                  reserved(0)
,
                  replaced(1)

                  }
       MAX-ACCESS read-write
       STATUS current
       DESCRIPTION
           "Tel to IP Source Number Mapping Dial Plan Mode - reserved or
replaced.
Access: Instant.
AC INI-Param: TEL2IPSOURCENUMBERMAPPINGDIALPLANMODE"
       ::= {misc 42}



     miscMaxSIPMessageLength OBJECT-TYPE
       SYNTAX Unsigned32 (1..50)
       MAX-ACCESS read-write
       STATUS current
       DESCRIPTION
           "Limit the maximum length in KB for SIP message.
Access: Instant.
AC INI-Param: MAXSIPMESSAGELENGTH"
       ::= {misc 43}



     miscQoSStatistics OBJECT-TYPE
       SYNTAX INTEGER {
                  disable(0)
,
                  enable(1)

                  }
       MAX-ACCESS read-write
       STATUS current
       DESCRIPTION
           "Whether or not add statistics to call release.
Access: Instant.
AC INI-Param: QOSSTATISTICS"
       ::= {misc 44}



     miscPingPongKeepAlive OBJECT-TYPE
       SYNTAX INTEGER {
                  disable(0)
,
                  enable(1)

                  }
       MAX-ACCESS read-write
       STATUS current
       DESCRIPTION
           "Use Ping-Pong for Keep-Alive to proxy via reliable connection.
Access: Instant.
AC INI-Param: USEPINGPONGKEEPALIVE"
       ::= {misc 45}



     miscPingPongKeepAliveTime OBJECT-TYPE
       SYNTAX Unsigned32 (5..2000000)
       MAX-ACCESS read-write
       STATUS current
       DESCRIPTION
           "The Ping Keep-Alivewill be sent (using CRLFCRLF) each time this
timer expires (seconds).
Access: Instant.
AC INI-Param: PINGPONGKEEPALIVETIME"
       ::= {misc 46}



     miscEmptyAuthorizationHeader OBJECT-TYPE
       SYNTAX INTEGER {
                  disable(0)
,
                  enable(1)

                  }
       MAX-ACCESS read-write
       STATUS current
       DESCRIPTION
           "If empty Authorization header should be added into Register
request.
Access: Instant.
AC INI-Param: EMPTYAUTHORIZATIONHEADER"
       ::= {misc 47}



     miscSIPT38Version OBJECT-TYPE
       SYNTAX INTEGER {
                  notConfigured(-1)
,
                  version0(0)
,
                  version3(3)

                  }
       MAX-ACCESS read-write
       STATUS current
       DESCRIPTION
           "SIP T38 Version.
Access: Instant.
AC INI-Param: SIPT38VERSION"
       ::= {misc 48}



     miscSIPRegistrationAction OBJECT-TYPE
       SYNTAX INTEGER {
                  unRegisterGW(0)
,
                  unRegisterChannelsTable(1)
,
                  unRegisterAccountTable(2)
,
                  unRegisterIsdnSuppServTable(3)
,
                  registerGW(16)
,
                  registerChannelsTable(17)
,
                  registerAccountTable(18)
,
                  registerIsdnSuppServTable(19)

                  }
       MAX-ACCESS read-write
       STATUS current
       DESCRIPTION
           "Register and unregister gateway and tables.
Access: Instant.
AC INI-Param: SHOULDREGISTER"
       ::= {misc 49}



     miscIp2IpXferMode OBJECT-TYPE
       SYNTAX INTEGER {
                  disable(0)
,
                  enable(1)

                  }
       MAX-ACCESS read-write
       STATUS current
       DESCRIPTION
           "IP2IP Transfer Mode.
Access: Instant.
AC INI-Param: IP2IPTRANSFERMODE"
       ::= {misc 50}



     miscENUMServiceDomain OBJECT-TYPE
       SYNTAX INTEGER {
                  disable(0)
,
                  enable(1)

                  }
       MAX-ACCESS read-write
       STATUS current
       DESCRIPTION
           "Specifies ENUM domain using for ENUM resolution. Default value
= 0 means the using of e164.arpa
 value = 1 - use nrenum.net.
Access: Instant.
AC INI-Param: ENUMSERVICE"
       ::= {misc 51}



     miscT38FaxSessImmStart OBJECT-TYPE
       SYNTAX INTEGER {
                  disable(0)
,
                  enableOnFaxInSDP(1)
,
                  enableOnBothFaxAndVoiceInSDP(2)

                  }
       MAX-ACCESS read-write
       STATUS current
       DESCRIPTION
           "T38 Fax Session Immediate Start (Fax behind NAT).
Access: Instant.
AC INI-Param: T38FAXSESSIONIMMEDIATESTART"
       ::= {misc 52}



     miscEmrgncySpecialRelCse OBJECT-TYPE
       SYNTAX INTEGER {
                  disable(0)
,
                  enable(1)

                  }
       MAX-ACCESS read-write
       STATUS current
       DESCRIPTION
           "When enabled, if an emergency call is rejected it will be rejected
with 503.
Access: Instant.
AC INI-Param: EMERGENCYSPECIALRELEASECAUSE"
       ::= {misc 53}



     miscCallXferUsingReinvites OBJECT-TYPE
       SYNTAX INTEGER {
                  disable(0)
,
                  enable(1)

                  }
       MAX-ACCESS read-write
       STATUS current
       DESCRIPTION
           "Enable Call Transfer service using reinvites.
Access: Instant.
AC INI-Param: ENABLECALLTRANSFERUSINGREINVITES"
       ::= {misc 54}



     miscLDAPPrivateAttrName OBJECT-TYPE
       SYNTAX SnmpAdminString (SIZE (0..49))
       MAX-ACCESS read-write
       STATUS current
       DESCRIPTION
           "The name of the attribute which represents the user Private
number in the Microsoft AD data base.
Access: Instant.
AC INI-Param: MSLDAPPRIVATENUMATTRIBUTENAME"
       ::= {misc 55}



     miscLDAPPrimaryKey OBJECT-TYPE
       SYNTAX SnmpAdminString (SIZE (0..49))
       MAX-ACCESS read-write
       STATUS current
       DESCRIPTION
           "The name of the query primary key in the Microsoft AD data base.
Access: Instant.
AC INI-Param: MSLDAPPRIMARYKEY"
       ::= {misc 56}



     miscLDAPSecondaryKey OBJECT-TYPE
       SYNTAX SnmpAdminString (SIZE (0..49))
       MAX-ACCESS read-write
       STATUS current
       DESCRIPTION
           "The name of the query secondary key in the Microsoft AD data
base.
Access: Instant.
AC INI-Param: MSLDAPSECONDARYKEY"
       ::= {misc 57}



     miscTestCallID OBJECT-TYPE
       SYNTAX SnmpAdminString (SIZE (0..14))
       MAX-ACCESS read-write
       STATUS current
       DESCRIPTION
           "Incoming test call prefix.
Access: Instant.
AC INI-Param: TESTCALLID"
       ::= {misc 58}



     miscSBCtestID OBJECT-TYPE
       SYNTAX SnmpAdminString (SIZE (0..14))
       MAX-ACCESS read-write
       STATUS current
       DESCRIPTION
           "Incoming SBC test ID (bypass TestCallID).
Access: Instant.
AC INI-Param: SBCTESTID"
       ::= {misc 59}



     miscSIPRemoteReset OBJECT-TYPE
       SYNTAX INTEGER {
                  disable(0)
,
                  enable(1)

                  }
       MAX-ACCESS read-write
       STATUS current
       DESCRIPTION
           "Performing Automatic Update remotely using SIP Specific Event.
Access: Instant.
AC INI-Param: SIPRemoteReset"
       ::= {misc 60}



     miscEnableNonInvite408Reply OBJECT-TYPE
       SYNTAX INTEGER {
                  disable(0)
,
                  enable(1)

                  }
       MAX-ACCESS read-write
       STATUS current
       DESCRIPTION
           "Enable sending 408 responses for non-INVITE transactions. Disable
this parameter to comply to RFC 4320.
Access: Instant.
AC INI-Param: EnableNonInvite408Reply"
       ::= {misc 61}



     miscUseAltRouteReasonsFor3xx OBJECT-TYPE
       SYNTAX INTEGER {
                  no(0)
,
                  noIf6xx(1)
,
                  yes(2)

                  }
       MAX-ACCESS read-write
       STATUS current
       DESCRIPTION
           "Use Alt Route Reasons Table For 3xx.
Access: Instant.
AC INI-Param: USEALTROUTEREASONSFOR3XX "
       ::= {misc 62}



     miscLDAPDisplayNameAttrName OBJECT-TYPE
       SYNTAX SnmpAdminString (SIZE (0..49))
       MAX-ACCESS read-write
       STATUS current
       DESCRIPTION
           "MS LDAP DISPLAY Name attribute name.
Access: Instant.
AC INI-Param: MSLDAPDISPLAYNAMEATTRIBUTENAME"
       ::= {misc 63}



     miscNetworkNodeId OBJECT-TYPE
       SYNTAX Unsigned32 (0..32767)
       MAX-ACCESS read-write
       STATUS current
       DESCRIPTION
           "Network Node Id.
Access: Instant.
AC INI-Param: NETWORKNODEID"
       ::= {misc 64}



     miscForkingDelayTimeForInvite OBJECT-TYPE
       SYNTAX Unsigned32 (0..20)
       MAX-ACCESS read-write
       STATUS current
       DESCRIPTION
           "Delay time (in seconds) to wait before sending Invite of 2nd
forking call.
Access: Instant.
AC INI-Param: FORKINGDELAYTIMEFORINVITE"
       ::= {misc 65}



     miscDisplayDefaultSIPPort OBJECT-TYPE
       SYNTAX INTEGER {
                  disable(0)
,
                  enable(1)

                  }
       MAX-ACCESS read-write
       STATUS current
       DESCRIPTION
           "When it is enabled and the headers have been manipulated the
default port 5060 is shown in the headers.
Access: Instant.
AC INI-Param: DISPLAYDEFAULTSIPPORT"
       ::= {misc 66}



     miscSendRejectOnOverload OBJECT-TYPE
       SYNTAX Unsigned32 (0..1)
       MAX-ACCESS read-write
       STATUS current
       DESCRIPTION
           "If set to false (0), a 503 response will not be sent on overload.
Access: Instant.
AC INI-Param: SendRejectOnOverload"
       ::= {misc 67}



     miscE911Gateway OBJECT-TYPE
       SYNTAX Unsigned32 (100..2000)
       MAX-ACCESS read-write
       STATUS current
       DESCRIPTION
           "time between first and second Wink generation (FXS).
Access: Instant.
AC INI-Param: TIMEBETWEENDIDWINKS"
       ::= {misc 68}



     miscUseDifferentRTPportAfterHold OBJECT-TYPE
       SYNTAX INTEGER {
                  disable(0)
,
                  enable(1)

                  }
       MAX-ACCESS read-write
       STATUS current
       DESCRIPTION
           "Use different RTP port after Hold.
Access: Instant.
AC INI-Param: USEDIFFERENTRTPPORTAFTERHOLD"
       ::= {misc 69}



     miscSessionExpiresDisconnectTime OBJECT-TYPE
       SYNTAX Unsigned32 (0..32)
       MAX-ACCESS read-write
       STATUS current
       DESCRIPTION
           "Defines the minimum time factor before the session expires.
By achieving this time without session refresh, the session
should be disconnected.
Access: Instant.
AC INI-Param: SESSIONEXPIRESDISCONNECTTIME"
       ::= {misc 70}



     miscCoderPriorityNegotiation OBJECT-TYPE
       SYNTAX INTEGER {
                  sdpRemotePriority(0)
,
                  sdpLocalPriority(1)

                  }
       MAX-ACCESS read-write
       STATUS current
       DESCRIPTION
           "Defines the coder priority in SDP negotiation. Default: according
remote SDP.
Access: Instant.
AC INI-Param: CODERPRIORITYNEGOTIATION"
       ::= {misc 71}



     miscRejectCancelAfterConnect OBJECT-TYPE
       SYNTAX INTEGER {
                  disable(0)
,
                  enable(1)

                  }
       MAX-ACCESS read-write
       STATUS current
       DESCRIPTION
           "Defines whether or not reject Cancel request after connect.
Access: Instant.
AC INI-Param: REJECTCANCELAFTERCONNECT"
       ::= {misc 72}



     miscAmdMode OBJECT-TYPE
       SYNTAX INTEGER {
                  doNotDisconnect(0)
,
                  disconnectOnAnsweringMachineDetection(1)

                  }
       MAX-ACCESS read-write
       STATUS current
       DESCRIPTION
           "0 -  not affected,1 - disconnect IP2TEL call on Answering Machine
detection.
Access: Instant.
AC INI-Param: AMDMODE"
       ::= {misc 73}



     miscSipNatDetection OBJECT-TYPE
       SYNTAX Unsigned32 (0..1)
       MAX-ACCESS read-write
       STATUS current
       DESCRIPTION
           "If not set, the incoming request will be always processed as
user NOT behind NAT.
Access: Instant.
AC INI-Param: SIPNATDETECTION"
       ::= {misc 74}



     miscVerifyReceivedVia OBJECT-TYPE
       SYNTAX Unsigned32 (0..1)
       MAX-ACCESS read-write
       STATUS current
       DESCRIPTION
           "Defines whether or not to verify Source IP with IP in Topmost
VIA.
Access: Instant.
AC INI-Param: VERIFYRECIEVEDVIA"
       ::= {misc 75}



     miscResetSRTPStateUponRekey OBJECT-TYPE
       SYNTAX INTEGER {
                  disable(0)
,
                  enable(1)

                  }
       MAX-ACCESS read-write
       STATUS current
       DESCRIPTION
           "Reset SRTP State Upon Re-key.
Access: Instant.
AC INI-Param: RESETSRTPSTATEUPONREKEY"
       ::= {misc 76}



     miscTestCallDTMFString OBJECT-TYPE
       SYNTAX SnmpAdminString (SIZE (0..15))
       MAX-ACCESS read-write
       STATUS current
       DESCRIPTION
           "DTMF string for test calls.
Access: Instant.
AC INI-Param: TESTCALLDTMFSTRING"
       ::= {misc 77}



     resourceManagement OBJECT IDENTIFIER ::= {common 12}


     resourceManagementMaxActiveCalls OBJECT-TYPE
       SYNTAX Unsigned32 (1..20000)
       MAX-ACCESS read-write
       STATUS current
       DESCRIPTION
           "Limit the number of calls that the gateway can handle at the
same time.
Access: Instant.
AC INI-Param: MAXACTIVECALLS"
       ::= {resourceManagement 1}



     resourceManagementIsSelfCheckAuditUsed OBJECT-TYPE
       SYNTAX INTEGER {
                  disable(0)
,
                  enable(1)

                  }
       MAX-ACCESS read-write
       STATUS current
       DESCRIPTION
           "defines whether the resources self check audit is used.
Access: Instant.
AC INI-Param: ISSELFCHECKAUDITUSED"
       ::= {resourceManagement 2}



     resourceManagementRejectCallsOnOverload OBJECT-TYPE
       SYNTAX INTEGER {
                  disable(0)
,
                  enable(1)

                  }
       MAX-ACCESS read-write
       STATUS obsolete
       DESCRIPTION
           "Defines whether new calls will be rejected during overload period.
Access: Instant.
AC INI-Param: REJECTCALLSONOVERLOAD"
       ::= {resourceManagement 3}



     resourceManagementDisconnectOnBrokenConnection OBJECT-TYPE
       SYNTAX INTEGER {
                  disable(0)
,
                  enable(1)

                  }
       MAX-ACCESS read-write
       STATUS current
       DESCRIPTION
           "Disconnect calls on receiving RTP broken notification.
Access: Instant.
AC INI-Param: DISCONNECTONBROKENCONNECTION"
       ::= {resourceManagement 4}



     resourceManagementMaxCallDuration OBJECT-TYPE
       SYNTAX Unsigned32 (0..35791)
       MAX-ACCESS read-write
       STATUS current
       DESCRIPTION
           "Limit the call time duration (minutes)
 0 = no limit.
Access: Instant.
AC INI-Param: MAXCALLDURATION"
       ::= {resourceManagement 5}



     resourceManagementOverloadSensitivityLevel OBJECT-TYPE
       SYNTAX INTEGER {
                  never(0)
,
                  highUtil(1)
,
                  medUtil(2)

                  }
       MAX-ACCESS read-write
       STATUS current
       DESCRIPTION
           "Defines when to enter overload state: 0:never 1:on very high
utilization  2:on medium utilization.
Access: Instant.
AC INI-Param: OverloadSensitivityLevel"
       ::= {resourceManagement 6}



     resourceManagementSignalingCpuUsageThreshold OBJECT-TYPE
       SYNTAX Unsigned32 (0..100)
       MAX-ACCESS read-write
       STATUS current
       DESCRIPTION
           "Signaling CPU Usage Threshold Alarm (percentage).
Access: Instant.
AC INI-Param: SIGNALINGCPUUSAGETHRESHOLDALARM"
       ::= {resourceManagement 7}



     aMD OBJECT IDENTIFIER ::= {common 13}


     aMDTimeOut OBJECT-TYPE
       SYNTAX Unsigned32 (1..30000)
       MAX-ACCESS read-write
       STATUS current
       DESCRIPTION
           "Amd Detection Timeout <mSec>.
Access: Instant.
AC INI-Param: AMDTIMEOUT"
       ::= {aMD 1}



     aaa OBJECT IDENTIFIER ::= {common 14}


     aaaIndications OBJECT-TYPE
       SYNTAX INTEGER {
                  none(0)
,
                  authorizeAndAuthenticate(1)
,
                  fullReport(2)
,
                  accountingOnly(3)

                  }
       MAX-ACCESS read-write
       STATUS current
       DESCRIPTION
           "Which Authentication, Authorization and Accounting indications
to use.
Access: Instant.
AC INI-Param: AAAINDICATIONS"
       ::= {aaa 1}



     aaaRadiusAccountingType OBJECT-TYPE
       SYNTAX INTEGER {
                  release(0)
,
                  connectAndRelease(1)
,
                  setupAndRelease(2)

                  }
       MAX-ACCESS read-write
       STATUS current
       DESCRIPTION
           "When will Radius Acounting messages be sent.
Access: Instant.
AC INI-Param: RADIUSACCOUNTINGTYPE"
       ::= {aaa 2}



     profile OBJECT IDENTIFIER ::= {common 15}


     -- ****************************************
     -- iPProfile table declaration
     -- ****************************************
     iPProfileTable OBJECT-TYPE
       SYNTAX SEQUENCE OF IPProfileEntry
       MAX-ACCESS not-accessible
       STATUS current
       DESCRIPTION
           ""
       ::= {profile 21}



     -- ****************************************
     -- iPProfile table entry
     -- ****************************************
     iPProfileEntry OBJECT-TYPE
       SYNTAX IPProfileEntry
       MAX-ACCESS not-accessible
       STATUS current
       DESCRIPTION
           ""
       INDEX {iPProfileIndex}
       ::= {iPProfileTable 1}



     -- ****************************************
     -- iPProfile TABLE
     -- ****************************************
     IPProfileEntry ::= SEQUENCE {
       iPProfileIndex                                  Unsigned32,
       iPProfileRowStatus                              RowStatus,
       iPProfileAction                                 INTEGER,
       iPProfileActionResult                           INTEGER,
       iPProfilePreference                             Unsigned32,
       iPProfileProfileName                            SnmpAdminString,
       iPProfileCodersGroupID                          Unsigned32,
       iPProfileFaxTransportMode                       Unsigned32,
       iPProfileIsFaxUsed                              INTEGER,
       iPProfileDJBufMinDelay                          Unsigned32,
       iPProfileDJBufOptFactor                         Unsigned32,
       iPProfileIPDiffServ                             Unsigned32,
       iPProfileSigIPDiffServ                          Unsigned32,
       iPProfileSCE                                    INTEGER,
       iPProfileRTPRedundancyDepth                     Unsigned32,
       iPProfileRemoteBaseUDPPort                      Unsigned32,
       iPProfileCngDetectorMode                        INTEGER,
       iPProfileVxxModemTransportType                  INTEGER,
       iPProfileNSEMode                                INTEGER,
       iPProfilePlayRingbackToneToIP                   INTEGER,
       iPProfileEnableEarlyMedia                       INTEGER,
       iPProfileProgressIndicatorToIP                  INTEGER,
       iPProfileECE                                    INTEGER,
       iPProfileMediaSecurityBehavior                  INTEGER,
       iPProfileCallLimit                              Integer32,
       iPProfileDisconnectOnBrokenConnection           INTEGER,
       iPProfileCopyDest2RedirectNumber                INTEGER,
       iPProfileAddIEInSetup                           SnmpAdminString,
       iPProfileRxDTMFOption                           INTEGER,
       iPProfileFirstTxDtmfOption                      INTEGER,
       iPProfileSecondTxDtmfOption                     INTEGER,
       iPProfileMediaIPVersionPreference               INTEGER,
       iPProfileSBCAllowedCodersGroupID                INTEGER,
       iPProfileSBCAllowedCodersMode                   INTEGER,
       iPProfileSBCMediaSecurityBehaviour              INTEGER,
       iPProfileSBCDiversionMode                       INTEGER,
       iPProfileSBCHistoryInfoMode                     INTEGER,
       iPProfileAMDSensitivityParameterSuit            Integer32,
       iPProfileAMDSensitivityLevel                    Integer32,
       iPProfileAMDMaxGreetingTime                     Integer32,
       iPProfileAMDMaxPostSilenceGreetingTime          Integer32,
       iPProfileSBCRFC2833Behavior                     INTEGER,
       iPProfileSBCAlternativeDTMFMethod               INTEGER,
       iPProfileSBCAssertIdentity                      INTEGER,
       iPProfileSBCFaxCodersGroupID                    INTEGER,
       iPProfileSBCFaxBehavior                         Unsigned32,
       iPProfileSBCFaxOfferMode                        Unsigned32,
       iPProfileSBCFaxAnswerMode                       Unsigned32,
       iPProfileEnableSymmetricMKI                     Integer32,
       iPProfileMKISize                                Integer32,
       iPProfileSBCSessionExpiresMode                  INTEGER,
       iPProfileSBCRemoteMultiple18xSupport            INTEGER,
       iPProfileSBCRemoteEarlyMediaResponseType        INTEGER,
       iPProfileSBCRemoteUpdateSupport                 INTEGER,
       iPProfileSBCRemoteReinviteSupport               INTEGER,
       iPProfileSBCRemoteReferBehavior                 INTEGER,
       iPProfileSBCRemoteEarlyMediaSupport             INTEGER,
       iPProfileSBCRemote3xxBehavior                   INTEGER,
       iPProfileSBCRemoteDelayedOfferSupport           INTEGER,
       iPProfileSBCPrackMode                           INTEGER,
       iPProfileSBCUserRegistrationTime                Unsigned32,
       iPProfileSBCRemoteHoldFormat                    INTEGER,
       iPProfileSBCRTPRedundancyBehavior               INTEGER,
       iPProfileSBCSDPPtimeAnswer                      INTEGER,
       iPProfileSBCPreferredPTime                      Unsigned32,
       iPProfileSBCUseSilenceSupp                      INTEGER,
       iPProfileSBC2833DTMFPayloadType                 Unsigned32,
       iPProfileSBCRemoteReplacesBehavior              INTEGER,
       iPProfileSBCPlayHeldTone                        INTEGER,
       iPProfileSBCReliableHeldToneSource              INTEGER,
       iPProfileSBCPlayRBTToTransferee                 INTEGER,
       iPProfileSBCJitterCompensation                  INTEGER,
       iPProfileSBCRtcpMode                            INTEGER,
       iPProfileSBCAllowedMediaTypes                   SnmpAdminString,
       iPProfileEarlyAnswerTimeout                     Unsigned32,
       iPProfileAmdMode                                INTEGER,
       iPProfileSBCRemoteRenegotiateOnFaxDetection     INTEGER,
       iPProfileResetSRTPStateUponRekey                INTEGER
     }



     iPProfileIndex OBJECT-TYPE
       SYNTAX Unsigned32 (1..9)
       MAX-ACCESS not-accessible
       STATUS current
       DESCRIPTION
           "Entry number, starting at 1.
AC INI-Param: IpProfile_Index"
       ::= {iPProfileEntry 1}



     iPProfileRowStatus OBJECT-TYPE
       SYNTAX RowStatus
       MAX-ACCESS read-create
       STATUS current
       DESCRIPTION
           "Row-Status Textual Conventions as defined in RFC 2579: Textual
Conventions for SMIv2.
AC INI-Param: N/A"
       ::= {iPProfileEntry 2}



     iPProfileAction OBJECT-TYPE
       SYNTAX INTEGER {
                  developmentImpending(0)

                  }
       MAX-ACCESS read-only
       STATUS current
       DESCRIPTION
           "Development Impending.
AC INI-Param: N/A"
       ::= {iPProfileEntry 3}



     iPProfileActionResult OBJECT-TYPE
       SYNTAX INTEGER {
                  developmentImpending(0)

                  }
       MAX-ACCESS read-only
       STATUS current
       DESCRIPTION
           "Development Impending.
AC INI-Param: N/A"
       ::= {iPProfileEntry 4}



     iPProfilePreference OBJECT-TYPE
       SYNTAX Unsigned32 (0..20)
       MAX-ACCESS read-create
       STATUS current
       DESCRIPTION
           "Preference.
Access: Instant.
AC INI-Param: IpProfile_IpPreference"
       ::= {iPProfileEntry 5}



     iPProfileProfileName OBJECT-TYPE
       SYNTAX SnmpAdminString (SIZE (0..19))
       MAX-ACCESS read-create
       STATUS current
       DESCRIPTION
           "Profile Name.
Access: Instant.
AC INI-Param: IpProfile_ProfileName"
       ::= {iPProfileEntry 6}



     iPProfileCodersGroupID OBJECT-TYPE
       SYNTAX Unsigned32 (0..4)
       MAX-ACCESS read-create
       STATUS current
       DESCRIPTION
           "Coders Group ID.
Access: Instant.
AC INI-Param: IpProfile_CodersGroupID"
       ::= {iPProfileEntry 7}



     iPProfileFaxTransportMode OBJECT-TYPE
       SYNTAX Unsigned32 (0..3)
       MAX-ACCESS read-write
       STATUS obsolete
       DESCRIPTION
           "Fax Transport Mode.
Access: Instant.
AC INI-Param: N/A"
       ::= {iPProfileEntry 8}



     iPProfileIsFaxUsed OBJECT-TYPE
       SYNTAX INTEGER {
                  noFax(0)
,
                  t38(1)
,
                  g711(2)
,
                  fallBack(3)
,
                  notConfigured(255)

                  }
       MAX-ACCESS read-create
       STATUS current
       DESCRIPTION
           "Use H.323/Annex D procedure for real time FAX relay. To use
this feature, disable inband DTMF by setting the FaxTransportMode
to 1.
Access: Instant.
AC INI-Param: IpProfile_IsFaxUsed"
       ::= {iPProfileEntry 9}



     iPProfileDJBufMinDelay OBJECT-TYPE
       SYNTAX Unsigned32 (0..255)
       MAX-ACCESS read-create
       STATUS current
       DESCRIPTION
           "Dynamic Jitter Buffer Minimum Delay (msec).
Access: Instant.
AC INI-Param: IpProfile_JitterBufMinDelay"
       ::= {iPProfileEntry 10}



     iPProfileDJBufOptFactor OBJECT-TYPE
       SYNTAX Unsigned32 (0..255)
       MAX-ACCESS read-create
       STATUS current
       DESCRIPTION
           "Dynamic jitter buffer frame error/delay optimization.
Access: Instant.
AC INI-Param: IpProfile_JitterBufOptFactor"
       ::= {iPProfileEntry 11}



     iPProfileIPDiffServ OBJECT-TYPE
       SYNTAX Unsigned32 (0..255)
       MAX-ACCESS read-create
       STATUS current
       DESCRIPTION
           "IP DiffServ byte value.
Access: Instant.
AC INI-Param: IpProfile_IPDiffServ"
       ::= {iPProfileEntry 12}



     iPProfileSigIPDiffServ OBJECT-TYPE
       SYNTAX Unsigned32 (0..255)
       MAX-ACCESS read-create
       STATUS current
       DESCRIPTION
           "Type Of Service bits in IP header of signalling messages.
Access: Instant.
AC INI-Param: IpProfile_SigIPDiffServ"
       ::= {iPProfileEntry 13}



     iPProfileSCE OBJECT-TYPE
       SYNTAX INTEGER {
                  disable(0)
,
                  enable(1)
,
                  enableWithoutAdaptation(2)
,
                  notConfigured(255)

                  }
       MAX-ACCESS read-create
       STATUS current
       DESCRIPTION
           "Silence Suppression mode.
Access: Instant.
AC INI-Param: IpProfile_SCE"
       ::= {iPProfileEntry 14}



     iPProfileRTPRedundancyDepth OBJECT-TYPE
       SYNTAX Unsigned32 (0..255)
       MAX-ACCESS read-create
       STATUS current
       DESCRIPTION
           "Enables or disables generation of RFC 2198 redundancy packets.
Access: Instant.
AC INI-Param: IpProfile_RTPRedundancyDepth"
       ::= {iPProfileEntry 15}



     iPProfileRemoteBaseUDPPort OBJECT-TYPE
       SYNTAX Unsigned32 (0..65535)
       MAX-ACCESS read-create
       STATUS current
       DESCRIPTION
           "Remote Base UDP Port For Aggregation.
Access: Instant.
AC INI-Param: IpProfile_RemoteBaseUDPPort"
       ::= {iPProfileEntry 16}



     iPProfileCngDetectorMode OBJECT-TYPE
       SYNTAX INTEGER {
                  disable(0)
,
                  relay(1)
,
                  eventsOnly(2)
,
                  notConfigured(255)

                  }
       MAX-ACCESS read-create
       STATUS current
       DESCRIPTION
           "
Access: Instant.
AC INI-Param: IpProfile_CNGmode"
       ::= {iPProfileEntry 17}



     iPProfileVxxModemTransportType OBJECT-TYPE
       SYNTAX INTEGER {
                  disable(0)
,
                  enableBypass(2)
,
                  eventsOnly(3)
,
                  notConfigured(255)

                  }
       MAX-ACCESS read-create
       STATUS current
       DESCRIPTION
           "
Access: Instant.
AC INI-Param: IpProfile_VxxTransportType"
       ::= {iPProfileEntry 18}



     iPProfileNSEMode OBJECT-TYPE
       SYNTAX INTEGER {
                  disable(0)
,
                  enable(1)
,
                  notConfigured(255)

                  }
       MAX-ACCESS read-create
       STATUS current
       DESCRIPTION
           "
Access: Instant.
AC INI-Param: IpProfile_NSEMode"
       ::= {iPProfileEntry 19}



     iPProfilePlayRingbackToneToIP OBJECT-TYPE
       SYNTAX INTEGER {
                  notPlay(0)
,
                  play(1)
,
                  notConfigured(255)

                  }
       MAX-ACCESS read-create
       STATUS current
       DESCRIPTION
           "
Access: Instant.
AC INI-Param: IpProfile_PlayRBTone2IP"
       ::= {iPProfileEntry 20}



     iPProfileEnableEarlyMedia OBJECT-TYPE
       SYNTAX INTEGER {
                  disable(0)
,
                  enable(1)
,
                  notConfigured(255)

                  }
       MAX-ACCESS read-create
       STATUS current
       DESCRIPTION
           "
Access: Instant.
AC INI-Param: IpProfile_EnableEarlyMedia"
       ::= {iPProfileEntry 21}



     iPProfileProgressIndicatorToIP OBJECT-TYPE
       SYNTAX INTEGER {
                  default(-1)
,
                  noPI(0)
,
                  pI1(1)
,
                  pI8(8)
,
                  notConfigured(255)

                  }
       MAX-ACCESS read-create
       STATUS current
       DESCRIPTION
           "
Access: Instant.
AC INI-Param: IpProfile_ProgressIndicator2IP"
       ::= {iPProfileEntry 22}



     iPProfileECE OBJECT-TYPE
       SYNTAX INTEGER {
                  notConfigured(-1)
,
                  disable(0)
,
                  enable(1)

                  }
       MAX-ACCESS read-create
       STATUS current
       DESCRIPTION
           "Enables or disables the echo canceler.
Access: Instant.
AC INI-Param: IpProfile_EnableEchoCanceller"
       ::= {iPProfileEntry 23}



     iPProfileMediaSecurityBehavior OBJECT-TYPE
       SYNTAX INTEGER {
                  notConfigured(-1)
,
                  preferable(0)
,
                  mandatory(1)
,
                  preferableSingleMedia(2)

                  }
       MAX-ACCESS read-create
       STATUS current
       DESCRIPTION
           "
Access: Instant.
AC INI-Param: IpProfile_MediaSecurityBehaviour"
       ::= {iPProfileEntry 24}



     iPProfileCallLimit OBJECT-TYPE
       SYNTAX Integer32 (-1..200000)
       MAX-ACCESS read-create
       STATUS current
       DESCRIPTION
           "
Access: Instant.
AC INI-Param: IpProfile_CallLimit"
       ::= {iPProfileEntry 25}



     iPProfileDisconnectOnBrokenConnection OBJECT-TYPE
       SYNTAX INTEGER {
                  notConfigured(-1)
,
                  no(0)
,
                  yes(1)

                  }
       MAX-ACCESS read-create
       STATUS current
       DESCRIPTION
           "
Access: Instant.
AC INI-Param: IpProfile_DisconnectOnBrokenConnection"
       ::= {iPProfileEntry 26}



     iPProfileCopyDest2RedirectNumber OBJECT-TYPE
       SYNTAX INTEGER {
                  notConfigured(-1)
,
                  disable(0)
,
                  afterManipulation(1)
,
                  beforeManipulation(2)

                  }
       MAX-ACCESS read-create
       STATUS current
       DESCRIPTION
           "
Access: Instant.
AC INI-Param: IpProfile_CopyDest2RedirectNumber"
       ::= {iPProfileEntry 27}



     iPProfileAddIEInSetup OBJECT-TYPE
       SYNTAX SnmpAdminString (SIZE (0..98))
       MAX-ACCESS read-create
       STATUS current
       DESCRIPTION
           "
Access: Instant.
AC INI-Param: IpProfile_AddIEInSetup"
       ::= {iPProfileEntry 28}



     iPProfileRxDTMFOption OBJECT-TYPE
       SYNTAX INTEGER {
                  notConfigured(-1)
,
                  notDeclared(0)
,
                  declareRFC2833InSDP(1)

                  }
       MAX-ACCESS read-create
       STATUS current
       DESCRIPTION
           "
Access: Instant.
AC INI-Param: IpProfile_RxDTMFOption"
       ::= {iPProfileEntry 29}



     iPProfileFirstTxDtmfOption OBJECT-TYPE
       SYNTAX INTEGER {
                  notConfigured(-1)
,
                  notSupported(0)
,
                  infoNortel(1)
,
                  notify(2)
,
                  infoCisco(3)
,
                  rFC2833(4)
,
                  infoKorea(5)

                  }
       MAX-ACCESS read-create
       STATUS current
       DESCRIPTION
           "
Access: Instant.
AC INI-Param: IpProfile_FirstTxDtmfOption"
       ::= {iPProfileEntry 30}



     iPProfileSecondTxDtmfOption OBJECT-TYPE
       SYNTAX INTEGER {
                  notConfigured(-1)
,
                  notSupported(0)
,
                  infoNortel(1)
,
                  notify(2)
,
                  infoCisco(3)
,
                  rFC2833(4)
,
                  infoKorea(5)

                  }
       MAX-ACCESS read-create
       STATUS current
       DESCRIPTION
           "
Access: Instant.
AC INI-Param: IpProfile_SecondTxDtmfOption"
       ::= {iPProfileEntry 31}



     iPProfileMediaIPVersionPreference OBJECT-TYPE
       SYNTAX INTEGER {
                  notConfigured(-1)
,
                  onlyIPv4(0)
,
                  onlyIPv6(1)
,
                  preferIPv4(2)
,
                  preferIPv6(3)

                  }
       MAX-ACCESS read-create
       STATUS current
       DESCRIPTION
           "
Access: Instant.
AC INI-Param: IpProfile_MediaIPVersionPreference"
       ::= {iPProfileEntry 32}



     iPProfileSBCAllowedCodersGroupID OBJECT-TYPE
       SYNTAX INTEGER {
                  notConfigured(-1)
,
                  codersGroup0(0)
,
                  codersGroup1(1)
,
                  codersGroup2(2)
,
                  codersGroup3(3)
,
                  codersGroup4(4)

                  }
       MAX-ACCESS read-create
       STATUS current
       DESCRIPTION
           "
Access: Instant.
AC INI-Param: IpProfile_SBCAllowedCodersGroupID"
       ::= {iPProfileEntry 33}



     iPProfileSBCAllowedCodersMode OBJECT-TYPE
       SYNTAX INTEGER {
                  restriction(0)
,
                  preference(1)
,
                  restictionAndPreference(2)

                  }
       MAX-ACCESS read-create
       STATUS current
       DESCRIPTION
           "
Access: Instant.
AC INI-Param: IpProfile_SBCAllowedCodersMode"
       ::= {iPProfileEntry 34}



     iPProfileSBCMediaSecurityBehaviour OBJECT-TYPE
       SYNTAX INTEGER {
                  asIs(0)
,
                  srtp(1)
,
                  rtp(2)
,
                  both(3)

                  }
       MAX-ACCESS read-create
       STATUS current
       DESCRIPTION
           "
Access: Instant.
AC INI-Param: IpProfile_SBCMediaSecurityBehaviour"
       ::= {iPProfileEntry 35}



     iPProfileSBCDiversionMode OBJECT-TYPE
       SYNTAX INTEGER {
                  notConfigured(-1)
,
                  dontCare(0)
,
                  add(1)
,
                  remove(2)

                  }
       MAX-ACCESS read-create
       STATUS current
       DESCRIPTION
           "
Access: Instant.
AC INI-Param: IpProfile_SBCDiversionMode"
       ::= {iPProfileEntry 36}



     iPProfileSBCHistoryInfoMode OBJECT-TYPE
       SYNTAX INTEGER {
                  notConfigured(-1)
,
                  dontCare(0)
,
                  add(1)
,
                  remove(2)

                  }
       MAX-ACCESS read-create
       STATUS current
       DESCRIPTION
           "
Access: Instant.
AC INI-Param: IpProfile_SBCHistoryInfoMode"
       ::= {iPProfileEntry 37}



     iPProfileAMDSensitivityParameterSuit OBJECT-TYPE
       SYNTAX Integer32 (-1..7)
       MAX-ACCESS read-create
       STATUS current
       DESCRIPTION
           "
Access: Instant.
AC INI-Param: IpProfile_AMDSensitivityParameterSuit"
       ::= {iPProfileEntry 38}



     iPProfileAMDSensitivityLevel OBJECT-TYPE
       SYNTAX Integer32 (-1..15)
       MAX-ACCESS read-create
       STATUS current
       DESCRIPTION
           "
Access: Instant.
AC INI-Param: IpProfile_AMDSensitivityLevel"
       ::= {iPProfileEntry 39}



     iPProfileAMDMaxGreetingTime OBJECT-TYPE
       SYNTAX Integer32 (-1..511)
       MAX-ACCESS read-create
       STATUS current
       DESCRIPTION
           "
Access: Instant.
AC INI-Param: IpProfile_AMDMaxGreetingTime"
       ::= {iPProfileEntry 40}



     iPProfileAMDMaxPostSilenceGreetingTime OBJECT-TYPE
       SYNTAX Integer32 (-1..511)
       MAX-ACCESS read-create
       STATUS current
       DESCRIPTION
           "
Access: Instant.
AC INI-Param: IpProfile_AMDMaxPostSilenceGreetingTime"
       ::= {iPProfileEntry 41}



     iPProfileSBCRFC2833Behavior OBJECT-TYPE
       SYNTAX INTEGER {
                  asIs(0)
,
                  extend(1)
,
                  disallow(2)

                  }
       MAX-ACCESS read-create
       STATUS current
       DESCRIPTION
           "
Access: Instant.
AC INI-Param: IpProfile_SBCRFC2833Behavior"
       ::= {iPProfileEntry 42}



     iPProfileSBCAlternativeDTMFMethod OBJECT-TYPE
       SYNTAX INTEGER {
                  dontCare(0)
,
                  transparent(1)
,
                  infoCisco(2)
,
                  infoNortel(3)
,
                  infoLucent(4)

                  }
       MAX-ACCESS read-create
       STATUS current
       DESCRIPTION
           "
Access: Instant.
AC INI-Param: IpProfile_SBCAlternativeDTMFMethod"
       ::= {iPProfileEntry 43}



     iPProfileSBCAssertIdentity OBJECT-TYPE
       SYNTAX INTEGER {
                  notConfigured(-1)
,
                  dontCare(0)
,
                  add(1)
,
                  remove(2)

                  }
       MAX-ACCESS read-create
       STATUS current
       DESCRIPTION
           "
Access: Instant.
AC INI-Param: IpProfile_SBCAssertIdentity"
       ::= {iPProfileEntry 44}



     iPProfileSBCFaxCodersGroupID OBJECT-TYPE
       SYNTAX INTEGER {
                  none(-1)
,
                  codersGroup0(0)
,
                  codersGroup1(1)
,
                  codersGroup2(2)
,
                  codersGroup3(3)
,
                  codersGroup4(4)

                  }
       MAX-ACCESS read-create
       STATUS current
       DESCRIPTION
           "SBC Fax Coders Group ID.
Access: Instant.
AC INI-Param: IpProfile_SBCFaxCodersGroupID"
       ::= {iPProfileEntry 45}



     iPProfileSBCFaxBehavior OBJECT-TYPE
       SYNTAX Unsigned32 (0..2)
       MAX-ACCESS read-create
       STATUS current
       DESCRIPTION
           " 0 - As Is, 1 - Handle always, 2 - Handle on Re-INVITE and block
on INVITE.
Access: Instant.
AC INI-Param: IpProfile_SBCFaxBehavior"
       ::= {iPProfileEntry 46}



     iPProfileSBCFaxOfferMode OBJECT-TYPE
       SYNTAX Unsigned32 (0..1)
       MAX-ACCESS read-create
       STATUS current
       DESCRIPTION
           "0 - Offer all supported fax coders, 1 - Offer a single fax coder
(try to avoid transcoding).
Access: Instant.
AC INI-Param: IpProfile_SBCFaxOfferMode"
       ::= {iPProfileEntry 47}



     iPProfileSBCFaxAnswerMode OBJECT-TYPE
       SYNTAX Unsigned32 (0..1)
       MAX-ACCESS read-create
       STATUS current
       DESCRIPTION
           "0 - Put all supported fax coders in outgoing answer, 1 - Put
a single fax coder in the outgoing answer (try to avoid transcoding).
Access: Instant.
AC INI-Param: IpProfile_SBCFaxAnswerMode"
       ::= {iPProfileEntry 48}



     iPProfileEnableSymmetricMKI OBJECT-TYPE
       SYNTAX Integer32 (-1..2147483647)
       MAX-ACCESS read-create
       STATUS current
       DESCRIPTION
           "
Access: Instant.
AC INI-Param: IpProfile_EnableSymmetricMKI"
       ::= {iPProfileEntry 49}



     iPProfileMKISize OBJECT-TYPE
       SYNTAX Integer32 (-1..4)
       MAX-ACCESS read-create
       STATUS current
       DESCRIPTION
           "
Access: Instant.
AC INI-Param: IpProfile_MKISize"
       ::= {iPProfileEntry 50}



     iPProfileSBCSessionExpiresMode OBJECT-TYPE
       SYNTAX INTEGER {
                  observer(0)
,
                  transparent(1)
,
                  notSupported(2)
,
                  supported(3)

                  }
       MAX-ACCESS read-create
       STATUS current
       DESCRIPTION
           "Defines SBC benavior with 'Session-Expires' header.
Access: Instant.
AC INI-Param: IpProfile_SBCSessionExpiresMode"
       ::= {iPProfileEntry 51}



     iPProfileSBCRemoteMultiple18xSupport OBJECT-TYPE
       SYNTAX INTEGER {
                  notSupported(0)
,
                  supported(1)

                  }
       MAX-ACCESS read-create
       STATUS current
       DESCRIPTION
           "SBC Remote Multiple 18x Support.
Access: Instant.
AC INI-Param: IpProfile_SBCRemoteMultiple18xSupport"
       ::= {iPProfileEntry 52}



     iPProfileSBCRemoteEarlyMediaResponseType OBJECT-TYPE
       SYNTAX INTEGER {
                  responseTypeTransparent(0)
,
                  responseType180(1)
,
                  responseType183(2)

                  }
       MAX-ACCESS read-create
       STATUS current
       DESCRIPTION
           "SBC Remote Early Media Response Type.
Access: Instant.
AC INI-Param: IpProfile_SBCRemoteEarlyMediaResponseType"
       ::= {iPProfileEntry 53}



     iPProfileSBCRemoteUpdateSupport OBJECT-TYPE
       SYNTAX INTEGER {
                  notSupported(0)
,
                  supportedOnlyAfterConnect(1)
,
                  supported(2)

                  }
       MAX-ACCESS read-create
       STATUS current
       DESCRIPTION
           "SBC Remote Update Support.
Access: Instant.
AC INI-Param: IpProfile_SBCRemoteUpdateSupport"
       ::= {iPProfileEntry 54}



     iPProfileSBCRemoteReinviteSupport OBJECT-TYPE
       SYNTAX INTEGER {
                  notSupported(0)
,
                  supportedOnlyWithSDP(1)
,
                  supported(2)

                  }
       MAX-ACCESS read-create
       STATUS current
       DESCRIPTION
           "SBC Remote Reinvite Support.
Access: Instant.
AC INI-Param: IpProfile_SBCRemoteReinviteSupport"
       ::= {iPProfileEntry 55}



     iPProfileSBCRemoteReferBehavior OBJECT-TYPE
       SYNTAX INTEGER {
                  notConfigured(-1)
,
                  regular(0)
,
                  dBURL(1)
,
                  iPGroupName(2)
,
                  handleLocally(3)

                  }
       MAX-ACCESS read-create
       STATUS current
       DESCRIPTION
           "SBC Remote Refer Behavior.
Access: Instant.
AC INI-Param: IpProfile_SBCRemoteReferBehavior"
       ::= {iPProfileEntry 56}



     iPProfileSBCRemoteEarlyMediaSupport OBJECT-TYPE
       SYNTAX INTEGER {
                  notSupported(0)
,
                  supported(1)

                  }
       MAX-ACCESS read-create
       STATUS current
       DESCRIPTION
           "SBC Remote Early Media Support.
Access: Instant.
AC INI-Param: IpProfile_SBCRemoteEarlyMediaSupport"
       ::= {iPProfileEntry 57}



     iPProfileSBCRemote3xxBehavior OBJECT-TYPE
       SYNTAX INTEGER {
                  notConfigured(-1)
,
                  transparent(0)
,
                  dBURL(1)
,
                  handleLocally(2)

                  }
       MAX-ACCESS read-create
       STATUS current
       DESCRIPTION
           "SBC Remote 3xx Behavior.
Access: Instant.
AC INI-Param: IpProfile_SBCRemote3xxBehavior"
       ::= {iPProfileEntry 58}



     iPProfileSBCRemoteDelayedOfferSupport OBJECT-TYPE
       SYNTAX INTEGER {
                  notSupported(0)
,
                  supported(1)

                  }
       MAX-ACCESS read-create
       STATUS current
       DESCRIPTION
           "SBC Remote Delayed Offer Support.
Access: Instant.
AC INI-Param: IpProfile_SBCRemoteDelayedOfferSupport"
       ::= {iPProfileEntry 59}



     iPProfileSBCPrackMode OBJECT-TYPE
       SYNTAX INTEGER {
                  optional(1)
,
                  mandatory(2)
,
                  transparent(3)

                  }
       MAX-ACCESS read-create
       STATUS current
       DESCRIPTION
           "Defines the LEG's related PRACK behavior.
Access: Instant.
AC INI-Param: IpProfile_SbcPrackMode"
       ::= {iPProfileEntry 60}



     iPProfileSBCUserRegistrationTime OBJECT-TYPE
       SYNTAX Unsigned32 (0..2000000)
       MAX-ACCESS read-create
       STATUS current
       DESCRIPTION
           "SBC User Registration Time.
Access: Instant.
AC INI-Param: IpProfile_SBCUserRegistrationTime "
       ::= {iPProfileEntry 61}



     iPProfileSBCRemoteHoldFormat OBJECT-TYPE
       SYNTAX INTEGER {
                  transparent(0)
,
                  sendOnly(1)
,
                  sendOnly-IpAddress0(2)
,
                  inactive(3)
,
                  inactive-IpAddress0(4)
,
                  notSupported(5)

                  }
       MAX-ACCESS read-create
       STATUS current
       DESCRIPTION
           "SBC Remote Hold Format.
Access: Instant.
AC INI-Param: IpProfile_SBCRemoteHoldFormat"
       ::= {iPProfileEntry 62}



     iPProfileSBCRTPRedundancyBehavior OBJECT-TYPE
       SYNTAX INTEGER {
                  asIs(0)
,
                  extend(1)
,
                  disallow(2)

                  }
       MAX-ACCESS read-create
       STATUS current
       DESCRIPTION
           "SBC RTP Redundancy Behavior.
Access: Instant.
AC INI-Param: IpProfile_SBCRTPRedundancyBehavior"
       ::= {iPProfileEntry 63}



     iPProfileSBCSDPPtimeAnswer OBJECT-TYPE
       SYNTAX INTEGER {
                  remoteAnswer(0)
,
                  originalOffer(1)
,
                  preferredValue(2)

                  }
       MAX-ACCESS read-create
       STATUS current
       DESCRIPTION
           "SBC SDP Ptime Answer.
Access: Instant.
AC INI-Param: IpProfile_SBCSDPPtimeAnswer"
       ::= {iPProfileEntry 64}



     iPProfileSBCPreferredPTime OBJECT-TYPE
       SYNTAX Unsigned32 (0..200)
       MAX-ACCESS read-create
       STATUS current
       DESCRIPTION
           "SBC Preferred PTime.
Access: Instant.
AC INI-Param: IpProfile_SBCPreferredPTime"
       ::= {iPProfileEntry 65}



     iPProfileSBCUseSilenceSupp OBJECT-TYPE
       SYNTAX INTEGER {
                  transparent(0)
,
                  add(1)
,
                  remove(2)

                  }
       MAX-ACCESS read-create
       STATUS current
       DESCRIPTION
           "SBC Use Silence Suppression.
Access: Instant.
AC INI-Param: IpProfile_SBCUseSilenceSupp"
       ::= {iPProfileEntry 66}



     iPProfileSBC2833DTMFPayloadType OBJECT-TYPE
       SYNTAX Unsigned32 (0..200)
       MAX-ACCESS read-create
       STATUS current
       DESCRIPTION
           "Defines SBC RFC2833 DTMF Payload Type Value.
Access: Instant.
AC INI-Param: IpProfile_SBC2833DTMFPayloadType"
       ::= {iPProfileEntry 67}



     iPProfileSBCRemoteReplacesBehavior OBJECT-TYPE
       SYNTAX INTEGER {
                  transparent(0)
,
                  handle-locally(1)

                  }
       MAX-ACCESS read-create
       STATUS current
       DESCRIPTION
           "Controls how SBC will handle INVITE with Replaces header.
Access: Instant.
AC INI-Param: IpProfile_SBCRemoteReplacesBehavior"
       ::= {iPProfileEntry 68}



     iPProfileSBCPlayHeldTone OBJECT-TYPE
       SYNTAX INTEGER {
                  false(0)
,
                  true(1)

                  }
       MAX-ACCESS read-create
       STATUS current
       DESCRIPTION
           "SBC Play Held Tone.
Access: Instant.
AC INI-Param: IpProfile_SBCPlayHeldTone"
       ::= {iPProfileEntry 69}



     iPProfileSBCReliableHeldToneSource OBJECT-TYPE
       SYNTAX INTEGER {
                  false(0)
,
                  true(1)

                  }
       MAX-ACCESS read-create
       STATUS current
       DESCRIPTION
           "SBC Reliable Held Tone Source.
Access: Instant.
AC INI-Param: IpProfile_SBCReliableHeldToneSource"
       ::= {iPProfileEntry 70}



     iPProfileSBCPlayRBTToTransferee OBJECT-TYPE
       SYNTAX INTEGER {
                  no(0)
,
                  yes(1)

                  }
       MAX-ACCESS read-create
       STATUS current
       DESCRIPTION
           "Play Ring Back Tone to transferred side on call transfer.
Access: Instant.
AC INI-Param: IpProfile_SBCPlayRBTToTransferee"
       ::= {iPProfileEntry 71}



     iPProfileSBCJitterCompensation OBJECT-TYPE
       SYNTAX INTEGER {
                  disable(0)
,
                  enable(1)

                  }
       MAX-ACCESS read-create
       STATUS current
       DESCRIPTION
           "SBC Jitter Compensation.
Access: Instant.
AC INI-Param: IpProfile_SBCJitterCompensation"
       ::= {iPProfileEntry 72}



     iPProfileSBCRtcpMode OBJECT-TYPE
       SYNTAX INTEGER {
                  transparent(0)
,
                  generateAlways(1)
,
                  generateOnlyIfRTPActive(2)

                  }
       MAX-ACCESS read-create
       STATUS current
       DESCRIPTION
           "SBC RTCP Mode.
Access: Instant.
AC INI-Param: IpProfile_SBCRTCPMode"
       ::= {iPProfileEntry 73}



     iPProfileSBCAllowedMediaTypes OBJECT-TYPE
       SYNTAX SnmpAdminString (SIZE (0..64))
       MAX-ACCESS read-create
       STATUS current
       DESCRIPTION
           "Defines SBC allowed media types (comma separated string).
Access: Instant.
AC INI-Param: IpProfile_SBCAllowedMediaTypes"
       ::= {iPProfileEntry 74}



     iPProfileEarlyAnswerTimeout OBJECT-TYPE
       SYNTAX Unsigned32 (0..2400)
       MAX-ACCESS read-create
       STATUS current
       DESCRIPTION
           "Max time (in seconds) to wait from sending setup message to
PSTN to receiving connect message from PSTN.
Access: Instant.
AC INI-Param: IpProfile_EarlyAnswerTimeout"
       ::= {iPProfileEntry 75}



     iPProfileAmdMode OBJECT-TYPE
       SYNTAX INTEGER {
                  doNotDisconnect(0)
,
                  disconnectOnAmd(1)

                  }
       MAX-ACCESS read-create
       STATUS current
       DESCRIPTION
           "0 -  not affected 1 - disconnect IP2TEL call on Answering Machine
detection.
Access: Instant.
AC INI-Param: IpProfile_AmdMode"
       ::= {iPProfileEntry 76}



     iPProfileSBCRemoteRenegotiateOnFaxDetection OBJECT-TYPE
       SYNTAX INTEGER {
                  dontCare(0)
,
                  onlyInAnswerSide(1)
,
                  no(2)

                  }
       MAX-ACCESS read-create
       STATUS current
       DESCRIPTION
           "Describes if the remote renegotiate on fax detection.
Access: Instant.
AC INI-Param: IpProfile_SBCRemoteRenegotiateOnFaxDetection"
       ::= {iPProfileEntry 77}



     iPProfileResetSRTPStateUponRekey OBJECT-TYPE
       SYNTAX INTEGER {
                  disable(0)
,
                  enable(1)

                  }
       MAX-ACCESS read-create
       STATUS current
       DESCRIPTION
           "Reset SRTP State Upon Re-key.
Access: Instant.
AC INI-Param: IpProfile_ResetSRTPStateUponRekey"
       ::= {iPProfileEntry 78}



     -- ****************************************
     -- telProfile table declaration
     -- ****************************************
     telProfileTable OBJECT-TYPE
       SYNTAX SEQUENCE OF TelProfileEntry
       MAX-ACCESS not-accessible
       STATUS current
       DESCRIPTION
           ""
       ::= {profile 22}



     -- ****************************************
     -- telProfile table entry
     -- ****************************************
     telProfileEntry OBJECT-TYPE
       SYNTAX TelProfileEntry
       MAX-ACCESS not-accessible
       STATUS current
       DESCRIPTION
           ""
       INDEX {telProfileIndex}
       ::= {telProfileTable 1}



     -- ****************************************
     -- telProfile TABLE
     -- ****************************************
     TelProfileEntry ::= SEQUENCE {
       telProfileIndex                                 Unsigned32,
       telProfileRowStatus                             RowStatus,
       telProfileAction                                INTEGER,
       telProfileActionResult                          INTEGER,
       telProfilePreference                            Unsigned32,
       telProfileProfileName                           SnmpAdminString,
       telProfileCodersGroupID                         Unsigned32,
       telProfileFaxTransportMode                      Unsigned32,
       telProfileIsFaxUsed                             INTEGER,
       telProfileDJBufMinDelay                         Unsigned32,
       telProfileDJBufOptFactor                        Unsigned32,
       telProfileIPDiffServ                            Unsigned32,
       telProfileSigIPDiffServ                         Unsigned32,
       telProfileVoiceVolume                           Integer32,
       telProfileDTMFVolume                            Integer32,
       telProfileInputGain                             Integer32,
       telProfileEnableReversalPolarity                INTEGER,
       telProfileEnableCurrentDisconnect               INTEGER,
       telProfileEnableDigitDelivery                   INTEGER,
       telProfileECE                                   INTEGER,
       telProfileMWIanalogLamp                         INTEGER,
       telProfileMWIDisplay                            INTEGER,
       telProfileMaxFlashHookDetectionPeriod           Unsigned32,
       telProfileEnableEarlyMedia                      INTEGER,
       telProfileProgressIndicatorToIP                 INTEGER,
       telProfileTimeForReorderTone                    Unsigned32,
       telProfileEnableDIDWink                         INTEGER,
       telProfileIsTwoStageDial                        INTEGER,
       telProfileDisconnectOnBusyTone                  INTEGER,
       telProfileEnableVoiceMailDelay                  INTEGER,
       telProfileDialPlanIndex                         Integer32,
       telProfileEnable911PSAP                         INTEGER,
       telProfileSwapTelToIpPhoneNumbers               INTEGER,
       telProfileEnableAGC                             INTEGER,
       telProfileECNlpMode                             INTEGER,
       telProfileEnableFXODoubleAnswer                 INTEGER,
       telProfileCallPriorityMode                      INTEGER,
       telProfileFXORingTimeout                        Integer32
     }



     telProfileIndex OBJECT-TYPE
       SYNTAX Unsigned32 (1..9)
       MAX-ACCESS not-accessible
       STATUS current
       DESCRIPTION
           "Entry number, starting at 1.
AC INI-Param: TelProfile_Index"
       ::= {telProfileEntry 1}



     telProfileRowStatus OBJECT-TYPE
       SYNTAX RowStatus
       MAX-ACCESS read-create
       STATUS current
       DESCRIPTION
           "Row-Status Textual Conventions as defined in RFC 2579: Textual
Conventions for SMIv2.
AC INI-Param: N/A"
       ::= {telProfileEntry 2}



     telProfileAction OBJECT-TYPE
       SYNTAX INTEGER {
                  developmentImpending(0)

                  }
       MAX-ACCESS read-only
       STATUS current
       DESCRIPTION
           "Development Impending.
AC INI-Param: N/A"
       ::= {telProfileEntry 3}



     telProfileActionResult OBJECT-TYPE
       SYNTAX INTEGER {
                  developmentImpending(0)

                  }
       MAX-ACCESS read-only
       STATUS current
       DESCRIPTION
           "Development Impending.
AC INI-Param: N/A"
       ::= {telProfileEntry 4}



     telProfilePreference OBJECT-TYPE
       SYNTAX Unsigned32 (0..20)
       MAX-ACCESS read-create
       STATUS current
       DESCRIPTION
           "Preference.
Access: Instant.
AC INI-Param: TelProfile_TelPreference"
       ::= {telProfileEntry 5}



     telProfileProfileName OBJECT-TYPE
       SYNTAX SnmpAdminString (SIZE (0..19))
       MAX-ACCESS read-create
       STATUS current
       DESCRIPTION
           "Profile Name.
Access: Instant.
AC INI-Param: TelProfile_ProfileName"
       ::= {telProfileEntry 6}



     telProfileCodersGroupID OBJECT-TYPE
       SYNTAX Unsigned32 (0..4)
       MAX-ACCESS read-create
       STATUS current
       DESCRIPTION
           "Coders Group ID.
Access: Instant.
AC INI-Param: TelProfile_CodersGroupID"
       ::= {telProfileEntry 7}



     telProfileFaxTransportMode OBJECT-TYPE
       SYNTAX Unsigned32 (0..3)
       MAX-ACCESS read-write
       STATUS obsolete
       DESCRIPTION
           "Fax Transport Mode.
Access: Instant.
AC INI-Param: N/A"
       ::= {telProfileEntry 8}



     telProfileIsFaxUsed OBJECT-TYPE
       SYNTAX INTEGER {
                  noFax(0)
,
                  t38(1)
,
                  g711(2)
,
                  fallBack(3)
,
                  notConfigured(255)

                  }
       MAX-ACCESS read-create
       STATUS current
       DESCRIPTION
           "Use H.323/Annex D procedure for real time FAX relay. To use
this feature, disable inband DTMF by setting the FaxTransportMode
to 1.0 - No fax , 1- T.38  , 2- Fax Fallback (G.711 with
optimization).
Access: Instant.
AC INI-Param: TelProfile_IsFaxUsed"
       ::= {telProfileEntry 9}



     telProfileDJBufMinDelay OBJECT-TYPE
       SYNTAX Unsigned32 (0..255)
       MAX-ACCESS read-create
       STATUS current
       DESCRIPTION
           "Dynamic Jitter Buffer Minimum Delay (msec).
Access: Instant.
AC INI-Param: TelProfile_JitterBufMinDelay"
       ::= {telProfileEntry 10}



     telProfileDJBufOptFactor OBJECT-TYPE
       SYNTAX Unsigned32 (0..255)
       MAX-ACCESS read-create
       STATUS current
       DESCRIPTION
           "Dynamic jitter buffer frame error/delay optimization.
Access: Instant.
AC INI-Param: TelProfile_JitterBufOptFactor"
       ::= {telProfileEntry 11}



     telProfileIPDiffServ OBJECT-TYPE
       SYNTAX Unsigned32 (0..255)
       MAX-ACCESS read-create
       STATUS current
       DESCRIPTION
           "IP DiffServ byte value.
Access: Instant.
AC INI-Param: TelProfile_IPDiffServ"
       ::= {telProfileEntry 12}



     telProfileSigIPDiffServ OBJECT-TYPE
       SYNTAX Unsigned32 (0..255)
       MAX-ACCESS read-create
       STATUS current
       DESCRIPTION
           "Type Of Service bits in IP header of signalling messages.
Access: Instant.
AC INI-Param: TelProfile_SigIPDiffServ"
       ::= {telProfileEntry 13}



     telProfileVoiceVolume OBJECT-TYPE
       SYNTAX Integer32 (-32..255)
       MAX-ACCESS read-create
       STATUS current
       DESCRIPTION
           "Voice Volume.
Access: Instant.
AC INI-Param: TelProfile_VoiceVolume"
       ::= {telProfileEntry 14}



     telProfileDTMFVolume OBJECT-TYPE
       SYNTAX Integer32 (-31..255)
       MAX-ACCESS read-create
       STATUS current
       DESCRIPTION
           "DTMF Volume.
Access: Instant.
AC INI-Param: TelProfile_DtmfVolume"
       ::= {telProfileEntry 15}



     telProfileInputGain OBJECT-TYPE
       SYNTAX Integer32 (-32..255)
       MAX-ACCESS read-create
       STATUS current
       DESCRIPTION
           "Input Gain.
Access: Instant.
AC INI-Param: TelProfile_InputGain"
       ::= {telProfileEntry 16}



     telProfileEnableReversalPolarity OBJECT-TYPE
       SYNTAX INTEGER {
                  no(0)
,
                  yes(1)
,
                  notConfigured(255)

                  }
       MAX-ACCESS read-create
       STATUS current
       DESCRIPTION
           "FXO: Connect/Disconnect calls upon detection of polarity reversal
signal. FXS: generate the signal.
Access: Instant.
AC INI-Param: TelProfile_EnableReversePolarity"
       ::= {telProfileEntry 17}



     telProfileEnableCurrentDisconnect OBJECT-TYPE
       SYNTAX INTEGER {
                  no(0)
,
                  yes(1)
,
                  notConfigured(255)

                  }
       MAX-ACCESS read-create
       STATUS current
       DESCRIPTION
           "Disconnect call upon detection of current disconnect signal.
Access: Instant.
AC INI-Param: TelProfile_EnableCurrentDisconnect"
       ::= {telProfileEntry 18}



     telProfileEnableDigitDelivery OBJECT-TYPE
       SYNTAX INTEGER {
                  disable(0)
,
                  enable(1)
,
                  notConfigured(255)

                  }
       MAX-ACCESS read-create
       STATUS current
       DESCRIPTION
           "Enables Digit delivery to TEL side.
Access: Instant.
AC INI-Param: TelProfile_EnableDigitDelivery"
       ::= {telProfileEntry 19}



     telProfileECE OBJECT-TYPE
       SYNTAX INTEGER {
                  disable(0)
,
                  enable(1)
,
                  notConfigured(255)

                  }
       MAX-ACCESS read-create
       STATUS current
       DESCRIPTION
           "Enables or disables the echo canceler.
Access: Instant.
AC INI-Param: TelProfile_EnableEC"
       ::= {telProfileEntry 20}



     telProfileMWIanalogLamp OBJECT-TYPE
       SYNTAX INTEGER {
                  disable(0)
,
                  enable(1)
,
                  notConfigured(255)

                  }
       MAX-ACCESS read-create
       STATUS current
       DESCRIPTION
           "Enable MWI support using an analog lamp (110 Volt).
Access: Instant.
AC INI-Param: TelProfile_MWIAnalog"
       ::= {telProfileEntry 21}



     telProfileMWIDisplay OBJECT-TYPE
       SYNTAX INTEGER {
                  disable(0)
,
                  enable(1)
,
                  notConfigured(255)

                  }
       MAX-ACCESS read-create
       STATUS current
       DESCRIPTION
           "Enable MWI support using Caller ID interface.
Access: Instant.
AC INI-Param: TelProfile_MWIDisplay"
       ::= {telProfileEntry 22}



     telProfileMaxFlashHookDetectionPeriod OBJECT-TYPE
       SYNTAX Unsigned32 (0..2000)
       MAX-ACCESS read-create
       STATUS current
       DESCRIPTION
           "
Access: Instant.
AC INI-Param: TelProfile_FlashHookPeriod"
       ::= {telProfileEntry 23}



     telProfileEnableEarlyMedia OBJECT-TYPE
       SYNTAX INTEGER {
                  disable(0)
,
                  enable(1)
,
                  notConfigured(255)

                  }
       MAX-ACCESS read-create
       STATUS current
       DESCRIPTION
           "Enable Early Media.
Access: Instant.
AC INI-Param: TelProfile_EnableEarlyMedia"
       ::= {telProfileEntry 24}



     telProfileProgressIndicatorToIP OBJECT-TYPE
       SYNTAX INTEGER {
                  default(-1)
,
                  noPI(0)
,
                  pI1(1)
,
                  pI8(8)
,
                  notConfigured(255)

                  }
       MAX-ACCESS read-create
       STATUS current
       DESCRIPTION
           "Determine whether to send the Progress Indicator to IP.
Access: Instant.
AC INI-Param: TelProfile_ProgressIndicator2IP"
       ::= {telProfileEntry 25}



     telProfileTimeForReorderTone OBJECT-TYPE
       SYNTAX Unsigned32 (0..255)
       MAX-ACCESS read-create
       STATUS current
       DESCRIPTION
           "Duration of reorder tone playing before FXO releases line.
Access: Instant.
AC INI-Param: TelProfile_TimeForReorderTone"
       ::= {telProfileEntry 26}



     telProfileEnableDIDWink OBJECT-TYPE
       SYNTAX INTEGER {
                  notConfigured(-1)
,
                  disable(0)
,
                  single(1)
,
                  doubleWink(2)
,
                  winkAndPolarity(3)

                  }
       MAX-ACCESS read-create
       STATUS current
       DESCRIPTION
           "Enable support for DID lines using Wink.
Access: Instant.
AC INI-Param: TelProfile_EnableDIDWink"
       ::= {telProfileEntry 27}



     telProfileIsTwoStageDial OBJECT-TYPE
       SYNTAX INTEGER {
                  notConfigured(-1)
,
                  disable(0)
,
                  enable(1)

                  }
       MAX-ACCESS read-create
       STATUS current
       DESCRIPTION
           "
Access: Instant.
AC INI-Param: TelProfile_IsTwoStageDial"
       ::= {telProfileEntry 28}



     telProfileDisconnectOnBusyTone OBJECT-TYPE
       SYNTAX INTEGER {
                  notConfigured(-1)
,
                  no(0)
,
                  yes(1)

                  }
       MAX-ACCESS read-create
       STATUS current
       DESCRIPTION
           "
Access: Instant.
AC INI-Param: TelProfile_DisconnectOnBusyTone"
       ::= {telProfileEntry 29}



     telProfileEnableVoiceMailDelay OBJECT-TYPE
       SYNTAX INTEGER {
                  notConfigured(-1)
,
                  disable(0)
,
                  enable(1)

                  }
       MAX-ACCESS read-create
       STATUS current
       DESCRIPTION
           "
Access: Instant.
AC INI-Param: TelProfile_EnableVoiceMailDelay"
       ::= {telProfileEntry 30}



     telProfileDialPlanIndex OBJECT-TYPE
       SYNTAX Integer32 (-1..7)
       MAX-ACCESS read-create
       STATUS current
       DESCRIPTION
           "Defines the plan index to be used from the external Dial Plan
file.
Access: Instant.
AC INI-Param: TelProfile_DialPlanIndex"
       ::= {telProfileEntry 31}



     telProfileEnable911PSAP OBJECT-TYPE
       SYNTAX INTEGER {
                  notConfigured(-1)
,
                  disable(0)
,
                  enable(1)

                  }
       MAX-ACCESS read-create
       STATUS current
       DESCRIPTION
           "GwApp Tel Profile Table.
Access: Instant.
AC INI-Param: TelProfile_Enable911PSAP"
       ::= {telProfileEntry 32}



     telProfileSwapTelToIpPhoneNumbers OBJECT-TYPE
       SYNTAX INTEGER {
                  notConfigured(-1)
,
                  disable(0)
,
                  enable(1)

                  }
       MAX-ACCESS read-create
       STATUS current
       DESCRIPTION
           "GwApp Tel Profile Table.
Access: Instant.
AC INI-Param: TelProfile_SwapTelToIpPhoneNumbers"
       ::= {telProfileEntry 33}



     telProfileEnableAGC OBJECT-TYPE
       SYNTAX INTEGER {
                  notConfigured(-1)
,
                  disable(0)
,
                  enable(1)

                  }
       MAX-ACCESS read-create
       STATUS current
       DESCRIPTION
           "
Access: Instant.
AC INI-Param: TelProfile_EnableAGC"
       ::= {telProfileEntry 34}



     telProfileECNlpMode OBJECT-TYPE
       SYNTAX INTEGER {
                  notConfigured(-1)
,
                  adaptiveNLP(0)
,
                  disabledNLP(1)
,
                  silenceOutputNLP(2)

                  }
       MAX-ACCESS read-create
       STATUS current
       DESCRIPTION
           "
Access: Instant.
AC INI-Param: TelProfile_ECNlpMode"
       ::= {telProfileEntry 35}



     telProfileEnableFXODoubleAnswer OBJECT-TYPE
       SYNTAX INTEGER {
                  notSet(-1)
,
                  disabled(0)
,
                  enabled(1)

                  }
       MAX-ACCESS read-create
       STATUS current
       DESCRIPTION
           "GwApp Tel Profile Table.
Access: Instant.
AC INI-Param: TelProfile_EnableFXODoubleAnswer"
       ::= {telProfileEntry 36}



     telProfileCallPriorityMode OBJECT-TYPE
       SYNTAX INTEGER {
                  notConfigured(-1)
,
                  none(0)
,
                  mLPP(1)
,
                  emergency(2)

                  }
       MAX-ACCESS read-create
       STATUS current
       DESCRIPTION
           "GwApp Tel Profile Table.
Access: Instant.
AC INI-Param: TelProfile_CallPriorityMode"
       ::= {telProfileEntry 37}



     telProfileFXORingTimeout OBJECT-TYPE
       SYNTAX Integer32 (-1..50)
       MAX-ACCESS read-create
       STATUS current
       DESCRIPTION
           "Defines the delay (in 100 msec) for generating INVITE after
RING_START detection. The valid range is 0 to 50.
Access: Instant.
AC INI-Param: TelProfile_FXORingTimeout"
       ::= {telProfileEntry 38}



     voiceMail OBJECT IDENTIFIER ::= {common 16}


     voiceMailLineTransferMode OBJECT-TYPE
       SYNTAX INTEGER {
                  ip(0)
,
                  pbxblindtransfer(1)
,
                  pbxsemisupervised(2)
,
                  pbxsupervisedtransfer(3)

                  }
       MAX-ACCESS read-write
       STATUS current
       DESCRIPTION
           "LineTransferMode: 0-ip 1-pbx blind transfer 2-pbx semi supv
transfer 3-supervised transfer (also known as warm transfer).
(in TP, feature key and parameter EnableIPMDetectors needed).
Access: Instant.
AC INI-Param: LineTransferMode"
       ::= {voiceMail 1}



     voiceMailInterface OBJECT-TYPE
       SYNTAX INTEGER {
                  none(0)
,
                  dtmf(1)
,
                  smdi(2)
,
                  qsig(3)
,
                  isdnsetup(4)
,
                  qsigMatra(5)
,
                   qsigSiemens(6)
,
                  ip2ip(7)
,
                  etsi(8)
,
                  ni2(9)

                  }
       MAX-ACCESS read-write
       STATUS current
       DESCRIPTION
           "Selects the method of communication between PBX and the Gateway,
that is used instead of legacy voicemail.
Access: Instant.
AC INI-Param: VoiceMailInterface"
       ::= {voiceMail 2}



     vmDigitPattern OBJECT IDENTIFIER ::= {voiceMail 20}


     vmDigitPatternNoReason OBJECT-TYPE
       SYNTAX SnmpAdminString (SIZE (0..119))
       MAX-ACCESS read-write
       STATUS current
       DESCRIPTION
           "Digit pattern used to indicate Call Forward with no reason (PBX
to VoiceMail).
Access: Instant.
AC INI-Param: DigitPatternForwardNoReason"
       ::= {vmDigitPattern 1}



     vmDigitPatternOnBusy OBJECT-TYPE
       SYNTAX SnmpAdminString (SIZE (0..119))
       MAX-ACCESS read-write
       STATUS current
       DESCRIPTION
           "Digit pattern used to indicate Call Forward on busy (PBX to
VoiceMail).
Access: Instant.
AC INI-Param: DigitPatternForwardOnBusy"
       ::= {vmDigitPattern 2}



     vmDigitPatternOnNoAnswer OBJECT-TYPE
       SYNTAX SnmpAdminString (SIZE (0..119))
       MAX-ACCESS read-write
       STATUS current
       DESCRIPTION
           "Digit pattern used to indicate Call Forward on no answer (PBX
to VoiceMail).
Access: Instant.
AC INI-Param: DigitPatternForwardOnNoAnswer"
       ::= {vmDigitPattern 3}



     vmDigitPatternOnDND OBJECT-TYPE
       SYNTAX SnmpAdminString (SIZE (0..119))
       MAX-ACCESS read-write
       STATUS current
       DESCRIPTION
           "Digit pattern used to indicate Call Forward on Do Not Disturb
(PBX to VoiceMail).
Access: Instant.
AC INI-Param: DigitPatternForwardOnDND"
       ::= {vmDigitPattern 4}



     vmDigitPatternInternalCall OBJECT-TYPE
       SYNTAX SnmpAdminString (SIZE (0..119))
       MAX-ACCESS read-write
       STATUS current
       DESCRIPTION
           "Digit pattern used to indicate internal call (PBX to VoiceMail).
Access: Instant.
AC INI-Param: DigitPatternInternalCall"
       ::= {vmDigitPattern 5}



     vmDigitPatternExternalCall OBJECT-TYPE
       SYNTAX SnmpAdminString (SIZE (0..119))
       MAX-ACCESS read-write
       STATUS current
       DESCRIPTION
           "Digit pattern used to indicate external call (PBX to VoiceMail).
Access: Instant.
AC INI-Param: DigitPatternExternalCall"
       ::= {vmDigitPattern 6}



     vmDigitPatternDisconnectCode OBJECT-TYPE
       SYNTAX SnmpAdminString (SIZE (0..24))
       MAX-ACCESS read-write
       STATUS current
       DESCRIPTION
           "Disconnect call if digit string is received from the TEL side
during session.
Access: Instant.
AC INI-Param: TelDisconnectCode"
       ::= {vmDigitPattern 7}



     vmDigitPatternConnectCode OBJECT-TYPE
       SYNTAX SnmpAdminString (SIZE (0..7))
       MAX-ACCESS read-write
       STATUS current
       DESCRIPTION
           "Play Code string to Tel side when connect message recieved from
IP side.
Access: Instant.
AC INI-Param: TELCONNECTCODE"
       ::= {vmDigitPattern 8}



     vmDigitPatternVmDigitPatternOnBusyExternal OBJECT-TYPE
       SYNTAX SnmpAdminString (SIZE (0..119))
       MAX-ACCESS read-write
       STATUS current
       DESCRIPTION
           "Digit pattern used to indicate Call Forward on busy (PBX to
VoiceMail).
Access: Instant.
AC INI-Param: DigitPatternForwardOnBusyExt"
       ::= {vmDigitPattern 9}



     vmDigitPatternVmDigitPatternOnNoAnswerExternal OBJECT-TYPE
       SYNTAX SnmpAdminString (SIZE (0..119))
       MAX-ACCESS read-write
       STATUS current
       DESCRIPTION
           "Digit pattern used to indicate Call Forward on no answer (PBX
to VoiceMail).
Access: Instant.
AC INI-Param: DigitPatternForwardOnNoAnswerExt"
       ::= {vmDigitPattern 10}



     vmDigitPatternVmDigitPatternOnDNDExternal OBJECT-TYPE
       SYNTAX SnmpAdminString (SIZE (0..119))
       MAX-ACCESS read-write
       STATUS current
       DESCRIPTION
           "Digit pattern used to indicate Call Forward on Do Not Disturb
(PBX to VoiceMail).
Access: Instant.
AC INI-Param: DigitPatternForwardOnDNDExt"
       ::= {vmDigitPattern 11}



     vmDigitPatternVmDigitPatternNoReasonExternal OBJECT-TYPE
       SYNTAX SnmpAdminString (SIZE (0..119))
       MAX-ACCESS read-write
       STATUS current
       DESCRIPTION
           "Digit pattern used to indicate Call Forward with no reason (PBX
to VoiceMail).
Access: Instant.
AC INI-Param: DigitPatternForwardNoReasonExt"
       ::= {vmDigitPattern 12}



     vmDigitPatternDigitToIgnore OBJECT-TYPE
       SYNTAX SnmpAdminString (SIZE (0..50))
       MAX-ACCESS read-write
       STATUS current
       DESCRIPTION
           "A digit (0-9,A-D,* or #) that if received as Src (S) or Redirect
(R), the digit is ignored and not added to that number.
Used in DTMF VoiceMail.
Access: Instant.
AC INI-Param: DigitPatternDigitToIgnore"
       ::= {vmDigitPattern 13}



     vmMWI OBJECT IDENTIFIER ::= {voiceMail 21}


     vmMWIOnCode OBJECT-TYPE
       SYNTAX SnmpAdminString (SIZE (0..25))
       MAX-ACCESS read-write
       STATUS current
       DESCRIPTION
           "Digit pattern used to notify PBX about messages waiting for
extension (added as prefix).
Access: Instant.
AC INI-Param: MWIOnCode"
       ::= {vmMWI 1}



     vmMWIOffCode OBJECT-TYPE
       SYNTAX SnmpAdminString (SIZE (0..25))
       MAX-ACCESS read-write
       STATUS current
       DESCRIPTION
           "Digit pattern used to notify PBX about no messages waiting for
extension (added as prefix).
Access: Instant.
AC INI-Param: MWIOffCode"
       ::= {vmMWI 2}



     vmMWISuffixCode OBJECT-TYPE
       SYNTAX SnmpAdminString (SIZE (0..25))
       MAX-ACCESS read-write
       STATUS current
       DESCRIPTION
           "MWI suffix code used to notify PBX about messages waiting for
extension (added as suffix to the extention number).
Access: Instant.
AC INI-Param: MWISuffixCode"
       ::= {vmMWI 3}



     vmMWISourceNumber OBJECT-TYPE
       SYNTAX SnmpAdminString (SIZE (0..50))
       MAX-ACCESS read-write
       STATUS current
       DESCRIPTION
           "The phone number sent as source number toward PSTN for MWI setup.
Access: Instant.
AC INI-Param: MWISOURCENUMBER"
       ::= {vmMWI 4}



     vmSMDI OBJECT IDENTIFIER ::= {voiceMail 22}


     vmSMDIEnable OBJECT-TYPE
       SYNTAX INTEGER {
                  disable(0)
,
                  enable(1)

                  }
       MAX-ACCESS read-write
       STATUS current
       DESCRIPTION
           "Enables the Simplified Message Desk Interface (SMDI). SMDI defines
a method whereby telephony systems can provide voice-messaging
systems with data required by those telephony systems
to process incoming calls intelligently. Whenever the phone
system routes a call, it sends an SMDI message through an
EIA/TIA-232 connection to the voice-messaging system that
tells it the line that it is using, the type of call that it
is forwarding, and information about the source and destination
of the call. 
0 = Normal Serial
1 = Serial SMDI.
Access: Offline.
AC INI-Param: SMDI"
       ::= {vmSMDI 1}



     vmSMDITimeOut OBJECT-TYPE
       SYNTAX Unsigned32 (0..120000)
       MAX-ACCESS read-write
       STATUS current
       DESCRIPTION
           "Time out <mSec> for:
1. From SMDI Info until SETUP
2. From SETUP until SMDI event.
Access: Instant.
AC INI-Param: SMDITimeOut"
       ::= {vmSMDI 2}



     digitalGWext OBJECT IDENTIFIER ::= {common 17}


     digitalGWextEnableQSIGTunneling OBJECT-TYPE
       SYNTAX INTEGER {
                  disable(0)
,
                  enable(1)

                  }
       MAX-ACCESS read-write
       STATUS current
       DESCRIPTION
           "Enables QSIG Tunneling over SIP.
Access: Instant.
AC INI-Param: ENABLEQSIGTUNNELING"
       ::= {digitalGWext 1}



     digitalGWextRemoveCLIWhenRestricted OBJECT-TYPE
       SYNTAX INTEGER {
                  disable(0)
,
                  enable(1)

                  }
       MAX-ACCESS read-write
       STATUS current
       DESCRIPTION
           "Removes CLI from IP->TEL calls if received CLI is restricted.
Access: Instant.
AC INI-Param: REMOVECLIWHENRESTRICTED"
       ::= {digitalGWext 2}



     digitalGWextDefaultCauseMapISDN2IP OBJECT-TYPE
       SYNTAX Unsigned32 (0..127)
       MAX-ACCESS read-write
       STATUS current
       DESCRIPTION
           "All ISDN release causes except normal, busy, no user responding,
and no answer will be mapped to this cause, if set.
Access: Instant.
AC INI-Param: DEFAULTCAUSEMAPISDN2IP"
       ::= {digitalGWext 3}



     digitalGWextISDNSubaddressFormat OBJECT-TYPE
       SYNTAX INTEGER {
                  ascii(0)
,
                  bcd(1)
,
                  userSpecified(2)

                  }
       MAX-ACCESS read-write
       STATUS current
       DESCRIPTION
           "ISDN SubAdress format.
Access: Instant.
AC INI-Param: ISDNSUBADDRESSFORMAT"
       ::= {digitalGWext 4}



     digitalGWextEnableAoC OBJECT-TYPE
       SYNTAX INTEGER {
                  disable(0)
,
                  enable(1)

                  }
       MAX-ACCESS read-write
       STATUS current
       DESCRIPTION
           "Enable AoC-D and AoC-E from ISDN to SIP.
Access: Instant.
AC INI-Param: ENABLEAOC"
       ::= {digitalGWext 5}



     digitalGWextRemoveCallingName OBJECT-TYPE
       SYNTAX INTEGER {
                  disable(0)
,
                  enable(1)

                  }
       MAX-ACCESS read-write
       STATUS current
       DESCRIPTION
           "If set to 1 - Removes Calling Name  from IP->TEL calls.
Access: Instant.
AC INI-Param: REMOVECALLINGNAME"
       ::= {digitalGWext 6}



     digitalGWextCopyDest2RedirectNumber OBJECT-TYPE
       SYNTAX INTEGER {
                  disable(0)
,
                  afterManipulation(1)
,
                  beforeManipulation(2)

                  }
       MAX-ACCESS read-write
       STATUS current
       DESCRIPTION
           "0 - Redirect N not affected,1- Called N after manipulation from
TEL2IP call will also be used as Redirect N,2 - the Called
N before manipulation - as Redirect N.
Access: Instant.
AC INI-Param: COPYDEST2REDIRECTNUMBER"
       ::= {digitalGWext 7}



     digitalGWextTDMOverIPMinCallsForTrunkActivation OBJECT-TYPE
       SYNTAX Unsigned32 (0..31)
       MAX-ACCESS read-write
       STATUS current
       DESCRIPTION
           "Minimum connected calls for trunk activation while in TDMOverIPMode
 if 0 - trunk is always active.
Access: Instant.
AC INI-Param: TDMOVERIPMINCALLSFORTRUNKACTIVATION"
       ::= {digitalGWext 8}



     digitalGWextUuiHeaderFormat OBJECT-TYPE
       SYNTAX Unsigned32 (0..2)
       MAX-ACCESS read-write
       STATUS current
       DESCRIPTION
           "0: X-UserToUser.
1: format: User-to-UserUser with protocol discriminator. 
2: format: User-to-User with 'encoding=hex' at the end.
Access: Instant.
AC INI-Param: USERTOUSERHEADERFORMAT"
       ::= {digitalGWext 9}



     -- ****************************************
     -- rtpOnlyModeForTrunk table declaration
     -- ****************************************
     rtpOnlyModeForTrunkTable OBJECT-TYPE
       SYNTAX SEQUENCE OF RtpOnlyModeForTrunkEntry
       MAX-ACCESS not-accessible
       STATUS current
       DESCRIPTION
           ""
       ::= {digitalGWext 21}



     -- ****************************************
     -- rtpOnlyModeForTrunk table entry
     -- ****************************************
     rtpOnlyModeForTrunkEntry OBJECT-TYPE
       SYNTAX RtpOnlyModeForTrunkEntry
       MAX-ACCESS not-accessible
       STATUS current
       DESCRIPTION
           ""
       INDEX {rtpOnlyModeForTrunkIndex}
       ::= {rtpOnlyModeForTrunkTable 1}



     -- ****************************************
     -- rtpOnlyModeForTrunk TABLE
     -- ****************************************
     RtpOnlyModeForTrunkEntry ::= SEQUENCE {
       rtpOnlyModeForTrunkIndex                        Unsigned32,
       rtpOnlyModeForTrunkRtpOnlyModeForTrunk          INTEGER
     }



     rtpOnlyModeForTrunkIndex OBJECT-TYPE
       SYNTAX Unsigned32 (0..84)
       MAX-ACCESS not-accessible
       STATUS current
       DESCRIPTION
           "Trunk number.
AC INI-Param: N/A"
       ::= {rtpOnlyModeForTrunkEntry 1}



     rtpOnlyModeForTrunkRtpOnlyModeForTrunk OBJECT-TYPE
       SYNTAX INTEGER {
                  notConfigured(-1)
,
                  disable(0)
,
                  transmitReceive(1)
,
                  transmitOnly(2)
,
                  receiveOnly(3)

                  }
       MAX-ACCESS read-write
       STATUS current
       DESCRIPTION
           "immediately. -1 - takes the RTPONLYMODE global value per gatewa
 0 - regular call establishment. 1 - The RTP channel open
for Rx & Tx. 2-The RTP channel open only for Tx 3 -The RTP
channel open only fo Rx.
Access: Instant.
AC INI-Param: RTPONLYMODEFORTRUNK"
       ::= {rtpOnlyModeForTrunkEntry 2}



     -- ****************************************
     -- acBChannelNegotiationForTrunk table declaration
     -- ****************************************
     acBChannelNegotiationForTrunkTable OBJECT-TYPE
       SYNTAX SEQUENCE OF AcBChannelNegotiationForTrunkEntry
       MAX-ACCESS not-accessible
       STATUS current
       DESCRIPTION
           "B-Channel Negotiation for Trunk table."
       ::= {digitalGWext 22}



     -- ****************************************
     -- acBChannelNegotiationForTrunk table entry
     -- ****************************************
     acBChannelNegotiationForTrunkEntry OBJECT-TYPE
       SYNTAX AcBChannelNegotiationForTrunkEntry
       MAX-ACCESS not-accessible
       STATUS current
       DESCRIPTION
           ""
       INDEX {acBChannelNegotiationForTrunkIndex}
       ::= {acBChannelNegotiationForTrunkTable 1}



     -- ****************************************
     -- acBChannelNegotiationForTrunk TABLE
     -- ****************************************
     AcBChannelNegotiationForTrunkEntry ::= SEQUENCE {
       acBChannelNegotiationForTrunkIndex              Unsigned32,
       acBChannelNegotiationForTrunkMode               INTEGER
     }



     acBChannelNegotiationForTrunkIndex OBJECT-TYPE
       SYNTAX Unsigned32 (0..83)
       MAX-ACCESS not-accessible
       STATUS current
       DESCRIPTION
           "Trunk number starting at 0.
AC INI-Param: N/A"
       ::= {acBChannelNegotiationForTrunkEntry 1}



     acBChannelNegotiationForTrunkMode OBJECT-TYPE
       SYNTAX INTEGER {
                  notConfigured(-1)
,
                  preferred(0)
,
                  exclusive(1)
,
                  any(2)

                  }
       MAX-ACCESS read-write
       STATUS current
       DESCRIPTION
           "ISDN B-Channel negotiation mode for trunk
put  MODE_NOT_SET (-1) to use BCHANNELNEGOTIATION per Gateway.
Access: Instant.
AC INI-Param: BCHANNELNEGOTIATIONFORTRUNK"
       ::= {acBChannelNegotiationForTrunkEntry 2}



     -- ****************************************
     -- acDigitalOOSBehaviorForTrunk table declaration
     -- ****************************************
     acDigitalOOSBehaviorForTrunkTable OBJECT-TYPE
       SYNTAX SEQUENCE OF AcDigitalOOSBehaviorForTrunkEntry
       MAX-ACCESS not-accessible
       STATUS current
       DESCRIPTION
           "Digital OOS Behavior for Trunk table."
       ::= {digitalGWext 23}



     -- ****************************************
     -- acDigitalOOSBehaviorForTrunk table entry
     -- ****************************************
     acDigitalOOSBehaviorForTrunkEntry OBJECT-TYPE
       SYNTAX AcDigitalOOSBehaviorForTrunkEntry
       MAX-ACCESS not-accessible
       STATUS current
       DESCRIPTION
           ""
       INDEX {acDigitalOOSBehaviorForTrunkIndex}
       ::= {acDigitalOOSBehaviorForTrunkTable 1}



     -- ****************************************
     -- acDigitalOOSBehaviorForTrunk TABLE
     -- ****************************************
     AcDigitalOOSBehaviorForTrunkEntry ::= SEQUENCE {
       acDigitalOOSBehaviorForTrunkIndex               Unsigned32,
       acDigitalOOSBehaviorForTrunkValue               INTEGER
     }



     acDigitalOOSBehaviorForTrunkIndex OBJECT-TYPE
       SYNTAX Unsigned32 (0..83)
       MAX-ACCESS not-accessible
       STATUS current
       DESCRIPTION
           "Trunk number starting at 0.
AC INI-Param: N/A"
       ::= {acDigitalOOSBehaviorForTrunkEntry 1}



     acDigitalOOSBehaviorForTrunkValue OBJECT-TYPE
       SYNTAX INTEGER {
                  notConfigured(-1)
,
                  default(0)
,
                  service(1)
,
                  dChannel(2)
,
                  alarm(3)
,
                  block(4)

                  }
       MAX-ACCESS read-write
       STATUS current
       DESCRIPTION
           "Digital OOS Behavior for trunk put  OOS_NOT_SET (-1) to use
DIGITALOOSBEHAVIOR per Gateway.
Access: Instant.
AC INI-Param: DIGITALOOSBEHAVIORFORTRUNK"
       ::= {acDigitalOOSBehaviorForTrunkEntry 2}



     -- ****************************************
     -- acRemoveCallingNameForTrunk table declaration
     -- ****************************************
     acRemoveCallingNameForTrunkTable OBJECT-TYPE
       SYNTAX SEQUENCE OF AcRemoveCallingNameForTrunkEntry
       MAX-ACCESS not-accessible
       STATUS current
       DESCRIPTION
           "Remove Calling Name For Trunk table."
       ::= {digitalGWext 24}



     -- ****************************************
     -- acRemoveCallingNameForTrunk table entry
     -- ****************************************
     acRemoveCallingNameForTrunkEntry OBJECT-TYPE
       SYNTAX AcRemoveCallingNameForTrunkEntry
       MAX-ACCESS not-accessible
       STATUS current
       DESCRIPTION
           ""
       INDEX {acRemoveCallingNameForTrunkIndex}
       ::= {acRemoveCallingNameForTrunkTable 1}



     -- ****************************************
     -- acRemoveCallingNameForTrunk TABLE
     -- ****************************************
     AcRemoveCallingNameForTrunkEntry ::= SEQUENCE {
       acRemoveCallingNameForTrunkIndex                Unsigned32,
       acRemoveCallingNameForTrunkMode                 INTEGER
     }



     acRemoveCallingNameForTrunkIndex OBJECT-TYPE
       SYNTAX Unsigned32 (0..83)
       MAX-ACCESS not-accessible
       STATUS current
       DESCRIPTION
           "Trunk number starting at 0.
AC INI-Param: N/A"
       ::= {acRemoveCallingNameForTrunkEntry 1}



     acRemoveCallingNameForTrunkMode OBJECT-TYPE
       SYNTAX INTEGER {
                  notConfigured(-1)
,
                  disable(0)
,
                  enable(1)

                  }
       MAX-ACCESS read-write
       STATUS current
       DESCRIPTION
           "Remove Calling Name For Trunk table .Set (-1) to use the global
parameter digitalGWextRemoveCallingName.
Access: Instant.
AC INI-Param: RemoveCallingNameForTrunk"
       ::= {acRemoveCallingNameForTrunkEntry 2}



     -- ****************************************
     -- acCallReroutingModeForTrunk table declaration
     -- ****************************************
     acCallReroutingModeForTrunkTable OBJECT-TYPE
       SYNTAX SEQUENCE OF AcCallReroutingModeForTrunkEntry
       MAX-ACCESS not-accessible
       STATUS current
       DESCRIPTION
           "Call Rerouting Mode. Set to 1 to enable ISDN call rerouting"
       ::= {digitalGWext 25}



     -- ****************************************
     -- acCallReroutingModeForTrunk table entry
     -- ****************************************
     acCallReroutingModeForTrunkEntry OBJECT-TYPE
       SYNTAX AcCallReroutingModeForTrunkEntry
       MAX-ACCESS not-accessible
       STATUS current
       DESCRIPTION
           ""
       INDEX {acCallReroutingModeForTrunkIndex}
       ::= {acCallReroutingModeForTrunkTable 1}



     -- ****************************************
     -- acCallReroutingModeForTrunk TABLE
     -- ****************************************
     AcCallReroutingModeForTrunkEntry ::= SEQUENCE {
       acCallReroutingModeForTrunkIndex                Unsigned32,
       acCallReroutingModeForTrunkMode                 INTEGER
     }



     acCallReroutingModeForTrunkIndex OBJECT-TYPE
       SYNTAX Unsigned32 (0..83)
       MAX-ACCESS not-accessible
       STATUS current
       DESCRIPTION
           "Trunk number starting at 0.
AC INI-Param: N/A"
       ::= {acCallReroutingModeForTrunkEntry 1}



     acCallReroutingModeForTrunkMode OBJECT-TYPE
       SYNTAX INTEGER {
                  none(0)
,
                  isdnReroutingEnabled(1)

                  }
       MAX-ACCESS read-write
       STATUS current
       DESCRIPTION
           "Call Rerouting Mode. Set to 1 to enable ISDN call rerouting.
Access: Instant.
AC INI-Param: CALLREROUTINGMODE"
       ::= {acCallReroutingModeForTrunkEntry 2}



     -- ****************************************
     -- acNATTranslation table declaration
     -- ****************************************
     acNATTranslationTable OBJECT-TYPE
       SYNTAX SEQUENCE OF AcNATTranslationEntry
       MAX-ACCESS not-accessible
       STATUS current
       DESCRIPTION
           "NATTranslation"
       ::= {digitalGWext 26}



     -- ****************************************
     -- acNATTranslation table entry
     -- ****************************************
     acNATTranslationEntry OBJECT-TYPE
       SYNTAX AcNATTranslationEntry
       MAX-ACCESS not-accessible
       STATUS current
       DESCRIPTION
           ""
       INDEX {acNATTranslationIndex}
       ::= {acNATTranslationTable 1}



     -- ****************************************
     -- acNATTranslation TABLE
     -- ****************************************
     AcNATTranslationEntry ::= SEQUENCE {
       acNATTranslationIndex                           Unsigned32,
       acNATTranslationRowStatus                       RowStatus,
       acNATTranslationAction                          INTEGER,
       acNATTranslationActionRes                       INTEGER,
       acNATTranslationSourceIPInterfaceName           SnmpAdminString,
       acNATTranslationTargetIPAddress                 SnmpAdminString,
       acNATTranslationSourceStartPort                 SnmpAdminString,
       acNATTranslationSourceEndPort                   SnmpAdminString,
       acNATTranslationTargetStartPort                 SnmpAdminString,
       acNATTranslationTargetEndPort                   SnmpAdminString
     }



     acNATTranslationIndex OBJECT-TYPE
       SYNTAX Unsigned32 (0..31)
       MAX-ACCESS not-accessible
       STATUS current
       DESCRIPTION
           "Index Field for line.
AC INI-Param: NATTranslation_Index"
       ::= {acNATTranslationEntry 1}



     acNATTranslationRowStatus OBJECT-TYPE
       SYNTAX RowStatus
       MAX-ACCESS read-create
       STATUS current
       DESCRIPTION
           "ROWSTATUS Field for line.
Access: Offline.
AC INI-Param: NATTranslation_RowStatus"
       ::= {acNATTranslationEntry 2}



     acNATTranslationAction OBJECT-TYPE
       SYNTAX INTEGER {
                  none(0)

                  }
       MAX-ACCESS read-create
       STATUS current
       DESCRIPTION
           "Mangement Field for ACTIONS.
Access: Offline.
AC INI-Param: NATTranslation_Action"
       ::= {acNATTranslationEntry 3}



     acNATTranslationActionRes OBJECT-TYPE
       SYNTAX INTEGER {
                  succeeded(0)

                  }
       MAX-ACCESS read-only
       STATUS current
       DESCRIPTION
           "Mangement Field for ACTIONS RESULT.
AC INI-Param: NATTranslation_ActionRes"
       ::= {acNATTranslationEntry 4}



     acNATTranslationSourceIPInterfaceName OBJECT-TYPE
       SYNTAX SnmpAdminString (SIZE (0..16))
       MAX-ACCESS read-write
       STATUS current
       DESCRIPTION
           "NATTranslation.
Access: Offline.
AC INI-Param: NATTranslation_SourceIPInterfaceName"
       ::= {acNATTranslationEntry 5}



     acNATTranslationTargetIPAddress OBJECT-TYPE
       SYNTAX SnmpAdminString (SIZE (0..70))
       MAX-ACCESS read-write
       STATUS current
       DESCRIPTION
           "NATTranslation.
Access: Offline.
AC INI-Param: NATTranslation_TargetIPAddress"
       ::= {acNATTranslationEntry 6}



     acNATTranslationSourceStartPort OBJECT-TYPE
       SYNTAX SnmpAdminString (SIZE (0..5))
       MAX-ACCESS read-write
       STATUS current
       DESCRIPTION
           "NATTranslation.
Access: Offline.
AC INI-Param: NATTranslation_SourceStartPort"
       ::= {acNATTranslationEntry 7}



     acNATTranslationSourceEndPort OBJECT-TYPE
       SYNTAX SnmpAdminString (SIZE (0..5))
       MAX-ACCESS read-write
       STATUS current
       DESCRIPTION
           "NATTranslation.
Access: Offline.
AC INI-Param: NATTranslation_SourceEndPort"
       ::= {acNATTranslationEntry 8}



     acNATTranslationTargetStartPort OBJECT-TYPE
       SYNTAX SnmpAdminString (SIZE (0..6))
       MAX-ACCESS read-write
       STATUS current
       DESCRIPTION
           "NATTranslation.
Access: Offline.
AC INI-Param: NATTranslation_TargetStartPort"
       ::= {acNATTranslationEntry 9}



     acNATTranslationTargetEndPort OBJECT-TYPE
       SYNTAX SnmpAdminString (SIZE (0..6))
       MAX-ACCESS read-write
       STATUS current
       DESCRIPTION
           "NATTranslation.
Access: Offline.
AC INI-Param: NATTranslation_TargetEndPort"
       ::= {acNATTranslationEntry 10}



     gwSecurity OBJECT IDENTIFIER ::= {common 18}


     gwSecurityMediaSecurityBehavior OBJECT-TYPE
       SYNTAX INTEGER {
                  preferable(0)
,
                  mandatory(1)
,
                  preferableSingleMedia(3)

                  }
       MAX-ACCESS read-write
       STATUS current
       DESCRIPTION
           "Gateway behavior when recieving offer/response for media encryption.
Access: Instant.
AC INI-Param: MEDIASECURITYBEHAVIOUR"
       ::= {gwSecurity 1}



     gwSecuritySIPSRequireClientCertificate OBJECT-TYPE
       SYNTAX INTEGER {
                  disable(0)
,
                  enable(1)

                  }
       MAX-ACCESS read-write
       STATUS current
       DESCRIPTION
           "Should require client certificate upon TLS connection request
arrival.
Access: Offline.
AC INI-Param: SIPSREQUIRECLIENTCERTIFICATE"
       ::= {gwSecurity 2}



     gwSecurityTLSReHandshakeInterval OBJECT-TYPE
       SYNTAX Unsigned32 (0..1500)
       MAX-ACCESS read-write
       STATUS current
       DESCRIPTION
           "The interval between consequent TLS re-handshakes (Minutes).
0 - Disables re-handshakes.
Access: Instant.
AC INI-Param: TLSREHANDSHAKEINTERVAL"
       ::= {gwSecurity 3}



     gwSecurityPeerHostNameVerificationMode OBJECT-TYPE
       SYNTAX INTEGER {
                  disable(0)
,
                  serverOnly(1)
,
                  serverAndClient(2)

                  }
       MAX-ACCESS read-write
       STATUS current
       DESCRIPTION
           "While using TLS, defines the verification behavior of the host
name sent in the certificate.
Access: Instant.
AC INI-Param: PEERHOSTNAMEVERIFICATIONMODE"
       ::= {gwSecurity 4}



     gwSecurityVerifyServerCertificate OBJECT-TYPE
       SYNTAX INTEGER {
                  disable(0)
,
                  enable(1)

                  }
       MAX-ACCESS read-write
       STATUS current
       DESCRIPTION
           "Certificate validation behavior
0 – No certificate validation.
1 – Server certificate validation.
Access: Instant.
AC INI-Param: VERIFYSERVERCERTIFICATE"
       ::= {gwSecurity 5}



     gwSecurityTLSRemoteSubjectName OBJECT-TYPE
       SYNTAX SnmpAdminString (SIZE (0..49))
       MAX-ACCESS read-write
       STATUS current
       DESCRIPTION
           "used to verify the remote peer Common Name (at certificate)
when using TLS.
Access: Instant.
AC INI-Param: TLSREMOTESUBJECTNAME"
       ::= {gwSecurity 6}



     gwSecuritySRTPofferedSuites OBJECT-TYPE
       SYNTAX Unsigned32 (0..15)
       MAX-ACCESS read-write
       STATUS current
       DESCRIPTION
           "Offered SRTP Cipher Suites. 
not defined(0) 
all(15) 
aesCm128HmacShaOne80(1) 
aesCm128HmacShaOne32(2) 
ariaCm128HmacShaOne80(4) 
ariaCm192HmacShaOne80(8).
Access: Instant.
AC INI-Param: SRTPOFFEREDSUITES"
       ::= {gwSecurity 7}



     gwSecurityEnableSymmetricMKI OBJECT-TYPE
       SYNTAX INTEGER {
                  disable(0)
,
                  enable(1)

                  }
       MAX-ACCESS read-write
       STATUS current
       DESCRIPTION
           "Enable symmetric MKI negotiation.
Access: Instant.
AC INI-Param: ENABLESYMMETRICMKI"
       ::= {gwSecurity 8}



     ids OBJECT IDENTIFIER ::= {gwSecurity 20}


     idsEnableIDS OBJECT-TYPE
       SYNTAX INTEGER {
                  disable(0)
,
                  enable(1)

                  }
       MAX-ACCESS read-write
       STATUS current
       DESCRIPTION
           "enable the ids service.
Access: Instant.
AC INI-Param: EnableIDS"
       ::= {ids 1}



     -- ****************************************
     -- idsPolicy table declaration
     -- ****************************************
     idsPolicyTable OBJECT-TYPE
       SYNTAX SEQUENCE OF IdsPolicyEntry
       MAX-ACCESS not-accessible
       STATUS current
       DESCRIPTION
           "GwApp IDS Policy Table"
       ::= {ids 21}



     -- ****************************************
     -- idsPolicy table entry
     -- ****************************************
     idsPolicyEntry OBJECT-TYPE
       SYNTAX IdsPolicyEntry
       MAX-ACCESS not-accessible
       STATUS current
       DESCRIPTION
           ""
       INDEX {idsPolicyIndex}
       ::= {idsPolicyTable 1}



     -- ****************************************
     -- idsPolicy TABLE
     -- ****************************************
     IdsPolicyEntry ::= SEQUENCE {
       idsPolicyIndex                                  Unsigned32,
       idsPolicyRowStatus                              RowStatus,
       idsPolicyAction                                 INTEGER,
       idsPolicyActionResult                           INTEGER,
       idsPolicyName                                   SnmpAdminString,
       idsPolicyDescription                            SnmpAdminString
     }



     idsPolicyIndex OBJECT-TYPE
       SYNTAX Unsigned32 (0..19)
       MAX-ACCESS read-only
       STATUS current
       DESCRIPTION
           "idsPolicy index field.
AC INI-Param: IDSPolicy_Index"
       ::= {idsPolicyEntry 1}



     idsPolicyRowStatus OBJECT-TYPE
       SYNTAX RowStatus
       MAX-ACCESS read-create
       STATUS current
       DESCRIPTION
           "Row-Status Textual Conventions as defined in RFC 2579: Textual
Conventions for SMIv2.
AC INI-Param: N/A"
       ::= {idsPolicyEntry 2}



     idsPolicyAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {idsPolicyEntry 3}



     idsPolicyActionResult OBJECT-TYPE
       SYNTAX INTEGER {
                  developmentImpending(0)

                  }
       MAX-ACCESS read-only
       STATUS current
       DESCRIPTION
           "Development Impending.
AC INI-Param: N/A"
       ::= {idsPolicyEntry 4}



     idsPolicyName OBJECT-TYPE
       SYNTAX SnmpAdminString (SIZE (0..19))
       MAX-ACCESS read-write
       STATUS current
       DESCRIPTION
           "Name of the policy.
Access: Online.
AC INI-Param: IDSPolicy_Name"
       ::= {idsPolicyEntry 5}



     idsPolicyDescription OBJECT-TYPE
       SYNTAX SnmpAdminString (SIZE (0..99))
       MAX-ACCESS read-write
       STATUS current
       DESCRIPTION
           "Description of the Policy.
Access: Online.
AC INI-Param: IDSPolicy_Description"
       ::= {idsPolicyEntry 6}



     -- ****************************************
     -- idsMatch table declaration
     -- ****************************************
     idsMatchTable OBJECT-TYPE
       SYNTAX SEQUENCE OF IdsMatchEntry
       MAX-ACCESS not-accessible
       STATUS current
       DESCRIPTION
           "GwApp IDS Match Table"
       ::= {ids 22}



     -- ****************************************
     -- idsMatch table entry
     -- ****************************************
     idsMatchEntry OBJECT-TYPE
       SYNTAX IdsMatchEntry
       MAX-ACCESS not-accessible
       STATUS current
       DESCRIPTION
           ""
       INDEX {idsMatchIndex}
       ::= {idsMatchTable 1}



     -- ****************************************
     -- idsMatch TABLE
     -- ****************************************
     IdsMatchEntry ::= SEQUENCE {
       idsMatchIndex                                   Unsigned32,
       idsMatchRowStatus                               RowStatus,
       idsMatchAction                                  INTEGER,
       idsMatchActionResult                            INTEGER,
       idsMatchSIPInterface                            SnmpAdminString,
       idsMatchProxySet                                SnmpAdminString,
       idsMatchSubnet                                  SnmpAdminString,
       idsMatchPolicy                                  RowPointer
     }



     idsMatchIndex OBJECT-TYPE
       SYNTAX Unsigned32 (0..19)
       MAX-ACCESS read-only
       STATUS current
       DESCRIPTION
           "idsMatch index field.
AC INI-Param: IDSMatch_Index"
       ::= {idsMatchEntry 1}



     idsMatchRowStatus OBJECT-TYPE
       SYNTAX RowStatus
       MAX-ACCESS read-create
       STATUS current
       DESCRIPTION
           "Row-Status Textual Conventions as defined in RFC 2579: Textual
Conventions for SMIv2.
AC INI-Param: N/A"
       ::= {idsMatchEntry 2}



     idsMatchAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {idsMatchEntry 3}



     idsMatchActionResult OBJECT-TYPE
       SYNTAX INTEGER {
                  developmentImpending(0)

                  }
       MAX-ACCESS read-only
       STATUS current
       DESCRIPTION
           "Development Impending.
AC INI-Param: N/A"
       ::= {idsMatchEntry 4}



     idsMatchSIPInterface OBJECT-TYPE
       SYNTAX SnmpAdminString (SIZE (0..19))
       MAX-ACCESS read-write
       STATUS current
       DESCRIPTION
           "Filter by SIP Interface. Can include multiple interfaces. For
example '2,4,6-8'.
Access: Online.
AC INI-Param: IDSMatch_SIPInterface"
       ::= {idsMatchEntry 5}



     idsMatchProxySet OBJECT-TYPE
       SYNTAX SnmpAdminString (SIZE (0..19))
       MAX-ACCESS read-write
       STATUS current
       DESCRIPTION
           "Filter by Proxy Set. Can include multiple interfaces. For example
'2,4,6-8'.
Access: Online.
AC INI-Param: IDSMatch_ProxySet"
       ::= {idsMatchEntry 6}



     idsMatchSubnet OBJECT-TYPE
       SYNTAX SnmpAdminString (SIZE (0..99))
       MAX-ACCESS read-write
       STATUS current
       DESCRIPTION
           "Filter by Subnet, with CIDR notation: '10.1.0.0/16'.
Access: Online.
AC INI-Param: IDSMatch_Subnet"
       ::= {idsMatchEntry 7}



     idsMatchPolicy OBJECT-TYPE
       SYNTAX RowPointer
       MAX-ACCESS read-write
       STATUS current
       DESCRIPTION
           "Policy to activate.
Access: Online.
AC INI-Param: IDSMatch_Policy"
       ::= {idsMatchEntry 8}



     -- ****************************************
     -- idsRule table declaration
     -- ****************************************
     idsRuleTable OBJECT-TYPE
       SYNTAX SEQUENCE OF IdsRuleEntry
       MAX-ACCESS not-accessible
       STATUS current
       DESCRIPTION
           "GwApp IDS Rule Table"
       ::= {ids 23}



     -- ****************************************
     -- idsRule table entry
     -- ****************************************
     idsRuleEntry OBJECT-TYPE
       SYNTAX IdsRuleEntry
       MAX-ACCESS not-accessible
       STATUS current
       DESCRIPTION
           ""
       INDEX {idsRulePolicyIndex,idsRuleRuleID}
       ::= {idsRuleTable 1}



     -- ****************************************
     -- idsRule TABLE
     -- ****************************************
     IdsRuleEntry ::= SEQUENCE {
       idsRulePolicyIndex                              Unsigned32,
       idsRuleRuleID                                   Unsigned32,
       idsRuleRowStatus                                RowStatus,
       idsRuleAction                                   INTEGER,
       idsRuleActionResult                             INTEGER,
       idsRuleReason                                   INTEGER,
       idsRuleThresholdScope                           INTEGER,
       idsRuleThresholdWindow                          Integer32,
       idsRuleMinorAlarmThreshold                      Integer32,
       idsRuleMajorAlarmThreshold                      Integer32,
       idsRuleCriticalAlarmThreshold                   Integer32
     }



     idsRulePolicyIndex OBJECT-TYPE
       SYNTAX Unsigned32 (0..19)
       MAX-ACCESS read-only
       STATUS current
       DESCRIPTION
           "Policy index according to idsPolicy table entries.
AC INI-Param: IDSRule_Policy"
       ::= {idsRuleEntry 1}



     idsRuleRuleID OBJECT-TYPE
       SYNTAX Unsigned32 (0..19)
       MAX-ACCESS read-only
       STATUS current
       DESCRIPTION
           "Rule Id.
AC INI-Param: IDSRule_RuleID"
       ::= {idsRuleEntry 2}



     idsRuleRowStatus OBJECT-TYPE
       SYNTAX RowStatus
       MAX-ACCESS read-create
       STATUS current
       DESCRIPTION
           "Row-Status Textual Conventions as defined in RFC 2579: Textual
Conventions for SMIv2.
AC INI-Param: N/A"
       ::= {idsRuleEntry 3}



     idsRuleAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {idsRuleEntry 4}



     idsRuleActionResult OBJECT-TYPE
       SYNTAX INTEGER {
                  developmentImpending(0)

                  }
       MAX-ACCESS read-only
       STATUS current
       DESCRIPTION
           "Development Impending.
AC INI-Param: N/A"
       ::= {idsRuleEntry 5}



     idsRuleReason OBJECT-TYPE
       SYNTAX INTEGER {
                  any(0)
,
                  connectionAbuse(1)
,
                  malformedMessage(2)
,
                  authenticationFailure(3)
,
                  dialogEstablishFailure(4)
,
                  abnormalFlow(5)

                  }
       MAX-ACCESS read-write
       STATUS current
       DESCRIPTION
           "Reason of the event.
Access: Online.
AC INI-Param: IDSRule_Reason"
       ::= {idsRuleEntry 6}



     idsRuleThresholdScope OBJECT-TYPE
       SYNTAX INTEGER {
                  global(0)
,
                  iP(2)
,
                  iPandPort(3)

                  }
       MAX-ACCESS read-write
       STATUS current
       DESCRIPTION
           "Threshold scope to count by.
Access: Online.
AC INI-Param: IDSRule_ThresholdScope"
       ::= {idsRuleEntry 7}



     idsRuleThresholdWindow OBJECT-TYPE
       SYNTAX Integer32 (-1..1000000)
       MAX-ACCESS read-write
       STATUS current
       DESCRIPTION
           "Threshold window (seconds).
Access: Online.
AC INI-Param: IDSRule_ThresholdWindow"
       ::= {idsRuleEntry 8}



     idsRuleMinorAlarmThreshold OBJECT-TYPE
       SYNTAX Integer32 (-1..1000000)
       MAX-ACCESS read-write
       STATUS current
       DESCRIPTION
           "SNMP Minor-Alarm threshold.
Access: Online.
AC INI-Param: IDSRule_MinorAlarmThreshold"
       ::= {idsRuleEntry 9}



     idsRuleMajorAlarmThreshold OBJECT-TYPE
       SYNTAX Integer32 (-1..1000000)
       MAX-ACCESS read-write
       STATUS current
       DESCRIPTION
           "SNMP Major-Alarm threshold.
Access: Online.
AC INI-Param: IDSRule_MajorAlarmThreshold"
       ::= {idsRuleEntry 10}



     idsRuleCriticalAlarmThreshold OBJECT-TYPE
       SYNTAX Integer32 (-1..1000000)
       MAX-ACCESS read-write
       STATUS current
       DESCRIPTION
           "SNMP Critical-Alarm threshold.
Access: Online.
AC INI-Param: IDSRule_CriticalAlarmThreshold"
       ::= {idsRuleEntry 11}



     acGWRtcpXr OBJECT IDENTIFIER ::= {common 19}


     acGWRtcpXrEscIP OBJECT-TYPE
       SYNTAX SnmpAdminString (SIZE (0..48))
       MAX-ACCESS read-write
       STATUS current
       DESCRIPTION
           "RTCP-XR server IP address.
Access: Instant.
AC INI-Param: RtcpXrEscIP"
       ::= {acGWRtcpXr 1}



     acGWRtcpXrReportMode OBJECT-TYPE
       SYNTAX INTEGER {
                  disable(0)
,
                  endCall(1)
,
                  endCallPeriodic(2)

                  }
       MAX-ACCESS read-write
       STATUS current
       DESCRIPTION
           "0:rtcpxr is not sent over SIP at all
1:rtcpxr is sent over sip when call ended
2:rtcpxr is sent over sip when on periodic interval and when
call ended


.
Access: Instant.
AC INI-Param: RtcpXrReportMode"
       ::= {acGWRtcpXr 2}



     acGWRtcpXrEscTransportType OBJECT-TYPE
       SYNTAX INTEGER {
                  notConfigured(-1)
,
                  uDP(0)
,
                  tCP(1)
,
                  tLS(2)

                  }
       MAX-ACCESS read-write
       STATUS current
       DESCRIPTION
           "RtcpXrEsc transport type.
Access: Instant.
AC INI-Param: RTCPXRESCTRANSPORTTYPE"
       ::= {acGWRtcpXr 3}



     acGWRtcpXrSbcReportMode OBJECT-TYPE
       SYNTAX INTEGER {
                  notSent(0)
,
                  sentWhenCallEnded(1)

                  }
       MAX-ACCESS read-write
       STATUS current
       DESCRIPTION
           "0:rtcpxr is not sent over SIP at all
1:rtcpxr is sent over sip when call ended.
Access: Instant.
AC INI-Param: SBCRtcpXrReportMode"
       ::= {acGWRtcpXr 4}



     acTimers OBJECT IDENTIFIER ::= {common 20}


     acTimersIPAlertTimeout OBJECT-TYPE
       SYNTAX Unsigned32 (0..3600)
       MAX-ACCESS read-write
       STATUS current
       DESCRIPTION
           "Maximal time to wait for connect from IP (seconds).
Access: Instant.
AC INI-Param: IPALERTTIMEOUT"
       ::= {acTimers 1}



     acTimersPSTNAlertTimeout OBJECT-TYPE
       SYNTAX Unsigned32 (1..600)
       MAX-ACCESS read-write
       STATUS current
       DESCRIPTION
           "Max time (in seconds) to wait for connect from PSTN.
Access: Instant.
AC INI-Param: PSTNALERTTIMEOUT"
       ::= {acTimers 2}



     acEmergency OBJECT IDENTIFIER ::= {common 21}


     acEmergencyRegretTimeout OBJECT-TYPE
       SYNTAX Unsigned32 (1..30)
       MAX-ACCESS read-write
       STATUS current
       DESCRIPTION
           "[min] Regret time for call that is marked as Emergency.
Access: Instant.
AC INI-Param: EmergencyRegretTimeout"
       ::= {acEmergency 1}



     -- ****************************************
     -- acEmergencyNumbers table declaration
     -- ****************************************
     acEmergencyNumbersTable OBJECT-TYPE
       SYNTAX SEQUENCE OF AcEmergencyNumbersEntry
       MAX-ACCESS not-accessible
       STATUS current
       DESCRIPTION
           "Emergency numbers table."
       ::= {acEmergency 21}



     -- ****************************************
     -- acEmergencyNumbers table entry
     -- ****************************************
     acEmergencyNumbersEntry OBJECT-TYPE
       SYNTAX AcEmergencyNumbersEntry
       MAX-ACCESS not-accessible
       STATUS current
       DESCRIPTION
           ""
       INDEX {acEmergencyNumbersIndex}
       ::= {acEmergencyNumbersTable 1}



     -- ****************************************
     -- acEmergencyNumbers TABLE
     -- ****************************************
     AcEmergencyNumbersEntry ::= SEQUENCE {
       acEmergencyNumbersIndex                         Unsigned32,
       acEmergencyNumbersNumbers                       SnmpAdminString
     }



     acEmergencyNumbersIndex OBJECT-TYPE
       SYNTAX Unsigned32 (0..3)
       MAX-ACCESS not-accessible
       STATUS current
       DESCRIPTION
           "Emergency numbers, starting at 0.
AC INI-Param: N/A"
       ::= {acEmergencyNumbersEntry 1}



     acEmergencyNumbersNumbers OBJECT-TYPE
       SYNTAX SnmpAdminString (SIZE (0..4))
       MAX-ACCESS read-write
       STATUS current
       DESCRIPTION
           "Emergency numbers.
Access: Instant.
AC INI-Param: EmergencyNumbers"
       ::= {acEmergencyNumbersEntry 2}



     accounts OBJECT IDENTIFIER ::= {common 22}


     -- ****************************************
     -- account table declaration
     -- ****************************************
     accountTable OBJECT-TYPE
       SYNTAX SEQUENCE OF AccountEntry
       MAX-ACCESS not-accessible
       STATUS current
       DESCRIPTION
           "GwApp Accounts table"
       ::= {accounts 21}



     -- ****************************************
     -- account table entry
     -- ****************************************
     accountEntry OBJECT-TYPE
       SYNTAX AccountEntry
       MAX-ACCESS not-accessible
       STATUS current
       DESCRIPTION
           "table"
       INDEX {accountIndex}
       ::= {accountTable 1}



     -- ****************************************
     -- account TABLE
     -- ****************************************
     AccountEntry ::= SEQUENCE {
       accountIndex                                    Unsigned32,
       accountRowStatus                                RowStatus,
       accountAction                                   INTEGER,
       accountActionResult                             INTEGER,
       accountServedTrunkGroup                         Integer32,
       accountServedIPGroup                            Integer32,
       accountServingIPGroup                           Unsigned32,
       accountUsername                                 SnmpAdminString,
       accountPassword                                 SnmpAdminString,
       accountHostName                                 SnmpAdminString,
       accountRegister                                 INTEGER,
       accountContactUser                              SnmpAdminString
     }



     accountIndex OBJECT-TYPE
       SYNTAX Unsigned32 (0..500)
       MAX-ACCESS read-only
       STATUS current
       DESCRIPTION
           ".
AC INI-Param: Account_Index"
       ::= {accountEntry 1}



     accountRowStatus OBJECT-TYPE
       SYNTAX RowStatus
       MAX-ACCESS read-create
       STATUS current
       DESCRIPTION
           "Row-Status Textual Conventions as defined in RFC 2579: Textual
Conventions for SMIv2.
AC INI-Param: N/A"
       ::= {accountEntry 2}



     accountAction OBJECT-TYPE
       SYNTAX INTEGER {
                  developmentImpending(0)

                  }
       MAX-ACCESS read-only
       STATUS current
       DESCRIPTION
           "Development Impending.
AC INI-Param: N/A"
       ::= {accountEntry 3}



     accountActionResult OBJECT-TYPE
       SYNTAX INTEGER {
                  developmentImpending(0)

                  }
       MAX-ACCESS read-only
       STATUS current
       DESCRIPTION
           "Development Impending.
AC INI-Param: N/A"
       ::= {accountEntry 4}



     accountServedTrunkGroup OBJECT-TYPE
       SYNTAX Integer32 (-1..100)
       MAX-ACCESS read-create
       STATUS current
       DESCRIPTION
           "GwApp Accounts table.
Access: Instant.
AC INI-Param: Account_ServedTrunkGroup"
       ::= {accountEntry 5}



     accountServedIPGroup OBJECT-TYPE
       SYNTAX Integer32 (-1..31)
       MAX-ACCESS read-create
       STATUS current
       DESCRIPTION
           "GwApp Accounts table.
Access: Instant.
AC INI-Param: Account_ServedIPGroup"
       ::= {accountEntry 6}



     accountServingIPGroup OBJECT-TYPE
       SYNTAX Unsigned32 (1..31)
       MAX-ACCESS read-create
       STATUS current
       DESCRIPTION
           "GwApp Accounts table.
Access: Instant.
AC INI-Param: Account_ServingIPGroup"
       ::= {accountEntry 7}



     accountUsername OBJECT-TYPE
       SYNTAX SnmpAdminString (SIZE (0..50))
       MAX-ACCESS read-create
       STATUS current
       DESCRIPTION
           "GwApp Accounts table.
Access: Instant.
AC INI-Param: Account_Username"
       ::= {accountEntry 8}



     accountPassword OBJECT-TYPE
       SYNTAX SnmpAdminString (SIZE (0..50))
       MAX-ACCESS read-create
       STATUS current
       DESCRIPTION
           "GwApp Accounts table.
Access: Instant.
AC INI-Param: Account_Password"
       ::= {accountEntry 9}



     accountHostName OBJECT-TYPE
       SYNTAX SnmpAdminString (SIZE (0..49))
       MAX-ACCESS read-create
       STATUS current
       DESCRIPTION
           "GwApp Accounts table.
Access: Instant.
AC INI-Param: Account_HostName"
       ::= {accountEntry 10}



     accountRegister OBJECT-TYPE
       SYNTAX INTEGER {
                  no(0)
,
                  regular(1)
,
                  gin(2)

                  }
       MAX-ACCESS read-create
       STATUS current
       DESCRIPTION
           "GwApp Accounts table.
Access: Instant.
AC INI-Param: Account_Register"
       ::= {accountEntry 11}



     accountContactUser OBJECT-TYPE
       SYNTAX SnmpAdminString (SIZE (0..50))
       MAX-ACCESS read-create
       STATUS current
       DESCRIPTION
           "GwApp Accounts table.
Access: Instant.
AC INI-Param: Account_ContactUser"
       ::= {accountEntry 12}



     ipGroups OBJECT IDENTIFIER ::= {common 23}


     -- ****************************************
     -- ipGroup table declaration
     -- ****************************************
     ipGroupTable OBJECT-TYPE
       SYNTAX SEQUENCE OF IpGroupEntry
       MAX-ACCESS not-accessible
       STATUS current
       DESCRIPTION
           "GwApp IP Group Table"
       ::= {ipGroups 21}



     -- ****************************************
     -- ipGroup table entry
     -- ****************************************
     ipGroupEntry OBJECT-TYPE
       SYNTAX IpGroupEntry
       MAX-ACCESS not-accessible
       STATUS current
       DESCRIPTION
           "table"
       INDEX {ipGroupIndex}
       ::= {ipGroupTable 1}



     -- ****************************************
     -- ipGroup TABLE
     -- ****************************************
     IpGroupEntry ::= SEQUENCE {
       ipGroupIndex                                    Unsigned32,
       ipGroupRowStatus                                RowStatus,
       ipGroupAction                                   INTEGER,
       ipGroupActionResult                             INTEGER,
       ipGroupType                                     INTEGER,
       ipGroupDescription                              SnmpAdminString,
       ipGroupProxySetId                               Integer32,
       ipGroupSIPGroupName                             SnmpAdminString,
       ipGroupContactUser                              SnmpAdminString,
       ipGroupEnableSurvivability                      INTEGER,
       ipGroupServingIPGroup                           Integer32,
       ipGroupSipReRoutingMode                         INTEGER,
       ipGroupAlwaysUseRouteTable                      INTEGER,
       ipGroupRoutingMode                              INTEGER,
       ipGroupProfileId                                Unsigned32,
       ipGroupMediaRealm                               RowPointer,
       ipGroupMaxNumOfRegUsers                         Integer32,
       ipGroupRegistrationMode                         INTEGER,
       ipGroupAuthenticationMode                       INTEGER,
       ipGroupMethodList                               SnmpAdminString,
       ipGroupSRD                                      Unsigned32,
       ipGroupEnableSBCClientForking                   INTEGER,
       ipGroupSrcUriInput                              INTEGER,
       ipGroupDstUriInput                              INTEGER,
       ipGroupUsername                                 SnmpAdminString,
       ipGroupPassword                                 SnmpAdminString,
       ipGroupAlwaysUseSourceAddr                      INTEGER,
       ipGroupQOEProfileName                           RowPointer,
       ipGroupBWProfileName                            RowPointer,
       ipGroupMediaEnhancementProfileName              RowPointer,
       ipGroupName                                     SnmpAdminString,
       ipGroupSRDName                                  RowPointer,
       ipGroupSBCOperationMode                         INTEGER,
       ipGroupProxySetName                             RowPointer,
       ipGroupProfileName                              RowPointer,
       ipGroupProxySetConnectivity                     SnmpAdminString,
       ipGroupRegisteredStatus                         SnmpAdminString,
       ipGroupRegisteredIP                             SnmpAdminString
     }



     ipGroupIndex OBJECT-TYPE
       SYNTAX Unsigned32 (1..5000)
       MAX-ACCESS read-only
       STATUS current
       DESCRIPTION
           ".
AC INI-Param: IPGroup_Index"
       ::= {ipGroupEntry 1}



     ipGroupRowStatus OBJECT-TYPE
       SYNTAX RowStatus
       MAX-ACCESS read-create
       STATUS current
       DESCRIPTION
           "Row-Status Textual Conventions as defined in RFC 2579: Textual
Conventions for SMIv2.
AC INI-Param: N/A"
       ::= {ipGroupEntry 2}



     ipGroupAction OBJECT-TYPE
       SYNTAX INTEGER {
                  developmentImpending(0)

                  }
       MAX-ACCESS read-only
       STATUS current
       DESCRIPTION
           "Development Impending.
AC INI-Param: N/A"
       ::= {ipGroupEntry 3}



     ipGroupActionResult OBJECT-TYPE
       SYNTAX INTEGER {
                  developmentImpending(0)

                  }
       MAX-ACCESS read-only
       STATUS current
       DESCRIPTION
           "Development Impending.
AC INI-Param: N/A"
       ::= {ipGroupEntry 4}



     ipGroupType OBJECT-TYPE
       SYNTAX INTEGER {
                  server(0)
,
                  user(1)
,
                  gateway(2)

                  }
       MAX-ACCESS read-create
       STATUS current
       DESCRIPTION
           "GwApp IP Group Table.
Access: Instant.
AC INI-Param: IPGroup_Type"
       ::= {ipGroupEntry 5}



     ipGroupDescription OBJECT-TYPE
       SYNTAX SnmpAdminString (SIZE (0..29))
       MAX-ACCESS read-create
       STATUS current
       DESCRIPTION
           "GwApp IP Group Table.
Access: Instant.
AC INI-Param: IPGroup_Description"
       ::= {ipGroupEntry 6}



     ipGroupProxySetId OBJECT-TYPE
       SYNTAX Integer32 (-1..5)
       MAX-ACCESS read-create
       STATUS current
       DESCRIPTION
           "GwApp IP Group Table.
Access: Instant.
AC INI-Param: IPGroup_ProxySetId"
       ::= {ipGroupEntry 7}



     ipGroupSIPGroupName OBJECT-TYPE
       SYNTAX SnmpAdminString (SIZE (0..49))
       MAX-ACCESS read-create
       STATUS current
       DESCRIPTION
           "GwApp IP Group Table.
Access: Instant.
AC INI-Param: IPGroup_SIPGroupName"
       ::= {ipGroupEntry 8}



     ipGroupContactUser OBJECT-TYPE
       SYNTAX SnmpAdminString (SIZE (0..50))
       MAX-ACCESS read-create
       STATUS current
       DESCRIPTION
           "GwApp IP Group Table.
Access: Instant.
AC INI-Param: IPGroup_ContactUser"
       ::= {ipGroupEntry 9}



     ipGroupEnableSurvivability OBJECT-TYPE
       SYNTAX INTEGER {
                  disable(0)
,
                  enableIfNecessary(1)
,
                  alwaysEnable(2)
,
                  alwaysTerminateRegister(3)

                  }
       MAX-ACCESS read-create
       STATUS current
       DESCRIPTION
           "GwApp IP Group Table.
Access: Instant.
AC INI-Param: IPGroup_EnableSurvivability"
       ::= {ipGroupEntry 10}



     ipGroupServingIPGroup OBJECT-TYPE
       SYNTAX Integer32 (-1..31)
       MAX-ACCESS read-create
       STATUS current
       DESCRIPTION
           "GwApp IP Group Table.
Access: Instant.
AC INI-Param: IPGroup_ServingIPGroup"
       ::= {ipGroupEntry 11}



     ipGroupSipReRoutingMode OBJECT-TYPE
       SYNTAX INTEGER {
                  notConfigured(-1)
,
                  standard(0)
,
                  proxy(1)
,
                  routingTable(2)

                  }
       MAX-ACCESS read-create
       STATUS current
       DESCRIPTION
           "GwApp IP Group Table.
Access: Instant.
AC INI-Param: IPGroup_SipReRoutingMode"
       ::= {ipGroupEntry 12}



     ipGroupAlwaysUseRouteTable OBJECT-TYPE
       SYNTAX INTEGER {
                  no(0)
,
                  yes(1)

                  }
       MAX-ACCESS read-create
       STATUS current
       DESCRIPTION
           "GwApp IP Group Table.
Access: Instant.
AC INI-Param: IPGroup_AlwaysUseRouteTable"
       ::= {ipGroupEntry 13}



     ipGroupRoutingMode OBJECT-TYPE
       SYNTAX INTEGER {
                  notConfigured(-1)
,
                  useRoutingTable(0)
,
                  sendToServingIPGroup(1)
,
                  routeToRequestURI(2)

                  }
       MAX-ACCESS read-create
       STATUS current
       DESCRIPTION
           "GwApp IP Group Table.
Access: Instant.
AC INI-Param: IPGroup_RoutingMode"
       ::= {ipGroupEntry 14}



     ipGroupProfileId OBJECT-TYPE
       SYNTAX Unsigned32 (0..9)
       MAX-ACCESS read-create
       STATUS current
       DESCRIPTION
           "
Access: Instant.
AC INI-Param: IPGroup_ProfileId"
       ::= {ipGroupEntry 15}



     ipGroupMediaRealm OBJECT-TYPE
       SYNTAX RowPointer
       MAX-ACCESS read-create
       STATUS current
       DESCRIPTION
           "MediaRealm Name.
Access: Instant.
AC INI-Param: IPGroup_MediaRealm"
       ::= {ipGroupEntry 16}



     ipGroupMaxNumOfRegUsers OBJECT-TYPE
       SYNTAX Integer32 (-1..3000)
       MAX-ACCESS read-create
       STATUS current
       DESCRIPTION
           "Max Number Of Registered Users.
MP1xx - 25
M1K - 200
M2K- 250
M3K - 3000.
Access: Offline.
AC INI-Param: IPGroup_MaxNumOfRegUsers"
       ::= {ipGroupEntry 17}



     ipGroupRegistrationMode OBJECT-TYPE
       SYNTAX INTEGER {
                  userInitiatesRegistrations(0)
,
                  sbcInitiatesRegistrations(1)
,
                  noRegistrationsNeeded(2)

                  }
       MAX-ACCESS read-create
       STATUS current
       DESCRIPTION
           "GwApp IP Group Table Registration Mode.
0 - User initiates registrations (default)
1 - SBC initiate registrations (works only with user info file)
2 - No registrations needed (users will be inserted to DB in
active state).
Can be used for the scenario, here the SBC authenticates (as
server) the incoming INVITE requests from the users.
Access: Offline.
AC INI-Param: IPGroup_RegistrationMode"
       ::= {ipGroupEntry 18}



     ipGroupAuthenticationMode OBJECT-TYPE
       SYNTAX INTEGER {
                  userAuthenticates(0)
,
                  sbcAuthenticatesAsClient(1)
,
                  sbcAuthenticatesAsServer(2)

                  }
       MAX-ACCESS read-create
       STATUS current
       DESCRIPTION
           "GwApp IP Group Table Authentication mode.
Access: Offline.
AC INI-Param: IPGroup_AuthenticationMode"
       ::= {ipGroupEntry 19}



     ipGroupMethodList OBJECT-TYPE
       SYNTAX SnmpAdminString (SIZE (0..255))
       MAX-ACCESS read-create
       STATUS current
       DESCRIPTION
           "List of methods separated by '\' that this IP group will challenge.
Access: Offline.
AC INI-Param: IPGroup_MethodList"
       ::= {ipGroupEntry 20}



     ipGroupSRD OBJECT-TYPE
       SYNTAX Unsigned32 (0..32)
       MAX-ACCESS read-create
       STATUS current
       DESCRIPTION
           "SRD Index.
Access: Online.
AC INI-Param: IPGroup_SRD"
       ::= {ipGroupEntry 21}



     ipGroupEnableSBCClientForking OBJECT-TYPE
       SYNTAX INTEGER {
                  sequential(0)
,
                  parallel(1)
,
                  sequentialAvailableOnly(2)

                  }
       MAX-ACCESS read-create
       STATUS current
       DESCRIPTION
           "0 - Sequential route to all contacts who registered with same
AOR. 1 - Fork INVITE messages in parallel to all registered
contacts (up to 5). 2 - Sequential route only to available
contacts.
Access: Instant.
AC INI-Param: IPGroup_EnableSBCClientForking"
       ::= {ipGroupEntry 22}



     ipGroupSrcUriInput OBJECT-TYPE
       SYNTAX INTEGER {
                  notConfigured(-1)
,
                  fROM(0)
,
                  tO(1)
,
                  requestURI(2)
,
                  pAssertedFirstHeader(3)
,
                  pAssertedSecondHeader(4)
,
                  ppreferred(5)
,
                  route(6)
,
                  diversion(7)
,
                  historyInfo(8)
,
                  pAssociatedURI(9)
,
                  pcalledPartyID(10)
,
                  contact(11)

                  }
       MAX-ACCESS read-create
       STATUS current
       DESCRIPTION
           "Configured the source URI input, used in the Classify-Manipulate-Route
process in SBC.
Access: Instant.
AC INI-Param: IPGroup_SourceUriInput"
       ::= {ipGroupEntry 23}



     ipGroupDstUriInput OBJECT-TYPE
       SYNTAX INTEGER {
                  notConfigured(-1)
,
                  fROM(0)
,
                  tO(1)
,
                  requestURI(2)
,
                  pAssertedFirstHeader(3)
,
                  pAssertedSecondHeader(4)
,
                  ppreferred(5)
,
                  route(6)
,
                  diversion(7)
,
                  historyInfo(8)
,
                  pAssociatedURI(9)
,
                  pcalledPartyID(10)
,
                  contact(11)

                  }
       MAX-ACCESS read-create
       STATUS current
       DESCRIPTION
           "Configured the destination URI input, used in the Classify-Manipulate-Route
process in SBC.
Access: Instant.
AC INI-Param: IPGroup_DestUriInput"
       ::= {ipGroupEntry 24}



     ipGroupUsername OBJECT-TYPE
       SYNTAX SnmpAdminString (SIZE (0..50))
       MAX-ACCESS read-create
       STATUS current
       DESCRIPTION
           "Server to server username for authentication.
Access: Instant.
AC INI-Param: IPGroup_Username"
       ::= {ipGroupEntry 25}



     ipGroupPassword OBJECT-TYPE
       SYNTAX SnmpAdminString (SIZE (0..50))
       MAX-ACCESS read-create
       STATUS current
       DESCRIPTION
           "Server to server password for authentication.
Access: Instant.
AC INI-Param: IPGroup_Password"
       ::= {ipGroupEntry 26}



     ipGroupAlwaysUseSourceAddr OBJECT-TYPE
       SYNTAX INTEGER {
                  no(0)
,
                  yes(1)

                  }
       MAX-ACCESS read-create
       STATUS current
       DESCRIPTION
           "Override SIP standard rules in sending responses and requests
within dialog. When flag is on, always send to the IP that
previous message was received from.
Access: Instant.
AC INI-Param: IPGroup_AlwaysUseSourceAddr"
       ::= {ipGroupEntry 27}



     ipGroupQOEProfileName OBJECT-TYPE
       SYNTAX RowPointer
       MAX-ACCESS read-create
       STATUS current
       DESCRIPTION
           "Quality of experience (QOE) Profile.
Access: Instant.
AC INI-Param: IPGroup_QOEProfile"
       ::= {ipGroupEntry 28}



     ipGroupBWProfileName OBJECT-TYPE
       SYNTAX RowPointer
       MAX-ACCESS read-create
       STATUS current
       DESCRIPTION
           "bandwidth Profile.
Access: Instant.
AC INI-Param: IPGroup_BWProfile"
       ::= {ipGroupEntry 29}



     ipGroupMediaEnhancementProfileName OBJECT-TYPE
       SYNTAX RowPointer
       MAX-ACCESS read-create
       STATUS current
       DESCRIPTION
           "Media Enhancement Profile.
Access: Instant.
AC INI-Param: IPGroup_MediaEnhancementProfile"
       ::= {ipGroupEntry 30}



     ipGroupName OBJECT-TYPE
       SYNTAX SnmpAdminString (SIZE (0..50))
       MAX-ACCESS read-create
       STATUS current
       DESCRIPTION
           "Name.
Access: Instant.
AC INI-Param: IPGroup_Name"
       ::= {ipGroupEntry 31}



     ipGroupSRDName OBJECT-TYPE
       SYNTAX RowPointer
       MAX-ACCESS read-create
       STATUS current
       DESCRIPTION
           "SRD Name.
Access: Instant.
AC INI-Param: IPGroup_SRDName"
       ::= {ipGroupEntry 32}



     ipGroupSBCOperationMode OBJECT-TYPE
       SYNTAX INTEGER {
                  notConfigured(-1)
,
                  b2BUA(0)
,
                  callStatefulProxy(1)
,
                  microsoftServer(2)

                  }
       MAX-ACCESS read-create
       STATUS current
       DESCRIPTION
           "Overrides the same parameter in the SRD, when configured.
Access: Instant.
AC INI-Param: IPGroup_SBCOperationMode"
       ::= {ipGroupEntry 33}



     ipGroupProxySetName OBJECT-TYPE
       SYNTAX RowPointer
       MAX-ACCESS read-create
       STATUS current
       DESCRIPTION
           "ProxySetName.
Access: Instant.
AC INI-Param: IPGroup_ProxySetName"
       ::= {ipGroupEntry 34}



     ipGroupProfileName OBJECT-TYPE
       SYNTAX RowPointer
       MAX-ACCESS read-create
       STATUS current
       DESCRIPTION
           "ProfileName.
Access: Instant.
AC INI-Param: IPGroup_ProfileName"
       ::= {ipGroupEntry 35}



     ipGroupProxySetConnectivity OBJECT-TYPE
       SYNTAX SnmpAdminString (SIZE (0..15))
       MAX-ACCESS read-only
       STATUS current
       DESCRIPTION
           "Indicates if an IPgroup is connected or not according to the
proxy set keepalive.
AC INI-Param: IPGroup_ProxySetStatus"
       ::= {ipGroupEntry 36}



     ipGroupRegisteredStatus OBJECT-TYPE
       SYNTAX SnmpAdminString (SIZE (0..16))
       MAX-ACCESS read-only
       STATUS current
       DESCRIPTION
           "GW Group Registered Status.
AC INI-Param: IPGroup_GWGroupRegisteredStatus"
       ::= {ipGroupEntry 37}



     ipGroupRegisteredIP OBJECT-TYPE
       SYNTAX SnmpAdminString (SIZE (0..25))
       MAX-ACCESS read-only
       STATUS current
       DESCRIPTION
           "GW Group Registered IP Address.
AC INI-Param: IPGroup_GWGroupRegisteredIP"
       ::= {ipGroupEntry 38}



     sbc OBJECT IDENTIFIER ::= {common 24}


     sbcEnable OBJECT-TYPE
       SYNTAX INTEGER {
                  disable(0)
,
                  enable(1)

                  }
       MAX-ACCESS read-write
       STATUS deprecated
       DESCRIPTION
           "Enables SBC functionality.
Access: Instant.
AC INI-Param: ENABLESBC"
       ::= {sbc 1}



     sbcRegistrationTime OBJECT-TYPE
       SYNTAX Unsigned32 (0..2000000)
       MAX-ACCESS read-write
       STATUS current
       DESCRIPTION
           "Expires value SBC responds to user with. Used when server is
offline or when the user is behind NAT. Otherwise expires is
defined by the server.
Access: Instant.
AC INI-Param: SBCREGISTRATIONTIME"
       ::= {sbc 2}



     sbcEnableISBCApplication OBJECT-TYPE
       SYNTAX INTEGER {
                  disable(0)
,
                  enable(1)

                  }
       MAX-ACCESS read-write
       STATUS current
       DESCRIPTION
           "Enables SBC functionality.
Access: Offline.
AC INI-Param: ENABLESBCAPPLICATION"
       ::= {sbc 3}



     sbcEnableIIP2IPApplication OBJECT-TYPE
       SYNTAX INTEGER {
                  disable(0)
,
                  enable(1)

                  }
       MAX-ACCESS read-write
       STATUS current
       DESCRIPTION
           "Enables IP2IP functionality.
Access: Offline.
AC INI-Param: ENABLEIP2IPAPPLICATION"
       ::= {sbc 4}



     sbcAlertTimeout OBJECT-TYPE
       SYNTAX Unsigned32 (0..3600)
       MAX-ACCESS read-write
       STATUS current
       DESCRIPTION
           "Maximal time to wait for connect in SBC (seconds).
Access: Instant.
AC INI-Param: SBCALERTTIMEOUT"
       ::= {sbc 5}



     sbcMaxForwardsLimit OBJECT-TYPE
       SYNTAX Unsigned32 (1..70)
       MAX-ACCESS read-write
       STATUS current
       DESCRIPTION
           "Limit the value of the Max-Forwards header. 
If the header's value is equal or smaller than the parameter's
value the header's value will stay as is. 
If the header's value is bigger then the parameter's value
the header's value will be set to the parameter's value.
Access: Instant.
AC INI-Param: SBCMAXFORWARDSLIMIT"
       ::= {sbc 6}



     sbcGruuMode OBJECT-TYPE
       SYNTAX INTEGER {
                  none(0)
,
                  asProxy(1)
,
                  temporaryOnly(2)
,
                  publicOnly(3)
,
                  both(4)

                  }
       MAX-ACCESS read-write
       STATUS current
       DESCRIPTION
           "SBC GRUU Behavior
0 - None. No GRUU is supplied to users.
1 - As Proxy. Supply same types of GRUU as Proxy does.
2 - Temporary only. Supply only temporary GRUU to users.
3 - Public only. Supply only public GRUU to users.
4 - Both. Supply temporary and public GRUU to users.
Access: Instant.
AC INI-Param: SBCGRUUMODE"
       ::= {sbc 7}



     sbcMinSE OBJECT-TYPE
       SYNTAX Unsigned32 (90..1000000)
       MAX-ACCESS read-write
       STATUS current
       DESCRIPTION
           "The minimum amount of time that can occur between session refresh
requests in a dialog before the session will be considered
timed out.
Access: Instant.
AC INI-Param: SBCMINSE"
       ::= {sbc 8}



     sbcCodersInExtensionMode OBJECT-TYPE
       SYNTAX INTEGER {
                  doesntIncludeExtensions(0)
,
                  includeExtensions(1)

                  }
       MAX-ACCESS read-write
       STATUS current
       DESCRIPTION
           "Defines the coders combination in the outgoing message.
0 - doesn’t include extentions (default). Extended coders will
be added at the end.
1- Include extentions.
Access: Instant.
AC INI-Param: SBCPREFERENCESMODE"
       ::= {sbc 9}



     sbcServAuthNonceDuration OBJECT-TYPE
       SYNTAX Unsigned32 (30..600)
       MAX-ACCESS read-write
       STATUS current
       DESCRIPTION
           "Lifetime of the nonce in seconds.
Access: Instant.
AC INI-Param: AUTHNONCEDURATION"
       ::= {sbc 10}



     sbcServAuthChallengeMethod OBJECT-TYPE
       SYNTAX Unsigned32 (0..1)
       MAX-ACCESS read-write
       STATUS current
       DESCRIPTION
           "Set to 0 to use a www-authenticate header or 1 to send a proxy-authenticate
header in the message.
Access: Offline.
AC INI-Param: AUTHCHALLENGEMETHOD"
       ::= {sbc 11}



     sbcServAuthQop OBJECT-TYPE
       SYNTAX Unsigned32 (0..3)
       MAX-ACCESS read-write
       STATUS current
       DESCRIPTION
           "Set to 0 to offer auth, 1 to offer auth-int or 2 to offer auth,
auth-int, or 3 to not offer any QOP.
Access: Offline.
AC INI-Param: AUTHQOP"
       ::= {sbc 12}



     sbcExtensionsProvisioningMode OBJECT-TYPE
       SYNTAX INTEGER {
                  disable(0)
,
                  enable(1)

                  }
       MAX-ACCESS read-write
       STATUS current
       DESCRIPTION
           "Indicates how the registration database is provisioned (0) -
use register request (1) - broadsoft automatic mode.
Access: Instant.
AC INI-Param: SBCEXTENSIONSPROVISIONINGMODE"
       ::= {sbc 13}



     sbcReleaseAckOnByeAck OBJECT-TYPE
       SYNTAX INTEGER {
                  disable(0)
,
                  enable(1)

                  }
       MAX-ACCESS read-write
       STATUS current
       DESCRIPTION
           "Allows the media to remain active upon receipt of a 401/407
response by sending a releaseNackEvent, rather than releaseEvent.
Useful for SIP endpoints that support authentication.
Access: Instant.
AC INI-Param: SBCENABLEBYEAUTHENTICATION"
       ::= {sbc 14}



     sbcForkingHandlingMode OBJECT-TYPE
       SYNTAX INTEGER {
                  latchOnFirst(0)
,
                  sequential(1)

                  }
       MAX-ACCESS read-write
       STATUS current
       DESCRIPTION
           "Decides the handling method to 18X response to forking.The parameter
only affects the SBC behavior.
Access: Instant.
AC INI-Param: SBCFORKINGHANDLINGMODE"
       ::= {sbc 15}



     sbcSessionExpiresTime OBJECT-TYPE
       SYNTAX Unsigned32 (90..86400)
       MAX-ACCESS read-write
       STATUS current
       DESCRIPTION
           "SBC session refresh timer for requests in a dialog.
Access: Instant.
AC INI-Param: SBCSESSIONEXPIRES"
       ::= {sbc 16}



     sbcDialogInfoInterworking OBJECT-TYPE
       SYNTAX INTEGER {
                  disable(0)
,
                  enable(1)

                  }
       MAX-ACCESS read-write
       STATUS current
       DESCRIPTION
           "Changes the WAN call identifiers in the dialog-info body of
NOTIFY messages to LAN call identifiers. 0 - Do not alter the
dialog info body in a notify message. 1 - alter the dialog
info body call tags.
Access: Instant.
AC INI-Param: ENABLESBCDIALOGINFOINTERNETWORKING"
       ::= {sbc 17}



     sbcUserRegistrationGraceTime OBJECT-TYPE
       SYNTAX Unsigned32 (0..300)
       MAX-ACCESS read-write
       STATUS current
       DESCRIPTION
           "SBC User Registration Grace Time.
Access: Instant.
AC INI-Param: SBCUSERREGISTRATIONGRACETIME"
       ::= {sbc 18}



     sbcCrpSurvivabilityMode OBJECT-TYPE
       SYNTAX INTEGER {
                  standardMode(0)
,
                  alwaysEmergencyMode(1)
,
                  autoAnswerRegister(2)

                  }
       MAX-ACCESS read-write
       STATUS current
       DESCRIPTION
           "Defines the CRP functionality modes: (0)Normal, (1)Always  Emergency,
(2)Auto answer to registrations.
Access: Instant.
AC INI-Param: CRPSURVIVABILITYMODE"
       ::= {sbc 19}



     sbcSharedLineRegMode OBJECT-TYPE
       SYNTAX INTEGER {
                  asConfigured(0)
,
                  terminateSecondaryLines(1)

                  }
       MAX-ACCESS read-write
       STATUS current
       DESCRIPTION
           "Define the registration handling mode in case of shared line
manipulation. 0 - as configured, 1- terminate secondary lines.
Access: Instant.
AC INI-Param: SBCSHAREDLINEREGMODE"
       ::= {sbc 20}



     -- ****************************************
     -- sbcClassification table declaration
     -- ****************************************
     sbcClassificationTable OBJECT-TYPE
       SYNTAX SEQUENCE OF SbcClassificationEntry
       MAX-ACCESS not-accessible
       STATUS current
       DESCRIPTION
           "Zero value means that SBC does not limit Session-Expires."
       ::= {sbc 21}



     -- ****************************************
     -- sbcClassification table entry
     -- ****************************************
     sbcClassificationEntry OBJECT-TYPE
       SYNTAX SbcClassificationEntry
       MAX-ACCESS not-accessible
       STATUS current
       DESCRIPTION
           ""
       INDEX {sbcClassificationIndex}
       ::= {sbcClassificationTable 1}



     -- ****************************************
     -- sbcClassification TABLE
     -- ****************************************
     SbcClassificationEntry ::= SEQUENCE {
       sbcClassificationIndex                          Unsigned32,
       sbcClassificationRowStatus                      RowStatus,
       sbcClassificationAction                         INTEGER,
       sbcClassificationActionResult                   INTEGER,
       sbcClassificationSrcIPGroupId                   Integer32,
       sbcClassificationSrcSRDId                       Integer32,
       sbcClassificationSrcAddress                     SnmpAdminString,
       sbcClassificationSrcUsernamePrefix              SnmpAdminString,
       sbcClassificationSrcHost                        SnmpAdminString,
       sbcClassificationDestUsernamePrefix             SnmpAdminString,
       sbcClassificationDestHost                       SnmpAdminString,
       sbcClassificationMessageCondition               RowPointer,
       sbcClassificationActionType                     Unsigned32,
       sbcClassificationSrcPort                        Unsigned32,
       sbcClassificationSrcTransportType               Integer32,
       sbcClassificationClassificationName             SnmpAdminString
     }



     sbcClassificationIndex OBJECT-TYPE
       SYNTAX Unsigned32 (0..500)
       MAX-ACCESS read-only
       STATUS current
       DESCRIPTION
           ".
AC INI-Param: Classification_Index"
       ::= {sbcClassificationEntry 1}



     sbcClassificationRowStatus OBJECT-TYPE
       SYNTAX RowStatus
       MAX-ACCESS read-create
       STATUS current
       DESCRIPTION
           "Row-Status Textual Conventions as defined in RFC 2579: Textual
Conventions for SMIv2.
AC INI-Param: N/A"
       ::= {sbcClassificationEntry 2}



     sbcClassificationAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {sbcClassificationEntry 3}



     sbcClassificationActionResult OBJECT-TYPE
       SYNTAX INTEGER {
                  developmentImpending(0)

                  }
       MAX-ACCESS read-only
       STATUS current
       DESCRIPTION
           "Development Impending.
AC INI-Param: N/A"
       ::= {sbcClassificationEntry 4}



     sbcClassificationSrcIPGroupId OBJECT-TYPE
       SYNTAX Integer32 (-1..31)
       MAX-ACCESS read-create
       STATUS current
       DESCRIPTION
           "Source IP group ID.
Access: Instant.
AC INI-Param: Classification_SrcIPGroupID"
       ::= {sbcClassificationEntry 5}



     sbcClassificationSrcSRDId OBJECT-TYPE
       SYNTAX Integer32 (-1..4)
       MAX-ACCESS read-create
       STATUS current
       DESCRIPTION
           "Source SRD ID.
Access: Instant.
AC INI-Param: Classification_SrcSRDID"
       ::= {sbcClassificationEntry 6}



     sbcClassificationSrcAddress OBJECT-TYPE
       SYNTAX SnmpAdminString (SIZE (0..70))
       MAX-ACCESS read-create
       STATUS current
       DESCRIPTION
           "Source address.
Access: Instant.
AC INI-Param: Classification_SrcAddress"
       ::= {sbcClassificationEntry 7}



     sbcClassificationSrcUsernamePrefix OBJECT-TYPE
       SYNTAX SnmpAdminString (SIZE (0..50))
       MAX-ACCESS read-create
       STATUS current
       DESCRIPTION
           "Source username prefix.
Access: Instant.
AC INI-Param: Classification_SrcUsernamePrefix"
       ::= {sbcClassificationEntry 8}



     sbcClassificationSrcHost OBJECT-TYPE
       SYNTAX SnmpAdminString (SIZE (0..49))
       MAX-ACCESS read-create
       STATUS current
       DESCRIPTION
           "Source host.
Access: Instant.
AC INI-Param: Classification_SrcHost"
       ::= {sbcClassificationEntry 9}



     sbcClassificationDestUsernamePrefix OBJECT-TYPE
       SYNTAX SnmpAdminString (SIZE (0..50))
       MAX-ACCESS read-create
       STATUS current
       DESCRIPTION
           "Destination username prefix.
Access: Instant.
AC INI-Param: Classification_DestUsernamePrefix"
       ::= {sbcClassificationEntry 10}



     sbcClassificationDestHost OBJECT-TYPE
       SYNTAX SnmpAdminString (SIZE (0..49))
       MAX-ACCESS read-create
       STATUS current
       DESCRIPTION
           "Destination host.
Access: Instant.
AC INI-Param: Classification_DestHost"
       ::= {sbcClassificationEntry 11}



     sbcClassificationMessageCondition OBJECT-TYPE
       SYNTAX RowPointer
       MAX-ACCESS read-create
       STATUS current
       DESCRIPTION
           "Message Condition.
Access: Offline.
AC INI-Param: Classification_MessageCondition"
       ::= {sbcClassificationEntry 12}



     sbcClassificationActionType OBJECT-TYPE
       SYNTAX Unsigned32 (0..1)
       MAX-ACCESS read-create
       STATUS current
       DESCRIPTION
           "Action Type.
Access: Instant.
AC INI-Param: Classification_ActionType"
       ::= {sbcClassificationEntry 13}



     sbcClassificationSrcPort OBJECT-TYPE
       SYNTAX Unsigned32 (0..2147483647)
       MAX-ACCESS read-create
       STATUS current
       DESCRIPTION
           "Source Port.
Access: Instant.
AC INI-Param: Classification_SrcPort"
       ::= {sbcClassificationEntry 14}



     sbcClassificationSrcTransportType OBJECT-TYPE
       SYNTAX Integer32 (-1..2)
       MAX-ACCESS read-create
       STATUS current
       DESCRIPTION
           "Source Transport Type.
Access: Instant.
AC INI-Param: Classification_SrcTransportType"
       ::= {sbcClassificationEntry 15}



     sbcClassificationClassificationName OBJECT-TYPE
       SYNTAX SnmpAdminString (SIZE (0..20))
       MAX-ACCESS read-create
       STATUS current
       DESCRIPTION
           "Classification Name.
Access: Instant.
AC INI-Param: Classification_ClassificationName"
       ::= {sbcClassificationEntry 16}



     -- ****************************************
     -- sbcRouting table declaration
     -- ****************************************
     sbcRoutingTable OBJECT-TYPE
       SYNTAX SEQUENCE OF SbcRoutingEntry
       MAX-ACCESS not-accessible
       STATUS current
       DESCRIPTION
           "GwApp SBC Routing Table"
       ::= {sbc 22}



     -- ****************************************
     -- sbcRouting table entry
     -- ****************************************
     sbcRoutingEntry OBJECT-TYPE
       SYNTAX SbcRoutingEntry
       MAX-ACCESS not-accessible
       STATUS current
       DESCRIPTION
           ""
       INDEX {sbcRoutingIndex}
       ::= {sbcRoutingTable 1}



     -- ****************************************
     -- sbcRouting TABLE
     -- ****************************************
     SbcRoutingEntry ::= SEQUENCE {
       sbcRoutingIndex                                 Unsigned32,
       sbcRoutingRowStatus                             RowStatus,
       sbcRoutingAction                                INTEGER,
       sbcRoutingActionResult                          INTEGER,
       sbcRoutingSrcIPGroupId                          Integer32,
       sbcRoutingSrcUsernamePrefix                     SnmpAdminString,
       sbcRoutingSrcHost                               SnmpAdminString,
       sbcRoutingDestUsernamePrefix                    SnmpAdminString,
       sbcRoutingDestHost                              SnmpAdminString,
       sbcRoutingDestType                              INTEGER,
       sbcRoutingDestIPGroupId                         Integer32,
       sbcRoutingDestSRDId                             Integer32,
       sbcRoutingDestAddress                           SnmpAdminString,
       sbcRoutingDestPort                              Unsigned32,
       sbcRoutingDestTransportType                     INTEGER,
       sbcRoutingAltRouteOptions                       INTEGER,
       sbcRoutingRequestType                           INTEGER,
       sbcRoutingCostGroupName                         RowPointer,
       sbcRoutingMessageCondition                      RowPointer,
       sbcRoutingReRouteIPGroupID                      Integer32,
       sbcRoutingTrigger                               INTEGER,
       sbcRoutingRouteName                             SnmpAdminString,
       sbcRoutingGroupPolicy                           INTEGER
     }



     sbcRoutingIndex OBJECT-TYPE
       SYNTAX Unsigned32 (0..999)
       MAX-ACCESS read-only
       STATUS current
       DESCRIPTION
           ".
AC INI-Param: IP2IPRouting_Index"
       ::= {sbcRoutingEntry 1}



     sbcRoutingRowStatus OBJECT-TYPE
       SYNTAX RowStatus
       MAX-ACCESS read-create
       STATUS current
       DESCRIPTION
           "Row-Status Textual Conventions as defined in RFC 2579: Textual
Conventions for SMIv2.
AC INI-Param: N/A"
       ::= {sbcRoutingEntry 2}



     sbcRoutingAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {sbcRoutingEntry 3}



     sbcRoutingActionResult OBJECT-TYPE
       SYNTAX INTEGER {
                  developmentImpending(0)

                  }
       MAX-ACCESS read-only
       STATUS current
       DESCRIPTION
           "Development Impending.
AC INI-Param: N/A"
       ::= {sbcRoutingEntry 4}



     sbcRoutingSrcIPGroupId OBJECT-TYPE
       SYNTAX Integer32 (-1..31)
       MAX-ACCESS read-create
       STATUS current
       DESCRIPTION
           "Source IP group ID.
Access: Instant.
AC INI-Param: IP2IPRouting_SrcIPGroupID"
       ::= {sbcRoutingEntry 5}



     sbcRoutingSrcUsernamePrefix OBJECT-TYPE
       SYNTAX SnmpAdminString (SIZE (0..50))
       MAX-ACCESS read-create
       STATUS current
       DESCRIPTION
           "Source username prefix.
Access: Instant.
AC INI-Param: IP2IPRouting_SrcUsernamePrefix"
       ::= {sbcRoutingEntry 6}



     sbcRoutingSrcHost OBJECT-TYPE
       SYNTAX SnmpAdminString (SIZE (0..49))
       MAX-ACCESS read-create
       STATUS current
       DESCRIPTION
           "Source host.
Access: Instant.
AC INI-Param: IP2IPRouting_SrcHost"
       ::= {sbcRoutingEntry 7}



     sbcRoutingDestUsernamePrefix OBJECT-TYPE
       SYNTAX SnmpAdminString (SIZE (0..50))
       MAX-ACCESS read-create
       STATUS current
       DESCRIPTION
           "Destination username prefix.
Access: Instant.
AC INI-Param: IP2IPRouting_DestUsernamePrefix"
       ::= {sbcRoutingEntry 8}



     sbcRoutingDestHost OBJECT-TYPE
       SYNTAX SnmpAdminString (SIZE (0..49))
       MAX-ACCESS read-create
       STATUS current
       DESCRIPTION
           "Destination host.
Access: Instant.
AC INI-Param: IP2IPRouting_DestHost"
       ::= {sbcRoutingEntry 9}



     sbcRoutingDestType OBJECT-TYPE
       SYNTAX INTEGER {
                  ipGroup(0)
,
                  dest(1)
,
                  requestURI(2)
,
                  enumTranslate (3)

                  }
       MAX-ACCESS read-create
       STATUS current
       DESCRIPTION
           "Destination type.
Access: Instant.
AC INI-Param: IP2IPRouting_DestType"
       ::= {sbcRoutingEntry 10}



     sbcRoutingDestIPGroupId OBJECT-TYPE
       SYNTAX Integer32 (-2..31)
       MAX-ACCESS read-create
       STATUS current
       DESCRIPTION
           "Destination IP group ID.
Access: Instant.
AC INI-Param: IP2IPRouting_DestIPGroupID"
       ::= {sbcRoutingEntry 11}



     sbcRoutingDestSRDId OBJECT-TYPE
       SYNTAX Integer32 (-1..4)
       MAX-ACCESS read-create
       STATUS current
       DESCRIPTION
           "Destination SRD ID.
Access: Instant.
AC INI-Param: IP2IPRouting_DestSRDID"
       ::= {sbcRoutingEntry 12}



     sbcRoutingDestAddress OBJECT-TYPE
       SYNTAX SnmpAdminString (SIZE (0..70))
       MAX-ACCESS read-create
       STATUS current
       DESCRIPTION
           "Destination Address.
Access: Instant.
AC INI-Param: IP2IPRouting_DestAddress"
       ::= {sbcRoutingEntry 13}



     sbcRoutingDestPort OBJECT-TYPE
       SYNTAX Unsigned32 (0..65534)
       MAX-ACCESS read-create
       STATUS current
       DESCRIPTION
           "Destination Port number.
Access: Instant.
AC INI-Param: IP2IPRouting_DestPort"
       ::= {sbcRoutingEntry 14}



     sbcRoutingDestTransportType OBJECT-TYPE
       SYNTAX INTEGER {
                  notConfigured(-1)
,
                  udp(0)
,
                  tcp(1)
,
                  tls(2)

                  }
       MAX-ACCESS read-create
       STATUS current
       DESCRIPTION
           "Destination transport type.
Access: Instant.
AC INI-Param: IP2IPRouting_DestTransportType"
       ::= {sbcRoutingEntry 15}



     sbcRoutingAltRouteOptions OBJECT-TYPE
       SYNTAX INTEGER {
                  routeRow(0)
,
                  ignoreInputs(1)
,
                  considerInputs(2)

                  }
       MAX-ACCESS read-create
       STATUS current
       DESCRIPTION
           "Alternative Route Options.
Access: Instant.
AC INI-Param: IP2IPRouting_AltRouteOptions"
       ::= {sbcRoutingEntry 16}



     sbcRoutingRequestType OBJECT-TYPE
       SYNTAX INTEGER {
                  all(0)
,
                  invite(1)
,
                  register(2)
,
                  subscribe(3)
,
                  inviteAndRegister(4)
,
                  inviteAndSubscribe(5)
,
                  options(6)

                  }
       MAX-ACCESS read-create
       STATUS current
       DESCRIPTION
           "Request Type.
Access: Instant.
AC INI-Param: IP2IPRouting_RequestType"
       ::= {sbcRoutingEntry 17}



     sbcRoutingCostGroupName OBJECT-TYPE
       SYNTAX RowPointer
       MAX-ACCESS read-create
       STATUS current
       DESCRIPTION
           "sbc Routing cost group. This is a pointer to the CostGroup in
the costGroupName.
Access: Offline.
AC INI-Param: IP2IPRouting_CostGroup"
       ::= {sbcRoutingEntry 18}



     sbcRoutingMessageCondition OBJECT-TYPE
       SYNTAX RowPointer
       MAX-ACCESS read-create
       STATUS current
       DESCRIPTION
           "Message Condition. This is a pointer to the sbcConditionIndex.
Access: Offline.
AC INI-Param: IP2IPRouting_MessageCondition"
       ::= {sbcRoutingEntry 19}



     sbcRoutingReRouteIPGroupID OBJECT-TYPE
       SYNTAX Integer32 (-1..32)
       MAX-ACCESS read-create
       STATUS current
       DESCRIPTION
           "The ip group id of redirect/refer initiator.
Access: Instant.
AC INI-Param: IP2IPRouting_ReRouteIPGroupID"
       ::= {sbcRoutingEntry 20}



     sbcRoutingTrigger OBJECT-TYPE
       SYNTAX INTEGER {
                  triggerAny(0)
,
                  trigger3xx(1)
,
                  triggerREFER(2)
,
                  trigger3xxOrREFER(3)
,
                  triggerInitialonly(4)

                  }
       MAX-ACCESS read-create
       STATUS current
       DESCRIPTION
           "Call Trigger.
Access: Instant.
AC INI-Param: IP2IPRouting_Trigger"
       ::= {sbcRoutingEntry 21}



     sbcRoutingRouteName OBJECT-TYPE
       SYNTAX SnmpAdminString (SIZE (0..20))
       MAX-ACCESS read-create
       STATUS current
       DESCRIPTION
           "Route Name.
Access: Instant.
AC INI-Param: IP2IPRouting_RouteName"
       ::= {sbcRoutingEntry 22}



     sbcRoutingGroupPolicy OBJECT-TYPE
       SYNTAX INTEGER {
                  none(0)
,
                  forking(1)

                  }
       MAX-ACCESS read-create
       STATUS current
       DESCRIPTION
           "Group Policy.
Access: Instant.
AC INI-Param: IP2IPRouting_GroupPolicy"
       ::= {sbcRoutingEntry 23}



     -- ****************************************
     -- sbcIP2IPInboundManipulation table declaration
     -- ****************************************
     sbcIP2IPInboundManipulationTable OBJECT-TYPE
       SYNTAX SEQUENCE OF SbcIP2IPInboundManipulationEntry
       MAX-ACCESS not-accessible
       STATUS current
       DESCRIPTION
           "GwApp IP Inbound Manipulation Table "
       ::= {sbc 23}



     -- ****************************************
     -- sbcIP2IPInboundManipulation table entry
     -- ****************************************
     sbcIP2IPInboundManipulationEntry OBJECT-TYPE
       SYNTAX SbcIP2IPInboundManipulationEntry
       MAX-ACCESS not-accessible
       STATUS current
       DESCRIPTION
           ""
       INDEX {sbcIP2IPInboundManipulationIndex}
       ::= {sbcIP2IPInboundManipulationTable 1}



     -- ****************************************
     -- sbcIP2IPInboundManipulation TABLE
     -- ****************************************
     SbcIP2IPInboundManipulationEntry ::= SEQUENCE {
       sbcIP2IPInboundManipulationIndex                Unsigned32,
       sbcIP2IPInboundManipulationRowStatus            RowStatus,
       sbcIP2IPInboundManipulationAction               INTEGER,
       sbcIP2IPInboundManipulationActionResult         INTEGER,
       sbcIP2IPInboundManipulationIsAdditionalManipulation 
                                                       INTEGER,
       sbcIP2IPInboundManipulationManipulatedURI       INTEGER,
       sbcIP2IPInboundManipulationSrcIPGroupID         Integer32,
       sbcIP2IPInboundManipulationSrcUsernamePrefix    SnmpAdminString,
       sbcIP2IPInboundManipulationSrcHost              SnmpAdminString,
       sbcIP2IPInboundManipulationDestUsernamePrefix   SnmpAdminString,
       sbcIP2IPInboundManipulationDestHost             SnmpAdminString,
       sbcIP2IPInboundManipulationRemoveFromLeft       Unsigned32,
       sbcIP2IPInboundManipulationRemoveFromRight      Unsigned32,
       sbcIP2IPInboundManipulationLeaveFromRight       Unsigned32,
       sbcIP2IPInboundManipulationPrefix2Add           SnmpAdminString,
       sbcIP2IPInboundManipulationSuffix2Add           SnmpAdminString,
       sbcIP2IPInboundManipulationRequestType          INTEGER,
       sbcIP2IPInboundManipulationManipulationName     SnmpAdminString
     }



     sbcIP2IPInboundManipulationIndex OBJECT-TYPE
       SYNTAX Unsigned32 (0..500)
       MAX-ACCESS read-only
       STATUS current
       DESCRIPTION
           ".
AC INI-Param: IPInboundManipulation_Index"
       ::= {sbcIP2IPInboundManipulationEntry 1}



     sbcIP2IPInboundManipulationRowStatus OBJECT-TYPE
       SYNTAX RowStatus
       MAX-ACCESS read-create
       STATUS current
       DESCRIPTION
           "Row-Status Textual Conventions as defined in RFC 2579: Textual
Conventions for SMIv2.
AC INI-Param: N/A"
       ::= {sbcIP2IPInboundManipulationEntry 2}



     sbcIP2IPInboundManipulationAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {sbcIP2IPInboundManipulationEntry 3}



     sbcIP2IPInboundManipulationActionResult OBJECT-TYPE
       SYNTAX INTEGER {
                  developmentImpending(0)

                  }
       MAX-ACCESS read-only
       STATUS current
       DESCRIPTION
           "Development Impending.
AC INI-Param: N/A"
       ::= {sbcIP2IPInboundManipulationEntry 4}



     sbcIP2IPInboundManipulationIsAdditionalManipulation OBJECT-TYPE
       SYNTAX INTEGER {
                  no(0)
,
                  yes(1)

                  }
       MAX-ACCESS read-create
       STATUS current
       DESCRIPTION
           "
Access: Instant.
AC INI-Param: IPInboundManipulation_IsAdditionalManipulation"
       ::= {sbcIP2IPInboundManipulationEntry 5}



     sbcIP2IPInboundManipulationManipulatedURI OBJECT-TYPE
       SYNTAX INTEGER {
                  no(0)
,
                  yes(1)

                  }
       MAX-ACCESS read-create
       STATUS current
       DESCRIPTION
           "
Access: Instant.
AC INI-Param: IPInboundManipulation_ManipulatedURI"
       ::= {sbcIP2IPInboundManipulationEntry 6}



     sbcIP2IPInboundManipulationSrcIPGroupID OBJECT-TYPE
       SYNTAX Integer32 (-1..31)
       MAX-ACCESS read-create
       STATUS current
       DESCRIPTION
           "
Access: Instant.
AC INI-Param: IPInboundManipulation_SrcIPGroupID"
       ::= {sbcIP2IPInboundManipulationEntry 7}



     sbcIP2IPInboundManipulationSrcUsernamePrefix OBJECT-TYPE
       SYNTAX SnmpAdminString (SIZE (0..50))
       MAX-ACCESS read-create
       STATUS current
       DESCRIPTION
           "
Access: Instant.
AC INI-Param: IPInboundManipulation_SrcUsernamePrefix"
       ::= {sbcIP2IPInboundManipulationEntry 8}



     sbcIP2IPInboundManipulationSrcHost OBJECT-TYPE
       SYNTAX SnmpAdminString (SIZE (0..49))
       MAX-ACCESS read-create
       STATUS current
       DESCRIPTION
           "
Access: Instant.
AC INI-Param: IPInboundManipulation_SrcHost"
       ::= {sbcIP2IPInboundManipulationEntry 9}



     sbcIP2IPInboundManipulationDestUsernamePrefix OBJECT-TYPE
       SYNTAX SnmpAdminString (SIZE (0..50))
       MAX-ACCESS read-create
       STATUS current
       DESCRIPTION
           "
Access: Instant.
AC INI-Param: IPInboundManipulation_DestUsernamePrefix"
       ::= {sbcIP2IPInboundManipulationEntry 10}



     sbcIP2IPInboundManipulationDestHost OBJECT-TYPE
       SYNTAX SnmpAdminString (SIZE (0..49))
       MAX-ACCESS read-create
       STATUS current
       DESCRIPTION
           "
Access: Instant.
AC INI-Param: IPInboundManipulation_DestHost"
       ::= {sbcIP2IPInboundManipulationEntry 11}



     sbcIP2IPInboundManipulationRemoveFromLeft OBJECT-TYPE
       SYNTAX Unsigned32 (0..50)
       MAX-ACCESS read-create
       STATUS current
       DESCRIPTION
           "
Access: Instant.
AC INI-Param: IPInboundManipulation_RemoveFromLeft"
       ::= {sbcIP2IPInboundManipulationEntry 12}



     sbcIP2IPInboundManipulationRemoveFromRight OBJECT-TYPE
       SYNTAX Unsigned32 (0..50)
       MAX-ACCESS read-create
       STATUS current
       DESCRIPTION
           "
Access: Instant.
AC INI-Param: IPInboundManipulation_RemoveFromRight"
       ::= {sbcIP2IPInboundManipulationEntry 13}



     sbcIP2IPInboundManipulationLeaveFromRight OBJECT-TYPE
       SYNTAX Unsigned32 (0..255)
       MAX-ACCESS read-create
       STATUS current
       DESCRIPTION
           "
Access: Instant.
AC INI-Param: IPInboundManipulation_LeaveFromRight"
       ::= {sbcIP2IPInboundManipulationEntry 14}



     sbcIP2IPInboundManipulationPrefix2Add OBJECT-TYPE
       SYNTAX SnmpAdminString (SIZE (0..49))
       MAX-ACCESS read-create
       STATUS current
       DESCRIPTION
           "
Access: Instant.
AC INI-Param: IPInboundManipulation_Prefix2Add"
       ::= {sbcIP2IPInboundManipulationEntry 15}



     sbcIP2IPInboundManipulationSuffix2Add OBJECT-TYPE
       SYNTAX SnmpAdminString (SIZE (0..49))
       MAX-ACCESS read-create
       STATUS current
       DESCRIPTION
           "
Access: Instant.
AC INI-Param: IPInboundManipulation_Suffix2Add"
       ::= {sbcIP2IPInboundManipulationEntry 16}



     sbcIP2IPInboundManipulationRequestType OBJECT-TYPE
       SYNTAX INTEGER {
                  all(0)
,
                  invite(1)
,
                  register(2)
,
                  subscribe(3)
,
                  inviteAndRegister(4)
,
                  inviteAndSubscribe(5)

                  }
       MAX-ACCESS read-create
       STATUS current
       DESCRIPTION
           "
Access: Instant.
AC INI-Param: IPInboundManipulation_RequestType"
       ::= {sbcIP2IPInboundManipulationEntry 17}



     sbcIP2IPInboundManipulationManipulationName OBJECT-TYPE
       SYNTAX SnmpAdminString (SIZE (0..20))
       MAX-ACCESS read-create
       STATUS current
       DESCRIPTION
           "Manipulation Name.
Access: Instant.
AC INI-Param: IPInboundManipulation_ManipulationName"
       ::= {sbcIP2IPInboundManipulationEntry 18}



     -- ****************************************
     -- sbcIP2IPOutboundManipulation table declaration
     -- ****************************************
     sbcIP2IPOutboundManipulationTable OBJECT-TYPE
       SYNTAX SEQUENCE OF SbcIP2IPOutboundManipulationEntry
       MAX-ACCESS not-accessible
       STATUS current
       DESCRIPTION
           "GwApp IP Outbound Manipulation Table"
       ::= {sbc 24}



     -- ****************************************
     -- sbcIP2IPOutboundManipulation table entry
     -- ****************************************
     sbcIP2IPOutboundManipulationEntry OBJECT-TYPE
       SYNTAX SbcIP2IPOutboundManipulationEntry
       MAX-ACCESS not-accessible
       STATUS current
       DESCRIPTION
           ""
       INDEX {sbcIP2IPOutboundManipulationIndex}
       ::= {sbcIP2IPOutboundManipulationTable 1}



     -- ****************************************
     -- sbcIP2IPOutboundManipulation TABLE
     -- ****************************************
     SbcIP2IPOutboundManipulationEntry ::= SEQUENCE {
       sbcIP2IPOutboundManipulationIndex               Unsigned32,
       sbcIP2IPOutboundManipulationRowStatus           RowStatus,
       sbcIP2IPOutboundManipulationAction              INTEGER,
       sbcIP2IPOutboundManipulationActionResult        INTEGER,
       sbcIP2IPOutboundManipulationIsAdditionalManipulation 
                                                       INTEGER,
       sbcIP2IPOutboundManipulationManipulatedURI      INTEGER,
       sbcIP2IPOutboundManipulationSrcIPGroupID        Integer32,
       sbcIP2IPOutboundManipulationDestIPGroupID       Integer32,
       sbcIP2IPOutboundManipulationSrcUsernamePrefix   SnmpAdminString,
       sbcIP2IPOutboundManipulationSrcHost             SnmpAdminString,
       sbcIP2IPOutboundManipulationDestUsernamePrefix  SnmpAdminString,
       sbcIP2IPOutboundManipulationDestHost            SnmpAdminString,
       sbcIP2IPOutboundManipulationRemoveFromLeft      Unsigned32,
       sbcIP2IPOutboundManipulationRemoveFromRight     Unsigned32,
       sbcIP2IPOutboundManipulationLeaveFromRight      Unsigned32,
       sbcIP2IPOutboundManipulationPrefix2Add          SnmpAdminString,
       sbcIP2IPOutboundManipulationSuffix2Add          SnmpAdminString,
       sbcIP2IPOutboundManipulationRequestType         INTEGER,
       sbcIP2IPOutboundManipulationReRouteIPGroupID    Integer32,
       sbcIP2IPOutboundManipulationTrigger             INTEGER,
       sbcIP2IPOutboundManipulationManipulationName    SnmpAdminString,
       sbcIP2IPOutboundManipulationMessageCondition    RowPointer,
       sbcIP2IPOutboundManipulationCallingNamePrefix   SnmpAdminString
     }



     sbcIP2IPOutboundManipulationIndex OBJECT-TYPE
       SYNTAX Unsigned32 (0..500)
       MAX-ACCESS read-only
       STATUS current
       DESCRIPTION
           ".
AC INI-Param: IPOutboundManipulation_Index"
       ::= {sbcIP2IPOutboundManipulationEntry 1}



     sbcIP2IPOutboundManipulationRowStatus OBJECT-TYPE
       SYNTAX RowStatus
       MAX-ACCESS read-create
       STATUS current
       DESCRIPTION
           "Row-Status Textual Conventions as defined in RFC 2579: Textual
Conventions for SMIv2.
AC INI-Param: N/A"
       ::= {sbcIP2IPOutboundManipulationEntry 2}



     sbcIP2IPOutboundManipulationAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {sbcIP2IPOutboundManipulationEntry 3}



     sbcIP2IPOutboundManipulationActionResult OBJECT-TYPE
       SYNTAX INTEGER {
                  developmentImpending(0)

                  }
       MAX-ACCESS read-only
       STATUS current
       DESCRIPTION
           "Development Impending.
AC INI-Param: N/A"
       ::= {sbcIP2IPOutboundManipulationEntry 4}



     sbcIP2IPOutboundManipulationIsAdditionalManipulation OBJECT-TYPE
       SYNTAX INTEGER {
                  no(0)
,
                  yes(1)

                  }
       MAX-ACCESS read-create
       STATUS current
       DESCRIPTION
           "
Access: Instant.
AC INI-Param: IPOutboundManipulation_IsAdditionalManipulation"
       ::= {sbcIP2IPOutboundManipulationEntry 5}



     sbcIP2IPOutboundManipulationManipulatedURI OBJECT-TYPE
       SYNTAX INTEGER {
                  sourceURI(0)
,
                  destinationURI(1)
,
                  callingName(2)

                  }
       MAX-ACCESS read-create
       STATUS current
       DESCRIPTION
           "
Access: Instant.
AC INI-Param: IPOutboundManipulation_ManipulatedURI"
       ::= {sbcIP2IPOutboundManipulationEntry 6}



     sbcIP2IPOutboundManipulationSrcIPGroupID OBJECT-TYPE
       SYNTAX Integer32 (-1..31)
       MAX-ACCESS read-create
       STATUS current
       DESCRIPTION
           "
Access: Instant.
AC INI-Param: IPOutboundManipulation_SrcIPGroupID"
       ::= {sbcIP2IPOutboundManipulationEntry 7}



     sbcIP2IPOutboundManipulationDestIPGroupID OBJECT-TYPE
       SYNTAX Integer32 (-1..31)
       MAX-ACCESS read-create
       STATUS current
       DESCRIPTION
           "
Access: Instant.
AC INI-Param: IPOutboundManipulation_DestIPGroupID"
       ::= {sbcIP2IPOutboundManipulationEntry 8}



     sbcIP2IPOutboundManipulationSrcUsernamePrefix OBJECT-TYPE
       SYNTAX SnmpAdminString (SIZE (0..50))
       MAX-ACCESS read-create
       STATUS current
       DESCRIPTION
           "
Access: Instant.
AC INI-Param: IPOutboundManipulation_SrcUsernamePrefix"
       ::= {sbcIP2IPOutboundManipulationEntry 9}



     sbcIP2IPOutboundManipulationSrcHost OBJECT-TYPE
       SYNTAX SnmpAdminString (SIZE (0..49))
       MAX-ACCESS read-create
       STATUS current
       DESCRIPTION
           "
Access: Instant.
AC INI-Param: IPOutboundManipulation_SrcHost"
       ::= {sbcIP2IPOutboundManipulationEntry 10}



     sbcIP2IPOutboundManipulationDestUsernamePrefix OBJECT-TYPE
       SYNTAX SnmpAdminString (SIZE (0..50))
       MAX-ACCESS read-create
       STATUS current
       DESCRIPTION
           "
Access: Instant.
AC INI-Param: IPOutboundManipulation_DestUsernamePrefix"
       ::= {sbcIP2IPOutboundManipulationEntry 11}



     sbcIP2IPOutboundManipulationDestHost OBJECT-TYPE
       SYNTAX SnmpAdminString (SIZE (0..49))
       MAX-ACCESS read-create
       STATUS current
       DESCRIPTION
           "
Access: Instant.
AC INI-Param: IPOutboundManipulation_DestHost"
       ::= {sbcIP2IPOutboundManipulationEntry 12}



     sbcIP2IPOutboundManipulationRemoveFromLeft OBJECT-TYPE
       SYNTAX Unsigned32 (0..50)
       MAX-ACCESS read-create
       STATUS current
       DESCRIPTION
           "
Access: Instant.
AC INI-Param: IPOutboundManipulation_RemoveFromLeft"
       ::= {sbcIP2IPOutboundManipulationEntry 13}



     sbcIP2IPOutboundManipulationRemoveFromRight OBJECT-TYPE
       SYNTAX Unsigned32 (0..50)
       MAX-ACCESS read-create
       STATUS current
       DESCRIPTION
           "
Access: Instant.
AC INI-Param: IPOutboundManipulation_RemoveFromRight"
       ::= {sbcIP2IPOutboundManipulationEntry 14}



     sbcIP2IPOutboundManipulationLeaveFromRight OBJECT-TYPE
       SYNTAX Unsigned32 (0..255)
       MAX-ACCESS read-create
       STATUS current
       DESCRIPTION
           "
Access: Instant.
AC INI-Param: IPOutboundManipulation_LeaveFromRight"
       ::= {sbcIP2IPOutboundManipulationEntry 15}



     sbcIP2IPOutboundManipulationPrefix2Add OBJECT-TYPE
       SYNTAX SnmpAdminString (SIZE (0..49))
       MAX-ACCESS read-create
       STATUS current
       DESCRIPTION
           "
Access: Instant.
AC INI-Param: IPOutboundManipulation_Prefix2Add"
       ::= {sbcIP2IPOutboundManipulationEntry 16}



     sbcIP2IPOutboundManipulationSuffix2Add OBJECT-TYPE
       SYNTAX SnmpAdminString (SIZE (0..49))
       MAX-ACCESS read-create
       STATUS current
       DESCRIPTION
           "
Access: Instant.
AC INI-Param: IPOutboundManipulation_Suffix2Add"
       ::= {sbcIP2IPOutboundManipulationEntry 17}



     sbcIP2IPOutboundManipulationRequestType OBJECT-TYPE
       SYNTAX INTEGER {
                  all(0)
,
                  invite(1)
,
                  register(2)
,
                  subscribe(3)
,
                  inviteAndRegister(4)
,
                  inviteAndSubscribe(5)

                  }
       MAX-ACCESS read-create
       STATUS current
       DESCRIPTION
           "
Access: Instant.
AC INI-Param: IPOutboundManipulation_RequestType"
       ::= {sbcIP2IPOutboundManipulationEntry 18}



     sbcIP2IPOutboundManipulationReRouteIPGroupID OBJECT-TYPE
       SYNTAX Integer32 (-1..32)
       MAX-ACCESS read-create
       STATUS current
       DESCRIPTION
           "ReRoute IP Group ID
The ip group id of redirect/refer initiator.
Access: Instant.
AC INI-Param: IPOutboundManipulation_ReRouteIPGroupID"
       ::= {sbcIP2IPOutboundManipulationEntry 19}



     sbcIP2IPOutboundManipulationTrigger OBJECT-TYPE
       SYNTAX INTEGER {
                  triggerAny(0)
,
                  trigger3xx(1)
,
                  triggerREFER(2)
,
                  trigger3xxOrREFER(3)
,
                  triggerInitialOnly(4)

                  }
       MAX-ACCESS read-create
       STATUS current
       DESCRIPTION
           "Call Trigger.
Access: Instant.
AC INI-Param: IPOutboundManipulation_Trigger"
       ::= {sbcIP2IPOutboundManipulationEntry 20}



     sbcIP2IPOutboundManipulationManipulationName OBJECT-TYPE
       SYNTAX SnmpAdminString (SIZE (0..20))
       MAX-ACCESS read-create
       STATUS current
       DESCRIPTION
           "Manipulation Name.
Access: Instant.
AC INI-Param: IPOutboundManipulation_ManipulationName"
       ::= {sbcIP2IPOutboundManipulationEntry 21}



     sbcIP2IPOutboundManipulationMessageCondition OBJECT-TYPE
       SYNTAX RowPointer
       MAX-ACCESS read-create
       STATUS current
       DESCRIPTION
           "Message Condition.
Access: Instant.
AC INI-Param: IPOutboundManipulation_MessageCondition"
       ::= {sbcIP2IPOutboundManipulationEntry 22}



     sbcIP2IPOutboundManipulationCallingNamePrefix OBJECT-TYPE
       SYNTAX SnmpAdminString (SIZE (0..36))
       MAX-ACCESS read-create
       STATUS current
       DESCRIPTION
           "Calling Name Prefix.
Access: Instant.
AC INI-Param: IPOutboundManipulation_CallingNamePrefix"
       ::= {sbcIP2IPOutboundManipulationEntry 23}



     -- ****************************************
     -- sbcAdmissionControl table declaration
     -- ****************************************
     sbcAdmissionControlTable OBJECT-TYPE
       SYNTAX SEQUENCE OF SbcAdmissionControlEntry
       MAX-ACCESS not-accessible
       STATUS current
       DESCRIPTION
           "GwApp SBC SIP Admission Control Table"
       ::= {sbc 25}



     -- ****************************************
     -- sbcAdmissionControl table entry
     -- ****************************************
     sbcAdmissionControlEntry OBJECT-TYPE
       SYNTAX SbcAdmissionControlEntry
       MAX-ACCESS not-accessible
       STATUS current
       DESCRIPTION
           ""
       INDEX {sbcAdmissionControlIndex}
       ::= {sbcAdmissionControlTable 1}



     -- ****************************************
     -- sbcAdmissionControl TABLE
     -- ****************************************
     SbcAdmissionControlEntry ::= SEQUENCE {
       sbcAdmissionControlIndex                        Unsigned32,
       sbcAdmissionControlRowStatus                    RowStatus,
       sbcAdmissionControlAction                       INTEGER,
       sbcAdmissionControlActionResult                 INTEGER,
       sbcAdmissionControlLimitType                    INTEGER,
       sbcAdmissionControlIpGroupID                    Integer32,
       sbcAdmissionControlSrdID                        Integer32,
       sbcAdmissionControlRequestType                  INTEGER,
       sbcAdmissionControlRequestDirection             INTEGER,
       sbcAdmissionControlLimit                        Integer32,
       sbcAdmissionControlLimitPerUser                 Integer32,
       sbcAdmissionControlRate                         Unsigned32,
       sbcAdmissionControlMaxBurst                     Unsigned32,
       sbcAdmissionControlName                         SnmpAdminString,
       sbcAdmissionControlReservation                  Unsigned32
     }



     sbcAdmissionControlIndex OBJECT-TYPE
       SYNTAX Unsigned32 (0..500)
       MAX-ACCESS read-only
       STATUS current
       DESCRIPTION
           ".
AC INI-Param: SBCAdmissionControl_Index"
       ::= {sbcAdmissionControlEntry 1}



     sbcAdmissionControlRowStatus OBJECT-TYPE
       SYNTAX RowStatus
       MAX-ACCESS read-create
       STATUS current
       DESCRIPTION
           "Row-Status Textual Conventions as defined in RFC 2579: Textual
Conventions for SMIv2.
AC INI-Param: N/A"
       ::= {sbcAdmissionControlEntry 2}



     sbcAdmissionControlAction OBJECT-TYPE
       SYNTAX INTEGER {
                  developmentImpending(0)

                  }
       MAX-ACCESS read-only
       STATUS current
       DESCRIPTION
           "Development Impending.
AC INI-Param: N/A"
       ::= {sbcAdmissionControlEntry 3}



     sbcAdmissionControlActionResult OBJECT-TYPE
       SYNTAX INTEGER {
                  developmentImpending(0)

                  }
       MAX-ACCESS read-only
       STATUS current
       DESCRIPTION
           "Development Impending.
AC INI-Param: N/A"
       ::= {sbcAdmissionControlEntry 4}



     sbcAdmissionControlLimitType OBJECT-TYPE
       SYNTAX INTEGER {
                  ipGroup(0)
,
                  sRD(1)

                  }
       MAX-ACCESS read-create
       STATUS current
       DESCRIPTION
           "
Access: Instant.
AC INI-Param: SBCAdmissionControl_LimitType"
       ::= {sbcAdmissionControlEntry 5}



     sbcAdmissionControlIpGroupID OBJECT-TYPE
       SYNTAX Integer32 (-1..31)
       MAX-ACCESS read-create
       STATUS current
       DESCRIPTION
           "
Access: Instant.
AC INI-Param: SBCAdmissionControl_IPGroupID"
       ::= {sbcAdmissionControlEntry 6}



     sbcAdmissionControlSrdID OBJECT-TYPE
       SYNTAX Integer32 (-1..4)
       MAX-ACCESS read-create
       STATUS current
       DESCRIPTION
           "
Access: Instant.
AC INI-Param: SBCAdmissionControl_SRDID"
       ::= {sbcAdmissionControlEntry 7}



     sbcAdmissionControlRequestType OBJECT-TYPE
       SYNTAX INTEGER {
                  all(0)
,
                  invite(1)
,
                  subscribe(2)
,
                  other(3)

                  }
       MAX-ACCESS read-create
       STATUS current
       DESCRIPTION
           "
Access: Instant.
AC INI-Param: SBCAdmissionControl_RequestType"
       ::= {sbcAdmissionControlEntry 8}



     sbcAdmissionControlRequestDirection OBJECT-TYPE
       SYNTAX INTEGER {
                  both(0)
,
                  in(1)
,
                  out(2)

                  }
       MAX-ACCESS read-create
       STATUS current
       DESCRIPTION
           "
Access: Instant.
AC INI-Param: SBCAdmissionControl_RequestDirection"
       ::= {sbcAdmissionControlEntry 9}



     sbcAdmissionControlLimit OBJECT-TYPE
       SYNTAX Integer32 (-1..2147483647)
       MAX-ACCESS read-create
       STATUS current
       DESCRIPTION
           "
Access: Instant.
AC INI-Param: SBCAdmissionControl_Limit"
       ::= {sbcAdmissionControlEntry 10}



     sbcAdmissionControlLimitPerUser OBJECT-TYPE
       SYNTAX Integer32 (-1..2147483647)
       MAX-ACCESS read-create
       STATUS current
       DESCRIPTION
           "
Access: Instant.
AC INI-Param: SBCAdmissionControl_LimitPerUser"
       ::= {sbcAdmissionControlEntry 11}



     sbcAdmissionControlRate OBJECT-TYPE
       SYNTAX Unsigned32 (0..2147483647)
       MAX-ACCESS read-create
       STATUS current
       DESCRIPTION
           "
Access: Instant.
AC INI-Param: SBCAdmissionControl_Rate"
       ::= {sbcAdmissionControlEntry 12}



     sbcAdmissionControlMaxBurst OBJECT-TYPE
       SYNTAX Unsigned32 (0..2147483647)
       MAX-ACCESS read-create
       STATUS current
       DESCRIPTION
           "
Access: Instant.
AC INI-Param: SBCAdmissionControl_MaxBurst"
       ::= {sbcAdmissionControlEntry 13}



     sbcAdmissionControlName OBJECT-TYPE
       SYNTAX SnmpAdminString (SIZE (0..20))
       MAX-ACCESS read-create
       STATUS current
       DESCRIPTION
           "Admission Control Name.
Access: Offline.
AC INI-Param: SBCAdmissionControl_AdmissionControlName"
       ::= {sbcAdmissionControlEntry 14}



     sbcAdmissionControlReservation OBJECT-TYPE
       SYNTAX Unsigned32 (0..2147483647)
       MAX-ACCESS read-create
       STATUS current
       DESCRIPTION
           "Reservation.
Access: Instant.
AC INI-Param: SBCAdmissionControl_Reservation"
       ::= {sbcAdmissionControlEntry 15}



     -- ****************************************
     -- sbcMessageManipulations table declaration
     -- ****************************************
     sbcMessageManipulationsTable OBJECT-TYPE
       SYNTAX SEQUENCE OF SbcMessageManipulationsEntry
       MAX-ACCESS not-accessible
       STATUS current
       DESCRIPTION
           "SBC Message Manipulations Table."
       ::= {sbc 26}



     -- ****************************************
     -- sbcMessageManipulations table entry
     -- ****************************************
     sbcMessageManipulationsEntry OBJECT-TYPE
       SYNTAX SbcMessageManipulationsEntry
       MAX-ACCESS not-accessible
       STATUS current
       DESCRIPTION
           ""
       INDEX {sbcMessageManipulationsIndex}
       ::= {sbcMessageManipulationsTable 1}



     -- ****************************************
     -- sbcMessageManipulations TABLE
     -- ****************************************
     SbcMessageManipulationsEntry ::= SEQUENCE {
       sbcMessageManipulationsIndex                    Unsigned32,
       sbcMessageManipulationsRowStatus                RowStatus,
       sbcMessageManipulationsAction                   INTEGER,
       sbcMessageManipulationsActionResult             INTEGER,
       sbcMessageManipulationsManipulationSetID        Unsigned32,
       sbcMessageManipulationsMessageType              SnmpAdminString,
       sbcMessageManipulationsCondition                SnmpAdminString,
       sbcMessageManipulationsActionSubject            SnmpAdminString,
       sbcMessageManipulationsActionType               INTEGER,
       sbcMessageManipulationsActionValue              SnmpAdminString,
       sbcMessageManipulationsRowRole                  INTEGER,
       sbcMessageManipulationsManipulationName         SnmpAdminString
     }



     sbcMessageManipulationsIndex OBJECT-TYPE
       SYNTAX Unsigned32 (0..500)
       MAX-ACCESS read-only
       STATUS current
       DESCRIPTION
           ".
AC INI-Param: MessageManipulations_Index"
       ::= {sbcMessageManipulationsEntry 1}



     sbcMessageManipulationsRowStatus OBJECT-TYPE
       SYNTAX RowStatus
       MAX-ACCESS read-create
       STATUS current
       DESCRIPTION
           "Row-Status Textual Conventions as defined in RFC 2579: Textual
Conventions for SMIv2.
AC INI-Param: N/A"
       ::= {sbcMessageManipulationsEntry 2}



     sbcMessageManipulationsAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {sbcMessageManipulationsEntry 3}



     sbcMessageManipulationsActionResult OBJECT-TYPE
       SYNTAX INTEGER {
                  developmentImpending(0)

                  }
       MAX-ACCESS read-only
       STATUS current
       DESCRIPTION
           "Development Impending.
AC INI-Param: N/A"
       ::= {sbcMessageManipulationsEntry 4}



     sbcMessageManipulationsManipulationSetID OBJECT-TYPE
       SYNTAX Unsigned32 (0..20)
       MAX-ACCESS read-create
       STATUS current
       DESCRIPTION
           "Manipulation Set ID.
Access: Instant.
AC INI-Param: MessageManipulations_ManSetID"
       ::= {sbcMessageManipulationsEntry 5}



     sbcMessageManipulationsMessageType OBJECT-TYPE
       SYNTAX SnmpAdminString (SIZE (0..49))
       MAX-ACCESS read-create
       STATUS current
       DESCRIPTION
           "Message type.
Access: Instant.
AC INI-Param: MessageManipulations_MessageType"
       ::= {sbcMessageManipulationsEntry 6}



     sbcMessageManipulationsCondition OBJECT-TYPE
       SYNTAX SnmpAdminString (SIZE (0..199))
       MAX-ACCESS read-create
       STATUS current
       DESCRIPTION
           "Message manipulation Condition.
Access: Instant.
AC INI-Param: MessageManipulations_Condition"
       ::= {sbcMessageManipulationsEntry 7}



     sbcMessageManipulationsActionSubject OBJECT-TYPE
       SYNTAX SnmpAdminString (SIZE (0..99))
       MAX-ACCESS read-create
       STATUS current
       DESCRIPTION
           "Message manipulation Action Subject.
Access: Instant.
AC INI-Param: MessageManipulations_ActionSubject"
       ::= {sbcMessageManipulationsEntry 8}



     sbcMessageManipulationsActionType OBJECT-TYPE
       SYNTAX INTEGER {
                  add(0)
,
                  remove(1)
,
                  modify(2)
,
                  addPrefix(3)
,
                  addSuffix(4)
,
                  removeSuffix(5)
,
                  removePrefix(6)
,
                  normalize(7)

                  }
       MAX-ACCESS read-create
       STATUS current
       DESCRIPTION
           "Message manipulation Action type.
Access: Instant.
AC INI-Param: MessageManipulations_ActionType"
       ::= {sbcMessageManipulationsEntry 9}



     sbcMessageManipulationsActionValue OBJECT-TYPE
       SYNTAX SnmpAdminString (SIZE (0..199))
       MAX-ACCESS read-create
       STATUS current
       DESCRIPTION
           "Message manipulation Action value.
Access: Instant.
AC INI-Param: MessageManipulations_ActionValue"
       ::= {sbcMessageManipulationsEntry 10}



     sbcMessageManipulationsRowRole OBJECT-TYPE
       SYNTAX INTEGER {
                  matchAndAction(0)
,
                  actionOnly(1)

                  }
       MAX-ACCESS read-create
       STATUS current
       DESCRIPTION
           "Message manipulation row rule.
Access: Instant.
AC INI-Param: MessageManipulations_RowRole"
       ::= {sbcMessageManipulationsEntry 11}



     sbcMessageManipulationsManipulationName OBJECT-TYPE
       SYNTAX SnmpAdminString (SIZE (0..20))
       MAX-ACCESS read-create
       STATUS current
       DESCRIPTION
           "Manipulation Name.
Access: Instant.
AC INI-Param: MessageManipulations_ManipulationName"
       ::= {sbcMessageManipulationsEntry 12}



     -- ****************************************
     -- sbcAlternativeRoutingReasons table declaration
     -- ****************************************
     sbcAlternativeRoutingReasonsTable OBJECT-TYPE
       SYNTAX SEQUENCE OF SbcAlternativeRoutingReasonsEntry
       MAX-ACCESS not-accessible
       STATUS current
       DESCRIPTION
           "GwApp Reasons For Alternative Routing For SBC Application(IP to IP) Table"
       ::= {sbc 27}



     -- ****************************************
     -- sbcAlternativeRoutingReasons table entry
     -- ****************************************
     sbcAlternativeRoutingReasonsEntry OBJECT-TYPE
       SYNTAX SbcAlternativeRoutingReasonsEntry
       MAX-ACCESS not-accessible
       STATUS current
       DESCRIPTION
           ""
       INDEX {sbcAlternativeRoutingReasonsIndex}
       ::= {sbcAlternativeRoutingReasonsTable 1}



     -- ****************************************
     -- sbcAlternativeRoutingReasons TABLE
     -- ****************************************
     SbcAlternativeRoutingReasonsEntry ::= SEQUENCE {
       sbcAlternativeRoutingReasonsIndex               Unsigned32,
       sbcAlternativeRoutingReasonsRowStatus           RowStatus,
       sbcAlternativeRoutingReasonsAction              INTEGER,
       sbcAlternativeRoutingReasonsActionResult        INTEGER,
       sbcAlternativeRoutingReasonsReleaseCause        INTEGER
     }



     sbcAlternativeRoutingReasonsIndex OBJECT-TYPE
       SYNTAX Unsigned32 (0..4)
       MAX-ACCESS read-only
       STATUS current
       DESCRIPTION
           ".
AC INI-Param: SBCAlternativeRoutingReasons_Index"
       ::= {sbcAlternativeRoutingReasonsEntry 1}



     sbcAlternativeRoutingReasonsRowStatus OBJECT-TYPE
       SYNTAX RowStatus
       MAX-ACCESS read-create
       STATUS current
       DESCRIPTION
           "Row-Status Textual Conventions as defined in RFC 2579: Textual
Conventions for SMIv2.
AC INI-Param: N/A"
       ::= {sbcAlternativeRoutingReasonsEntry 2}



     sbcAlternativeRoutingReasonsAction OBJECT-TYPE
       SYNTAX INTEGER {
                  developmentImpending(0)

                  }
       MAX-ACCESS read-only
       STATUS current
       DESCRIPTION
           "Development Impending.
AC INI-Param: N/A"
       ::= {sbcAlternativeRoutingReasonsEntry 3}



     sbcAlternativeRoutingReasonsActionResult OBJECT-TYPE
       SYNTAX INTEGER {
                  developmentImpending(0)

                  }
       MAX-ACCESS read-only
       STATUS current
       DESCRIPTION
           "Development Impending.
AC INI-Param: N/A"
       ::= {sbcAlternativeRoutingReasonsEntry 4}



     sbcAlternativeRoutingReasonsReleaseCause OBJECT-TYPE
       SYNTAX INTEGER {
                  wildCard4xx(4)
,
                  wildCardFivexx(5)
,
                  wildCardSixxx(6)
,
                  badRequest(400)
,
                  unauthorized(401)
,
                  paymentRequired(402)
,
                  forbidden(403)
,
                  notFound(404)
,
                  methodNotAllowed(405)
,
                  requestNotAcceptable(406)
,
                  authenticationRequired(407)
,
                  requestTimeout(408)
,
                  conflict(409)
,
                  gone(410)
,
                  requestTooLarge(413)
,
                  requestURITooLong(414)
,
                  unsupportedMedia(415)
,
                  badExtension(420)
,
                  extensionRequired(421)
,
                  sessionIntervalTooSmall(423)
,
                  unavailable(480)
,
                  transactionDoesNotExist(481)
,
                  loopDetected(482)
,
                  tooManyHops(483)
,
                  addressIncomplete(484)
,
                  ambiguous(485)
,
                  busy(486)
,
                  requestTerminated(487)
,
                  notAcceptableHere(488)
,
                  requestPending(491)
,
                  undecipherable(493)
,
                  internalError(500)
,
                  notImplemented(501)
,
                  badGateway(502)
,
                  serviceUnavailable(503)
,
                  serverTimeout(504)
,
                  versionNotSupported(505)
,
                  messageTooLarge(513)
,
                  busyEverywhere(600)
,
                  decline(603)
,
                  doesNotExistAnywhere(604)
,
                  sDPNotAcceptable(606)
,
                  iPProfileCallLimit(805)
,
                  mediaLimitsExceeded(806)

                  }
       MAX-ACCESS read-create
       STATUS current
       DESCRIPTION
           "Release Cause.
Access: Instant.
AC INI-Param: SBCAlternativeRoutingReasons_ReleaseCause"
       ::= {sbcAlternativeRoutingReasonsEntry 5}



     -- ****************************************
     -- sbcCondition table declaration
     -- ****************************************
     sbcConditionTable OBJECT-TYPE
       SYNTAX SEQUENCE OF SbcConditionEntry
       MAX-ACCESS not-accessible
       STATUS current
       DESCRIPTION
           ""
       ::= {sbc 28}



     -- ****************************************
     -- sbcCondition table entry
     -- ****************************************
     sbcConditionEntry OBJECT-TYPE
       SYNTAX SbcConditionEntry
       MAX-ACCESS not-accessible
       STATUS current
       DESCRIPTION
           ""
       INDEX {sbcConditionIndex}
       ::= {sbcConditionTable 1}



     -- ****************************************
     -- sbcCondition TABLE
     -- ****************************************
     SbcConditionEntry ::= SEQUENCE {
       sbcConditionIndex                               Unsigned32,
       sbcConditionRowStatus                           RowStatus,
       sbcConditionAction                              INTEGER,
       sbcConditionActionResult                        INTEGER,
       sbcConditionRule                                SnmpAdminString
     }



     sbcConditionIndex OBJECT-TYPE
       SYNTAX Unsigned32 (0..19)
       MAX-ACCESS read-only
       STATUS current
       DESCRIPTION
           ".
AC INI-Param: N/A"
       ::= {sbcConditionEntry 1}



     sbcConditionRowStatus OBJECT-TYPE
       SYNTAX RowStatus
       MAX-ACCESS read-create
       STATUS current
       DESCRIPTION
           "Row-Status Textual Conventions as defined in RFC 2579: Textual
Conventions for SMIv2.
AC INI-Param: N/A"
       ::= {sbcConditionEntry 2}



     sbcConditionAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {sbcConditionEntry 3}



     sbcConditionActionResult OBJECT-TYPE
       SYNTAX INTEGER {
                  developmentImpending(0)

                  }
       MAX-ACCESS read-only
       STATUS current
       DESCRIPTION
           "Development Impending.
AC INI-Param: N/A"
       ::= {sbcConditionEntry 4}



     sbcConditionRule OBJECT-TYPE
       SYNTAX SnmpAdminString (SIZE (0..298))
       MAX-ACCESS read-create
       STATUS current
       DESCRIPTION
           "Each condition is a Boolean expression, up to 298 characters
in length.
Access: Instant.
AC INI-Param: ConditionTable_Condition"
       ::= {sbcConditionEntry 5}



     -- ****************************************
     -- sbcMessagePolicy table declaration
     -- ****************************************
     sbcMessagePolicyTable OBJECT-TYPE
       SYNTAX SEQUENCE OF SbcMessagePolicyEntry
       MAX-ACCESS not-accessible
       STATUS current
       DESCRIPTION
           ""
       ::= {sbc 29}



     -- ****************************************
     -- sbcMessagePolicy table entry
     -- ****************************************
     sbcMessagePolicyEntry OBJECT-TYPE
       SYNTAX SbcMessagePolicyEntry
       MAX-ACCESS not-accessible
       STATUS current
       DESCRIPTION
           ""
       INDEX {sbcMessagePolicyIndex}
       ::= {sbcMessagePolicyTable 1}



     -- ****************************************
     -- sbcMessagePolicy TABLE
     -- ****************************************
     SbcMessagePolicyEntry ::= SEQUENCE {
       sbcMessagePolicyIndex                           Unsigned32,
       sbcMessagePolicyRowStatus                       RowStatus,
       sbcMessagePolicyAction                          INTEGER,
       sbcMessagePolicyActionResult                    INTEGER,
       sbcMessagePolicyMaxMessageLength                Integer32,
       sbcMessagePolicyMaxHeaderLength                 Integer32,
       sbcMessagePolicyMaxBodyLength                   Integer32,
       sbcMessagePolicyMaxNumHeaders                   Integer32,
       sbcMessagePolicyMaxNumBodies                    Integer32,
       sbcMessagePolicySendRejection                   INTEGER,
       sbcMessagePolicyMethodListType                  INTEGER,
       sbcMessagePolicyMethodList                      SnmpAdminString,
       sbcMessagePolicyBodyListType                    INTEGER,
       sbcMessagePolicyBodyList                        SnmpAdminString
     }



     sbcMessagePolicyIndex OBJECT-TYPE
       SYNTAX Unsigned32 (0..19)
       MAX-ACCESS read-only
       STATUS current
       DESCRIPTION
           ".
AC INI-Param: N/A"
       ::= {sbcMessagePolicyEntry 1}



     sbcMessagePolicyRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {sbcMessagePolicyEntry 2}



     sbcMessagePolicyAction OBJECT-TYPE
       SYNTAX INTEGER {
                  noAction(0)
,
                  insertLine(100)
,
                  moveRowUp(101)
,
                  moveRowDown(102)

                  }
       MAX-ACCESS read-create
       STATUS current
       DESCRIPTION
           "Development Impending.
AC INI-Param: N/A"
       ::= {sbcMessagePolicyEntry 3}



     sbcMessagePolicyActionResult OBJECT-TYPE
       SYNTAX INTEGER {
                  developmentImpending(0)

                  }
       MAX-ACCESS read-only
       STATUS current
       DESCRIPTION
           "Development Impending.
AC INI-Param: N/A"
       ::= {sbcMessagePolicyEntry 4}



     sbcMessagePolicyMaxMessageLength OBJECT-TYPE
       SYNTAX Integer32 (-1..32768)
       MAX-ACCESS read-create
       STATUS current
       DESCRIPTION
           "Message Policy Table Max Message Length.
Access: Instant.
AC INI-Param: MessagePolicy_MaxMessageLength"
       ::= {sbcMessagePolicyEntry 5}



     sbcMessagePolicyMaxHeaderLength OBJECT-TYPE
       SYNTAX Integer32 (-1..512)
       MAX-ACCESS read-create
       STATUS current
       DESCRIPTION
           "Message Policy Table Max Header Length.
Access: Instant.
AC INI-Param: MessagePolicy_MaxHeaderLength"
       ::= {sbcMessagePolicyEntry 6}



     sbcMessagePolicyMaxBodyLength OBJECT-TYPE
       SYNTAX Integer32 (-1..1024)
       MAX-ACCESS read-create
       STATUS current
       DESCRIPTION
           "Message Policy Table Max Body Length.
Access: Instant.
AC INI-Param: MessagePolicy_MaxBodyLength"
       ::= {sbcMessagePolicyEntry 7}



     sbcMessagePolicyMaxNumHeaders OBJECT-TYPE
       SYNTAX Integer32 (-1..32)
       MAX-ACCESS read-create
       STATUS current
       DESCRIPTION
           "Message Policy Table Max Num Headers.
Access: Instant.
AC INI-Param: MessagePolicy_MaxNumHeaders"
       ::= {sbcMessagePolicyEntry 8}



     sbcMessagePolicyMaxNumBodies OBJECT-TYPE
       SYNTAX Integer32 (-1..8)
       MAX-ACCESS read-create
       STATUS current
       DESCRIPTION
           "Message Policy Table Max Num Bodies.
Access: Instant.
AC INI-Param: MessagePolicy_MaxNumBodies"
       ::= {sbcMessagePolicyEntry 9}



     sbcMessagePolicySendRejection OBJECT-TYPE
       SYNTAX INTEGER {
                  sipPolicyReject(0)
,
                  sipPolicyDrop(1)

                  }
       MAX-ACCESS read-create
       STATUS current
       DESCRIPTION
           "Message Policy Table Send Rejection.
Access: Instant.
AC INI-Param: MessagePolicy_SendRejection"
       ::= {sbcMessagePolicyEntry 10}



     sbcMessagePolicyMethodListType OBJECT-TYPE
       SYNTAX INTEGER {
                  sipPolicyBlacklist(0)
,
                  sipPolicyWhitelist(1)

                  }
       MAX-ACCESS read-create
       STATUS current
       DESCRIPTION
           "Message Policy Table Method List.
Access: Instant.
AC INI-Param: MessagePolicy_MethodListType"
       ::= {sbcMessagePolicyEntry 11}



     sbcMessagePolicyMethodList OBJECT-TYPE
       SYNTAX SnmpAdminString (SIZE (0..255))
       MAX-ACCESS read-create
       STATUS current
       DESCRIPTION
           "Message Policy Table Method List Type.
Access: Instant.
AC INI-Param: MessagePolicy_MethodList"
       ::= {sbcMessagePolicyEntry 12}



     sbcMessagePolicyBodyListType OBJECT-TYPE
       SYNTAX INTEGER {
                  sipPolicyBlacklist(0)
,
                  sipPolicyWhitelist(1)

                  }
       MAX-ACCESS read-create
       STATUS current
       DESCRIPTION
           "Message Policy Table Body List Type.
Access: Instant.
AC INI-Param: MessagePolicy_BodyListType"
       ::= {sbcMessagePolicyEntry 13}



     sbcMessagePolicyBodyList OBJECT-TYPE
       SYNTAX SnmpAdminString (SIZE (0..255))
       MAX-ACCESS read-create
       STATUS current
       DESCRIPTION
           "Message Policy Table Body List.
Access: Instant.
AC INI-Param: MessagePolicy_BodyList"
       ::= {sbcMessagePolicyEntry 14}



     gwIPv6 OBJECT IDENTIFIER ::= {common 25}


     gwIPv6GwAppDualIPStackSDPMethod OBJECT-TYPE
       SYNTAX INTEGER {
                  nONE(0)
,
                  aNAT(1)

                  }
       MAX-ACCESS read-write
       STATUS obsolete
       DESCRIPTION
           "0. Always offer a single (preferrable) media IP address.
1. ANAT - Construct offer using ANAT semantics (RFC 4091 &
RFC 4092)
.
Access: Instant.
AC INI-Param: DUALIPSTACKSDPMETHOD"
       ::= {gwIPv6 1}



     gwIPv6GwAppPrimaryMediaInterface OBJECT-TYPE
       SYNTAX Integer32 (-1..32)
       MAX-ACCESS read-write
       STATUS obsolete
       DESCRIPTION
           "Primary media interface to be used within SDP.
Access: Instant.
AC INI-Param: PRIMARYMEDIAINTERFACE"
       ::= {gwIPv6 2}



     gwIPv6GwAppSecondaryMediaInterface OBJECT-TYPE
       SYNTAX Integer32 (-1..32)
       MAX-ACCESS read-write
       STATUS obsolete
       DESCRIPTION
           "Secondary media interface to be used within SDP.
Access: Instant.
AC INI-Param: SECONDARYMEDIAINTERFACE"
       ::= {gwIPv6 3}



     gwIPv6MediaIPVersionPreference OBJECT-TYPE
       SYNTAX INTEGER {
                  onlyIPv4(0)
,
                  onlyIPv6(1)
,
                  preferIPv4(2)
,
                  preferIPv6(3)

                  }
       MAX-ACCESS read-write
       STATUS current
       DESCRIPTION
           "Select the preferred Media IP version.
Access: Instant.
AC INI-Param: MEDIAIPVERSIONPREFERENCE"
       ::= {gwIPv6 4}



     srdSettings OBJECT IDENTIFIER ::= {common 26}


     -- ****************************************
     -- srd table declaration
     -- ****************************************
     srdTable OBJECT-TYPE
       SYNTAX SEQUENCE OF SrdEntry
       MAX-ACCESS not-accessible
       STATUS current
       DESCRIPTION
           "GwApp Signaling Routing Domain (SRD) Table"
       ::= {srdSettings 21}



     -- ****************************************
     -- srd table entry
     -- ****************************************
     srdEntry OBJECT-TYPE
       SYNTAX SrdEntry
       MAX-ACCESS not-accessible
       STATUS current
       DESCRIPTION
           ""
       INDEX {srdIndex}
       ::= {srdTable 1}



     -- ****************************************
     -- srd TABLE
     -- ****************************************
     SrdEntry ::= SEQUENCE {
       srdIndex                                        Unsigned32,
       srdRowStatus                                    RowStatus,
       srdAction                                       INTEGER,
       srdActionResult                                 INTEGER,
       srdName                                         SnmpAdminString,
       srdMediaRealm                                   RowPointer,
       srdIntraSRDMediaAnchoring                       INTEGER,
       srdBlockUnRegUsers                              INTEGER,
       srdMaxNumOfRegUsers                             Integer32,
       srdSharingPolicy                                INTEGER,
       srdSBCOperationMode                             INTEGER
     }



     srdIndex OBJECT-TYPE
       SYNTAX Unsigned32 (0..200)
       MAX-ACCESS read-only
       STATUS current
       DESCRIPTION
           ".
AC INI-Param: SRD_Index"
       ::= {srdEntry 1}



     srdRowStatus OBJECT-TYPE
       SYNTAX RowStatus
       MAX-ACCESS read-create
       STATUS current
       DESCRIPTION
           "Row-Status Textual Conventions as defined in RFC 2579: Textual
Conventions for SMIv2.
AC INI-Param: N/A"
       ::= {srdEntry 2}



     srdAction OBJECT-TYPE
       SYNTAX INTEGER {
                  developmentImpending(0)

                  }
       MAX-ACCESS read-only
       STATUS current
       DESCRIPTION
           "Development Impending.
AC INI-Param: N/A"
       ::= {srdEntry 3}



     srdActionResult OBJECT-TYPE
       SYNTAX INTEGER {
                  developmentImpending(0)

                  }
       MAX-ACCESS read-only
       STATUS current
       DESCRIPTION
           "Development Impending.
AC INI-Param: N/A"
       ::= {srdEntry 4}



     srdName OBJECT-TYPE
       SYNTAX SnmpAdminString (SIZE (0..20))
       MAX-ACCESS read-create
       STATUS current
       DESCRIPTION
           "GwApp Signaling Routing Domain name.
Access: Instant.
AC INI-Param: SRD_Name"
       ::= {srdEntry 5}



     srdMediaRealm OBJECT-TYPE
       SYNTAX RowPointer
       MAX-ACCESS read-create
       STATUS current
       DESCRIPTION
           "MediaRealm Name.
Access: Instant.
AC INI-Param: SRD_MediaRealm"
       ::= {srdEntry 6}



     srdIntraSRDMediaAnchoring OBJECT-TYPE
       SYNTAX INTEGER {
                  anchorMedia(0)
,
                  dontAnchorMedia(1)

                  }
       MAX-ACCESS read-create
       STATUS current
       DESCRIPTION
           "Internal SRD Media Anchoring.
Access: Offline.
AC INI-Param: SRD_IntraSRDMediaAnchoring"
       ::= {srdEntry 7}



     srdBlockUnRegUsers OBJECT-TYPE
       SYNTAX INTEGER {
                  no(0)
,
                  yes(1)

                  }
       MAX-ACCESS read-create
       STATUS current
       DESCRIPTION
           "Block Calls From Unregistered User.
Access: Offline.
AC INI-Param: SRD_BlockUnRegUsers"
       ::= {srdEntry 8}



     srdMaxNumOfRegUsers OBJECT-TYPE
       SYNTAX Integer32 (-1..3000)
       MAX-ACCESS read-create
       STATUS current
       DESCRIPTION
           "Max Number Of Registered Users.
MP1xx - 25
M1K - 200
M2K- 250
M3K - 3000.
Access: Offline.
AC INI-Param: SRD_MaxNumOfRegUsers"
       ::= {srdEntry 9}



     srdSharingPolicy OBJECT-TYPE
       SYNTAX INTEGER {
                  shared(0)
,
                  isolated(1)

                  }
       MAX-ACCESS read-create
       STATUS current
       DESCRIPTION
           "Defines the SRD Sharing Policy.
Access: Offline.
AC INI-Param: SRD_SharingPolicy"
       ::= {srdEntry 10}



     srdSBCOperationMode OBJECT-TYPE
       SYNTAX INTEGER {
                  b2BUA(0)
,
                  callStatefulProxy(1)
,
                  microsoftServer(2)

                  }
       MAX-ACCESS read-create
       STATUS current
       DESCRIPTION
           "For Call Stateful Proxy, the SBC uses the same Call-Id and From
tag for both sides of calls and dialogs. For B2BUA it changes
them.
Access: Offline.
AC INI-Param: SRD_SBCOperationMode"
       ::= {srdEntry 11}



     sipInterfaceSettings OBJECT IDENTIFIER ::= {common 27}


     -- ****************************************
     -- sipInterface table declaration
     -- ****************************************
     sipInterfaceTable OBJECT-TYPE
       SYNTAX SEQUENCE OF SipInterfaceEntry
       MAX-ACCESS not-accessible
       STATUS current
       DESCRIPTION
           "GwApp SIP Interface Table"
       ::= {sipInterfaceSettings 21}



     -- ****************************************
     -- sipInterface table entry
     -- ****************************************
     sipInterfaceEntry OBJECT-TYPE
       SYNTAX SipInterfaceEntry
       MAX-ACCESS not-accessible
       STATUS current
       DESCRIPTION
           ""
       INDEX {sipInterfaceIndex}
       ::= {sipInterfaceTable 1}



     -- ****************************************
     -- sipInterface TABLE
     -- ****************************************
     SipInterfaceEntry ::= SEQUENCE {
       sipInterfaceIndex                               Unsigned32,
       sipInterfaceRowStatus                           RowStatus,
       sipInterfaceAction                              INTEGER,
       sipInterfaceActionResult                        INTEGER,
       sipInterfaceNetworkInterface                    RowPointer,
       sipInterfaceApplicationType                     INTEGER,
       sipInterfaceUDPPort                             Unsigned32,
       sipInterfaceTCPPort                             Unsigned32,
       sipInterfaceTLSPort                             Unsigned32,
       sipInterfaceSRD                                 Unsigned32,
       sipInterfaceInterfaceName                       SnmpAdminString,
       sipInterfaceClassificationFailureResponseType   Unsigned32
     }



     sipInterfaceIndex OBJECT-TYPE
       SYNTAX Unsigned32 (0..200)
       MAX-ACCESS read-only
       STATUS current
       DESCRIPTION
           ".
AC INI-Param: SIPInterface_Index"
       ::= {sipInterfaceEntry 1}



     sipInterfaceRowStatus OBJECT-TYPE
       SYNTAX RowStatus
       MAX-ACCESS read-create
       STATUS current
       DESCRIPTION
           "Row-Status Textual Conventions as defined in RFC 2579: Textual
Conventions for SMIv2.
AC INI-Param: N/A"
       ::= {sipInterfaceEntry 2}



     sipInterfaceAction OBJECT-TYPE
       SYNTAX INTEGER {
                  developmentImpending(0)

                  }
       MAX-ACCESS read-only
       STATUS current
       DESCRIPTION
           "Development Impending.
AC INI-Param: N/A"
       ::= {sipInterfaceEntry 3}



     sipInterfaceActionResult OBJECT-TYPE
       SYNTAX INTEGER {
                  developmentImpending(0)

                  }
       MAX-ACCESS read-only
       STATUS current
       DESCRIPTION
           "Development Impending.
AC INI-Param: N/A"
       ::= {sipInterfaceEntry 4}



     sipInterfaceNetworkInterface OBJECT-TYPE
       SYNTAX RowPointer
       MAX-ACCESS read-create
       STATUS current
       DESCRIPTION
           "Network Interface.
Access: Instant.
AC INI-Param: SIPInterface_NetworkInterface"
       ::= {sipInterfaceEntry 5}



     sipInterfaceApplicationType OBJECT-TYPE
       SYNTAX INTEGER {
                  gwIP2IP(0)
,
                  sas(1)
,
                  sbc(2)

                  }
       MAX-ACCESS read-create
       STATUS current
       DESCRIPTION
           "Application Type.
Access: Instant.
AC INI-Param: SIPInterface_ApplicationType"
       ::= {sipInterfaceEntry 6}



     sipInterfaceUDPPort OBJECT-TYPE
       SYNTAX Unsigned32 (0..65534)
       MAX-ACCESS read-create
       STATUS current
       DESCRIPTION
           "UDP Port number.
Access: Instant.
AC INI-Param: SIPInterface_UDPPort"
       ::= {sipInterfaceEntry 7}



     sipInterfaceTCPPort OBJECT-TYPE
       SYNTAX Unsigned32 (0..65534)
       MAX-ACCESS read-create
       STATUS current
       DESCRIPTION
           "TCP Port number.
Access: Instant.
AC INI-Param: SIPInterface_TCPPort"
       ::= {sipInterfaceEntry 8}



     sipInterfaceTLSPort OBJECT-TYPE
       SYNTAX Unsigned32 (0..65534)
       MAX-ACCESS read-create
       STATUS current
       DESCRIPTION
           "TLS Port number.
Access: Instant.
AC INI-Param: SIPInterface_TLSPort"
       ::= {sipInterfaceEntry 9}



     sipInterfaceSRD OBJECT-TYPE
       SYNTAX Unsigned32 (0..31)
       MAX-ACCESS read-create
       STATUS current
       DESCRIPTION
           "
Access: Instant.
AC INI-Param: SIPInterface_SRD"
       ::= {sipInterfaceEntry 10}



     sipInterfaceInterfaceName OBJECT-TYPE
       SYNTAX SnmpAdminString (SIZE (0..20))
       MAX-ACCESS read-create
       STATUS current
       DESCRIPTION
           "Interface Name.
Access: Instant.
AC INI-Param: SIPInterface_InterfaceName"
       ::= {sipInterfaceEntry 11}



     sipInterfaceClassificationFailureResponseType OBJECT-TYPE
       SYNTAX Unsigned32 (0..699)
       MAX-ACCESS read-create
       STATUS current
       DESCRIPTION
           "Classification Failure Response Type - the response type that
will be returned after classification fails. The value 0 means
ignore - response will not be sent.
Access: Instant.
AC INI-Param: SIPInterface_ClassificationFailureResponseType"
       ::= {sipInterfaceEntry 12}



     bri OBJECT IDENTIFIER ::= {common 28}


     -- ****************************************
     -- isdnSuppServ table declaration
     -- ****************************************
     isdnSuppServTable OBJECT-TYPE
       SYNTAX SEQUENCE OF IsdnSuppServEntry
       MAX-ACCESS not-accessible
       STATUS current
       DESCRIPTION
           "GwApp ISDN Supplementary Services Table"
       ::= {bri 21}



     -- ****************************************
     -- isdnSuppServ table entry
     -- ****************************************
     isdnSuppServEntry OBJECT-TYPE
       SYNTAX IsdnSuppServEntry
       MAX-ACCESS not-accessible
       STATUS current
       DESCRIPTION
           ""
       INDEX {isdnSuppServIndex}
       ::= {isdnSuppServTable 1}



     -- ****************************************
     -- isdnSuppServ TABLE
     -- ****************************************
     IsdnSuppServEntry ::= SEQUENCE {
       isdnSuppServIndex                               Unsigned32,
       isdnSuppServRowStatus                           RowStatus,
       isdnSuppServAction                              INTEGER,
       isdnSuppServActionResult                        INTEGER,
       isdnSuppServPhoneNumber                         SnmpAdminString,
       isdnSuppServModule                              Integer32,
       isdnSuppServPort                                Integer32,
       isdnSuppServUserId                              SnmpAdminString,
       isdnSuppServUserPassword                        SnmpAdminString,
       isdnSuppServCallerID                            SnmpAdminString,
       isdnSuppServIsPresentationRestricted            INTEGER,
       isdnSuppServIsCallerIDEnabled                   INTEGER
     }



     isdnSuppServIndex OBJECT-TYPE
       SYNTAX Unsigned32 (0..159)
       MAX-ACCESS read-only
       STATUS current
       DESCRIPTION
           ".
AC INI-Param: ISDNSuppServ_Index"
       ::= {isdnSuppServEntry 1}



     isdnSuppServRowStatus OBJECT-TYPE
       SYNTAX RowStatus
       MAX-ACCESS read-create
       STATUS current
       DESCRIPTION
           "Row-Status Textual Conventions as defined in RFC 2579: Textual
Conventions for SMIv2.
AC INI-Param: ISDNSuppServ_RowStatus"
       ::= {isdnSuppServEntry 2}



     isdnSuppServAction OBJECT-TYPE
       SYNTAX INTEGER {
                  developmentImpending(0)

                  }
       MAX-ACCESS read-only
       STATUS current
       DESCRIPTION
           "Development Impending.
AC INI-Param: ISDNSuppServ_Action"
       ::= {isdnSuppServEntry 3}



     isdnSuppServActionResult OBJECT-TYPE
       SYNTAX INTEGER {
                  developmentImpending(0)

                  }
       MAX-ACCESS read-only
       STATUS current
       DESCRIPTION
           "Development Impending.
AC INI-Param: ISDNSuppServ_ActionRes"
       ::= {isdnSuppServEntry 4}



     isdnSuppServPhoneNumber OBJECT-TYPE
       SYNTAX SnmpAdminString (SIZE (0..25))
       MAX-ACCESS read-create
       STATUS current
       DESCRIPTION
           "GwApp ISDN Supplementary Services Table.
Access: Offline.
AC INI-Param: ISDNSuppServ_PhoneNumber"
       ::= {isdnSuppServEntry 5}



     isdnSuppServModule OBJECT-TYPE
       SYNTAX Integer32 (-2147483647..2147483647)
       MAX-ACCESS read-create
       STATUS current
       DESCRIPTION
           "GwApp ISDN Supplementary Services Table.
Access: Offline.
AC INI-Param: ISDNSuppServ_Module"
       ::= {isdnSuppServEntry 6}



     isdnSuppServPort OBJECT-TYPE
       SYNTAX Integer32 (-2147483647..2147483647)
       MAX-ACCESS read-create
       STATUS current
       DESCRIPTION
           "GwApp ISDN Supplementary Services Table.
Access: Offline.
AC INI-Param: ISDNSuppServ_Port"
       ::= {isdnSuppServEntry 7}



     isdnSuppServUserId OBJECT-TYPE
       SYNTAX SnmpAdminString (SIZE (0..50))
       MAX-ACCESS read-create
       STATUS current
       DESCRIPTION
           "GwApp ISDN Supplementary Services Table.
Access: Offline.
AC INI-Param: ISDNSuppServ_UserId"
       ::= {isdnSuppServEntry 8}



     isdnSuppServUserPassword OBJECT-TYPE
       SYNTAX SnmpAdminString (SIZE (0..50))
       MAX-ACCESS read-create
       STATUS current
       DESCRIPTION
           "GwApp ISDN Supplementary Services Table.
Access: Offline.
AC INI-Param: ISDNSuppServ_UserPassword"
       ::= {isdnSuppServEntry 9}



     isdnSuppServCallerID OBJECT-TYPE
       SYNTAX SnmpAdminString (SIZE (0..32))
       MAX-ACCESS read-create
       STATUS current
       DESCRIPTION
           "GwApp ISDN Supplementary Services Table.
Access: Offline.
AC INI-Param: ISDNSuppServ_CallerID"
       ::= {isdnSuppServEntry 10}



     isdnSuppServIsPresentationRestricted OBJECT-TYPE
       SYNTAX INTEGER {
                  notConfigured(255)
,
                  allowed(0)
,
                  restricted(1)

                  }
       MAX-ACCESS read-create
       STATUS current
       DESCRIPTION
           "GwApp ISDN Supplementary Services Table.
Access: Offline.
AC INI-Param: ISDNSuppServ_IsPresentationRestricted"
       ::= {isdnSuppServEntry 11}



     isdnSuppServIsCallerIDEnabled OBJECT-TYPE
       SYNTAX INTEGER {
                  notConfigured(255)
,
                  disabled(0)
,
                  enabled(1)

                  }
       MAX-ACCESS read-create
       STATUS current
       DESCRIPTION
           "GwApp ISDN Supplementary Services Table.
Access: Offline.
AC INI-Param: ISDNSuppServ_IsCallerIDEnabled"
       ::= {isdnSuppServEntry 12}



     sbcRegistration OBJECT IDENTIFIER ::= {common 29}


     sbcRegistrationUserTime OBJECT-TYPE
       SYNTAX Unsigned32 (0..2000000)
       MAX-ACCESS read-write
       STATUS current
       DESCRIPTION
           "Expires value SBC responds to user with. Used when server is
offline or when the user is behind NAT. Otherwise expires is
defined by the server. When the parameter is set to 0, the
SBC does not change the Expires value, received in the user’s
REGISTER request.
Access: Instant.
AC INI-Param: SBCUSERREGISTRATIONTIME"
       ::= {sbcRegistration 1}



     sbcRegistrationSurvivabilityTime OBJECT-TYPE
       SYNTAX Unsigned32 (0..2000000)
       MAX-ACCESS read-write
       STATUS current
       DESCRIPTION
           "This parameter defines the duration of the periodic registrations
between the user and the SBC, when the SBC is in survivability
state (the REGISTER request cannot be forwarded to
proxy, and is terminated by the SBC).
When SBCSurvivabilityRegistrationTime is set to 0, the SBC
will use the value of the parameter SBCUserRegistrationTime
for the SBC response.
Access: Instant.
AC INI-Param: SBCSURVIVABILITYREGISTRATIONTIME"
       ::= {sbcRegistration 2}



     sbcRegistrationProxyTime OBJECT-TYPE
       SYNTAX Unsigned32 (0..2000000)
       MAX-ACCESS read-write
       STATUS current
       DESCRIPTION
           "This parameter defines the duration (in seconds)  in which the
user is registered in the proxy DB, after the REGISTER was
forwarded by SBC. When the parameter is set to 0, the SBC
will send the Expires value as received from user to the proxy.
Access: Instant.
AC INI-Param: SBCPROXYREGISTRATIONTIME"
       ::= {sbcRegistration 3}



     leastCostRouting OBJECT IDENTIFIER ::= {common 30}


     -- ****************************************
     -- costGroup table declaration
     -- ****************************************
     costGroupTable OBJECT-TYPE
       SYNTAX SEQUENCE OF CostGroupEntry
       MAX-ACCESS not-accessible
       STATUS current
       DESCRIPTION
           "GwApp Cost Group Table"
       ::= {leastCostRouting 21}



     -- ****************************************
     -- costGroup table entry
     -- ****************************************
     costGroupEntry OBJECT-TYPE
       SYNTAX CostGroupEntry
       MAX-ACCESS not-accessible
       STATUS current
       DESCRIPTION
           ""
       INDEX {costGroupIndex}
       ::= {costGroupTable 1}



     -- ****************************************
     -- costGroup TABLE
     -- ****************************************
     CostGroupEntry ::= SEQUENCE {
       costGroupIndex                                  Unsigned32,
       costGroupRowStatus                              RowStatus,
       costGroupAction                                 INTEGER,
       costGroupActionResult                           INTEGER,
       costGroupName                                   SnmpAdminString,
       costGroupDefaultConnectionCost                  Unsigned32,
       costGroupDefaultMinuteCost                      Unsigned32
     }



     costGroupIndex OBJECT-TYPE
       SYNTAX Unsigned32 (0..9)
       MAX-ACCESS read-only
       STATUS current
       DESCRIPTION
           "The index of the cost group.
AC INI-Param: CostGroupTable_Index"
       ::= {costGroupEntry 1}



     costGroupRowStatus OBJECT-TYPE
       SYNTAX RowStatus
       MAX-ACCESS read-create
       STATUS current
       DESCRIPTION
           "Row-Status Textual Conventions as defined in RFC 2579: Textual
Conventions for SMIv2.
AC INI-Param: CostGroupTable_RowStatus"
       ::= {costGroupEntry 2}



     costGroupAction OBJECT-TYPE
       SYNTAX INTEGER {
                  developmentImpending(0)

                  }
       MAX-ACCESS read-only
       STATUS current
       DESCRIPTION
           "Development Impending.
AC INI-Param: CostGroupTable_Action"
       ::= {costGroupEntry 3}



     costGroupActionResult OBJECT-TYPE
       SYNTAX INTEGER {
                  developmentImpending(0)

                  }
       MAX-ACCESS read-only
       STATUS current
       DESCRIPTION
           "Development Impending.
AC INI-Param: CostGroupTable_ActionRes"
       ::= {costGroupEntry 4}



     costGroupName OBJECT-TYPE
       SYNTAX SnmpAdminString (SIZE (0..29))
       MAX-ACCESS read-create
       STATUS current
       DESCRIPTION
           "Cost Group Name.
Access: Instant.
AC INI-Param: CostGroupTable_CostGroupName"
       ::= {costGroupEntry 5}



     costGroupDefaultConnectionCost OBJECT-TYPE
       SYNTAX Unsigned32 (0..30000)
       MAX-ACCESS read-create
       STATUS current
       DESCRIPTION
           "The default connection cost for calls in this cost group. 
Used if not in a timeband.
Access: Instant.
AC INI-Param: CostGroupTable_DefaultConnectionCost"
       ::= {costGroupEntry 6}



     costGroupDefaultMinuteCost OBJECT-TYPE
       SYNTAX Unsigned32 (0..30000)
       MAX-ACCESS read-create
       STATUS current
       DESCRIPTION
           "The default cost per minute for calls in this cost group. 
 Used if not in a timeband.
Access: Instant.
AC INI-Param: CostGroupTable_DefaultMinuteCost"
       ::= {costGroupEntry 7}



     -- ****************************************
     -- timeband table declaration
     -- ****************************************
     timebandTable OBJECT-TYPE
       SYNTAX SEQUENCE OF TimebandEntry
       MAX-ACCESS not-accessible
       STATUS current
       DESCRIPTION
           "GwApp time band Table"
       ::= {leastCostRouting 22}



     -- ****************************************
     -- timeband table entry
     -- ****************************************
     timebandEntry OBJECT-TYPE
       SYNTAX TimebandEntry
       MAX-ACCESS not-accessible
       STATUS current
       DESCRIPTION
           ""
       INDEX {timebandCostGroupIndex,timebandIndex}
       ::= {timebandTable 1}



     -- ****************************************
     -- timeband TABLE
     -- ****************************************
     TimebandEntry ::= SEQUENCE {
       timebandCostGroupIndex                          Unsigned32,
       timebandIndex                                   Unsigned32,
       timebandRowStatus                               RowStatus,
       timebandAction                                  INTEGER,
       timebandActionResult                            INTEGER,
       timebandStartTime                               SnmpAdminString,
       timebandEndTime                                 SnmpAdminString,
       timebandConnectionCost                          Unsigned32,
       timebandMinuteCost                              Unsigned32
     }



     timebandCostGroupIndex OBJECT-TYPE
       SYNTAX Unsigned32
       MAX-ACCESS not-accessible
       STATUS current
       DESCRIPTION
           "The cost group index this timeband is associated with.
AC INI-Param: CostGroupTimebands_CostGroup"
       ::= {timebandEntry 1}



     timebandIndex OBJECT-TYPE
       SYNTAX Unsigned32 (0..69)
       MAX-ACCESS not-accessible
       STATUS current
       DESCRIPTION
           "The index of the timeband.
AC INI-Param: CostGroupTimebands_TimebandIndex"
       ::= {timebandEntry 2}



     timebandRowStatus OBJECT-TYPE
       SYNTAX RowStatus
       MAX-ACCESS read-create
       STATUS current
       DESCRIPTION
           "Row-Status Textual Conventions as defined in RFC 2579: Textual
Conventions for SMIv2.
AC INI-Param: CostGroupTimebands_RowStatus"
       ::= {timebandEntry 3}



     timebandAction OBJECT-TYPE
       SYNTAX INTEGER {
                  developmentImpending(0)

                  }
       MAX-ACCESS read-only
       STATUS current
       DESCRIPTION
           "Development Impending.
AC INI-Param: CostGroupTimebands_Action"
       ::= {timebandEntry 4}



     timebandActionResult OBJECT-TYPE
       SYNTAX INTEGER {
                  developmentImpending(0)

                  }
       MAX-ACCESS read-only
       STATUS current
       DESCRIPTION
           "Development Impending.
AC INI-Param: CostGroupTimebands_ActionRes"
       ::= {timebandEntry 5}



     timebandStartTime OBJECT-TYPE
       SYNTAX SnmpAdminString (SIZE (0..13))
       MAX-ACCESS read-create
       STATUS current
       DESCRIPTION
           "The start time and day of the time band. 
For example: FRI:08:00.
Access: Instant.
AC INI-Param: CostGroupTimebands_StartTime"
       ::= {timebandEntry 6}



     timebandEndTime OBJECT-TYPE
       SYNTAX SnmpAdminString (SIZE (0..13))
       MAX-ACCESS read-create
       STATUS current
       DESCRIPTION
           "The end time and day of the time band. 
For example: FRI:08:00.
Access: Instant.
AC INI-Param: CostGroupTimebands_EndTime"
       ::= {timebandEntry 7}



     timebandConnectionCost OBJECT-TYPE
       SYNTAX Unsigned32 (0..30000)
       MAX-ACCESS read-create
       STATUS current
       DESCRIPTION
           "The cost per minute for calls within this timeband.
Access: Instant.
AC INI-Param: CostGroupTimebands_ConnectionCost"
       ::= {timebandEntry 8}



     timebandMinuteCost OBJECT-TYPE
       SYNTAX Unsigned32 (0..30000)
       MAX-ACCESS read-create
       STATUS current
       DESCRIPTION
           "The cost per minute for calls within this timeband.
Access: Instant.
AC INI-Param: CostGroupTimebands_MinuteCost"
       ::= {timebandEntry 9}



     -- ****************************************
     -- routingRuleGroups table declaration
     -- ****************************************
     routingRuleGroupsTable OBJECT-TYPE
       SYNTAX SEQUENCE OF RoutingRuleGroupsEntry
       MAX-ACCESS not-accessible
       STATUS current
       DESCRIPTION
           "GwApp Routing Rule Groups"
       ::= {leastCostRouting 23}



     -- ****************************************
     -- routingRuleGroups table entry
     -- ****************************************
     routingRuleGroupsEntry OBJECT-TYPE
       SYNTAX RoutingRuleGroupsEntry
       MAX-ACCESS not-accessible
       STATUS current
       DESCRIPTION
           ""
       INDEX {routingRuleGroupsIndex}
       ::= {routingRuleGroupsTable 1}



     -- ****************************************
     -- routingRuleGroups TABLE
     -- ****************************************
     RoutingRuleGroupsEntry ::= SEQUENCE {
       routingRuleGroupsIndex                          Unsigned32,
       routingRuleGroupsRowStatus                      RowStatus,
       routingRuleGroupsAction                         INTEGER,
       routingRuleGroupsActionResult                   INTEGER,
       routingRuleGroupsLCREnable                      INTEGER,
       routingRuleGroupsLCRAverageCallLength           Unsigned32,
       routingRuleGroupsLCRDefaultCost                 INTEGER
     }



     routingRuleGroupsIndex OBJECT-TYPE
       SYNTAX Unsigned32 (0..0)
       MAX-ACCESS read-only
       STATUS current
       DESCRIPTION
           "The index of the cost group.
AC INI-Param: RoutingRuleGroups_Index"
       ::= {routingRuleGroupsEntry 1}



     routingRuleGroupsRowStatus OBJECT-TYPE
       SYNTAX RowStatus
       MAX-ACCESS read-create
       STATUS current
       DESCRIPTION
           "Row-Status Textual Conventions as defined in RFC 2579: Textual
Conventions for SMIv2.
AC INI-Param: RoutingRuleGroups_RowStatus"
       ::= {routingRuleGroupsEntry 2}



     routingRuleGroupsAction OBJECT-TYPE
       SYNTAX INTEGER {
                  developmentImpending(0)

                  }
       MAX-ACCESS read-only
       STATUS current
       DESCRIPTION
           "Development Impending.
AC INI-Param: RoutingRuleGroups_Action"
       ::= {routingRuleGroupsEntry 3}



     routingRuleGroupsActionResult OBJECT-TYPE
       SYNTAX INTEGER {
                  developmentImpending(0)

                  }
       MAX-ACCESS read-only
       STATUS current
       DESCRIPTION
           "Development Impending.
AC INI-Param: RoutingRuleGroups_ActionRes"
       ::= {routingRuleGroupsEntry 4}



     routingRuleGroupsLCREnable OBJECT-TYPE
       SYNTAX INTEGER {
                  notConfigured(-1)
,
                  disabled(0)
,
                  enabled(1)

                  }
       MAX-ACCESS read-create
       STATUS current
       DESCRIPTION
           "Enables the Least Cost Routing feature.
Access: Instant.
AC INI-Param: RoutingRuleGroups_LCREnable"
       ::= {routingRuleGroupsEntry 5}



     routingRuleGroupsLCRAverageCallLength OBJECT-TYPE
       SYNTAX Unsigned32 (0..30000)
       MAX-ACCESS read-create
       STATUS current
       DESCRIPTION
           "The average call length used for Least Cost Routing calculations.
Access: Instant.
AC INI-Param: RoutingRuleGroups_LCRAverageCallLength"
       ::= {routingRuleGroupsEntry 6}



     routingRuleGroupsLCRDefaultCost OBJECT-TYPE
       SYNTAX INTEGER {
                  notConfigured(-1)
,
                  lowestCost(0)
,
                  highestCost(1)

                  }
       MAX-ACCESS read-create
       STATUS current
       DESCRIPTION
           "The cost used for calls not with a cost group, specified as
highest or lowest.
Access: Instant.
AC INI-Param: RoutingRuleGroups_LCRDefaultCost"
       ::= {routingRuleGroupsEntry 7}



     testCallSettings OBJECT IDENTIFIER ::= {common 31}


     -- ****************************************
     -- testCall table declaration
     -- ****************************************
     testCallTable OBJECT-TYPE
       SYNTAX SEQUENCE OF TestCallEntry
       MAX-ACCESS not-accessible
       STATUS current
       DESCRIPTION
           "GwApp Test Call Table"
       ::= {testCallSettings 21}



     -- ****************************************
     -- testCall table entry
     -- ****************************************
     testCallEntry OBJECT-TYPE
       SYNTAX TestCallEntry
       MAX-ACCESS not-accessible
       STATUS current
       DESCRIPTION
           ""
       INDEX {testCallIndex}
       ::= {testCallTable 1}



     -- ****************************************
     -- testCall TABLE
     -- ****************************************
     TestCallEntry ::= SEQUENCE {
       testCallIndex                                   Unsigned32,
       testCallRowStatus                               RowStatus,
       testCallAction                                  INTEGER,
       testCallActionResult                            INTEGER,
       testCallURI                                     SnmpAdminString,
       testCallCalledURI                               SnmpAdminString,
       testCallRouteBy                                 INTEGER,
       testCallIPGroupID                               Integer32,
       testCallDestAddress                             SnmpAdminString,
       testCallDestTransportType                       INTEGER,
       testCallSRD                                     Integer32,
       testCallApplicationType                         INTEGER,
       testCallAutoRegister                            Unsigned32,
       testCallUserName                                SnmpAdminString,
       testCallPassword                                SnmpAdminString,
       testCallCallParty                               INTEGER,
       testCallMaxChannels                             Unsigned32,
       testCallCallDuration                            Integer32,
       testCallCallsPerSecond                          Unsigned32,
       testCallTestMode                                INTEGER,
       testCallTestDuration                            Unsigned32,
       testCallPlay                                    INTEGER,
       testCallScheduleInterval                        Unsigned32,
       testCallActiveCalls                             Unsigned32,
       testCallCallAttempts                            Unsigned32,
       testCallEstablishedCalls                        Unsigned32,
       testCallFailedAttempts                          Unsigned32,
       testCallRemoteDisconnects                       Unsigned32,
       testCallAverageCPS                              SnmpAdminString,
       testCallElapsedTime                             SnmpAdminString,
       testCallTestSummary                             SnmpAdminString,
       testCallTestStatus                              SnmpAdminString
     }



     testCallIndex OBJECT-TYPE
       SYNTAX Unsigned32 (0..4)
       MAX-ACCESS read-only
       STATUS current
       DESCRIPTION
           "The index of the cost group.
AC INI-Param: Test_Call_Index"
       ::= {testCallEntry 1}



     testCallRowStatus OBJECT-TYPE
       SYNTAX RowStatus
       MAX-ACCESS read-create
       STATUS current
       DESCRIPTION
           "Row-Status Textual Conventions as defined in RFC 2579: Textual
Conventions for SMIv2.
AC INI-Param: Test_Call_RowStatus"
       ::= {testCallEntry 2}



     testCallAction OBJECT-TYPE
       SYNTAX INTEGER {
                  none(0)
,
                  dial(1)
,
                  dropCall(2)
,
                  restart(3)

                  }
       MAX-ACCESS read-create
       STATUS current
       DESCRIPTION
           "Dial.
Access: Instant.
AC INI-Param: Test_Call_Action"
       ::= {testCallEntry 3}



     testCallActionResult OBJECT-TYPE
       SYNTAX INTEGER {
                  actionDone(0)
,
                  inProgress(1)
,
                  failed(2)

                  }
       MAX-ACCESS read-only
       STATUS current
       DESCRIPTION
           "Development Impending.
AC INI-Param: Test_Call_ActionRes"
       ::= {testCallEntry 4}



     testCallURI OBJECT-TYPE
       SYNTAX SnmpAdminString (SIZE (0..152))
       MAX-ACCESS read-create
       STATUS current
       DESCRIPTION
           "Endpoint URI (can be either 'user' or 'user@host').
Access: Instant.
AC INI-Param: Test_Call_EndpointURI"
       ::= {testCallEntry 5}



     testCallCalledURI OBJECT-TYPE
       SYNTAX SnmpAdminString (SIZE (0..152))
       MAX-ACCESS read-create
       STATUS current
       DESCRIPTION
           "Called URI.
Access: Instant.
AC INI-Param: Test_Call_CalledURI"
       ::= {testCallEntry 6}



     testCallRouteBy OBJECT-TYPE
       SYNTAX INTEGER {
                  tel2IP(0)
,
                  ipGroup(1)
,
                  destAddress(2)

                  }
       MAX-ACCESS read-create
       STATUS current
       DESCRIPTION
           "Route By Type.
Access: Instant.
AC INI-Param: Test_Call_RouteBy"
       ::= {testCallEntry 7}



     testCallIPGroupID OBJECT-TYPE
       SYNTAX Integer32 (-2..48)
       MAX-ACCESS read-create
       STATUS current
       DESCRIPTION
           "IP Group ID.
Access: Instant.
AC INI-Param: Test_Call_IPGroupID"
       ::= {testCallEntry 8}



     testCallDestAddress OBJECT-TYPE
       SYNTAX SnmpAdminString (SIZE (0..49))
       MAX-ACCESS read-create
       STATUS current
       DESCRIPTION
           "Destination address and optional port.
Access: Instant.
AC INI-Param: Test_Call_DestAddress"
       ::= {testCallEntry 9}



     testCallDestTransportType OBJECT-TYPE
       SYNTAX INTEGER {
                  notConfigured(-1)
,
                  uDP(0)
,
                  tCP(1)
,
                  tLS(2)

                  }
       MAX-ACCESS read-create
       STATUS current
       DESCRIPTION
           "Destination transport type.
Access: Instant.
AC INI-Param: Test_Call_DestTransportType"
       ::= {testCallEntry 10}



     testCallSRD OBJECT-TYPE
       SYNTAX Integer32 (-1..48)
       MAX-ACCESS read-create
       STATUS current
       DESCRIPTION
           "SRD.
Access: Instant.
AC INI-Param: Test_Call_SRD"
       ::= {testCallEntry 11}



     testCallApplicationType OBJECT-TYPE
       SYNTAX INTEGER {
                  ip2ip(0)
,
                  sAs(1)
,
                  sBC(2)

                  }
       MAX-ACCESS read-create
       STATUS current
       DESCRIPTION
           "Application type.
Access: Instant.
AC INI-Param: Test_Call_ApplicationType"
       ::= {testCallEntry 12}



     testCallAutoRegister OBJECT-TYPE
       SYNTAX Unsigned32 (0..1)
       MAX-ACCESS read-create
       STATUS current
       DESCRIPTION
           "Auto register.
Access: Instant.
AC INI-Param: Test_Call_AutoRegister"
       ::= {testCallEntry 13}



     testCallUserName OBJECT-TYPE
       SYNTAX SnmpAdminString (SIZE (0..49))
       MAX-ACCESS read-create
       STATUS current
       DESCRIPTION
           "User name for registration.
Access: Instant.
AC INI-Param: Test_Call_UserName"
       ::= {testCallEntry 14}



     testCallPassword OBJECT-TYPE
       SYNTAX SnmpAdminString (SIZE (0..50))
       MAX-ACCESS read-create
       STATUS current
       DESCRIPTION
           "Password for registration.
Access: Instant.
AC INI-Param: Test_Call_Password"
       ::= {testCallEntry 15}



     testCallCallParty OBJECT-TYPE
       SYNTAX INTEGER {
                  caller(0)
,
                  called(1)

                  }
       MAX-ACCESS read-create
       STATUS current
       DESCRIPTION
           "Test call party - i.e. Caller or Called.
Access: Instant.
AC INI-Param: Test_Call_CallParty"
       ::= {testCallEntry 16}



     testCallMaxChannels OBJECT-TYPE
       SYNTAX Unsigned32 (1..240)
       MAX-ACCESS read-create
       STATUS current
       DESCRIPTION
           "Maximum concurrent channels for session.
Access: Instant.
AC INI-Param: Test_Call_MaxChannels"
       ::= {testCallEntry 17}



     testCallCallDuration OBJECT-TYPE
       SYNTAX Integer32 (-1..100000)
       MAX-ACCESS read-create
       STATUS current
       DESCRIPTION
           "Call duration in seconds (-1 for auto, 0 for infinite).
Access: Instant.
AC INI-Param: Test_Call_CallDuration"
       ::= {testCallEntry 18}



     testCallCallsPerSecond OBJECT-TYPE
       SYNTAX Unsigned32 (1..10)
       MAX-ACCESS read-create
       STATUS current
       DESCRIPTION
           "Calls per second.
Access: Instant.
AC INI-Param: Test_Call_CallsPerSecond"
       ::= {testCallEntry 19}



     testCallTestMode OBJECT-TYPE
       SYNTAX INTEGER {
                  once(0)
,
                  continuous(1)

                  }
       MAX-ACCESS read-create
       STATUS current
       DESCRIPTION
           "Test mode.
Access: Instant.
AC INI-Param: Test_Call_TestMode"
       ::= {testCallEntry 20}



     testCallTestDuration OBJECT-TYPE
       SYNTAX Unsigned32 (0..100000)
       MAX-ACCESS read-create
       STATUS current
       DESCRIPTION
           "Test duration (minutes).
Access: Instant.
AC INI-Param: Test_Call_TestDuration"
       ::= {testCallEntry 21}



     testCallPlay OBJECT-TYPE
       SYNTAX INTEGER {
                  disable(0)
,
                  dTMF(1)
,
                  pRT(2)

                  }
       MAX-ACCESS read-create
       STATUS current
       DESCRIPTION
           "Playback mode.
Access: Instant.
AC INI-Param: Test_Call_Play"
       ::= {testCallEntry 22}



     testCallScheduleInterval OBJECT-TYPE
       SYNTAX Unsigned32 (0..100000)
       MAX-ACCESS read-create
       STATUS current
       DESCRIPTION
           "0 disables scheduling, any positive number defines the inetrval
between scheduled calls in minutes.
Access: Instant.
AC INI-Param: Test_Call_ScheduleInterval"
       ::= {testCallEntry 23}



     testCallActiveCalls OBJECT-TYPE
       SYNTAX Unsigned32 (0..4294967296)
       MAX-ACCESS read-only
       STATUS obsolete
       DESCRIPTION
           "Current active calls.
AC INI-Param: Test_Call_ActiveCalls"
       ::= {testCallEntry 24}



     testCallCallAttempts OBJECT-TYPE
       SYNTAX Unsigned32 (0..4294967296)
       MAX-ACCESS read-only
       STATUS obsolete
       DESCRIPTION
           "Total call attempts.
AC INI-Param: Test_Call_CallAttempts"
       ::= {testCallEntry 25}



     testCallEstablishedCalls OBJECT-TYPE
       SYNTAX Unsigned32 (0..4294967296)
       MAX-ACCESS read-only
       STATUS obsolete
       DESCRIPTION
           "Total established calls.
AC INI-Param: Test_Call_EstablishedCalls"
       ::= {testCallEntry 26}



     testCallFailedAttempts OBJECT-TYPE
       SYNTAX Unsigned32 (0..4294967296)
       MAX-ACCESS read-only
       STATUS obsolete
       DESCRIPTION
           "Total failed attempts.
AC INI-Param: Test_Call_FailedAttempts"
       ::= {testCallEntry 27}



     testCallRemoteDisconnects OBJECT-TYPE
       SYNTAX Unsigned32 (0..4294967296)
       MAX-ACCESS read-only
       STATUS obsolete
       DESCRIPTION
           "Remote disconnections.
AC INI-Param: Test_Call_RemoteDisconnects"
       ::= {testCallEntry 28}



     testCallAverageCPS OBJECT-TYPE
       SYNTAX SnmpAdminString (SIZE (0..5))
       MAX-ACCESS read-only
       STATUS obsolete
       DESCRIPTION
           "Average calls per second.
AC INI-Param: Test_Call_AverageCPS"
       ::= {testCallEntry 29}



     testCallElapsedTime OBJECT-TYPE
       SYNTAX SnmpAdminString (SIZE (0..12))
       MAX-ACCESS read-only
       STATUS obsolete
       DESCRIPTION
           "Elapsed time since last session beginning or stats reset.
AC INI-Param: Test_Call_ElapsedTime"
       ::= {testCallEntry 30}



     testCallTestSummary OBJECT-TYPE
       SYNTAX SnmpAdminString (SIZE (0..15))
       MAX-ACCESS read-only
       STATUS obsolete
       DESCRIPTION
           "Short summary of current test status (Idle, Running...).
AC INI-Param: Test_Call_TestSummary"
       ::= {testCallEntry 31}



     testCallTestStatus OBJECT-TYPE
       SYNTAX SnmpAdminString (SIZE (0..39))
       MAX-ACCESS read-only
       STATUS obsolete
       DESCRIPTION
           "Test status.
AC INI-Param: Test_Call_TestStatus"
       ::= {testCallEntry 32}



     crp OBJECT IDENTIFIER ::= {common 32}


     crpEnableCRPApplication OBJECT-TYPE
       SYNTAX INTEGER {
                  disable(0)
,
                  enable(1)

                  }
       MAX-ACCESS read-write
       STATUS current
       DESCRIPTION
           "Enables CRP functionality.
Access: Offline.
AC INI-Param: ENABLECRPAPPLICATION"
       ::= {crp 1}



     userInfo OBJECT IDENTIFIER ::= {common 33}


     userInfoEnableUsage OBJECT-TYPE
       SYNTAX INTEGER {
                  disable(0)
,
                  enable(1)

                  }
       MAX-ACCESS read-write
       STATUS current
       DESCRIPTION
           "Enables the usage of the User Information, which is loaded to
the device in the User Information auxiliary file. 0 - disable,
1 - enable.
Access: Instant.
AC INI-Param: ENABLEUSERINFOUSAGE"
       ::= {userInfo 1}



     -- ****************************************
     -- gwUserInfo table declaration
     -- ****************************************
     gwUserInfoTable OBJECT-TYPE
       SYNTAX SEQUENCE OF GwUserInfoEntry
       MAX-ACCESS not-accessible
       STATUS current
       DESCRIPTION
           ""
       ::= {userInfo 21}



     -- ****************************************
     -- gwUserInfo table entry
     -- ****************************************
     gwUserInfoEntry OBJECT-TYPE
       SYNTAX GwUserInfoEntry
       MAX-ACCESS not-accessible
       STATUS current
       DESCRIPTION
           ""
       INDEX {gwUserInfoIndex}
       ::= {gwUserInfoTable 1}



     -- ****************************************
     -- gwUserInfo TABLE
     -- ****************************************
     GwUserInfoEntry ::= SEQUENCE {
       gwUserInfoIndex                                 Unsigned32,
       gwUserInfoRowStatus                             RowStatus,
       gwUserInfoAction                                INTEGER,
       gwUserInfoActionResult                          INTEGER,
       gwUserInfoPBXExtension                          SnmpAdminString,
       gwUserInfoGlobalPhoneNumber                     SnmpAdminString,
       gwUserInfoDisplayName                           SnmpAdminString,
       gwUserInfoUsername                              SnmpAdminString,
       gwUserInfoPassword                              SnmpAdminString,
       gwUserInfoStatus                                INTEGER
     }



     gwUserInfoIndex OBJECT-TYPE
       SYNTAX Unsigned32 (0..999)
       MAX-ACCESS not-accessible
       STATUS current
       DESCRIPTION
           "Entry number, starting at 0.
AC INI-Param: GWUserInfoTable_Index"
       ::= {gwUserInfoEntry 1}



     gwUserInfoRowStatus OBJECT-TYPE
       SYNTAX RowStatus
       MAX-ACCESS read-create
       STATUS current
       DESCRIPTION
           "Row-Status Textual Conventions as defined in RFC 2579: Textual
Conventions for SMIv2.
AC INI-Param: GWUserInfoTable_RowStatus"
       ::= {gwUserInfoEntry 2}



     gwUserInfoAction OBJECT-TYPE
       SYNTAX INTEGER {
                  developmentImpending(0)

                  }
       MAX-ACCESS read-only
       STATUS current
       DESCRIPTION
           "Development Impending.
AC INI-Param: GWUserInfoTable_Action"
       ::= {gwUserInfoEntry 3}



     gwUserInfoActionResult OBJECT-TYPE
       SYNTAX INTEGER {
                  developmentImpending(0)

                  }
       MAX-ACCESS read-only
       STATUS current
       DESCRIPTION
           "Development Impending.
AC INI-Param: GWUserInfoTable_ActionRes"
       ::= {gwUserInfoEntry 4}



     gwUserInfoPBXExtension OBJECT-TYPE
       SYNTAX SnmpAdminString (SIZE (0..20))
       MAX-ACCESS read-write
       STATUS current
       DESCRIPTION
           "PBX Extension.
Access: Instant.
AC INI-Param: GWUserInfoTable_PBXExtension"
       ::= {gwUserInfoEntry 5}



     gwUserInfoGlobalPhoneNumber OBJECT-TYPE
       SYNTAX SnmpAdminString (SIZE (0..20))
       MAX-ACCESS read-write
       STATUS current
       DESCRIPTION
           "Global Phone Number.
Access: Instant.
AC INI-Param: GWUserInfoTable_GlobalPhoneNumber"
       ::= {gwUserInfoEntry 6}



     gwUserInfoDisplayName OBJECT-TYPE
       SYNTAX SnmpAdminString (SIZE (0..30))
       MAX-ACCESS read-write
       STATUS current
       DESCRIPTION
           "Display Name.
Access: Instant.
AC INI-Param: GWUserInfoTable_DisplayName"
       ::= {gwUserInfoEntry 7}



     gwUserInfoUsername OBJECT-TYPE
       SYNTAX SnmpAdminString (SIZE (0..50))
       MAX-ACCESS read-write
       STATUS current
       DESCRIPTION
           "Username.
Access: Instant.
AC INI-Param: GWUserInfoTable_Username"
       ::= {gwUserInfoEntry 8}



     gwUserInfoPassword OBJECT-TYPE
       SYNTAX SnmpAdminString (SIZE (0..50))
       MAX-ACCESS read-write
       STATUS current
       DESCRIPTION
           "Password.
Access: Instant.
AC INI-Param: GWUserInfoTable_Password"
       ::= {gwUserInfoEntry 9}



     gwUserInfoStatus OBJECT-TYPE
       SYNTAX INTEGER {
                  notRegistered(0)
,
                  registered(1)

                  }
       MAX-ACCESS read-only
       STATUS current
       DESCRIPTION
           "Status.
AC INI-Param: GWUserInfoTable_Status"
       ::= {gwUserInfoEntry 10}



     -- ****************************************
     -- sbcUserInfo table declaration
     -- ****************************************
     sbcUserInfoTable OBJECT-TYPE
       SYNTAX SEQUENCE OF SbcUserInfoEntry
       MAX-ACCESS not-accessible
       STATUS current
       DESCRIPTION
           ""
       ::= {userInfo 22}



     -- ****************************************
     -- sbcUserInfo table entry
     -- ****************************************
     sbcUserInfoEntry OBJECT-TYPE
       SYNTAX SbcUserInfoEntry
       MAX-ACCESS not-accessible
       STATUS current
       DESCRIPTION
           ""
       INDEX {sbcUserInfoIndex}
       ::= {sbcUserInfoTable 1}



     -- ****************************************
     -- sbcUserInfo TABLE
     -- ****************************************
     SbcUserInfoEntry ::= SEQUENCE {
       sbcUserInfoIndex                                Unsigned32,
       sbcUserInfoRowStatus                            RowStatus,
       sbcUserInfoAction                               INTEGER,
       sbcUserInfoActionResult                         INTEGER,
       sbcUserInfoLocalUser                            SnmpAdminString,
       sbcUserInfoUsername                             SnmpAdminString,
       sbcUserInfoPassword                             SnmpAdminString,
       sbcUserInfoIPGroupID                            Integer32,
       sbcUserInfoStatus                               INTEGER
     }



     sbcUserInfoIndex OBJECT-TYPE
       SYNTAX Unsigned32 (0..20000)
       MAX-ACCESS not-accessible
       STATUS current
       DESCRIPTION
           "Entry number, starting at 0.
AC INI-Param: SBCUserInfoTable_Index"
       ::= {sbcUserInfoEntry 1}



     sbcUserInfoRowStatus OBJECT-TYPE
       SYNTAX RowStatus
       MAX-ACCESS read-create
       STATUS current
       DESCRIPTION
           "Row-Status Textual Conventions as defined in RFC 2579: Textual
Conventions for SMIv2.
AC INI-Param: SBCUserInfoTable_RowStatus"
       ::= {sbcUserInfoEntry 2}



     sbcUserInfoAction OBJECT-TYPE
       SYNTAX INTEGER {
                  developmentImpending(0)

                  }
       MAX-ACCESS read-only
       STATUS current
       DESCRIPTION
           "Development Impending.
AC INI-Param: SBCUserInfoTable_Action"
       ::= {sbcUserInfoEntry 3}



     sbcUserInfoActionResult OBJECT-TYPE
       SYNTAX INTEGER {
                  developmentImpending(0)

                  }
       MAX-ACCESS read-only
       STATUS current
       DESCRIPTION
           "Development Impending.
AC INI-Param: SBCUserInfoTable_ActionRes"
       ::= {sbcUserInfoEntry 4}



     sbcUserInfoLocalUser OBJECT-TYPE
       SYNTAX SnmpAdminString (SIZE (0..50))
       MAX-ACCESS read-write
       STATUS current
       DESCRIPTION
           "Local User.
Access: Instant.
AC INI-Param: SBCUserInfoTable_LocalUser"
       ::= {sbcUserInfoEntry 5}



     sbcUserInfoUsername OBJECT-TYPE
       SYNTAX SnmpAdminString (SIZE (0..50))
       MAX-ACCESS read-write
       STATUS current
       DESCRIPTION
           "Username.
Access: Instant.
AC INI-Param: SBCUserInfoTable_Username"
       ::= {sbcUserInfoEntry 6}



     sbcUserInfoPassword OBJECT-TYPE
       SYNTAX SnmpAdminString (SIZE (0..50))
       MAX-ACCESS read-write
       STATUS current
       DESCRIPTION
           "Password.
Access: Instant.
AC INI-Param: SBCUserInfoTable_Password"
       ::= {sbcUserInfoEntry 7}



     sbcUserInfoIPGroupID OBJECT-TYPE
       SYNTAX Integer32 (-1..200)
       MAX-ACCESS read-write
       STATUS current
       DESCRIPTION
           "IP Group ID.
Access: Instant.
AC INI-Param: SBCUserInfoTable_IPGroupID"
       ::= {sbcUserInfoEntry 8}



     sbcUserInfoStatus OBJECT-TYPE
       SYNTAX INTEGER {
                  notRegistered(0)
,
                  registered(1)

                  }
       MAX-ACCESS read-only
       STATUS current
       DESCRIPTION
           "Status.
AC INI-Param: SBCUserInfoTable_Status"
       ::= {sbcUserInfoEntry 9}



     sbcExt OBJECT IDENTIFIER ::= {common 34}


     sbcExtSharedLineRegMode OBJECT-TYPE
       SYNTAX INTEGER {
                  disable(0)
,
                  enable(1)

                  }
       MAX-ACCESS read-write
       STATUS current
       DESCRIPTION
           "Disable-SBC sends INVITE according to the Request-URI. Enabled-if
the Request-URI is of specific contact, SBC sends the
INVITE to all contacts under the parent AOR.
Access: Instant.
AC INI-Param: SBCSENDINVITETOALLCONTACTS"
       ::= {sbcExt 1}



     sbcExtDiversionURIType OBJECT-TYPE
       SYNTAX INTEGER {
                  transparent(0)
,
                  sip(1)
,
                  tel(2)

                  }
       MAX-ACCESS read-write
       STATUS current
       DESCRIPTION
           "Which uri type to use for Diversion header in SBC.
Access: Instant.
AC INI-Param: SBCDIVERSIONURITYPE"
       ::= {sbcExt 2}



     sbcExtEnforceMediaOrder OBJECT-TYPE
       SYNTAX INTEGER {
                  disable(0)
,
                  enable(1)

                  }
       MAX-ACCESS read-write
       STATUS current
       DESCRIPTION
           "enforces media order according to rfc 3264.
Access: Instant.
AC INI-Param: SBCENFORCEMEDIAORDER"
       ::= {sbcExt 3}



     sbcExtFaxDetectionTimeout OBJECT-TYPE
       SYNTAX Unsigned32 (0..30)
       MAX-ACCESS read-write
       STATUS current
       DESCRIPTION
           "Maximum time for Fax Detection on SBC(seconds).
Access: Instant.
AC INI-Param: SBCFAXDETECTIONTIMEOUT"
       ::= {sbcExt 4}



     sipRec OBJECT IDENTIFIER ::= {common 35}


     sipRecEnableRecApplication OBJECT-TYPE
       SYNTAX INTEGER {
                  disable(0)
,
                  enable(1)

                  }
       MAX-ACCESS read-write
       STATUS current
       DESCRIPTION
           "Enables SIP rec functionality.
Access: Offline.
AC INI-Param: ENABLESIPREC"
       ::= {sipRec 1}



     sipRecServerDestUsername OBJECT-TYPE
       SYNTAX SnmpAdminString (SIZE (0..51))
       MAX-ACCESS read-write
       STATUS current
       DESCRIPTION
           "SIPRec Server Destination Username.
Access: Instant.
AC INI-Param: SIPRECSERVERDESTUSERNAME"
       ::= {sipRec 2}



     -- ****************************************
     -- sipRecRouting table declaration
     -- ****************************************
     sipRecRoutingTable OBJECT-TYPE
       SYNTAX SEQUENCE OF SipRecRoutingEntry
       MAX-ACCESS not-accessible
       STATUS current
       DESCRIPTION
           "Gwapp SIP Rec Routing table"
       ::= {sipRec 21}



     -- ****************************************
     -- sipRecRouting table entry
     -- ****************************************
     sipRecRoutingEntry OBJECT-TYPE
       SYNTAX SipRecRoutingEntry
       MAX-ACCESS not-accessible
       STATUS current
       DESCRIPTION
           ""
       INDEX {sipRecRoutingIndex}
       ::= {sipRecRoutingTable 1}



     -- ****************************************
     -- sipRecRouting TABLE
     -- ****************************************
     SipRecRoutingEntry ::= SEQUENCE {
       sipRecRoutingIndex                              Unsigned32,
       sipRecRoutingRowStatus                          RowStatus,
       sipRecRoutingAction                             INTEGER,
       sipRecRoutingActionResult                       INTEGER,
       sipRecRoutingRecordedIPGroupID                  Integer32,
       sipRecRoutingRecordedSourcePrefix               SnmpAdminString,
       sipRecRoutingRecordedDestinationPrefix          SnmpAdminString,
       sipRecRoutingPeerIPGroupID                      Integer32,
       sipRecRoutingPeerTrunkGroupID                   Integer32,
       sipRecRoutingCaller                             INTEGER,
       sipRecRoutingSRSIPGroupID                       Integer32
     }



     sipRecRoutingIndex OBJECT-TYPE
       SYNTAX Unsigned32 (0..29)
       MAX-ACCESS read-only
       STATUS current
       DESCRIPTION
           "The index of the table.
AC INI-Param: SIPRecRouting_Index"
       ::= {sipRecRoutingEntry 1}



     sipRecRoutingRowStatus OBJECT-TYPE
       SYNTAX RowStatus
       MAX-ACCESS read-create
       STATUS current
       DESCRIPTION
           "Row-Status Textual Conventions as defined in RFC 2579: Textual
Conventions for SMIv2.
AC INI-Param: SIPRecRouting_RowStatus"
       ::= {sipRecRoutingEntry 2}



     sipRecRoutingAction OBJECT-TYPE
       SYNTAX INTEGER {
                  none(0)
,
                  dial(1)
,
                  dropCall(2)
,
                  restart(3)

                  }
       MAX-ACCESS read-create
       STATUS current
       DESCRIPTION
           "Development Impending.
AC INI-Param: SIPRecRouting_Action"
       ::= {sipRecRoutingEntry 3}



     sipRecRoutingActionResult OBJECT-TYPE
       SYNTAX INTEGER {
                  actionDone(0)
,
                  inProgress(1)
,
                  failed(2)

                  }
       MAX-ACCESS read-only
       STATUS current
       DESCRIPTION
           "Development Impending.
AC INI-Param: SIPRecRouting_ActionRes"
       ::= {sipRecRoutingEntry 4}



     sipRecRoutingRecordedIPGroupID OBJECT-TYPE
       SYNTAX Integer32 (-1..200)
       MAX-ACCESS read-create
       STATUS current
       DESCRIPTION
           "Recorded IP Group ID.
Access: Instant.
AC INI-Param: SIPRecRouting_RecordedIPGroupID"
       ::= {sipRecRoutingEntry 5}



     sipRecRoutingRecordedSourcePrefix OBJECT-TYPE
       SYNTAX SnmpAdminString (SIZE (0..100))
       MAX-ACCESS read-create
       STATUS current
       DESCRIPTION
           "Recorded Source Prefix.
Access: Instant.
AC INI-Param: SIPRecRouting_RecordedSourcePrefix"
       ::= {sipRecRoutingEntry 6}



     sipRecRoutingRecordedDestinationPrefix OBJECT-TYPE
       SYNTAX SnmpAdminString (SIZE (0..100))
       MAX-ACCESS read-create
       STATUS current
       DESCRIPTION
           "Recorded Destination Prefix.
Access: Instant.
AC INI-Param: SIPRecRouting_RecordedDestinationPrefix"
       ::= {sipRecRoutingEntry 7}



     sipRecRoutingPeerIPGroupID OBJECT-TYPE
       SYNTAX Integer32 (-1..200)
       MAX-ACCESS read-create
       STATUS current
       DESCRIPTION
           "Peer IP Group ID.
Access: Instant.
AC INI-Param: SIPRecRouting_PeerIPGroupID"
       ::= {sipRecRoutingEntry 8}



     sipRecRoutingPeerTrunkGroupID OBJECT-TYPE
       SYNTAX Integer32 (-1..241)
       MAX-ACCESS read-create
       STATUS current
       DESCRIPTION
           "Peer Trunk Group ID.
Access: Instant.
AC INI-Param: SIPRecRouting_PeerTrunkGroupID"
       ::= {sipRecRoutingEntry 9}



     sipRecRoutingCaller OBJECT-TYPE
       SYNTAX INTEGER {
                  both(0)
,
                  recordedParty(1)
,
                  peerParty(2)

                  }
       MAX-ACCESS read-create
       STATUS current
       DESCRIPTION
           "Caller.
Access: Instant.
AC INI-Param: SIPRecRouting_Caller"
       ::= {sipRecRoutingEntry 10}



     sipRecRoutingSRSIPGroupID OBJECT-TYPE
       SYNTAX Integer32 (-1..200)
       MAX-ACCESS read-create
       STATUS current
       DESCRIPTION
           "Recording Server (SRS) IP Group ID.
Access: Instant.
AC INI-Param: SIPRecRouting_SRSIPGroupID"
       ::= {sipRecRoutingEntry 11}



     sip OBJECT IDENTIFIER ::= {gwConfiguration 2}


     sipProxy OBJECT IDENTIFIER ::= {sip 1}


     sipProxyUsed OBJECT-TYPE
       SYNTAX INTEGER {
                  no(0)
,
                  yes(1)

                  }
       MAX-ACCESS read-write
       STATUS current
       DESCRIPTION
           "Is SIP Proxy used.
Access: Instant.
AC INI-Param: ISPROXYUSED"
       ::= {sipProxy 1}



     sipProxyEnableKeepAlive OBJECT-TYPE
       SYNTAX INTEGER {
                  disable (0)
,
                  usingOptions (1)
,
                  usingRegister (2)

                  }
       MAX-ACCESS read-write
       STATUS current
       DESCRIPTION
           "Enable Proxy Keep-Alive over OPTIONS method or REGISTER method.
Access: Instant.
AC INI-Param: ENABLEPROXYKEEPALIVE"
       ::= {sipProxy 2}



     sipProxyName OBJECT-TYPE
       SYNTAX SnmpAdminString (SIZE (0..49))
       MAX-ACCESS read-write
       STATUS current
       DESCRIPTION
           "SIP Proxy name.
Access: Instant.
AC INI-Param: PROXYNAME"
       ::= {sipProxy 3}



     sipProxyIsHotSwap OBJECT-TYPE
       SYNTAX INTEGER {
                  no(0)
,
                  yes(1)

                  }
       MAX-ACCESS read-write
       STATUS current
       DESCRIPTION
           "Enable Proxy Hot-Swap mode.
Access: Instant.
AC INI-Param: ISPROXYHOTSWAP"
       ::= {sipProxy 4}



     sipProxyHotSwapRtx OBJECT-TYPE
       SYNTAX Unsigned32 (1..30)
       MAX-ACCESS read-write
       STATUS current
       DESCRIPTION
           "Number of Rtx before Hotswap is performed.
Access: Instant.
AC INI-Param: PROXYHOTSWAPRTX"
       ::= {sipProxy 5}



     sipProxyRedundancyMode OBJECT-TYPE
       SYNTAX INTEGER {
                  parking(0)
,
                  homing(1)

                  }
       MAX-ACCESS read-write
       STATUS current
       DESCRIPTION
           "Redundancy Mode - Parking on active proxy or switching to main
Proxy whenever online.
Access: Instant.
AC INI-Param: PROXYREDUNDANCYMODE"
       ::= {sipProxy 6}



     sipProxyAlwaysUseRouteTable OBJECT-TYPE
       SYNTAX INTEGER {
                  no(0)
,
                  yes(1)

                  }
       MAX-ACCESS read-write
       STATUS current
       DESCRIPTION
           "Always use routing table even though proxy is available.
Access: Instant.
AC INI-Param: ALWAYSUSEROUTETABLE"
       ::= {sipProxy 7}



     sipProxyAlwaysSendToProxy OBJECT-TYPE
       SYNTAX INTEGER {
                  no(0)
,
                  yes(1)

                  }
       MAX-ACCESS read-write
       STATUS current
       DESCRIPTION
           "Send all messages to Proxy server.
Access: Instant.
AC INI-Param: ALWAYSSENDTOPROXY"
       ::= {sipProxy 8}



     sipProxyKeepAliveTime OBJECT-TYPE
       SYNTAX Unsigned32 (5..2000000)
       MAX-ACCESS read-write
       STATUS current
       DESCRIPTION
           "Time interval between Proxy Keep-Alive messages (seconds).
Access: Instant.
AC INI-Param: ProxyKeepAliveTime"
       ::= {sipProxy 9}



     sipProxyIsFallbackUsed OBJECT-TYPE
       SYNTAX INTEGER {
                  no(0)
,
                  yes(1)

                  }
       MAX-ACCESS read-write
       STATUS current
       DESCRIPTION
           "Allow fallback to internal Tel to IP routing table if Proxy
is not responding.
Access: Instant.
AC INI-Param: IsFallbackUsed"
       ::= {sipProxy 10}



     sipProxySendInviteToProxy OBJECT-TYPE
       SYNTAX INTEGER {
                  disable(0)
,
                  enable(1)

                  }
       MAX-ACCESS read-write
       STATUS current
       DESCRIPTION
           "Always send INVITE messages to Proxy server.
Access: Instant.
AC INI-Param: SENDINVITETOPROXY"
       ::= {sipProxy 11}



     sipProxyIsTrustedProxy OBJECT-TYPE
       SYNTAX INTEGER {
                  disable(0)
,
                  enable(1)

                  }
       MAX-ACCESS read-write
       STATUS current
       DESCRIPTION
           "Determine whether the proxy is a trusted node.
Access: Instant.
AC INI-Param: ISTRUSTEDPROXY"
       ::= {sipProxy 12}



     sipProxyUseGatewayNameForOptions OBJECT-TYPE
       SYNTAX INTEGER {
                  disable(0)
,
                  enable(1)

                  }
       MAX-ACCESS read-write
       STATUS current
       DESCRIPTION
           "Use Gateway name (instead of IP address) in Keep-Alive OPTIONS
messages.
Access: Instant.
AC INI-Param: USEGATEWAYNAMEFOROPTIONS"
       ::= {sipProxy 13}



     sipProxyEnableSRVQuery OBJECT-TYPE
       SYNTAX INTEGER {
                  disable(0)
,
                  enable(1)

                  }
       MAX-ACCESS read-write
       STATUS obsolete
       DESCRIPTION
           "Enable DNS SRV queries for Proxy domain name.
Access: Instant.
AC INI-Param: ENABLEPROXYSRVQUERY"
       ::= {sipProxy 14}



     sipProxyDNSQueryType OBJECT-TYPE
       SYNTAX INTEGER {
                  aRecord(0)
,
                  sRV(1)
,
                  nAPTR(2)

                  }
       MAX-ACCESS read-write
       STATUS current
       DESCRIPTION
           "DNS Query Type: 0-ARecord, 1-SRV, 2-NAPTR . Has effect on every
DNS query in the system.
Access: Instant.
AC INI-Param: DNSQUERYTYPE"
       ::= {sipProxy 15}



     sipProxyLoadBalancingMethod OBJECT-TYPE
       SYNTAX INTEGER {
                  disable(0)
,
                  roundRobin(1)
,
                  randomWeights(2)

                  }
       MAX-ACCESS read-write
       STATUS current
       DESCRIPTION
           "Method of the proxies load balancing:
0 - Disabled (default)
1 - RoundRobin
2 - Random SRV Weights.
Access: Instant.
AC INI-Param: PROXYLOADBALANCINGMETHOD"
       ::= {sipProxy 16}



     sipProxyIPListRefreshTime OBJECT-TYPE
       SYNTAX Unsigned32 (5..2000000)
       MAX-ACCESS read-write
       STATUS current
       DESCRIPTION
           "Time interval between refresh of proxies list (seconds). For
example SRV query will be done every ProxyIPListRefreshTime
seconds.
Access: Instant.
AC INI-Param: PROXYIPLISTREFRESHTIME"
       ::= {sipProxy 17}



     sipProxyUseProxyIpAsHost OBJECT-TYPE
       SYNTAX INTEGER {
                  disable(0)
,
                  enable(1)

                  }
       MAX-ACCESS read-write
       STATUS current
       DESCRIPTION
           "Whether or not to use the Proxy IP as Host in From and To headers.
Access: Instant.
AC INI-Param: USEPROXYIPASHOST"
       ::= {sipProxy 18}



     -- ****************************************
     -- proxyIP table declaration
     -- ****************************************
     proxyIPTable OBJECT-TYPE
       SYNTAX SEQUENCE OF ProxyIPEntry
       MAX-ACCESS not-accessible
       STATUS current
       DESCRIPTION
           "The table defines phone numbers for gateway endpoints. 
The endpoints that aren’t defined will be disabled."
       ::= {sipProxy 21}



     -- ****************************************
     -- proxyIP table entry
     -- ****************************************
     proxyIPEntry OBJECT-TYPE
       SYNTAX ProxyIPEntry
       MAX-ACCESS not-accessible
       STATUS current
       DESCRIPTION
           ""
       INDEX {proxyIPIndex}
       ::= {proxyIPTable 1}



     -- ****************************************
     -- proxyIP TABLE
     -- ****************************************
     ProxyIPEntry ::= SEQUENCE {
       proxyIPIndex                                    Unsigned32,
       proxyIPRowStatus                                RowStatus,
       proxyIPAction                                   INTEGER,
       proxyIPActionResult                             INTEGER,
       proxyIPProxyIP                                  SnmpAdminString,
       proxyIPTransportType                            INTEGER,
       proxyIPProxySetId                               Unsigned32
     }



     proxyIPIndex OBJECT-TYPE
       SYNTAX Unsigned32 (0..4999)
       MAX-ACCESS not-accessible
       STATUS current
       DESCRIPTION
           "Entry number, starting at 0.
AC INI-Param: ProxyIp_Index"
       ::= {proxyIPEntry 1}



     proxyIPRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {proxyIPEntry 2}



     proxyIPAction OBJECT-TYPE
       SYNTAX INTEGER {
                  developmentImpending(0)

                  }
       MAX-ACCESS read-only
       STATUS current
       DESCRIPTION
           "Development Impending.
AC INI-Param: N/A"
       ::= {proxyIPEntry 3}



     proxyIPActionResult OBJECT-TYPE
       SYNTAX INTEGER {
                  developmentImpending(0)

                  }
       MAX-ACCESS read-only
       STATUS current
       DESCRIPTION
           "Development Impending.
AC INI-Param: N/A"
       ::= {proxyIPEntry 4}



     proxyIPProxyIP OBJECT-TYPE
       SYNTAX SnmpAdminString (SIZE (0..49))
       MAX-ACCESS read-create
       STATUS deprecated
       DESCRIPTION
           "IpAddress.
Access: Instant.
AC INI-Param: ProxyIp_IpAddress"
       ::= {proxyIPEntry 5}



     proxyIPTransportType OBJECT-TYPE
       SYNTAX INTEGER {
                  unknown(-1)
,
                  uDP(0)
,
                  tCP(1)
,
                  tLS(2)

                  }
       MAX-ACCESS read-create
       STATUS current
       DESCRIPTION
           "TransportType.
Access: Instant.
AC INI-Param: ProxyIp_TransportType"
       ::= {proxyIPEntry 6}



     proxyIPProxySetId OBJECT-TYPE
       SYNTAX Unsigned32 (0..499)
       MAX-ACCESS read-create
       STATUS current
       DESCRIPTION
           "ProxySetId.
Access: Instant.
AC INI-Param: ProxyIp_ProxySetId"
       ::= {proxyIPEntry 7}



     -- ****************************************
     -- sipProxySet table declaration
     -- ****************************************
     sipProxySetTable OBJECT-TYPE
       SYNTAX SEQUENCE OF SipProxySetEntry
       MAX-ACCESS not-accessible
       STATUS current
       DESCRIPTION
           "GwApp Proxy Set Table"
       ::= {sipProxy 22}



     -- ****************************************
     -- sipProxySet table entry
     -- ****************************************
     sipProxySetEntry OBJECT-TYPE
       SYNTAX SipProxySetEntry
       MAX-ACCESS not-accessible
       STATUS current
       DESCRIPTION
           ""
       INDEX {sipProxySetIndex}
       ::= {sipProxySetTable 1}



     -- ****************************************
     -- sipProxySet TABLE
     -- ****************************************
     SipProxySetEntry ::= SEQUENCE {
       sipProxySetIndex                                Unsigned32,
       sipProxySetRowStatus                            RowStatus,
       sipProxySetAction                               INTEGER,
       sipProxySetActionResult                         INTEGER,
       sipProxySetEnableProxyKeepAlive                 INTEGER,
       sipProxySetProxyKeepAliveTime                   Unsigned32,
       sipProxySetProxyLoadBalancingMethod             INTEGER,
       sipProxySetIsProxyHotSwap                       INTEGER,
       sipProxySetProxyRedundancyMode                  INTEGER,
       sipProxySetClassificationInput                  INTEGER,
       sipProxySetSRD                                  Unsigned32,
       sipProxySetProxyName                            SnmpAdminString,
       sipProxySetDNSResolveMethod                     INTEGER,
       sipProxySetKeepAliveFailureResp                 SnmpAdminString
     }



     sipProxySetIndex OBJECT-TYPE
       SYNTAX Unsigned32 (0..499)
       MAX-ACCESS not-accessible
       STATUS current
       DESCRIPTION
           "
AC INI-Param: ProxySet_Index"
       ::= {sipProxySetEntry 1}



     sipProxySetRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {sipProxySetEntry 2}



     sipProxySetAction OBJECT-TYPE
       SYNTAX INTEGER {
                  developmentImpending(0)

                  }
       MAX-ACCESS read-only
       STATUS current
       DESCRIPTION
           "Development Impending.
AC INI-Param: N/A"
       ::= {sipProxySetEntry 3}



     sipProxySetActionResult OBJECT-TYPE
       SYNTAX INTEGER {
                  developmentImpending(0)

                  }
       MAX-ACCESS read-only
       STATUS current
       DESCRIPTION
           "Development Impending.
AC INI-Param: N/A"
       ::= {sipProxySetEntry 4}



     sipProxySetEnableProxyKeepAlive OBJECT-TYPE
       SYNTAX INTEGER {
                  disable(0)
,
                  usingOptions(1)
,
                  usingRegister(2)

                  }
       MAX-ACCESS read-create
       STATUS current
       DESCRIPTION
           "GwApp Proxy Set Table.
Access: Instant.
AC INI-Param: ProxySet_EnableProxyKeepAlive"
       ::= {sipProxySetEntry 5}



     sipProxySetProxyKeepAliveTime OBJECT-TYPE
       SYNTAX Unsigned32 (5..2000000)
       MAX-ACCESS read-create
       STATUS current
       DESCRIPTION
           "GwApp Proxy Set Table.
Access: Instant.
AC INI-Param: ProxySet_ProxyKeepAliveTime"
       ::= {sipProxySetEntry 6}



     sipProxySetProxyLoadBalancingMethod OBJECT-TYPE
       SYNTAX INTEGER {
                  disable (0)
,
                  roundRobin(1)
,
                  randomWeights(2)

                  }
       MAX-ACCESS read-create
       STATUS current
       DESCRIPTION
           "GwApp Proxy Set Table.
Access: Instant.
AC INI-Param: ProxySet_ProxyLoadBalancingMethod"
       ::= {sipProxySetEntry 7}



     sipProxySetIsProxyHotSwap OBJECT-TYPE
       SYNTAX INTEGER {
                  disable(0)
,
                  enable(1)

                  }
       MAX-ACCESS read-create
       STATUS current
       DESCRIPTION
           "GwApp Proxy Set Table.
Access: Instant.
AC INI-Param: ProxySet_IsProxyHotSwap"
       ::= {sipProxySetEntry 8}



     sipProxySetProxyRedundancyMode OBJECT-TYPE
       SYNTAX INTEGER {
                  notConfigured(-1)
,
                  parking(0)
,
                  homing(1)

                  }
       MAX-ACCESS read-create
       STATUS current
       DESCRIPTION
           "GwApp Proxy Set Table.
Access: Online.
AC INI-Param: ProxySet_ProxyRedundancyMode"
       ::= {sipProxySetEntry 9}



     sipProxySetClassificationInput OBJECT-TYPE
       SYNTAX INTEGER {
                  ipOnly(0)
,
                  ipAndPortAndTransport(1)

                  }
       MAX-ACCESS read-create
       STATUS current
       DESCRIPTION
           "GwApp Proxy Set Table.
Access: Instant.
AC INI-Param: ProxySet_ClassificationInput"
       ::= {sipProxySetEntry 10}



     sipProxySetSRD OBJECT-TYPE
       SYNTAX Unsigned32 (0..32)
       MAX-ACCESS read-create
       STATUS current
       DESCRIPTION
           "GwApp Proxy Set Table.
Access: Online.
AC INI-Param: ProxySet_SRD"
       ::= {sipProxySetEntry 11}



     sipProxySetProxyName OBJECT-TYPE
       SYNTAX SnmpAdminString (SIZE (0..20))
       MAX-ACCESS read-create
       STATUS current
       DESCRIPTION
           "Proxy Name.
Access: Online.
AC INI-Param: ProxySet_ProxyName"
       ::= {sipProxySetEntry 12}



     sipProxySetDNSResolveMethod OBJECT-TYPE
       SYNTAX INTEGER {
                  notConfigured(-1)
,
                  a-Record (0)
,
                  srv(1)
,
                  naptr(2)

                  }
       MAX-ACCESS read-create
       STATUS current
       DESCRIPTION
           "DNS Resolve Method.
Access: Online.
AC INI-Param: ProxySet_DNSResolveMethod"
       ::= {sipProxySetEntry 13}



     sipProxySetKeepAliveFailureResp OBJECT-TYPE
       SYNTAX SnmpAdminString (SIZE (0..12))
       MAX-ACCESS read-create
       STATUS current
       DESCRIPTION
           "Defines responses for keepalive meaning failure(comma separated
string).
Access: Online.
AC INI-Param: ProxySet_KeepAliveFailureResp"
       ::= {sipProxySetEntry 14}



     sipDTMF OBJECT IDENTIFIER ::= {sip 2}


     sipDTMFIsHookFlashUsed OBJECT-TYPE
       SYNTAX INTEGER {
                  no(0)
,
                  yes(1)

                  }
       MAX-ACCESS read-write
       STATUS obsolete
       DESCRIPTION
           "Detect and send Hook-Flash as Out-of-Band message.
Access: Instant.
AC INI-Param: ISHOOKFLASHUSED"
       ::= {sipDTMF 1}



     sipDTMFIsDTMFUsed OBJECT-TYPE
       SYNTAX INTEGER {
                  no(0)
,
                  yes(1)

                  }
       MAX-ACCESS read-write
       STATUS obsolete
       DESCRIPTION
           "Send DTMFs on the Signaling path (not on the Media path).
Access: Instant.
AC INI-Param: ISDTMFUSED"
       ::= {sipDTMF 2}



     sipDTMFOutOfBandDtmfFormat OBJECT-TYPE
       SYNTAX INTEGER {
                  info-Nortel(1)
,
                  info-Cisco(2)
,
                  notify(3)

                  }
       MAX-ACCESS read-write
       STATUS obsolete
       DESCRIPTION
           "DTMF Out-of-Band transport method.
Access: Instant.
AC INI-Param: OUTOFBANDDTMFFORMAT"
       ::= {sipDTMF 3}



     sipDTMFDisableAutoMute OBJECT-TYPE
       SYNTAX INTEGER {
                  no(0)
,
                  yes(1)

                  }
       MAX-ACCESS read-write
       STATUS current
       DESCRIPTION
           "Disables inband auto mute of DTMFs when signalling is used for
sending DTMFs.
Access: Instant.
AC INI-Param: DISABLEAUTODTMFMUTE"
       ::= {sipDTMF 4}



     sipDTMFRxDTMFOption OBJECT-TYPE
       SYNTAX INTEGER {
                  noSupportRFC2833inSDP(0)
,
                  supportRFC2833inSDP(3)

                  }
       MAX-ACCESS read-write
       STATUS current
       DESCRIPTION
           "Declare support for RFC 2833 in SDP.
Access: Instant.
AC INI-Param: RXDTMFOPTION"
       ::= {sipDTMF 5}



     sipDTMFHookFlashOption OBJECT-TYPE
       SYNTAX INTEGER {
                  notSupported(0)
,
                  iNFO(1)
,
                  rFC2833(4)
,
                  infoLucent(5)

                  }
       MAX-ACCESS read-write
       STATUS current
       DESCRIPTION
           "Detect and send Hook-Flash using the selected method.
Access: Instant.
AC INI-Param: HOOKFLASHOPTION"
       ::= {sipDTMF 6}



     sipDTMFUseDigitForSpecialDTMF OBJECT-TYPE
       SYNTAX INTEGER {
                  special(0)
,
                  numeric(1)

                  }
       MAX-ACCESS read-write
       STATUS current
       DESCRIPTION
           "Indicates whether a special DTMF, sent with INFO(Cisco), is
sent using its digit representation or not.
Access: Instant.
AC INI-Param: USEDIGITFORSPECIALDTMF"
       ::= {sipDTMF 7}



     sipDTMFMinRoutingOverlapDigits OBJECT-TYPE
       SYNTAX Unsigned32 (0..49)
       MAX-ACCESS read-write
       STATUS current
       DESCRIPTION
           "Minimum number of overlap digits before routing.
Access: Instant.
AC INI-Param: MINOVERLAPDIGITSFORROUTING"
       ::= {sipDTMF 8}



     sipDTMFISDNOverlapIPtoTelDialing OBJECT-TYPE
       SYNTAX INTEGER {
                  disable(0)
,
                  enable(1)

                  }
       MAX-ACCESS read-write
       STATUS current
       DESCRIPTION
           "Enable ISDN Overlap IP to Tel Dialing.
Access: Instant.
AC INI-Param: ISDNTXOVERLAP"
       ::= {sipDTMF 9}



     -- ****************************************
     -- sipTxDTMFOption table declaration
     -- ****************************************
     sipTxDTMFOptionTable OBJECT-TYPE
       SYNTAX SEQUENCE OF SipTxDTMFOptionEntry
       MAX-ACCESS not-accessible
       STATUS current
       DESCRIPTION
           "The names of the five possible coders."
       ::= {sipDTMF 21}



     -- ****************************************
     -- sipTxDTMFOption table entry
     -- ****************************************
     sipTxDTMFOptionEntry OBJECT-TYPE
       SYNTAX SipTxDTMFOptionEntry
       MAX-ACCESS not-accessible
       STATUS current
       DESCRIPTION
           ""
       INDEX {sipTxDTMFOptionIndex}
       ::= {sipTxDTMFOptionTable 1}



     -- ****************************************
     -- sipTxDTMFOption TABLE
     -- ****************************************
     SipTxDTMFOptionEntry ::= SEQUENCE {
       sipTxDTMFOptionIndex                            Unsigned32,
       sipTxDTMFOptionRowStatus                        RowStatus,
       sipTxDTMFOptionAction                           INTEGER,
       sipTxDTMFOptionActionResult                     INTEGER,
       sipTxDTMFOptionValue                            INTEGER
     }



     sipTxDTMFOptionIndex OBJECT-TYPE
       SYNTAX Unsigned32 (0..4)
       MAX-ACCESS not-accessible
       STATUS current
       DESCRIPTION
           "Entry number, starting at 0.
AC INI-Param: TxDtmfOption_Index"
       ::= {sipTxDTMFOptionEntry 1}



     sipTxDTMFOptionRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {sipTxDTMFOptionEntry 2}



     sipTxDTMFOptionAction OBJECT-TYPE
       SYNTAX INTEGER {
                  developmentImpending(0)

                  }
       MAX-ACCESS read-only
       STATUS current
       DESCRIPTION
           "Development Impending.
AC INI-Param: N/A"
       ::= {sipTxDTMFOptionEntry 3}



     sipTxDTMFOptionActionResult OBJECT-TYPE
       SYNTAX INTEGER {
                  developmentImpending(0)

                  }
       MAX-ACCESS read-only
       STATUS current
       DESCRIPTION
           "Development Impending.
AC INI-Param: N/A"
       ::= {sipTxDTMFOptionEntry 4}



     sipTxDTMFOptionValue OBJECT-TYPE
       SYNTAX INTEGER {
                  notSupported(0)
,
                  nortelINFO(1)
,
                  nOTIFY(2)
,
                  ciscoINFO(3)
,
                  rFC2833(4)
,
                  koreaTelecomINFO(5)

                  }
       MAX-ACCESS read-create
       STATUS current
       DESCRIPTION
           "Transmit DTMF option.
Access: Instant.
AC INI-Param: TxDtmfOption_Type"
       ::= {sipTxDTMFOptionEntry 5}



     sipPorts OBJECT IDENTIFIER ::= {sip 3}


     sipPortsDestinationPort OBJECT-TYPE
       SYNTAX Unsigned32 (1..65534)
       MAX-ACCESS read-write
       STATUS current
       DESCRIPTION
           "Default SIP destination port (usually 5060).
Access: Instant.
AC INI-Param: SIPDESTINATIONPORT"
       ::= {sipPorts 1}



     sipPortsLocalSipPort OBJECT-TYPE
       SYNTAX Unsigned32 (1..65534)
       MAX-ACCESS read-write
       STATUS current
       DESCRIPTION
           "Local SIP port used for signaling.
Access: Instant.
AC INI-Param: LOCALSIPPORT"
       ::= {sipPorts 2}



     sipPortsTCPLocalSipPort OBJECT-TYPE
       SYNTAX Unsigned32 (1..65535)
       MAX-ACCESS read-write
       STATUS current
       DESCRIPTION
           "Local SIP port used for signaling.
Access: Instant.
AC INI-Param: TCPLOCALSIPPORT"
       ::= {sipPorts 3}



     sipPortsTLSLocalSipPort OBJECT-TYPE
       SYNTAX Unsigned32 (1..65535)
       MAX-ACCESS read-write
       STATUS current
       DESCRIPTION
           "Local TLS SIP port used for signaling.
Access: Instant.
AC INI-Param: TLSLOCALSIPPORT"
       ::= {sipPorts 4}



     sipAuth OBJECT IDENTIFIER ::= {sip 4}


     sipAuthMode OBJECT-TYPE
       SYNTAX INTEGER {
                  perEP(0)
,
                  perGW(1)
,
                  perFXSOnly(3)

                  }
       MAX-ACCESS read-write
       STATUS current
       DESCRIPTION
           "Authentication mode.
Access: Instant.
AC INI-Param: AUTHENTICATIONMODE"
       ::= {sipAuth 1}



     sipAuthUserName OBJECT-TYPE
       SYNTAX SnmpAdminString (SIZE (0..50))
       MAX-ACCESS read-write
       STATUS current
       DESCRIPTION
           "User Name used for authentication.
Access: Instant.
AC INI-Param: USERNAME"
       ::= {sipAuth 2}



     sipAuthPassword OBJECT-TYPE
       SYNTAX SnmpAdminString (SIZE (0..50))
       MAX-ACCESS read-write
       STATUS current
       DESCRIPTION
           "Password used for authentication.
Access: Instant.
AC INI-Param: PASSWORD"
       ::= {sipAuth 3}



     sipAuthCnonce OBJECT-TYPE
       SYNTAX SnmpAdminString (SIZE (0..15))
       MAX-ACCESS read-write
       STATUS current
       DESCRIPTION
           "Cnonce parameter used for authentication.
Access: Instant.
AC INI-Param: CNONCE"
       ::= {sipAuth 4}



     sipAuthMutualAuthenticationMode OBJECT-TYPE
       SYNTAX INTEGER {
                  optional(0)
,
                  mandatory(1)

                  }
       MAX-ACCESS read-write
       STATUS current
       DESCRIPTION
           "Mutual Authentication Mode: 0 - Optional, 1 - Mandatory.
Access: Instant.
AC INI-Param: MUTUALAUTHENTICATIONMODE"
       ::= {sipAuth 5}



     sipAuthChallengeCachingMode OBJECT-TYPE
       SYNTAX INTEGER {
                  noCaching(0)
,
                  inviteOnly(1)
,
                  fullCaching(2)

                  }
       MAX-ACCESS read-write
       STATUS current
       DESCRIPTION
           "0. No caching mode – don't cache any challenges. Every new request
will be sent without preliminary authorization. If the
request is challenged – new request with authorization data
will be sent.
1. Cache for INVITE mode – challenges issued for INVITE request
and within the session will be cached. This will prevent
the mixture of REGISTER and INVITE authorizations.
2. Full cache mode – cache any challenges from the proxies.
.
Access: Instant.
AC INI-Param: SIPCHALLENGECACHINGMODE"
       ::= {sipAuth 6}



     -- ****************************************
     -- auth table declaration
     -- ****************************************
     authTable OBJECT-TYPE
       SYNTAX SEQUENCE OF AuthEntry
       MAX-ACCESS not-accessible
       STATUS current
       DESCRIPTION
           ""
       ::= {sipAuth 21}



     -- ****************************************
     -- auth table entry
     -- ****************************************
     authEntry OBJECT-TYPE
       SYNTAX AuthEntry
       MAX-ACCESS not-accessible
       STATUS current
       DESCRIPTION
           ""
       INDEX {authIndex}
       ::= {authTable 1}



     -- ****************************************
     -- auth TABLE
     -- ****************************************
     AuthEntry ::= SEQUENCE {
       authIndex                                       Unsigned32,
       authIsUsed                                      INTEGER,
       authAction                                      INTEGER,
       authActionResult                                INTEGER,
       authUserID                                      SnmpAdminString,
       authUserPassword                                SnmpAdminString,
       authModule                                      Unsigned32,
       authPort                                        Unsigned32
     }



     authIndex OBJECT-TYPE
       SYNTAX Unsigned32 (0..23)
       MAX-ACCESS read-only
       STATUS current
       DESCRIPTION
           "Entry number, starting at 0.
AC INI-Param: Authentication_Index"
       ::= {authEntry 1}



     authIsUsed OBJECT-TYPE
       SYNTAX INTEGER {
                  no(0)
,
                  yes(1)

                  }
       MAX-ACCESS read-write
       STATUS current
       DESCRIPTION
           "Is this index used.
Access: Offline.
AC INI-Param: Authentication_IsUsed"
       ::= {authEntry 2}



     authAction OBJECT-TYPE
       SYNTAX INTEGER {
                  developmentImpending(0)

                  }
       MAX-ACCESS read-only
       STATUS current
       DESCRIPTION
           "Development Impending.
AC INI-Param: N/A"
       ::= {authEntry 3}



     authActionResult OBJECT-TYPE
       SYNTAX INTEGER {
                  developmentImpending(0)

                  }
       MAX-ACCESS read-only
       STATUS current
       DESCRIPTION
           "Development Impending.
AC INI-Param: N/A"
       ::= {authEntry 4}



     authUserID OBJECT-TYPE
       SYNTAX SnmpAdminString (SIZE (0..50))
       MAX-ACCESS read-write
       STATUS current
       DESCRIPTION
           "
Access: Instant.
AC INI-Param: Authentication_UserId"
       ::= {authEntry 5}



     authUserPassword OBJECT-TYPE
       SYNTAX SnmpAdminString (SIZE (0..50))
       MAX-ACCESS read-write
       STATUS current
       DESCRIPTION
           "
Access: Instant.
AC INI-Param: Authentication_UserPassword"
       ::= {authEntry 6}



     authModule OBJECT-TYPE
       SYNTAX Unsigned32 (0..255)
       MAX-ACCESS read-only
       STATUS current
       DESCRIPTION
           "Module.
AC INI-Param: Authentication_Module"
       ::= {authEntry 7}



     authPort OBJECT-TYPE
       SYNTAX Unsigned32 (0..65535)
       MAX-ACCESS read-only
       STATUS current
       DESCRIPTION
           "Port.
AC INI-Param: Authentication_Port"
       ::= {authEntry 8}



     sipRetransmission OBJECT IDENTIFIER ::= {sip 5}


     sipRetransmissionT1Rtx OBJECT-TYPE
       SYNTAX Unsigned32 (100..4000)
       MAX-ACCESS read-write
       STATUS current
       DESCRIPTION
           "SIP T1 timeout for retransmission.
Access: Instant.
AC INI-Param: SIPT1RTX"
       ::= {sipRetransmission 1}



     sipRetransmissionT2Rtx OBJECT-TYPE
       SYNTAX Unsigned32 (100..10000)
       MAX-ACCESS read-write
       STATUS current
       DESCRIPTION
           "SIP T2 timeout for retransmission.
Access: Instant.
AC INI-Param: SIPT2RTX"
       ::= {sipRetransmission 2}



     sipRetransmissionSipMaxRtx OBJECT-TYPE
       SYNTAX Unsigned32 (1..30)
       MAX-ACCESS read-write
       STATUS current
       DESCRIPTION
           "Maximum number of retransmissions.
Access: Instant.
AC INI-Param: SipMaxRtx"
       ::= {sipRetransmission 3}



     sipRetransmissionIsRtxEnable OBJECT-TYPE
       SYNTAX INTEGER {
                  no(0)
,
                  yes(1)

                  }
       MAX-ACCESS read-write
       STATUS current
       DESCRIPTION
           "is Rtx timer enabled.
Access: Instant.
AC INI-Param: ISRTXENABLE"
       ::= {sipRetransmission 4}



     sipRetransmissionEnablePTime OBJECT-TYPE
       SYNTAX INTEGER {
                  disable(0)
,
                  enable(1)

                  }
       MAX-ACCESS read-write
       STATUS current
       DESCRIPTION
           "is ptime parameter needed in sdp.
Access: Instant.
AC INI-Param: ENABLEPTIME"
       ::= {sipRetransmission 5}



     sipRetransmissionTCPTimeout OBJECT-TYPE
       SYNTAX Unsigned32 (0..60)
       MAX-ACCESS read-write
       STATUS current
       DESCRIPTION
           "SIP TCP time out (influence timerB and Timer F).
Access: Instant.
AC INI-Param: SIPTCPTIMEOUT"
       ::= {sipRetransmission 6}



     sipRetransmissionRetryAfterTime OBJECT-TYPE
       SYNTAX Unsigned32 (0..3600)
       MAX-ACCESS read-write
       STATUS current
       DESCRIPTION
           "Retry After time for the proxy to be in state Unavailable.
Access: Instant.
AC INI-Param: RETRYAFTERTIME"
       ::= {sipRetransmission 7}



     sipRegistration OBJECT IDENTIFIER ::= {sip 6}


     sipRegistrationIsNeeded OBJECT-TYPE
       SYNTAX INTEGER {
                  no(0)
,
                  yes(1)

                  }
       MAX-ACCESS read-write
       STATUS current
       DESCRIPTION
           "Is Proxy registration necessary.
Access: Instant.
AC INI-Param: ISREGISTERNEEDED"
       ::= {sipRegistration 1}



     sipRegistrationIP OBJECT-TYPE
       SYNTAX SnmpAdminString (SIZE (0..49))
       MAX-ACCESS read-write
       STATUS current
       DESCRIPTION
           "SIP Registrar IP address.
Access: Instant.
AC INI-Param: REGISTRARIP"
       ::= {sipRegistration 2}



     sipRegistrationTime OBJECT-TYPE
       SYNTAX Unsigned32 (10..2000000)
       MAX-ACCESS read-write
       STATUS current
       DESCRIPTION
           "Time for which registration to Gatekeeper/Proxy is valid. Causes
periodic registration (seconds).
Access: Instant.
AC INI-Param: RegistrationTime"
       ::= {sipRegistration 3}



     sipRegistrationRegistrationRetryTime OBJECT-TYPE
       SYNTAX Unsigned32 (10..2000000)
       MAX-ACCESS read-write
       STATUS current
       DESCRIPTION
           "Time in which the gateway will try to register after last registration
failure (seconds).
Access: Instant.
AC INI-Param: REGISTRATIONRETRYTIME"
       ::= {sipRegistration 4}



     sipRegistrationRegistrarName OBJECT-TYPE
       SYNTAX SnmpAdminString (SIZE (0..49))
       MAX-ACCESS read-write
       STATUS current
       DESCRIPTION
           "SIP Registrar name.
Access: Instant.
AC INI-Param: REGISTRARNAME"
       ::= {sipRegistration 5}



     sipRegistrationTimeDivider OBJECT-TYPE
       SYNTAX Unsigned32 (30..100)
       MAX-ACCESS read-write
       STATUS current
       DESCRIPTION
           "Percentage of RegistrationTime when the actual new REGISTER
request will be sent out.
Access: Instant.
AC INI-Param: REGISTRATIONTIMEDIVIDER"
       ::= {sipRegistration 6}



     sipRegistrationName OBJECT-TYPE
       SYNTAX SnmpAdminString (SIZE (0..15))
       MAX-ACCESS read-write
       STATUS current
       DESCRIPTION
           "Gateway registration name.
Access: Instant.
AC INI-Param: GWREGISTRATIONNAME"
       ::= {sipRegistration 7}



     sipRegistrationRegisterOnInviteFailure OBJECT-TYPE
       SYNTAX INTEGER {
                  disable(0)
,
                  enable(1)

                  }
       MAX-ACCESS read-write
       STATUS current
       DESCRIPTION
           "Enable ReRegister upon INVITE transaction failure.
Access: Instant.
AC INI-Param: REGISTERONINVITEFAILURE"
       ::= {sipRegistration 8}



     sipRegistrationTimeThreshold OBJECT-TYPE
       SYNTAX Unsigned32 (0..2000000)
       MAX-ACCESS read-write
       STATUS current
       DESCRIPTION
           "If (REGISTRATIONTIMETHRESHOLD > 0) and (REGISTRATIONTIMETHRESHOLD
< computed registration time using existing logic) then
new registration time will be (Registration time from expires
header – REGISTRATIONTIMETHRESHOLD).
Access: Instant.
AC INI-Param: REGISTRATIONTIMETHRESHOLD"
       ::= {sipRegistration 9}



     sipRegistrationRegistrarTransportType OBJECT-TYPE
       SYNTAX INTEGER {
                  notConfigured(-1)
,
                  uDP(0)
,
                  tCP(1)
,
                  tLS(2)

                  }
       MAX-ACCESS read-write
       STATUS current
       DESCRIPTION
           "Registrar transport type.
Access: Instant.
AC INI-Param: REGISTRARTRANSPORTTYPE"
       ::= {sipRegistration 10}



     sipRegistrationReRegisterOnConnectionFailure OBJECT-TYPE
       SYNTAX INTEGER {
                  disable(0)
,
                  enable(1)

                  }
       MAX-ACCESS read-write
       STATUS current
       DESCRIPTION
           "Enables GW to perform Re-Registeration on TCP/TLS connection
failure.
Access: Instant.
AC INI-Param: REREGISTERONCONNECTIONFAILURE"
       ::= {sipRegistration 11}



     sipMisc OBJECT IDENTIFIER ::= {sip 7}


     sipMiscEnableEarlyMedia OBJECT-TYPE
       SYNTAX INTEGER {
                  no(0)
,
                  yes(1)

                  }
       MAX-ACCESS read-write
       STATUS current
       DESCRIPTION
           "Enable Early Media.
Access: Instant.
AC INI-Param: ENABLEEARLYMEDIA"
       ::= {sipMisc 1}



     sipMiscSipSessionExpires OBJECT-TYPE
       SYNTAX Unsigned32 (0..86400)
       MAX-ACCESS read-write
       STATUS current
       DESCRIPTION
           "The SIP session will be refreshed (using INVITE) each time this
timer expires (seconds).
Access: Instant.
AC INI-Param: SIPSESSIONEXPIRES"
       ::= {sipMisc 2}



     sipMiscIsUserPhone OBJECT-TYPE
       SYNTAX INTEGER {
                  no(0)
,
                  yes(1)

                  }
       MAX-ACCESS read-write
       STATUS current
       DESCRIPTION
           "Add User=Phone parameter to SIP URL.
Access: Instant.
AC INI-Param: ISUSERPHONE"
       ::= {sipMisc 3}



     sipMiscGatewayName OBJECT-TYPE
       SYNTAX SnmpAdminString (SIZE (0..49))
       MAX-ACCESS read-write
       STATUS current
       DESCRIPTION
           "Gateway name.
Access: Instant.
AC INI-Param: SIPGATEWAYNAME"
       ::= {sipMisc 4}



     sipMiscPrackMode OBJECT-TYPE
       SYNTAX INTEGER {
                  disabled(0)
,
                  supported(1)
,
                  required(2)

                  }
       MAX-ACCESS read-write
       STATUS current
       DESCRIPTION
           "PRACK mechanism mode for 1XX reliable responses: 0- Disabled
, 1- Supported , 2- Required.
Access: Instant.
AC INI-Param: PrackMode"
       ::= {sipMisc 5}



     sipMiscEnableRpiHeader OBJECT-TYPE
       SYNTAX INTEGER {
                  no(0)
,
                  yes(1)

                  }
       MAX-ACCESS read-write
       STATUS current
       DESCRIPTION
           "Enable Remote-Party-ID header.
Access: Instant.
AC INI-Param: ENABLERPIHEADER"
       ::= {sipMisc 6}



     sipMiscXChannelHeader OBJECT-TYPE
       SYNTAX INTEGER {
                  disable(0)
,
                  enable(1)

                  }
       MAX-ACCESS read-write
       STATUS current
       DESCRIPTION
           "0 (default): No special header  1:Add special header for trunk
and B-Channel.
Access: Instant.
AC INI-Param: XCHANNELHEADER"
       ::= {sipMisc 7}



     sipMiscAssertedIDMode OBJECT-TYPE
       SYNTAX INTEGER {
                  noHeaderAdded(0)
,
                  pAssertedIdRFC3325(1)
,
                  pPreferreddIdRFC3325(2)

                  }
       MAX-ACCESS read-write
       STATUS current
       DESCRIPTION
           "Select Asserted Identity header method.
Access: Instant.
AC INI-Param: ASSERTEDIDMODE"
       ::= {sipMisc 8}



     sipMiscIsUserPhoneInFrom OBJECT-TYPE
       SYNTAX INTEGER {
                  disable(0)
,
                  enable(1)

                  }
       MAX-ACCESS read-write
       STATUS current
       DESCRIPTION
           "Add 'User=Phone' to From header.
Access: Instant.
AC INI-Param: ISUSERPHONEINFROM"
       ::= {sipMisc 9}



     sipMiscAddTon2Rpi OBJECT-TYPE
       SYNTAX INTEGER {
                  disable(0)
,
                  enable(1)

                  }
       MAX-ACCESS read-write
       STATUS current
       DESCRIPTION
           "Add Number Type and Plan to Remote-Party-ID header.
Access: Instant.
AC INI-Param: ADDTON2RPI"
       ::= {sipMisc 10}



     sipMiscEnableCIC OBJECT-TYPE
       SYNTAX INTEGER {
                  no(0)
,
                  yes(1)

                  }
       MAX-ACCESS read-write
       STATUS current
       DESCRIPTION
           "Enables CIC -> ISDN TNS IE interworking.
Access: Instant.
AC INI-Param: ENABLECIC"
       ::= {sipMisc 11}



     sipMiscTransportType OBJECT-TYPE
       SYNTAX INTEGER {
                  udp(0)
,
                  tcp(1)
,
                  tls(2)

                  }
       MAX-ACCESS read-write
       STATUS current
       DESCRIPTION
           "SIP transport type.
Access: Instant.
AC INI-Param: SIPTRANSPORTTYPE"
       ::= {sipMisc 12}



     sipMiscISubNumberOfDigits OBJECT-TYPE
       SYNTAX Unsigned32 (0..36)
       MAX-ACCESS read-write
       STATUS current
       DESCRIPTION
           "Number of digits that will be taken from end of phone number
as Subaddress.
Access: Instant.
AC INI-Param: ISUBNUMBEROFDIGITS"
       ::= {sipMisc 13}



     sipMiscSIP183Behaviour OBJECT-TYPE
       SYNTAX INTEGER {
                  disable(0)
,
                  enable(1)

                  }
       MAX-ACCESS read-write
       STATUS current
       DESCRIPTION
           "If this parameter set to 1, ALERT to ISDN will be sent upon
183 receive.
Access: Instant.
AC INI-Param: SIP183BEHAVIOUR"
       ::= {sipMisc 14}



     sipMiscUseToHeaderAsCalledNum OBJECT-TYPE
       SYNTAX INTEGER {
                  disable(0)
,
                  enable(1)

                  }
       MAX-ACCESS read-write
       STATUS current
       DESCRIPTION
           "Use the user part of To header URL as called number (IP->TEL).
Access: Instant.
AC INI-Param: ISUSETOHEADERASCALLEDNUMBER"
       ::= {sipMisc 15}



     sipMiscEnableSIPS OBJECT-TYPE
       SYNTAX INTEGER {
                  disable(0)
,
                  enable(1)

                  }
       MAX-ACCESS read-write
       STATUS current
       DESCRIPTION
           "Enable SIP secured URI usage.
Access: Instant.
AC INI-Param: ENABLESIPS"
       ::= {sipMisc 16}



     sipMiscEnableSRVQuery OBJECT-TYPE
       SYNTAX INTEGER {
                  disable(0)
,
                  enable(1)

                  }
       MAX-ACCESS read-write
       STATUS obsolete
       DESCRIPTION
           "Enable DNS SRV queries.
Access: Instant.
AC INI-Param: ENABLESRVQUERY"
       ::= {sipMisc 17}



     sipMiscSubject OBJECT-TYPE
       SYNTAX SnmpAdminString (SIZE (0..49))
       MAX-ACCESS read-write
       STATUS current
       DESCRIPTION
           "User-defined sip subject.
Access: Instant.
AC INI-Param: SIPSUBJECT"
       ::= {sipMisc 18}



     sipMiscUseSIPTgrp OBJECT-TYPE
       SYNTAX INTEGER {
                  disable (0)
,
                  sendOnly (1)
,
                  sendAndReceive (2)
,
                  hotline(3)
,
                  hotlineExtended(4)

                  }
       MAX-ACCESS read-write
       STATUS current
       DESCRIPTION
           "Use TGRP parameter 0 - disable [Default] , 1 - send only , 2
- send and use if in the RequestURI when receiving INVITE,
3 -  Hotline, 4 - Extended Hotline (tgrp added both to Contact
header and to RequestURI header).
Access: Instant.
AC INI-Param: USESIPTGRP"
       ::= {sipMisc 19}



     sipMiscSend180ForCallWaiting OBJECT-TYPE
       SYNTAX INTEGER {
                  disable(0)
,
                  enable(1)

                  }
       MAX-ACCESS read-write
       STATUS current
       DESCRIPTION
           "Send 180 for call waiting.  Used for parties that do not support
182.
Access: Instant.
AC INI-Param: SEND180FORCALLWAITING"
       ::= {sipMisc 20}



     sipMiscUserAgentDisplayInfo OBJECT-TYPE
       SYNTAX SnmpAdminString (SIZE (0..50))
       MAX-ACCESS read-write
       STATUS current
       DESCRIPTION
           "String that will be displayed in the SIP Header 'User-Agent'
or 'Server'.
Access: Instant.
AC INI-Param: USERAGENTDISPLAYINFO"
       ::= {sipMisc 21}



     sipMiscSessionExpiresMethod OBJECT-TYPE
       SYNTAX INTEGER {
                  invite(0)
,
                  update(1)

                  }
       MAX-ACCESS read-write
       STATUS current
       DESCRIPTION
           "Determines the Method which the SIP session will be using to
referesh the session.
Access: Instant.
AC INI-Param: SESSIONEXPIRESMETHOD"
       ::= {sipMisc 22}



     sipMiscEnableGRUU OBJECT-TYPE
       SYNTAX INTEGER {
                  disable(0)
,
                  enable(1)

                  }
       MAX-ACCESS read-write
       STATUS current
       DESCRIPTION
           "Obtain and use GRUU (Global Routable UserAgentURIs).
Access: Instant.
AC INI-Param: ENABLEGRUU"
       ::= {sipMisc 23}



     sipMiscDNSQueryType OBJECT-TYPE
       SYNTAX INTEGER {
                  aRecord(0)
,
                  sRV(1)
,
                  nAPTR(2)

                  }
       MAX-ACCESS read-write
       STATUS current
       DESCRIPTION
           "DNS Query Type: 0-ARecord, 1-SRV, 2-NAPTR . Has effect on every
DNS query in the system.
Access: Instant.
AC INI-Param: DNSQUERYTYPE"
       ::= {sipMisc 24}



     sipMiscEnableHistoryInfo OBJECT-TYPE
       SYNTAX INTEGER {
                  disable(0)
,
                  enable(1)

                  }
       MAX-ACCESS read-write
       STATUS current
       DESCRIPTION
           "Enable History-Info header support.
Access: Instant.
AC INI-Param: ENABLEHISTORYINFO"
       ::= {sipMisc 25}



     sipMiscEnableTCPConnectionReuse OBJECT-TYPE
       SYNTAX INTEGER {
                  disable(0)
,
                  enable(1)

                  }
       MAX-ACCESS read-write
       STATUS current
       DESCRIPTION
           "Enable reuse of TCP connection.
Access: Instant.
AC INI-Param: ENABLETCPCONNECTIONREUSE"
       ::= {sipMisc 26}



     sipMiscComfortNoiseNegotiation OBJECT-TYPE
       SYNTAX INTEGER {
                  disable(0)
,
                  enable(1)

                  }
       MAX-ACCESS read-write
       STATUS current
       DESCRIPTION
           "is CN payload type is used and being negotiate.
Access: Instant.
AC INI-Param: COMFORTNOISENEGOTIATION"
       ::= {sipMisc 27}



     sipMiscMultiPtimeFormat OBJECT-TYPE
       SYNTAX INTEGER {
                  none(0) 
,
                  packetCable(1) 

                  }
       MAX-ACCESS read-write
       STATUS current
       DESCRIPTION
           "Format of multiple ptime (ptime per coder) in outgoing SDP.
Access: Instant.
AC INI-Param: MULTIPTIMEFORMAT"
       ::= {sipMisc 28}



     sipMiscRTPOnlyMode OBJECT-TYPE
       SYNTAX INTEGER {
                  disable(0)
,
                  transmitNReceive(1)
,
                  transmitOnly(2)
,
                  receiveOnly(3)

                  }
       MAX-ACCESS read-write
       STATUS current
       DESCRIPTION
           "On RTP only mode their is no signalling protocol (for media
parameters negotiation with the remote side). The channel is
open immediately. The IP for the media is taken from the routing
table. The RTP ports are corresponding to the local side
ports.
RTP-Only mode Values:
0 - regular call establishment
1 - No Signalling. The RTP channel open for Rx & Tx
2-  No Signalling. The RTP channel open only for Tx
3 -  No Signalling. The RTP channel open only for Rx.
Access: Instant.
AC INI-Param: RTPONLYMODE"
       ::= {sipMisc 29}



     sipMiscEnableReasonHeader OBJECT-TYPE
       SYNTAX INTEGER {
                  disable(0)
,
                  enable(1)

                  }
       MAX-ACCESS read-write
       STATUS current
       DESCRIPTION
           "Enable Reason header in the outgoing messages.
Access: Instant.
AC INI-Param: ENABLEREASONHEADER"
       ::= {sipMisc 30}



     sipMisc3xxBehavior OBJECT-TYPE
       SYNTAX INTEGER {
                  forward(0)
,
                  redirect(1)

                  }
       MAX-ACCESS read-write
       STATUS current
       DESCRIPTION
           "3xx response behavior:
Forwarding behavior - use different call identifiers
Redirect behavior - use the same call identifiers: From, To
& CallID.
Access: Instant.
AC INI-Param: 3XXBEHAVIOR"
       ::= {sipMisc 31}



     sipMiscEnableSemiAttendedTransfer OBJECT-TYPE
       SYNTAX INTEGER {
                  disable(0)
,
                  enable(1)

                  }
       MAX-ACCESS read-write
       STATUS current
       DESCRIPTION
           "Semi-Attended Transfer when the session to the Target is not
established.
false - Use REFER with Replaces.
true - Use CANCEL and REFER without Replaces if session is
not established.
Access: Instant.
AC INI-Param: ENABLESEMIATTENDEDTRANSFER"
       ::= {sipMisc 32}



     sipMiscUseSIPURIForDiversionHeader OBJECT-TYPE
       SYNTAX INTEGER {
                  tel(0)
,
                  sip(1)

                  }
       MAX-ACCESS read-write
       STATUS current
       DESCRIPTION
           "Use Tel uri or Sip uri for Diversion header.
Access: Instant.
AC INI-Param: UseSIPURIForDiversionHeader"
       ::= {sipMisc 33}



     sipMiscEnableVMURI OBJECT-TYPE
       SYNTAX INTEGER {
                  disable(0)
,
                  enable(1)

                  }
       MAX-ACCESS read-write
       STATUS current
       DESCRIPTION
           "Enable History-Info header support.
Access: Instant.
AC INI-Param: ENABLEVMURI"
       ::= {sipMisc 34}



     sipMiscEnablePChargingVector OBJECT-TYPE
       SYNTAX INTEGER {
                  disable(0)
,
                  enable(1)

                  }
       MAX-ACCESS read-write
       STATUS current
       DESCRIPTION
           "Generate P-Charging-Vector header
[0] - disabled
[1] - enabled.
Access: Instant.
AC INI-Param: ENABLEPCHARGINGVECTOR"
       ::= {sipMisc 35}



     sipMiscPAssertedUserName OBJECT-TYPE
       SYNTAX SnmpAdminString (SIZE (0..50))
       MAX-ACCESS read-write
       STATUS current
       DESCRIPTION
           "Digit pattern used to indicate Call Forward on Do Not Disturb
(PBX to VoiceMail).
Access: Instant.
AC INI-Param: PASSERTEDUSERNAME"
       ::= {sipMisc 36}



     sipMiscSDPSessionOwner OBJECT-TYPE
       SYNTAX SnmpAdminString (SIZE (0..39))
       MAX-ACCESS read-write
       STATUS current
       DESCRIPTION
           "The SDP owner string.
Access: Instant.
AC INI-Param: SIPSDPSESSIONOWNER"
       ::= {sipMisc 37}



     sipMiscResetOnINIFileDownload OBJECT-TYPE
       SYNTAX INTEGER {
                  disable(0)
,
                  enable(1)

                  }
       MAX-ACCESS read-write
       STATUS obsolete
       DESCRIPTION
           "Determine if Reset after INI File Download is execute.
Access: Instant.
AC INI-Param: ResetOnINIFileDownload"
       ::= {sipMisc 38}



     sipMiscSetDefaultOnIniFileProcess OBJECT-TYPE
       SYNTAX Unsigned32 (0..1)
       MAX-ACCESS read-write
       STATUS current
       DESCRIPTION
           "Determine if all parameters are set to their defaults before
processing updated INI File.
Access: Instant.
AC INI-Param: SetDefaultOnIniFileProcess"
       ::= {sipMisc 39}



     sipMiscEnableContactRestriction OBJECT-TYPE
       SYNTAX INTEGER {
                  disable(0)
,
                  enable(1)

                  }
       MAX-ACCESS read-write
       STATUS current
       DESCRIPTION
           "Hides the user part of the URI in the Contact Header
0 - Disable
1 - Enable.
Access: Instant.
AC INI-Param: ENABLECONTACTRESTRICTION"
       ::= {sipMisc 40}



     sipMiscEnablePAssociatedURIHeader OBJECT-TYPE
       SYNTAX INTEGER {
                  disable(0)
,
                  enable(1)

                  }
       MAX-ACCESS read-write
       STATUS current
       DESCRIPTION
           "Handles the P-Associated-URI  header in a 200OK response for
a REGISTER request.
Access: Instant.
AC INI-Param: ENABLEPASSOCIATEDURIHEADER"
       ::= {sipMisc 41}



     sipMiscMinSE OBJECT-TYPE
       SYNTAX Unsigned32 (10..100000)
       MAX-ACCESS read-write
       STATUS current
       DESCRIPTION
           "Minimal value for session refresh.
Access: Instant.
AC INI-Param: MINSE"
       ::= {sipMisc 42}



     sipMiscApplicationProfile OBJECT-TYPE
       SYNTAX Unsigned32 (0..2000000)
       MAX-ACCESS read-write
       STATUS current
       DESCRIPTION
           "ApplicationProfile, read it later for validating that the board
is theirs.
Access: Offline.
AC INI-Param: APPLICATIONPROFILE"
       ::= {sipMisc 43}



     sipMiscOPTIONSUserPart OBJECT-TYPE
       SYNTAX SnmpAdminString (SIZE (0..30))
       MAX-ACCESS read-write
       STATUS current
       DESCRIPTION
           "Allow to configure the OPTIONS userpart string for all gateways.

The default value should be empty string which means that we
don't use this parameter. Another special value is 'empty'
which means that the we don't populate the user part of the
OPTIONS request URI.
Any other value will be taken as is and used as the user part
of the OPTIONS request URI.
Access: Instant.
AC INI-Param: OPTIONSUSERPART"
       ::= {sipMisc 44}



     sipMiscUseAORInReferToHeader OBJECT-TYPE
       SYNTAX INTEGER {
                  disable(0)
,
                  enable(1)

                  }
       MAX-ACCESS read-write
       STATUS current
       DESCRIPTION
           "If enabled, we will use URI from To/From headers in Refer-To
header. If disabled, we will take the URI from Contact.
Access: Instant.
AC INI-Param: USEAORINREFERTOHEADER"
       ::= {sipMisc 45}



     sipMiscForkingHandlingMode OBJECT-TYPE
       SYNTAX INTEGER {
                  sequential(0)
,
                  parallel(1)

                  }
       MAX-ACCESS read-write
       STATUS current
       DESCRIPTION
           "Decides the handling method to 18X response to forking
0 -  Parallel handling - only the first 18X response is handled
1 - Sequential handling - all the 18X responses are handled.
Access: Instant.
AC INI-Param: FORKINGHANDLINGMODE"
       ::= {sipMisc 46}



     sipMiscOfferUnencryptedSRTCP OBJECT-TYPE
       SYNTAX INTEGER {
                  disable(0)
,
                  enable(1)

                  }
       MAX-ACCESS read-write
       STATUS obsolete
       DESCRIPTION
           "If set to 1, the 'crypto' attribute includes the UNENCRYPTED_SRTCP
parameter. If set to 1, the UNENCRYPTED_SRTCP parameter
is not included.
Access: Instant.
AC INI-Param: OFFERUNENCRYPTEDSRTCP"
       ::= {sipMisc 47}



     sipMiscSourceNumberPreference OBJECT-TYPE
       SYNTAX SnmpAdminString (SIZE (0..10))
       MAX-ACCESS read-write
       STATUS current
       DESCRIPTION
           "Determines from where the source number shall be taken from
(in an incoming  INVITE request).
Parameter values:
 - NULL: no changes in current logic
- FROM: source number is taken from 'FROM' field.
Access: Instant.
AC INI-Param: SOURCENUMBERPREFERENCE"
       ::= {sipMisc 48}



     sipMiscEnableRekeyAfter181 OBJECT-TYPE
       SYNTAX INTEGER {
                  disable(0)
,
                  enable(1)

                  }
       MAX-ACCESS read-write
       STATUS current
       DESCRIPTION
           "Send Reinvite after 181 (Call Is Being Forwarded) with new generated
STRTP keys.
Access: Instant.
AC INI-Param: ENABLEREKEYAFTER181"
       ::= {sipMisc 49}



     sipMiscUseDestinationAsConnectedNumber OBJECT-TYPE
       SYNTAX INTEGER {
                  disable(0)
,
                  enable(1)

                  }
       MAX-ACCESS read-write
       STATUS current
       DESCRIPTION
           "Use Destination As Connected Number.
Access: Instant.
AC INI-Param: USEDESTINATIONASCONNECTEDNUMBER"
       ::= {sipMisc 50}



     sipMiscIgnoreISDNSubaddress OBJECT-TYPE
       SYNTAX INTEGER {
                  disable(0)
,
                  enable(1)

                  }
       MAX-ACCESS read-write
       STATUS current
       DESCRIPTION
           "Ignore ISDN Subaddress.
Access: Instant.
AC INI-Param: IGNOREISDNSUBADDRESS"
       ::= {sipMisc 51}



     sipMiscPerformAdditionalIP2TELSourceManipulation OBJECT-TYPE
       SYNTAX INTEGER {
                  disable(0)
,
                  enable(1)

                  }
       MAX-ACCESS read-write
       STATUS current
       DESCRIPTION
           "Perform Additional IP2TEL Source Manipulation.
Access: Instant.
AC INI-Param: PERFORMADDITIONALIP2TELSOURCEMANIPULATION"
       ::= {sipMisc 52}



     sipMiscPerformAdditionalIP2TELDestinationManipulation OBJECT-TYPE
       SYNTAX INTEGER {
                  disable(0)
,
                  enable(1)

                  }
       MAX-ACCESS read-write
       STATUS current
       DESCRIPTION
           "Perform Additional IP2TEL Destination Manipulation.
Access: Instant.
AC INI-Param: PERFORMADDITIONALIP2TELDESTINATIONMANIPULATION"
       ::= {sipMisc 53}



     sipMiscUseEPNumAsCallingNumTel2IP OBJECT-TYPE
       SYNTAX INTEGER {
                  disable(0)
,
                  enable(1)

                  }
       MAX-ACCESS read-write
       STATUS current
       DESCRIPTION
           "Use EndPoint Number As Calling Number Tel2IP.
Access: Instant.
AC INI-Param: USEEPNUMASCALLINGNUMTEL2IP"
       ::= {sipMisc 54}



     sipMiscUseEPNumAsCallingNumIP2Tel OBJECT-TYPE
       SYNTAX INTEGER {
                  disable(0)
,
                  enable(1)

                  }
       MAX-ACCESS read-write
       STATUS current
       DESCRIPTION
           "Use EndPoint Number As Calling Number IP2Tel.
Access: Instant.
AC INI-Param: USEEPNUMASCALLINGNUMIP2TEL"
       ::= {sipMisc 55}



     sipMiscSBCRTCPMode OBJECT-TYPE
       SYNTAX INTEGER {
                  transparent(0)
,
                  generateAlways(1)
,
                  generateOnlyIfRTPActive(2)

                  }
       MAX-ACCESS read-write
       STATUS current
       DESCRIPTION
           "SBC RTCP Mode.
Access: Offline.
AC INI-Param: SBCRTCPMODE"
       ::= {sipMisc 56}



     sipSubscribe OBJECT IDENTIFIER ::= {sip 8}


     sipSubscribeEnable OBJECT-TYPE
       SYNTAX INTEGER {
                  disable(0)
,
                  enable(1)

                  }
       MAX-ACCESS read-write
       STATUS current
       DESCRIPTION
           "This parameter related to Subscribe/UnSubscribe buttons.
Access: Instant.
AC INI-Param: SHOULDSUBSCRIBE"
       ::= {sipSubscribe 1}



     sipSubscribeRetryTime OBJECT-TYPE
       SYNTAX Unsigned32 (10..2000000)
       MAX-ACCESS read-write
       STATUS current
       DESCRIPTION
           "MWI service subscription retry time after last subscription
failure (seconds).
Access: Instant.
AC INI-Param: SUBSCRIBERETRYTIME"
       ::= {sipSubscribe 2}



     sipSubscribeEnableMWISubscription OBJECT-TYPE
       SYNTAX INTEGER {
                  disable(0)
,
                  enable(1)

                  }
       MAX-ACCESS read-write
       STATUS current
       DESCRIPTION
           "Enable subscription for Message Waiting Indicator service.
Access: Instant.
AC INI-Param: ENABLEMWISUBSCRIPTION"
       ::= {sipSubscribe 3}



     sipSubscribeSubscriptionMode OBJECT-TYPE
       SYNTAX INTEGER {
                  perEndpoint(0)
,
                  perGateway(1)

                  }
       MAX-ACCESS read-write
       STATUS current
       DESCRIPTION
           "Subscription Mode: 0 - Per Endpoint, 1 - Per Gateway.
Access: Instant.
AC INI-Param: SUBSCRIPTIONMODE"
       ::= {sipSubscribe 4}



     sipDigitalGW OBJECT IDENTIFIER ::= {sip 9}


     -- ****************************************
     -- causeMapSIP2ISDN table declaration
     -- ****************************************
     causeMapSIP2ISDNTable OBJECT-TYPE
       SYNTAX SEQUENCE OF CauseMapSIP2ISDNEntry
       MAX-ACCESS not-accessible
       STATUS current
       DESCRIPTION
           "Cause Map SIP to ISDN Table."
       ::= {sipDigitalGW 21}



     -- ****************************************
     -- causeMapSIP2ISDN table entry
     -- ****************************************
     causeMapSIP2ISDNEntry OBJECT-TYPE
       SYNTAX CauseMapSIP2ISDNEntry
       MAX-ACCESS not-accessible
       STATUS current
       DESCRIPTION
           ""
       INDEX {causeMapSIP2ISDNIndex}
       ::= {causeMapSIP2ISDNTable 1}



     -- ****************************************
     -- causeMapSIP2ISDN TABLE
     -- ****************************************
     CauseMapSIP2ISDNEntry ::= SEQUENCE {
       causeMapSIP2ISDNIndex                           Unsigned32,
       causeMapSIP2ISDNRowStatus                       RowStatus,
       causeMapSIP2ISDNAction                          INTEGER,
       causeMapSIP2ISDNActionResult                    INTEGER,
       causeMapSIP2ISDNSIPResponse                     Integer32,
       causeMapSIP2ISDNQ850Cause                       Integer32
     }



     causeMapSIP2ISDNIndex OBJECT-TYPE
       SYNTAX Unsigned32 (0..11)
       MAX-ACCESS not-accessible
       STATUS current
       DESCRIPTION
           "
AC INI-Param: CauseMapSip2Isdn_Index"
       ::= {causeMapSIP2ISDNEntry 1}



     causeMapSIP2ISDNRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {causeMapSIP2ISDNEntry 2}



     causeMapSIP2ISDNAction OBJECT-TYPE
       SYNTAX INTEGER {
                  developmentImpending(0)

                  }
       MAX-ACCESS read-only
       STATUS current
       DESCRIPTION
           "Development Impending.
AC INI-Param: N/A"
       ::= {causeMapSIP2ISDNEntry 3}



     causeMapSIP2ISDNActionResult OBJECT-TYPE
       SYNTAX INTEGER {
                  developmentImpending(0)

                  }
       MAX-ACCESS read-only
       STATUS current
       DESCRIPTION
           "Development Impending.
AC INI-Param: N/A"
       ::= {causeMapSIP2ISDNEntry 4}



     causeMapSIP2ISDNSIPResponse OBJECT-TYPE
       SYNTAX Integer32 (-1..700)
       MAX-ACCESS read-write
       STATUS current
       DESCRIPTION
           "
Access: Instant.
AC INI-Param: CauseMapSip2Isdn_SipResponse"
       ::= {causeMapSIP2ISDNEntry 5}



     causeMapSIP2ISDNQ850Cause OBJECT-TYPE
       SYNTAX Integer32 (-1..805)
       MAX-ACCESS read-write
       STATUS current
       DESCRIPTION
           "
Access: Instant.
AC INI-Param: CauseMapSip2Isdn_IsdnReleaseCause"
       ::= {causeMapSIP2ISDNEntry 6}



     -- ****************************************
     -- causeMapISDN2SIP table declaration
     -- ****************************************
     causeMapISDN2SIPTable OBJECT-TYPE
       SYNTAX SEQUENCE OF CauseMapISDN2SIPEntry
       MAX-ACCESS not-accessible
       STATUS current
       DESCRIPTION
           "Cause Map SIP to ISDN Table."
       ::= {sipDigitalGW 22}



     -- ****************************************
     -- causeMapISDN2SIP table entry
     -- ****************************************
     causeMapISDN2SIPEntry OBJECT-TYPE
       SYNTAX CauseMapISDN2SIPEntry
       MAX-ACCESS not-accessible
       STATUS current
       DESCRIPTION
           ""
       INDEX {causeMapISDN2SIPIndex}
       ::= {causeMapISDN2SIPTable 1}



     -- ****************************************
     -- causeMapISDN2SIP TABLE
     -- ****************************************
     CauseMapISDN2SIPEntry ::= SEQUENCE {
       causeMapISDN2SIPIndex                           Unsigned32,
       causeMapISDN2SIPRowStatus                       RowStatus,
       causeMapISDN2SIPAction                          INTEGER,
       causeMapISDN2SIPActionResult                    INTEGER,
       causeMapISDN2SIPQ850Cause                       Integer32,
       causeMapISDN2SIPSIPResponse                     Integer32
     }



     causeMapISDN2SIPIndex OBJECT-TYPE
       SYNTAX Unsigned32 (0..11)
       MAX-ACCESS not-accessible
       STATUS current
       DESCRIPTION
           "
AC INI-Param: CauseMapIsdn2Sip_Index"
       ::= {causeMapISDN2SIPEntry 1}



     causeMapISDN2SIPRowStatus OBJECT-TYPE
       SYNTAX RowStatus
       MAX-ACCESS read-create
       STATUS current
       DESCRIPTION
           "Row-Status Textual Conventions as defined in RFC 2579: Textual
Conventions for SMIv2.
Access: Instant.
AC INI-Param: N/A"
       ::= {causeMapISDN2SIPEntry 2}



     causeMapISDN2SIPAction OBJECT-TYPE
       SYNTAX INTEGER {
                  developmentImpending(0)

                  }
       MAX-ACCESS read-only
       STATUS current
       DESCRIPTION
           "Development Impending.
AC INI-Param: N/A"
       ::= {causeMapISDN2SIPEntry 3}



     causeMapISDN2SIPActionResult OBJECT-TYPE
       SYNTAX INTEGER {
                  developmentImpending(0)

                  }
       MAX-ACCESS read-only
       STATUS current
       DESCRIPTION
           "Development Impending.
AC INI-Param: N/A"
       ::= {causeMapISDN2SIPEntry 4}



     causeMapISDN2SIPQ850Cause OBJECT-TYPE
       SYNTAX Integer32 (-1..805)
       MAX-ACCESS read-write
       STATUS current
       DESCRIPTION
           "
Access: Instant.
AC INI-Param: CauseMapIsdn2Sip_IsdnReleaseCause"
       ::= {causeMapISDN2SIPEntry 5}



     causeMapISDN2SIPSIPResponse OBJECT-TYPE
       SYNTAX Integer32 (-1..700)
       MAX-ACCESS read-write
       STATUS current
       DESCRIPTION
           "
Access: Instant.
AC INI-Param: CauseMapIsdn2Sip_SipResponse"
       ::= {causeMapISDN2SIPEntry 6}



     sipSAS OBJECT IDENTIFIER ::= {sip 10}


     sipSASEnable OBJECT-TYPE
       SYNTAX INTEGER {
                  disable(0)
,
                  enable(1)

                  }
       MAX-ACCESS read-write
       STATUS obsolete
       DESCRIPTION
           "Enables SAS functionality.
Access: Offline.
AC INI-Param: ENABLESAS"
       ::= {sipSAS 1}



     sipSASLocalSIPUdpPort OBJECT-TYPE
       SYNTAX Unsigned32 (1..65534)
       MAX-ACCESS read-write
       STATUS obsolete
       DESCRIPTION
           "Local SAS SIP port used for signaling over UDP.
Access: Instant.
AC INI-Param: SASLOCALSIPUDPPORT"
       ::= {sipSAS 2}



     sipSASDefaultGatewayIP OBJECT-TYPE
       SYNTAX SnmpAdminString (SIZE (0..49))
       MAX-ACCESS read-write
       STATUS obsolete
       DESCRIPTION
           "SIP SAS default IP address for incoming requests in emergency
mode.
Access: Instant.
AC INI-Param: SASDEFAULTGATEWAYIP"
       ::= {sipSAS 3}



     sipSASLocalSIPTlsPort OBJECT-TYPE
       SYNTAX Unsigned32 (1..65534)
       MAX-ACCESS read-write
       STATUS obsolete
       DESCRIPTION
           "Local SAS SIP port used for signaling over TLS.
Access: Instant.
AC INI-Param: SASLOCALSIPTLSPORT"
       ::= {sipSAS 4}



     sipSASRegistrationTime OBJECT-TYPE
       SYNTAX Unsigned32 (0..2000000)
       MAX-ACCESS read-write
       STATUS obsolete
       DESCRIPTION
           "SAS will send this value in expires header while working in
emergency mode.
Access: Instant.
AC INI-Param: SASREGISTRATIONTIME"
       ::= {sipSAS 5}



     sipSASShortNumberLength OBJECT-TYPE
       SYNTAX Unsigned32 (0..255)
       MAX-ACCESS read-write
       STATUS obsolete
       DESCRIPTION
           "Upon incoming request the user info in the request is compared
to the registered one. SAS performs comparison of the arrived
user info with the suffix of the registered one. The length
of the suffix is determined by this parameter.
Access: Instant.
AC INI-Param: SASSHORTNUMBERLENGTH"
       ::= {sipSAS 6}



     sipSASLocalSIPTcpPort OBJECT-TYPE
       SYNTAX Unsigned32 (1..65534)
       MAX-ACCESS read-write
       STATUS obsolete
       DESCRIPTION
           "Local SAS SIP port used for signaling over TCP.
Access: Instant.
AC INI-Param: SASLOCALSIPTCPPORT"
       ::= {sipSAS 7}



     sipSASProxySet OBJECT-TYPE
       SYNTAX Unsigned32 (0..5)
       MAX-ACCESS read-write
       STATUS obsolete
       DESCRIPTION
           "Proxy Set Id for SAS.
Access: Instant.
AC INI-Param: SASPROXYSET"
       ::= {sipSAS 8}



     sipSASRedundantProxySet OBJECT-TYPE
       SYNTAX Integer32 (-1..5)
       MAX-ACCESS read-write
       STATUS obsolete
       DESCRIPTION
           "Proxy Set Id for Redundant SAS.
Access: Instant.
AC INI-Param: REDUNDANTSASPROXYSET"
       ::= {sipSAS 9}



     sipSASBindingMode OBJECT-TYPE
       SYNTAX INTEGER {
                  uRI(0)
,
                  userPartOnly(1)

                  }
       MAX-ACCESS read-write
       STATUS obsolete
       DESCRIPTION
           "Defines the SAS database binding mode:
0 - URI dependant 
1 - according to user part.
Access: Instant.
AC INI-Param: SASBINDINGMODE"
       ::= {sipSAS 10}



     sipSASSurvivabilityMode OBJECT-TYPE
       SYNTAX INTEGER {
                  standard(0)
,
                  alwaysEmergency(1)
,
                  ignoreRegister(2)
,
                  autoAnswerRegister(3)
,
                  useRoutingTableOnlyInNormalMode(4)

                  }
       MAX-ACCESS read-write
       STATUS obsolete
       DESCRIPTION
           "Defines the SAS working mode:
0 – Standard Mode (working with configured proxy set)
1 – Always emergency mode (working without proxy)
2 – Ignore REGISTER in normal mode 
3 – Auto-answer REGISTER (do not forward to proxy)
4 – Use Routing Table only in normal mode (berfore forward
to proxy).
Access: Instant.
AC INI-Param: SASSURVIVABILITYMODE"
       ::= {sipSAS 11}



     sipSASEnableENUM OBJECT-TYPE
       SYNTAX INTEGER {
                  disable(0)
,
                  enable(1)

                  }
       MAX-ACCESS read-write
       STATUS obsolete
       DESCRIPTION
           "Enables SAS to perform ENUM query when receiving INVITE messages
in emergency mode.
Access: Instant.
AC INI-Param: SASENABLEENUM"
       ::= {sipSAS 12}



     sipSASEnableRecordRoute OBJECT-TYPE
       SYNTAX INTEGER {
                  disable(0)
,
                  enable(1)

                  }
       MAX-ACCESS read-write
       STATUS obsolete
       DESCRIPTION
           "Enables SAS to add record-Route header to requests.
Access: Instant.
AC INI-Param: SASENABLERECORDROUTE"
       ::= {sipSAS 13}



     sipSASBlockUnRegUsers OBJECT-TYPE
       SYNTAX INTEGER {
                  unblock(0)
,
                  block(1)

                  }
       MAX-ACCESS read-write
       STATUS obsolete
       DESCRIPTION
           "Enables SAS to reject dialog-establishment requests from un-registered
users.
Access: Instant.
AC INI-Param: SASBLOCKUNREGUSERS"
       ::= {sipSAS 14}



     sipSASConnectionReuse OBJECT-TYPE
       SYNTAX INTEGER {
                  disable(0)
,
                  enable(1)

                  }
       MAX-ACCESS read-write
       STATUS obsolete
       DESCRIPTION
           "Re-using TCP/TLS connection in SAS application.
Access: Offline.
AC INI-Param: SASCONNECTIONREUSE"
       ::= {sipSAS 15}



     sipSASEnteringEmergencyMode OBJECT-TYPE
       SYNTAX INTEGER {
                  optionsOnly(0)
,
                  optionsInviteRegister(1)

                  }
       MAX-ACCESS read-write
       STATUS obsolete
       DESCRIPTION
           "Defines which methods cause SAS to enter EMERGENCY mode. (0)-OPTIONS
only, (1)-OPTIONS/INVITE/REGISTER.
Access: Instant.
AC INI-Param: SASENTERINGEMERGENCYMODE"
       ::= {sipSAS 16}



     -- ****************************************
     -- sasRegistrationManipulation table declaration
     -- ****************************************
     sasRegistrationManipulationTable OBJECT-TYPE
       SYNTAX SEQUENCE OF SasRegistrationManipulationEntry
       MAX-ACCESS not-accessible
       STATUS obsolete
       DESCRIPTION
           "GWAPP SAS Registration Manipulation Table."
       ::= {sipSAS 21}



     -- ****************************************
     -- sasRegistrationManipulation table entry
     -- ****************************************
     sasRegistrationManipulationEntry OBJECT-TYPE
       SYNTAX SasRegistrationManipulationEntry
       MAX-ACCESS not-accessible
       STATUS obsolete
       DESCRIPTION
           ""
       INDEX {sasRegistrationManipulationIndex}
       ::= {sasRegistrationManipulationTable 1}



     -- ****************************************
     -- sasRegistrationManipulation TABLE
     -- ****************************************
     SasRegistrationManipulationEntry ::= SEQUENCE {
       sasRegistrationManipulationIndex                Unsigned32,
       sasRegistrationManipulationRowStatus            RowStatus,
       sasRegistrationManipulationAction               INTEGER,
       sasRegistrationManipulationActionResult         INTEGER,
       sasRegistrationManipulationRemoveFromRight      Unsigned32,
       sasRegistrationManipulationLeaveFromRight       Unsigned32
     }



     sasRegistrationManipulationIndex OBJECT-TYPE
       SYNTAX Unsigned32 (0..0)
       MAX-ACCESS not-accessible
       STATUS obsolete
       DESCRIPTION
           "
AC INI-Param: SASRegistrationManipulation_Index"
       ::= {sasRegistrationManipulationEntry 1}



     sasRegistrationManipulationRowStatus OBJECT-TYPE
       SYNTAX RowStatus
       MAX-ACCESS read-create
       STATUS obsolete
       DESCRIPTION
           "Row-Status Textual Conventions as defined in RFC 2579: Textual
Conventions for SMIv2.
AC INI-Param: N/A"
       ::= {sasRegistrationManipulationEntry 2}



     sasRegistrationManipulationAction OBJECT-TYPE
       SYNTAX INTEGER {
                  developmentImpending(0)

                  }
       MAX-ACCESS read-only
       STATUS obsolete
       DESCRIPTION
           "Development Impending.
AC INI-Param: N/A"
       ::= {sasRegistrationManipulationEntry 3}



     sasRegistrationManipulationActionResult OBJECT-TYPE
       SYNTAX INTEGER {
                  developmentImpending(0)

                  }
       MAX-ACCESS read-only
       STATUS obsolete
       DESCRIPTION
           "Development Impending.
AC INI-Param: N/A"
       ::= {sasRegistrationManipulationEntry 4}



     sasRegistrationManipulationRemoveFromRight OBJECT-TYPE
       SYNTAX Unsigned32 (0..30)
       MAX-ACCESS read-create
       STATUS obsolete
       DESCRIPTION
           "
Access: Instant.
AC INI-Param: SASRegistrationManipulation_RemoveFromRight"
       ::= {sasRegistrationManipulationEntry 5}



     sasRegistrationManipulationLeaveFromRight OBJECT-TYPE
       SYNTAX Unsigned32 (0..30)
       MAX-ACCESS read-create
       STATUS obsolete
       DESCRIPTION
           "
Access: Instant.
AC INI-Param: SASRegistrationManipulation_LeaveFromRight"
       ::= {sasRegistrationManipulationEntry 6}





END
