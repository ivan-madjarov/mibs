-- Avaya Aura Session Manager MIB
-- Copyright (c) 2008-2009 by Avaya Inc. All rights reserved. 
-- MIB version 1.0.0 
-- Avaya Compas ID: NA

AV-AURA-SESSION-MANAGER-ELEMMGR-MIB DEFINITIONS ::= BEGIN

-- Add your MIB specific imports in the below import section.
IMPORTS 
MODULE-IDENTITY, OBJECT-TYPE, NOTIFICATION-TYPE, enterprises
    FROM SNMPv2-SMI
InetAddressIPv6
    FROM INET-ADDRESS-MIB
MODULE-COMPLIANCE, OBJECT-GROUP
    FROM SNMPv2-CONF
SnmpAdminString
    FROM SNMP-FRAMEWORK-MIB
DateAndTime
    FROM SNMPv2-TC;

        
--
-- The following are defined in Avaya Aura Session Manager-MIB
--

avAuraSessMgrMibs MODULE-IDENTITY
       LAST-UPDATED "201611170423Z" -- 17 November 2016
       ORGANIZATION "Avaya, Inc."
       CONTACT-INFO "Avaya Customer Services

                     Postal: Avaya, Inc.
                             211 Mount Airy Rd
                             Basking Ridge. NJ 07920
                             USA
                             Tel: +1 908 953 6000
                             WWW: http://www.avaya.com"
       DESCRIPTION "This MIB module is for exposing Avaya Aura Session Manager inventory information via SNMP GET."
       
       REVISION 	"201611170423Z" -- 17 November 2016
       DESCRIPTION "MIB Version 1.0.0 - autobuild. Generated via the MIBTOOL."
             
       
       ::= { mibs 36 }

avaya              OBJECT IDENTIFIER ::= { enterprises 6889 }
products           OBJECT IDENTIFIER ::= { avaya 1 }
mibs               OBJECT IDENTIFIER ::= { avaya 2 }

avAuraSessMgrProd OBJECT IDENTIFIER ::= { products 36 }

avAuraSessMgrMibNotifications OBJECT IDENTIFIER ::= { avAuraSessMgrMibs 0 }

avAuraSessMgrMibObjects OBJECT IDENTIFIER ::= { avAuraSessMgrMibs 1 }
avAuraSessMgrMibConformance OBJECT IDENTIFIER ::= { avAuraSessMgrMibs 2 }

-- Avaya Aura Session Manager Notifications (avAuraSessMgrMibNotifications) will be added here
-- --------------------------------------------------------------------
-- According to RFC 2578 section 8.5, the next to last sub-identifier
-- in the name of any newly defined notification must have the value
-- zero. This is to achieve compatibility with SNMPv1 traps.
-- ----------------------------------------------------------------------
avSessMgrEmTestAlarm NOTIFICATION-TYPE
	STATUS current
	DESCRIPTION
	"test alarm(Minor)"
	::= { avAuraSessMgrMibNotifications 211 }

avSessMgrEmTestClearAlarm NOTIFICATION-TYPE
	STATUS current
	DESCRIPTION
	"Clear alarm(Minor)"
	::= { avAuraSessMgrMibNotifications 212 }

avSessMgrEmMMTC20011 NOTIFICATION-TYPE
	STATUS current
	DESCRIPTION
	"Postgres database sanity check failed; the database is unaccessible(Major)"
	::= { avAuraSessMgrMibNotifications 221 }

avSessMgrEmMMTC20012 NOTIFICATION-TYPE
	STATUS current
	DESCRIPTION
	"Postgres database sanity check passed(Major)"
	::= { avAuraSessMgrMibNotifications 222 }

avSessMgrEmMMTC20019 NOTIFICATION-TYPE
	STATUS current
	DESCRIPTION
	"SAL-Agent sanity check failed; alarms are not being processed(Minor)"
	::= { avAuraSessMgrMibNotifications 223 }

avSessMgrEmMMTC20020 NOTIFICATION-TYPE
	STATUS current
	DESCRIPTION
	"SAL-Agent sanity check passed(Minor)"
	::= { avAuraSessMgrMibNotifications 224 }

avSessMgrEmMMTC20033 NOTIFICATION-TYPE
	STATUS current
	DESCRIPTION
	"Management Instance check failed(Minor)"
	::= { avAuraSessMgrMibNotifications 225 }

avSessMgrEmMMTC20034 NOTIFICATION-TYPE
	STATUS current
	DESCRIPTION
	"Management Instance check passed(Minor)"
	::= { avAuraSessMgrMibNotifications 226 }

avSessMgrEmMMTC20043 NOTIFICATION-TYPE
	STATUS current
	DESCRIPTION
	"Management BSM Instance check failed(Minor)"
	::= { avAuraSessMgrMibNotifications 227 }

avSessMgrEmMMTC20044 NOTIFICATION-TYPE
	STATUS current
	DESCRIPTION
	"Management BSM Instance check passed(Minor)"
	::= { avAuraSessMgrMibNotifications 228 }

avSessMgrEmMMTC20045 NOTIFICATION-TYPE
	STATUS current
	DESCRIPTION
	"SM/BSM host name resolution failed(Minor)"
	::= { avAuraSessMgrMibNotifications 229 }

avSessMgrEmMMTC20046 NOTIFICATION-TYPE
	STATUS current
	DESCRIPTION
	"SM/BSM host name resolution passed(Minor)"
	::= { avAuraSessMgrMibNotifications 230 }

avSessMgrEmMPER20226 NOTIFICATION-TYPE
	STATUS current
	DESCRIPTION
	"Performance Management disk usage threshold(Minor)"
	::= { avAuraSessMgrMibNotifications 231 }

avSessMgrEmMPER20230 NOTIFICATION-TYPE
	STATUS current
	DESCRIPTION
	"Performance data storage current disk usage is OK(Minor)"
	::= { avAuraSessMgrMibNotifications 232 }

avSessMgrEmMPER20227 NOTIFICATION-TYPE
	STATUS current
	DESCRIPTION
	"Performance Management disk usage limit and collection disabled(Major)"
	::= { avAuraSessMgrMibNotifications 233 }

avSessMgrEmMPER20231 NOTIFICATION-TYPE
	STATUS current
	DESCRIPTION
	"Performance data storage current disk usage is OK and collection enabled(Minor)"
	::= { avAuraSessMgrMibNotifications 234 }

avSessMgrEmMPER20228 NOTIFICATION-TYPE
	STATUS current
	DESCRIPTION
	"NFS server used for performance data storage not accessible(Minor)"
	::= { avAuraSessMgrMibNotifications 235 }

avSessMgrEmMPER20232 NOTIFICATION-TYPE
	STATUS current
	DESCRIPTION
	"NFS server used for performance data storage is now accessible(Major)"
	::= { avAuraSessMgrMibNotifications 236 }

avSessMgrEmMPER20229 NOTIFICATION-TYPE
	STATUS current
	DESCRIPTION
	"NFS server used for performance data storage not accessible(Major)"
	::= { avAuraSessMgrMibNotifications 237 }

avSessMgrEmMPER20233 NOTIFICATION-TYPE
	STATUS current
	DESCRIPTION
	"NFS server used for performance data storage is now accessible(Major)"
	::= { avAuraSessMgrMibNotifications 238 }

avSessMgrEmLIC20251 NOTIFICATION-TYPE
	STATUS current
	DESCRIPTION
	"SIP session counts exceeded the licensed number(Warning)"
	::= { avAuraSessMgrMibNotifications 239 }

avSessMgrEmLIC20252 NOTIFICATION-TYPE
	STATUS current
	DESCRIPTION
	"SIP session counts no longer exceeds the licensed number(Warning)"
	::= { avAuraSessMgrMibNotifications 240 }

avSessMgrEmLIC20253 NOTIFICATION-TYPE
	STATUS current
	DESCRIPTION
	"SM instance license in error(Major)"
	::= { avAuraSessMgrMibNotifications 241 }

avSessMgrEmLIC20254 NOTIFICATION-TYPE
	STATUS current
	DESCRIPTION
	"SM instance license error has cleared(Major)"
	::= { avAuraSessMgrMibNotifications 242 }

avSessMgrEmLIC20255 NOTIFICATION-TYPE
	STATUS current
	DESCRIPTION
	"SM instance license restricted(Critical)"
	::= { avAuraSessMgrMibNotifications 243 }

avSessMgrEmLIC20256 NOTIFICATION-TYPE
	STATUS current
	DESCRIPTION
	"SM instance license restriction has cleared(Critical)"
	::= { avAuraSessMgrMibNotifications 244 }

END
